CORIANT-GROOVE-MIB DEFINITIONS ::= BEGIN
IMPORTS
    MODULE-IDENTITY, OBJECT-TYPE, NOTIFICATION-TYPE, enterprises, Counter64, Unsigned32
        FROM SNMPv2-SMI    -- http://www.ietf.org/rfc/rfc2578.txt
    TEXTUAL-CONVENTION, DateAndTime, DisplayString, TruthValue, RowStatus,RowPointer
        FROM SNMPv2-TC;     -- http://www.ietf.org/rfc/rfc2579.txt


groove MODULE-IDENTITY
    LAST-UPDATED "201807100722Z"
    ORGANIZATION "Coriant R&D"
    CONTACT-INFO "Contact Coriant Customer Service at http://www.coriant.com/services_support"
    DESCRIPTION "SNMP MIB for Groove G30 release 2.1.0"
    REVISION "201807100722Z"
    DESCRIPTION "Auto-build version at 201807100722Z"
::= { products 2 }
CoriantCommonOtnEncryStatusEnum ::= TEXTUAL-CONVENTION
    STATUS current
    DESCRIPTION "NULL
		"
    SYNTAX BITS  {
	 notAvailable (0),
	 handshake (1),
	 keyInitializing (2),
	 keyInSync (3),
	 unreachable (4),
	 mismatch (5),
	 connectFailed (6),
	 disabled (7),
	 encryptFail (8),
	 encryptNormal (9),
	 authenticationFailed (10),
	 trafficSquelched (11)
	}

CoriantCommonOtnKeySyncSession ::= TEXTUAL-CONVENTION
    STATUS current
    DESCRIPTION "Indicate the associated session for the ODU channel to synchronize keys.
		"
    SYNTAX OCTET STRING 

CoriantCommonpmThresholdValue ::= TEXTUAL-CONVENTION
    STATUS current
    DESCRIPTION "NULL
		"
    SYNTAX OCTET STRING  (SIZE (1..32))

CoriantCommonpmUnitOfValue ::= TEXTUAL-CONVENTION
    STATUS current
    DESCRIPTION "NULL
		"
    SYNTAX INTEGER  {
	 notApplicable (0),
	 dbm (1),
	 microseconds (2),
	 ps (3),
	 psNm (4),
	 db (5),
	 seconds (6),
	 packets (7),
	 events (8),
	 octets (9),
	 bits (10),
	 bitsS (11),
	 blocks (12),
	 times (13),
	 percentage (14),
	 bitRatio (15),
	 mhz (16),
	 degreec (17),
	 frames (18)
	}

CoriantFileSwTypesDeviceFwVersion ::= TEXTUAL-CONVENTION
    STATUS current
    DESCRIPTION "NULL
		"
    SYNTAX OCTET STRING  (SIZE (0..64))

CoriantFileSwTypesDeviceName ::= TEXTUAL-CONVENTION
    STATUS current
    DESCRIPTION "NULL
		"
    SYNTAX OCTET STRING  (SIZE (0..64))

CoriantFileSwTypesSwVersion ::= TEXTUAL-CONVENTION
    STATUS current
    DESCRIPTION "NULL
		"
    SYNTAX OCTET STRING  (SIZE (0..20))

CoriantFileSwTypesSwloadProduct ::= TEXTUAL-CONVENTION
    STATUS current
    DESCRIPTION "NULL
		"
    SYNTAX OCTET STRING  (SIZE (0..32))

CoriantFileSwTypesSwloadVendor ::= TEXTUAL-CONVENTION
    STATUS current
    DESCRIPTION "NULL
		"
    SYNTAX OCTET STRING  (SIZE (0..32))

CoriantFmtypesConditionType ::= TEXTUAL-CONVENTION
    STATUS current
    DESCRIPTION "NULL
		"
    SYNTAX INTEGER  {
	 idp (1),
	 rupDeg (2),
	 rupFail (3),
	 meaHwvm (4),
	 mea (5),
	 pwra (6),
	 pwrb (7),
	 rupMiss (8),
	 sbanr (9),
	 sdf (10),
	 thermal (11),
	 sdcardmiss (12),
	 sdcardfail (13),
	 mgmtrst (14),
	 progflt (15),
	 ntppu (16),
	 linkdown (17),
	 los (18),
	 lol (19),
	 lofOtu (20),
	 lomOtu (21),
	 timOtu (22),
	 bdiOtu (23),
	 bersdOtu (24),
	 aisOtu (25),
	 bersdOdu (26),
	 lckOdu (27),
	 ociOdu (28),
	 aisOdu (29),
	 bdiOdu (30),
	 timOdu (31),
	 plmOdu (32),
	 loomfi (33),
	 msim (34),
	 loflom (35),
	 csfOpu (36),
	 losync (37),
	 lf (38),
	 rf (39),
	 csfLosGfp (40),
	 csfLosyncGfp (41),
	 csfFdiGfp (42),
	 csfRdiGfp (43),
	 lofdGfp (44),
	 plmGfp (45),
	 lpbkfacility (46),
	 lpbkfterm (47),
	 contcom (48),
	 latchOpen (49),
	 lof (50),
	 aisL (51),
	 msAis (52),
	 timR (53),
	 rsTim (54),
	 rfiL (55),
	 msRfi (56),
	 cabs (99),
	 oog (100),
	 connectFail (101),
	 encryptFail (102),
	 keyexFail (103),
	 bdi (104),
	 bdiO (105),
	 autoshutoff (106),
	 fibrconnMiss (107),
	 bdiP (108),
	 losMsa (109),
	 protna (110),
	 switchThres (111),
	 losyncCd (112),
	 updatePskFail (113),
	 encTrafficSquelch (114),
	 tSe (10001),
	 tDropevents (10002),
	 tOctets (10003),
	 tPkts (10004),
	 tBroadcastpkts (10005),
	 tMulticastpkts (10006),
	 tCrcalignerrors (10007),
	 tUndersizepkts (10008),
	 tOversizepkts (10009),
	 tFragments (10010),
	 tJabbers (10011),
	 tPkts64octets (10012),
	 tPkts65to127octets (10013),
	 tPkts128to255octets (10014),
	 tPkts256to511octets (10015),
	 tPkts512to1023octets (10016),
	 tPkts1024to1518octets (10017),
	 tUtilHt (10018),
	 tBeFec (10019),
	 tUbeFec (10020),
	 tBerFecHt (10021),
	 tEbOtu (10022),
	 tEsOtu (10023),
	 tSesOtu (10024),
	 tUasOtu (10025),
	 tEbOdu (10026),
	 tEsOdu (10027),
	 tSesOdu (10028),
	 tUasOdu (10029),
	 tDelayOduHt (10030),
	 tDelayOduLt (10031),
	 tDgdHt (10032),
	 tCdLt (10033),
	 tCdHt (10034),
	 tOsnrLt (10035),
	 tLoss (10036),
	 tOprHt (10037),
	 tOprLt (10038),
	 tQfactorLt (10039),
	 tOptHt (10040),
	 tOptLt (10041),
	 tPdlHt (10042),
	 tOftHt (10043),
	 tOftLt (10044),
	 tOfrHt (10045),
	 tOfrLt (10046),
	 tCvS (10047),
	 tEsS (10048),
	 tSesS (10049),
	 tUasS (10050),
	 tSefs (10051),
	 tBbeRs (10052),
	 tEsRs (10053),
	 tSesRs (10054),
	 tUasRs (10055),
	 tOfs (10056),
	 tOprLaneHt (10057),
	 tOprLaneLt (10058),
	 tOprTotalHt (10059),
	 tOprTotalLt (10060),
	 tOptLaneHt (10061),
	 tOptLaneLt (10062),
	 tOptTotalHt (10063),
	 tOptTotalLt (10064),
	 tLossTx (10065),
	 tLossRx (10066),
	 init (11001),
	 swupgCompld (11002),
	 swupgFail (11003),
	 swupgRollback (11004),
	 upgCompld (11005),
	 upgFail (11006),
	 intrusion (11007),
	 userlock (11008),
	 swupgIp (11009),
	 ztcFail (11010),
	 ztcComplete (11011),
	 dbactFail (11012),
	 inactive (11013),
	 restart (11014),
	 fstoprot (11015),
	 fstowkg (11016),
	 lockout (11017),
	 mantoprot (11018),
	 mantowkg (11019),
	 noreq (11020),
	 sdonprot (11021),
	 sdonwkg (11022),
	 sfonprot (11023),
	 sfonwkg (11024),
	 wkswpr (11025),
	 prswwk (11026),
	 wtr (11027),
	 dnr (11028),
	 authnFailed (11029),
	 loginFailed (11030),
	 candidatePskMismatch (11031),
	 updatePskCompld (11032),
	 candidatePskAuthenticated (11033),
	 updatePskReqRcv (11034)
	}

CoriantFmtypesEntityTypeFm ::= TEXTUAL-CONVENTION
    STATUS current
    DESCRIPTION "NULL
		"
    SYNTAX INTEGER  {
	 t10gbe (1),
	 t40gbe (2),
	 t100gbe (3),
	 ochOs (4),
	 otu4 (5),
	 otuc2 (6),
	 otuc3 (7),
	 oduc2 (8),
	 oduc3 (9),
	 odu4 (10),
	 odu3 (11),
	 odu2e (12),
	 odu2 (13),
	 shelf (14),
	 slot (15),
	 port (16),
	 fan (17),
	 chm1 (18),
	 chm2 (19),
	 bfm (20),
	 mgteth (21),
	 ntppeer (22),
	 db (23),
	 sw (24),
	 log (25),
	 security (26),
	 psu (27),
	 cfp2 (28),
	 qsfp (29),
	 time (30),
	 user (31),
	 ztc (32),
	 ppp (33),
	 fc8g (34),
	 fc16g (35),
	 oduflex (36),
	 otu2 (37),
	 otu2e (38),
	 oc192 (39),
	 stm64 (40),
	 oms (41),
	 gopt (42),
	 paoscofp2 (43),
	 pabaofp2 (44),
	 pairofp2 (45),
	 palrofp2 (46),
	 paerofp2 (47),
	 bahofp2 (48),
	 subslot (50),
	 occ2 (51),
	 omd96 (52),
	 amplifier (53),
	 omd48S (54),
	 omd48O (55),
	 chm1g (56),
	 tdcmofp2 (57),
	 bauofp2 (58),
	 paulrofp2 (59),
	 osc (60),
	 ots (61),
	 sfpplus (62),
	 xtm2 (63),
	 omd8b1ofp2 (64),
	 omd8b2ofp2 (65),
	 opsofp2 (66),
	 ops (67),
	 chm1lh (68),
	 chm2lh (69),
	 t10gwanSonet (70),
	 t10gwanSdh (71),
	 otdrofp2 (72)
	}

CoriantFmtypesServiceAffectFm ::= TEXTUAL-CONVENTION
    STATUS current
    DESCRIPTION "
	SA: service affecting
	NSA: non-service affecting
	
		"
    SYNTAX INTEGER  {
	 sa (1),
	 nsa (2)
	}

CoriantFmtypesSeverityLevel ::= TEXTUAL-CONVENTION
    STATUS current
    DESCRIPTION "
	alarm severity
	
		"
    SYNTAX INTEGER  {
	 notApplicable (0),
	 critical (1),
	 major (2),
	 minor (3),
	 notAlarmed (4),
	 notReported (5),
	 cleared (6)
	}

CoriantPmtypesPmParameter ::= TEXTUAL-CONVENTION
    STATUS current
    DESCRIPTION "NULL
		"
    SYNTAX INTEGER  {
	 all (0),
	 eb (1),
	 es (2),
	 ses (3),
	 uas (4),
	 delay (5),
	 delayMax (6),
	 delayMin (7),
	 dgd (8),
	 dgdMax (9),
	 dgdMin (10),
	 cd (11),
	 cdMax (12),
	 cdMin (13),
	 osnr (14),
	 osnrMax (15),
	 osnrMin (16),
	 qFactor (17),
	 qFactorMax (18),
	 qFactorMin (19),
	 opr (20),
	 oprMax (21),
	 oprMin (22),
	 loss (23),
	 se (24),
	 dropevents (25),
	 octets (26),
	 pkts (27),
	 broadcastpkts (28),
	 multicastpkts (29),
	 crcalignerrors (30),
	 undersizepkts (31),
	 oversizepkts (32),
	 fragments (33),
	 jabbers (34),
	 pkts64octets (35),
	 pkts65to127octets (36),
	 pkts128to255octets (37),
	 pkts256to511octets (38),
	 pkts512to1023octets (39),
	 pkts1024to1518octets (40),
	 utilization (41),
	 utilizationMax (42),
	 utilizationMin (43),
	 beFec (44),
	 ubeFec (45),
	 berFec (46),
	 berFecMax (47),
	 berFecMin (48),
	 opt (49),
	 optMax (50),
	 optMin (51),
	 pdl (52),
	 pdlMax (53),
	 pdlMin (54),
	 oft (55),
	 oftMax (56),
	 oftMin (57),
	 ofr (58),
	 ofrMax (59),
	 ofrMin (60),
	 bbe (61),
	 ofs (65),
	 cv (66),
	 sefs (67),
	 oprLaneHigh (68),
	 oprLaneHighMax (69),
	 oprLaneHighMin (70),
	 oprLaneLow (71),
	 oprLaneLowMax (72),
	 oprLaneLowMin (73),
	 oprTotal (74),
	 oprTotalMax (75),
	 oprTotalMin (76),
	 optLaneHigh (77),
	 optLaneHighMax (78),
	 optLaneHighMin (79),
	 optLaneLow (80),
	 optLaneLowMax (81),
	 optLaneLowMin (82),
	 optTotal (83),
	 optTotalMax (84),
	 optTotalMin (85),
	 tmodule (86),
	 tinlet (87),
	 toutlet (88),
	 tmoduleMax (89),
	 tmoduleMin (90),
	 tinletMax (91),
	 tinletMin (92),
	 toutletMax (93),
	 toutletMin (94),
	 berPostFec (95),
	 berPostFecMax (96),
	 berPostFecMin (97),
	 psd (98),
	 psc (99),
	 lossTx (100),
	 lossRx (101),
	 encryptionFailRx (102)
	}

CoriantPmtypesPmpType ::= TEXTUAL-CONVENTION
    STATUS current
    DESCRIPTION "NULL
		"
    SYNTAX INTEGER  {
	 notApplicable (0),
	 oduNendEgress (1),
	 oduNendIngress (2),
	 otuNendIngress (3),
	 delayMeasurementOdu (4),
	 coherentOpticalInterface (5),
	 opticalPower (6),
	 loss (7),
	 ethernetNendIngress (8),
	 ethernetNendEgress (9),
	 fec (10),
	 fcNendIngress (11),
	 sonetSNendIngress (12),
	 sdhRsNendIngress (13),
	 sonetSNendEgress (14),
	 sdhRsNendEgress (15),
	 shelfTemperature (16),
	 equipmentTemperature (17),
	 opticalPowerLane (18),
	 protectionSwitch (19),
	 lossTxrx (20),
	 opticalPowerIngress (21),
	 opticalPowerEgress (22),
	 oduEncryption (23),
	 all (100)
	}

CoriantPmtypesValidityType ::= TEXTUAL-CONVENTION
    STATUS current
    DESCRIPTION "NULL
		"
    SYNTAX INTEGER  {
	 complete (1),
	 partial (2),
	 notAvailable (3)
	}

CoriantRpcConfigurableLedTypes ::= TEXTUAL-CONVENTION
    STATUS current
    DESCRIPTION "Types of LEDs that can be enabled/disabled by the user.
		"
    SYNTAX INTEGER  {
	 ledTest (1),
	 locationLed (2)
	}

CoriantTypesCardType ::= TEXTUAL-CONVENTION
    STATUS current
    DESCRIPTION "NULL
		"
    SYNTAX INTEGER  {
	 fan (11),
	 psu (12),
	 chm1 (13),
	 chm2 (14),
	 xtm2 (16),
	 chm1g (17),
	 chm1lh (18),
	 chm2lh (19),
	 occ2 (100),
	 omd96 (101),
	 paoscofp2 (102),
	 pabaofp2 (103),
	 pairofp2 (104),
	 palrofp2 (105),
	 paerofp2 (106),
	 bahofp2 (107),
	 omd48S (109),
	 omd48O (110),
	 tdcmofp2 (111),
	 bauofp2 (112),
	 paulrofp2 (113),
	 omd8b1ofp2 (114),
	 omd8b2ofp2 (115),
	 opsofp2 (116),
	 otdrofp2 (117)
	}

CoriantTypesCreationscope ::= TEXTUAL-CONVENTION
    STATUS current
    DESCRIPTION "NULL
		"
    SYNTAX INTEGER  {
	 systemCreated (0),
	 userCreated (1)
	}

CoriantTypesDBPrecision1 ::= TEXTUAL-CONVENTION
    STATUS current
    DESCRIPTION "dB for 0.1 precision
		UNITS:dB"
    SYNTAX OCTET STRING 

CoriantTypesDate ::= TEXTUAL-CONVENTION
    STATUS current
    DESCRIPTION "The type of date show the mm/dd/year. The date type does not allow negative years
		"
    SYNTAX OCTET STRING  (SIZE (0|10))

CoriantTypesDecimalFract1 ::= TEXTUAL-CONVENTION
    STATUS current
    DESCRIPTION "NULL
		"
    SYNTAX OCTET STRING 

CoriantTypesDuplexMode ::= TEXTUAL-CONVENTION
    STATUS current
    DESCRIPTION "NULL
		"
    SYNTAX INTEGER  {
	 na (0),
	 full (1),
	 half (2)
	}

CoriantTypesEnableSwitch ::= TEXTUAL-CONVENTION
    STATUS current
    DESCRIPTION "NULL
		"
    SYNTAX INTEGER  {
	 enabled (1),
	 disabled (2)
	}

CoriantTypesEquipmentType ::= TEXTUAL-CONVENTION
    STATUS current
    DESCRIPTION "NULL
		"
    SYNTAX INTEGER  {
	 empty (0),
	 filled (1),
	 reserved (2),
	 unrecognized (3),
	 fan (11),
	 psu (12),
	 chm1 (13),
	 chm2 (14),
	 bfm (15),
	 xtm2 (16),
	 chm1g (17),
	 chm1lh (18),
	 chm2lh (19),
	 qsfp (21),
	 cfp2 (22),
	 sfpplus (23),
	 occ2 (100),
	 omd96 (101),
	 paoscofp2 (102),
	 pabaofp2 (103),
	 pairofp2 (104),
	 palrofp2 (105),
	 paerofp2 (106),
	 bahofp2 (107),
	 omd48S (109),
	 omd48O (110),
	 tdcmofp2 (111),
	 bauofp2 (112),
	 paulrofp2 (113),
	 omd8b1ofp2 (114),
	 omd8b2ofp2 (115),
	 opsofp2 (116),
	 otdrofp2 (117)
	}

CoriantTypesEthFec ::= TEXTUAL-CONVENTION
    STATUS current
    DESCRIPTION "NULL
		"
    SYNTAX INTEGER  {
	 enabled (1),
	 disabled (2),
	 auto (3)
	}

CoriantTypesEthernetRate ::= TEXTUAL-CONVENTION
    STATUS current
    DESCRIPTION "NULL
		UNITS:Mbit/s"
    SYNTAX INTEGER  {
	 na (0),
	 t10 (1),
	 t100 (2),
	 t1000 (3),
	 maxRate (4)
	}

CoriantTypesFilename ::= TEXTUAL-CONVENTION
    STATUS current
    DESCRIPTION "String representing a filename
		"
    SYNTAX OCTET STRING  (SIZE (1..128))

CoriantTypesFlowControl ::= TEXTUAL-CONVENTION
    STATUS current
    DESCRIPTION "NULL
		"
    SYNTAX INTEGER  {
	 na (0),
	 off (1),
	 txRx (2),
	 tx (3),
	 rx (4)
	}

CoriantTypesFreq ::= TEXTUAL-CONVENTION
    STATUS current
    DESCRIPTION "Supported Frequency Range.
		UNITS:MHz"
    SYNTAX Unsigned32  (0|191300000..196111250)

CoriantTypesFtpPath ::= TEXTUAL-CONVENTION
    STATUS current
    DESCRIPTION "Representation of a FTP/STPF/FTPS/SCP path 'ftp://user@hostname/directorypath/filename'
	or an HTTP URL 'http://domain.com/filename'
		"
    SYNTAX OCTET STRING  (SIZE (1..1024))

CoriantTypesManagementDirection ::= TEXTUAL-CONVENTION
    STATUS current
    DESCRIPTION "NULL
		"
    SYNTAX INTEGER  {
	 notApplicable (0),
	 ingress (1),
	 egress (2)
	}

CoriantTypesManagementLocation ::= TEXTUAL-CONVENTION
    STATUS current
    DESCRIPTION "NULL
		"
    SYNTAX INTEGER  {
	 nearEnd (1),
	 farEnd (2),
	 notApplicable (3)
	}

CoriantTypesManagementTimePeriod ::= TEXTUAL-CONVENTION
    STATUS current
    DESCRIPTION "NULL
		"
    SYNTAX INTEGER  {
	 notApplicable (0),
	 t15min (1),
	 t24h (2),
	 all (4),
	 t1min (5),
	 t1h (6)
	}

CoriantTypesNameIdentifier ::= TEXTUAL-CONVENTION
    STATUS current
    DESCRIPTION "NULL
		"
    SYNTAX OCTET STRING  (SIZE (1..32))

CoriantTypesNumberList ::= TEXTUAL-CONVENTION
    STATUS current
    DESCRIPTION "List of numbers using ',' as separator and '..' to represent ranges. 
	Examples: '12' , '1..4' , '1,5,10..12,20' 
		"
    SYNTAX OCTET STRING  (SIZE (0..255))

CoriantTypesOduType ::= TEXTUAL-CONVENTION
    STATUS current
    DESCRIPTION "NULL
		"
    SYNTAX INTEGER  {
	 unused (0),
	 odu0 (1),
	 odu1 (2),
	 odu2 (3),
	 odu2e (4),
	 odu3 (5),
	 odu3e (6),
	 odu4 (7),
	 oduflex (8),
	 oduc2 (9),
	 oduc3 (10)
	}

CoriantTypesOnOff ::= TEXTUAL-CONVENTION
    STATUS current
    DESCRIPTION "NULL
		"
    SYNTAX INTEGER  {
	 on (1),
	 off (2)
	}

CoriantTypesOpticalDB ::= TEXTUAL-CONVENTION
    STATUS current
    DESCRIPTION "Optical Attribute value with Unit dB
		UNITS:dB"
    SYNTAX OCTET STRING 

CoriantTypesOpticalPower ::= TEXTUAL-CONVENTION
    STATUS current
    DESCRIPTION "Optical Power value in dBm
		UNITS:dBm"
    SYNTAX OCTET STRING 

CoriantTypesOtukFec ::= TEXTUAL-CONVENTION
    STATUS current
    DESCRIPTION "NULL
		"
    SYNTAX INTEGER  {
	 sdfec15 (1),
	 sdfec25 (2),
	 g709 (3),
	 i4 (4),
	 i7 (5),
	 nofec (6),
	 staircase7 (7),
	 sdfec15nd (8)
	}

CoriantTypesPassword ::= TEXTUAL-CONVENTION
    STATUS current
    DESCRIPTION "Any ASCII values between 32 and 126 decimal
		"
    SYNTAX OCTET STRING  (SIZE (8..32))

CoriantTypesPercentage ::= TEXTUAL-CONVENTION
    STATUS current
    DESCRIPTION "NULL
		UNITS:%"
    SYNTAX Unsigned32  (0..100)

CoriantTypesPluggableFormFactor ::= TEXTUAL-CONVENTION
    STATUS current
    DESCRIPTION "Indicating the exact form factor of the pluggable.
		"
    SYNTAX INTEGER  {
	 notApplicable (0),
	 unrecognized (1),
	 qsfpplus (2),
	 qsfp28 (3),
	 cfp2Aco (4),
	 sfpplus (5),
	 sfp (6),
	 xfp (7)
	}

CoriantTypesPluggableType ::= TEXTUAL-CONVENTION
    STATUS current
    DESCRIPTION "NULL
		"
    SYNTAX INTEGER  {
	 qsfp (21),
	 cfp2 (22),
	 sfpplus (23)
	}

CoriantTypesPortId ::= TEXTUAL-CONVENTION
    STATUS current
    DESCRIPTION "NULL
		"
    SYNTAX Unsigned32 

CoriantTypesPortMode ::= TEXTUAL-CONVENTION
    STATUS current
    DESCRIPTION "NULL
		"
    SYNTAX INTEGER  {
	 notApplicable (0),
	 t10gbe (1),
	 t40gbe (2),
	 t100gbe (3),
	 subport (4),
	 qpsk100g (5),
	 t8qam300g (6),
	 t16qam200g (7),
	 fc16g (8),
	 fc8g (9),
	 otu4 (10),
	 otu2 (12),
	 otu2e (13),
	 oc192 (14),
	 stm64 (15),
	 ochosOtu2 (16),
	 ochosOtu2e (17),
	 t8qam200g (18),
	 t10gwanSonet (19),
	 t10gwanSdh (20)
	}

CoriantTypesPower ::= TEXTUAL-CONVENTION
    STATUS current
    DESCRIPTION "Power consumption value in W(WAT)
		UNITS:W"
    SYNTAX OCTET STRING 

CoriantTypesRtpType ::= TEXTUAL-CONVENTION
    STATUS current
    DESCRIPTION "Type of the routing protocol.
		"
    SYNTAX INTEGER  {
	 direct (1),
	 static (2),
	 ospfv2 (3)
	}

CoriantTypesSessionId ::= TEXTUAL-CONVENTION
    STATUS current
    DESCRIPTION "NULL
		"
    SYNTAX OCTET STRING  (SIZE (0..21))

CoriantTypesShelfId ::= TEXTUAL-CONVENTION
    STATUS current
    DESCRIPTION "NULL
		"
    SYNTAX Unsigned32  (1..65535)

CoriantTypesSlotId ::= TEXTUAL-CONVENTION
    STATUS current
    DESCRIPTION "NULL
		"
    SYNTAX Unsigned32 

CoriantTypesSnmpString ::= TEXTUAL-CONVENTION
    STATUS current
    DESCRIPTION "NULL
		"
    SYNTAX OCTET STRING  (SIZE (1..32))

CoriantTypesSourceProtocol ::= TEXTUAL-CONVENTION
    STATUS current
    DESCRIPTION "NULL
		"
    SYNTAX INTEGER  {
	 direct (1),
	 static (2),
	 ospfv2 (3)
	}

CoriantTypesSubslotId ::= TEXTUAL-CONVENTION
    STATUS current
    DESCRIPTION "NULL
		"
    SYNTAX Unsigned32 

CoriantTypesTemperature ::= TEXTUAL-CONVENTION
    STATUS current
    DESCRIPTION "Temperature value in degree Celsius.
		UNITS:Celsius"
    SYNTAX OCTET STRING 

CoriantTypesTemperaturePrecision3 ::= TEXTUAL-CONVENTION
    STATUS current
    DESCRIPTION "Temperature value in Celsius with 0.001 precision
		UNITS:Celsius"
    SYNTAX OCTET STRING 

CoriantTypesTestSignalConfig ::= TEXTUAL-CONVENTION
    STATUS current
    DESCRIPTION "NULL
		"
    SYNTAX INTEGER  {
	 none (0),
	 rxtx (3)
	}

CoriantTypesTestSignalType ::= TEXTUAL-CONVENTION
    STATUS current
    DESCRIPTION "NULL
		"
    SYNTAX INTEGER  {
	 none (0),
	 prbs (1),
	 idle (3)
	}

CoriantTypesTimMode ::= TEXTUAL-CONVENTION
    STATUS current
    DESCRIPTION "NULL
		"
    SYNTAX INTEGER  {
	 none (0),
	 sapi (1),
	 dapi (2),
	 oper (3),
	 sapiDapi (4),
	 sapiOper (5),
	 dapiOper (6),
	 sapiDapiOper (7)
	}

CoriantTypesTimePeriod ::= TEXTUAL-CONVENTION
    STATUS current
    DESCRIPTION "Representation of a time period in 'hh:mm:ss'
		"
    SYNTAX OCTET STRING  (SIZE (8))

CoriantTypesTypeOfDirection ::= TEXTUAL-CONVENTION
    STATUS current
    DESCRIPTION "NULL
		"
    SYNTAX INTEGER  {
	 notApplicable (0),
	 tx (2),
	 rx (3),
	 rxtx (4)
	}

CoriantTypesUserName ::= TEXTUAL-CONVENTION
    STATUS current
    DESCRIPTION "According with Linux user-name pattern
		"
    SYNTAX OCTET STRING  (SIZE (1..20))

CoriantTypesYesNo ::= TEXTUAL-CONVENTION
    STATUS current
    DESCRIPTION "NULL
		"
    SYNTAX INTEGER  {
	 yes (1),
	 no (2)
	}

IetfInetTypesAsNumber ::= TEXTUAL-CONVENTION
    STATUS current
    DESCRIPTION "The as-number type represents autonomous system numbers
	which identify an Autonomous System (AS).  An AS is a set
	of routers under a single technical administration, using
	an interior gateway protocol and common metrics to route
	packets within the AS, and using an exterior gateway
	protocol to route packets to other ASes.  IANA maintains
	the AS number space and has delegated large parts to the
	regional registries. 
	
	Autonomous system numbers were originally limited to 16
	bits.  BGP extensions have enlarged the autonomous system
	number space to 32 bits.  This type therefore uses an uint32
	base type without a range restriction in order to support
	a larger autonomous system number space.
	
	In the value set and its semantics, this type is equivalent
	to the InetAutonomousSystemNumber textual convention of
	the SMIv2.
		"
    SYNTAX Unsigned32 

IetfInetTypesDomainName ::= TEXTUAL-CONVENTION
    STATUS current
    DESCRIPTION "The domain-name type represents a DNS domain name.  The
	name SHOULD be fully qualified whenever possible. 
	
	Internet domain names are only loosely specified.  Section
	3.5 of RFC 1034 recommends a syntax (modified in Section
	2.1 of RFC 1123).  The pattern above is intended to allow
	for current practice in domain name use, and some possible
	future expansion.  It is designed to hold various types of
	domain names, including names used for A or AAAA records
	(host names) and other records, such as SRV records.  Note
	that Internet host names have a stricter syntax (described
	in RFC 952) than the DNS recommendations in RFCs 1034 and
	1123, and that systems that want to store host names in
	schema nodes using the domain-name type are recommended to
	adhere to this stricter standard to ensure interoperability.
	
	The encoding of DNS names in the DNS protocol is limited
	to 255 characters.  Since the encoding consists of labels
	prefixed by a length bytes and there is a trailing NULL
	byte, only 253 characters can appear in the textual dotted
	notation.
	
	The description clause of schema nodes using the domain-name
	type MUST describe when and how these names are resolved to
	IP addresses.  Note that the resolution of a domain-name value
	may require to query multiple DNS records (e.g., A for IPv4
	and AAAA for IPv6).  The order of the resolution process and
	which DNS record takes precedence can either be defined
	explicitly or may depend on the configuration of the
	resolver.
	
	Domain-name values use the US-ASCII encoding.  Their canonical
	format uses lowercase US-ASCII characters.  Internationalized
	domain names MUST be A-labels as per RFC 5890.
		"
    SYNTAX OCTET STRING  (SIZE (1..253))

IetfInetTypesDscp ::= TEXTUAL-CONVENTION
    STATUS current
    DESCRIPTION "The dscp type represents a Differentiated Services Code Point
	that may be used for marking packets in a traffic stream. 
	In the value set and its semantics, this type is equivalent
	to the Dscp textual convention of the SMIv2.
		"
    SYNTAX Unsigned32  (0..63)

IetfInetTypesHost ::= TEXTUAL-CONVENTION
    STATUS current
    DESCRIPTION "The host type represents either an IP address or a DNS
	domain name.
		"
    SYNTAX OCTET STRING 

IetfInetTypesIpAddress ::= TEXTUAL-CONVENTION
    STATUS current
    DESCRIPTION "The ip-address type represents an IP address and is IP
	version neutral.  The format of the textual representation
	implies the IP version.  This type supports scoped addresses
	by allowing zone identifiers in the address format.
		"
    SYNTAX OCTET STRING 

IetfInetTypesIpAddressNoZone ::= TEXTUAL-CONVENTION
    STATUS current
    DESCRIPTION "The ip-address-no-zone type represents an IP address and is
	IP version neutral.  The format of the textual representation
	implies the IP version.  This type does not support scoped
	addresses since it does not allow zone identifiers in the
	address format.
		"
    SYNTAX OCTET STRING 

IetfInetTypesIpPrefix ::= TEXTUAL-CONVENTION
    STATUS current
    DESCRIPTION "The ip-prefix type represents an IP prefix and is IP
	version neutral.  The format of the textual representations
	implies the IP version.
		"
    SYNTAX OCTET STRING 

IetfInetTypesIpVersion ::= TEXTUAL-CONVENTION
    STATUS current
    DESCRIPTION "This value represents the version of the IP protocol. 
	
	In the value set and its semantics, this type is equivalent
	to the InetVersion textual convention of the SMIv2.
		"
    SYNTAX INTEGER  {
	 unknown (0),
	 ipv4 (1),
	 ipv6 (2)
	}

IetfInetTypesIpv4Address ::= TEXTUAL-CONVENTION
    STATUS current
    DESCRIPTION "The ipv4-address type represents an IPv4 address in
	dotted-quad notation.  The IPv4 address may include a zone
	index, separated by a % sign.
	
	The zone index is used to disambiguate identical address
	values.  For link-local addresses, the zone index will
	typically be the interface index number or the name of an
	interface.  If the zone index is not present, the default
	zone of the device will be used.
	
	The canonical format for the zone index is the numerical
	format
		"
    SYNTAX OCTET STRING 

IetfInetTypesIpv4AddressNoZone ::= TEXTUAL-CONVENTION
    STATUS current
    DESCRIPTION "An IPv4 address without a zone index.  This type, derived from
	ipv4-address, may be used in situations where the zone is
	known from the context and hence no zone index is needed.
		"
    SYNTAX OCTET STRING 

IetfInetTypesIpv4Prefix ::= TEXTUAL-CONVENTION
    STATUS current
    DESCRIPTION "The ipv4-prefix type represents an IPv4 address prefix. 
	The prefix length is given by the number following the
	slash character and must be less than or equal to 32. 
	
	A prefix length value of n corresponds to an IP address
	mask that has n contiguous 1-bits from the most
	significant bit (MSB) and all other bits set to 0.
	
	The canonical format of an IPv4 prefix has all bits of
	the IPv4 address set to zero that are not part of the
	IPv4 prefix.
		"
    SYNTAX OCTET STRING 

IetfInetTypesIpv6Address ::= TEXTUAL-CONVENTION
    STATUS current
    DESCRIPTION "The ipv6-address type represents an IPv6 address in full,
	mixed, shortened, and shortened-mixed notation.  The IPv6
	address may include a zone index, separated by a % sign. 
	
	The zone index is used to disambiguate identical address
	values.  For link-local addresses, the zone index will
	typically be the interface index number or the name of an
	interface.  If the zone index is not present, the default
	zone of the device will be used.
	
	
	
	The canonical format of IPv6 addresses uses the textual
	representation defined in Section 4 of RFC 5952.  The
	canonical format for the zone index is the numerical
	format as described in Section 11.2 of RFC 4007.
		"
    SYNTAX OCTET STRING 

IetfInetTypesIpv6AddressNoZone ::= TEXTUAL-CONVENTION
    STATUS current
    DESCRIPTION "An IPv6 address without a zone index.  This type, derived from
	ipv6-address, may be used in situations where the zone is
	known from the context and hence no zone index is needed.
		"
    SYNTAX OCTET STRING 

IetfInetTypesIpv6FlowLabel ::= TEXTUAL-CONVENTION
    STATUS current
    DESCRIPTION "The ipv6-flow-label type represents the flow identifier or Flow
	Label in an IPv6 packet header that may be used to
	discriminate traffic flows. 
	
	In the value set and its semantics, this type is equivalent
	to the IPv6FlowLabel textual convention of the SMIv2.
		"
    SYNTAX Unsigned32  (0..1048575)

IetfInetTypesIpv6Prefix ::= TEXTUAL-CONVENTION
    STATUS current
    DESCRIPTION "The ipv6-prefix type represents an IPv6 address prefix. 
	The prefix length is given by the number following the
	slash character and must be less than or equal to 128. 
	
	A prefix length value of n corresponds to an IP address
	mask that has n contiguous 1-bits from the most
	significant bit (MSB) and all other bits set to 0.
	
	The IPv6 address should have all bits that do not belong
	to the prefix set to zero.
	
	The canonical format of an IPv6 prefix has all bits of
	the IPv6 address set to zero that are not part of the
	IPv6 prefix.  Furthermore, the IPv6 address is represented
	as defined in Section 4 of RFC 5952.
		"
    SYNTAX OCTET STRING 

IetfInetTypesPortNumber ::= TEXTUAL-CONVENTION
    STATUS current
    DESCRIPTION "The port-number type represents a 16-bit port number of an
	Internet transport-layer protocol such as UDP, TCP, DCCP, or
	SCTP.  Port numbers are assigned by IANA.  A current list of
	all assignments is available from <http://www.iana.org/>.  
	
	Note that the port number value zero is reserved by IANA.  In
	situations where the value zero does not make sense, it can
	be excluded by subtyping the port-number type.
	In the value set and its semantics, this type is equivalent
	to the InetPortNumber textual convention of the SMIv2.
		"
    SYNTAX Unsigned32  (0..65535)

IetfInetTypesUri ::= TEXTUAL-CONVENTION
    STATUS current
    DESCRIPTION "The uri type represents a Uniform Resource Identifier
	(URI) as defined by STD 66. 
	
	Objects using the uri type MUST be in US-ASCII encoding,
	and MUST be normalized as described by RFC 3986 Sections
	6.2.1, 6.2.2.1, and 6.2.2.2.  All unnecessary
	percent-encoding is removed, and all case-insensitive
	characters are set to lowercase except for hexadecimal
	digits, which are normalized to uppercase as described in
	Section 6.2.2.1.
	
	The purpose of this normalization is to help provide
	unique URIs.  Note that this normalization is not
	sufficient to provide uniqueness.  Two URIs that are
	textually distinct after this normalization may still be
	equivalent. 
	
	Objects using the uri type may restrict the schemes that
	they permit.  For example, 'data:' and 'urn:' schemes
	might not be appropriate.
	
	A zero-length URI is not a valid URI.  This can be used to
	express 'URI absent' where required.
	
	In the value set and its semantics, this type is equivalent
	to the Uri SMIv2 textual convention defined in RFC 5017.
		"
    SYNTAX OCTET STRING 

IetfNetconfAcmAccessOperationsType ::= TEXTUAL-CONVENTION
    STATUS current
    DESCRIPTION "NETCONF Access Operation.
		"
    SYNTAX BITS  {
	 create (0),
	 read (1),
	 update (2),
	 delete (3),
	 exec (4)
	}

IetfNetconfAcmActionType ::= TEXTUAL-CONVENTION
    STATUS current
    DESCRIPTION "Action taken by the server when a particular
	rule matches.
		"
    SYNTAX INTEGER  {
	 permit (0),
	 deny (1)
	}

IetfNetconfAcmGroupNameType ::= TEXTUAL-CONVENTION
    STATUS current
    DESCRIPTION "Name of administrative group to which
	users can be assigned.
		"
    SYNTAX OCTET STRING  (SIZE (1..65535))

IetfNetconfAcmMatchallStringType ::= TEXTUAL-CONVENTION
    STATUS current
    DESCRIPTION "The string containing a single asterisk '*' is used
	to conceptually represent all possible values
	for the particular leaf using this data type.
		"
    SYNTAX OCTET STRING 

IetfNetconfAcmNodeInstanceIdentifier ::= TEXTUAL-CONVENTION
    STATUS current
    DESCRIPTION "Path expression used to represent a special
	data node instance identifier string. 
	
	A node-instance-identifier value is an
	unrestricted YANG instance-identifier expression.
	All the same rules as an instance-identifier apply
	except predicates for keys are optional.  If a key
	predicate is missing, then the node-instance-identifier
	represents all possible server instances for that key.
	
	This XPath expression is evaluated in the following context:
	
	 o  The set of namespace declarations are those in scope on
	    the leaf element where this type is used.
	
	 o  The set of variable bindings contains one variable,
	    'USER', which contains the name of the user of the current
	     session.
	
	 o  The function library is the core function library, but
	    note that due to the syntax restrictions of an
	    instance-identifier, no functions are allowed.
	
	 o  The context node is the root node in the data tree.
		"
    SYNTAX OCTET STRING 

IetfNetconfAcmUserNameType ::= TEXTUAL-CONVENTION
    STATUS current
    DESCRIPTION "General Purpose Username string.
		"
    SYNTAX OCTET STRING  (SIZE (1..65535))

IetfNetconfEditOperationType ::= TEXTUAL-CONVENTION
    STATUS current
    DESCRIPTION "NETCONF 'operation' attribute values
		"
    SYNTAX INTEGER  {
	 merge (0),
	 replace (1),
	 create (2),
	 delete (3),
	 remove (4)
	}

IetfNetconfErrorSeverityType ::= TEXTUAL-CONVENTION
    STATUS current
    DESCRIPTION "NETCONF Error Severity
		"
    SYNTAX INTEGER  {
	 error (0),
	 warning (1)
	}

IetfNetconfErrorTagType ::= TEXTUAL-CONVENTION
    STATUS current
    DESCRIPTION "NETCONF Error Tag
		"
    SYNTAX INTEGER  {
	 inUse (0),
	 invalidValue (1),
	 tooBig (2),
	 missingAttribute (3),
	 badAttribute (4),
	 unknownAttribute (5),
	 missingElement (6),
	 badElement (7),
	 unknownElement (8),
	 unknownNamespace (9),
	 accessDenied (10),
	 lockDenied (11),
	 resourceDenied (12),
	 rollbackFailed (13),
	 dataExists (14),
	 dataMissing (15),
	 operationNotSupported (16),
	 operationFailed (17),
	 partialOperation (18),
	 malformedMessage (19)
	}

IetfNetconfSessionIdOrZeroType ::= TEXTUAL-CONVENTION
    STATUS current
    DESCRIPTION "NETCONF Session Id or Zero to indicate none
		"
    SYNTAX Unsigned32 

IetfNetconfSessionIdType ::= TEXTUAL-CONVENTION
    STATUS current
    DESCRIPTION "NETCONF Session Id
		"
    SYNTAX Unsigned32  (1..4294967295)

IetfNetconfWithDefaultsWithDefaultsMode ::= TEXTUAL-CONVENTION
    STATUS current
    DESCRIPTION "Possible modes to report default data.
		"
    SYNTAX INTEGER  {
	 reportAll (0),
	 reportAllTagged (1),
	 trim (2),
	 explicit (3)
	}

IetfYangTypesCounter32 ::= TEXTUAL-CONVENTION
    STATUS current
    DESCRIPTION "The counter32 type represents a non-negative integer
	that monotonically increases until it reaches a
	maximum value of 2^32-1 (4294967295 decimal), when it
	wraps around and starts increasing again from zero. 
	
	Counters have no defined 'initial' value, and thus, a
	single value of a counter has (in general) no information
	content.  Discontinuities in the monotonically increasing
	value normally occur at re-initialization of the
	management system, and at other times as specified in the
	description of a schema node using this type.  If such
	other times can occur, for example, the creation of
	a schema node of type counter32 at times other than
	re-initialization, then a corresponding schema node
	should be defined, with an appropriate type, to indicate
	the last discontinuity.
	
	The counter32 type should not be used for configuration
	schema nodes.  A default statement SHOULD NOT be used in
	combination with the type counter32.
	
	In the value set and its semantics, this type is equivalent
	to the Counter32 type of the SMIv2.
		"
    SYNTAX Unsigned32 

IetfYangTypesCounter64 ::= TEXTUAL-CONVENTION
    STATUS current
    DESCRIPTION "The counter64 type represents a non-negative integer
	that monotonically increases until it reaches a
	maximum value of 2^64-1 (18446744073709551615 decimal),
	when it wraps around and starts increasing again from zero. 
	
	Counters have no defined 'initial' value, and thus, a
	single value of a counter has (in general) no information
	content.  Discontinuities in the monotonically increasing
	value normally occur at re-initialization of the
	management system, and at other times as specified in the
	description of a schema node using this type.  If such
	other times can occur, for example, the creation of
	a schema node of type counter64 at times other than
	re-initialization, then a corresponding schema node
	should be defined, with an appropriate type, to indicate
	the last discontinuity.
	
	The counter64 type should not be used for configuration
	schema nodes.  A default statement SHOULD NOT be used in
	combination with the type counter64.
	
	In the value set and its semantics, this type is equivalent
	to the Counter64 type of the SMIv2.
		"
    SYNTAX OCTET STRING 

IetfYangTypesDateAndTime ::= TEXTUAL-CONVENTION
    STATUS current
    DESCRIPTION "The date-and-time type is a profile of the ISO 8601
	standard for representation of dates and times using the
	Gregorian calendar.  The profile is defined by the
	date-time production in Section 5.6 of RFC 3339.
	
	The date-and-time type is compatible with the dateTime XML
	schema type with the following notable exceptions:
	
	(a) The date-and-time type does not allow negative years.
	
	(b) The date-and-time time-offset -00:00 indicates an unknown
	    time zone (see RFC 3339) while -00:00 and +00:00 and Z
	    all represent the same time zone in dateTime.
	
	(c) The canonical format (see below) of data-and-time values
	    differs from the canonical format used by the dateTime XML
	    schema type, which requires all times to be in UTC using
	    the time-offset 'Z'.
	
	This type is not equivalent to the DateAndTime textual
	convention of the SMIv2 since RFC 3339 uses a different
	separator between full-date and full-time and provides
	higher resolution of time-secfrac.
	
	The canonical format for date-and-time values with a known time
	zone uses a numeric time zone offset that is calculated using
	the device's configured known offset to UTC time.  A change of
	the device's offset to UTC time will cause date-and-time values
	to change accordingly.  Such changes might happen periodically
	in case a server follows automatically daylight saving time
	(DST) time zone offset changes.  The canonical format for
	date-and-time values with an unknown time zone (usually
	referring to the notion of local time) uses the time-offset
	-00:00.
		"
    SYNTAX OCTET STRING 

IetfYangTypesDottedQuad ::= TEXTUAL-CONVENTION
    STATUS current
    DESCRIPTION "An unsigned 32-bit number expressed in the dotted-quad
	notation, i.e., four octets written as decimal numbers
	and separated with the '.' (full stop) character.
		"
    SYNTAX OCTET STRING 

IetfYangTypesGauge32 ::= TEXTUAL-CONVENTION
    STATUS current
    DESCRIPTION "The gauge32 type represents a non-negative integer, which
	may increase or decrease, but shall never exceed a maximum
	value, nor fall below a minimum value.  The maximum value
	cannot be greater than 2^32-1 (4294967295 decimal), and
	the minimum value cannot be smaller than 0.  The value of
	a gauge32 has its maximum value whenever the information
	being modeled is greater than or equal to its maximum
	value, and has its minimum value whenever the information
	being modeled is smaller than or equal to its minimum value.
	If the information being modeled subsequently decreases
	below (increases above) the maximum (minimum) value, the
	gauge32 also decreases (increases).
	
	In the value set and its semantics, this type is equivalent
	to the Gauge32 type of the SMIv2.
		"
    SYNTAX Unsigned32 

IetfYangTypesGauge64 ::= TEXTUAL-CONVENTION
    STATUS current
    DESCRIPTION "The gauge64 type represents a non-negative integer, which
	may increase or decrease, but shall never exceed a maximum
	value, nor fall below a minimum value.  The maximum value
	cannot be greater than 2^64-1 (18446744073709551615), and
	the minimum value cannot be smaller than 0.  The value of
	a gauge64 has its maximum value whenever the information
	being modeled is greater than or equal to its maximum
	value, and has its minimum value whenever the information
	being modeled is smaller than or equal to its minimum value.
	If the information being modeled subsequently decreases
	below (increases above) the maximum (minimum) value, the
	gauge64 also decreases (increases).
	
	In the value set and its semantics, this type is equivalent
	to the CounterBasedGauge64 SMIv2 textual convention defined
	in RFC 2856
		"
    SYNTAX OCTET STRING 

IetfYangTypesHexString ::= TEXTUAL-CONVENTION
    STATUS current
    DESCRIPTION "A hexadecimal string with octets represented as hex digits
	separated by colons.  The canonical representation uses
	lowercase characters.
		"
    SYNTAX OCTET STRING 

IetfYangTypesMacAddress ::= TEXTUAL-CONVENTION
    STATUS current
    DESCRIPTION "The mac-address type represents an IEEE 802 MAC address. 
	The canonical representation uses lowercase characters.
	
	In the value set and its semantics, this type is equivalent
	to the MacAddress textual convention of the SMIv2.
		"
    SYNTAX OCTET STRING 

IetfYangTypesObjectIdentifier ::= TEXTUAL-CONVENTION
    STATUS current
    DESCRIPTION "The object-identifier type represents administratively
	assigned names in a registration-hierarchical-name tree. 
	
	Values of this type are denoted as a sequence of numerical
	non-negative sub-identifier values.  Each sub-identifier
	value MUST NOT exceed 2^32-1 (4294967295).  Sub-identifiers
	are separated by single dots and without any intermediate
	whitespace.
	
	The ASN.1 standard restricts the value space of the first
	sub-identifier to 0, 1, or 2.  Furthermore, the value space
	of the second sub-identifier is restricted to the range
	0 to 39 if the first sub-identifier is 0 or 1.  Finally,
	the ASN.1 standard requires that an object identifier
	has always at least two sub-identifiers.  The pattern
	captures these restrictions.
	
	Although the number of sub-identifiers is not limited,
	module designers should realize that there may be
	implementations that stick with the SMIv2 limit of 128
	sub-identifiers.
	
	This type is a superset of the SMIv2 OBJECT IDENTIFIER type
	since it is not restricted to 128 sub-identifiers.  Hence,
	this type SHOULD NOT be used to represent the SMIv2 OBJECT
	IDENTIFIER type; the object-identifier-128 type SHOULD be
	used instead.
		"
    SYNTAX OCTET STRING 

IetfYangTypesObjectIdentifier128 ::= TEXTUAL-CONVENTION
    STATUS current
    DESCRIPTION "This type represents object-identifiers restricted to 128
	sub-identifiers. 
	
	In the value set and its semantics, this type is equivalent
	to the OBJECT IDENTIFIER type of the SMIv2.
		"
    SYNTAX OCTET STRING 

IetfYangTypesPhysAddress ::= TEXTUAL-CONVENTION
    STATUS current
    DESCRIPTION "Represents media- or physical-level addresses represented
	as a sequence octets, each octet represented by two hexadecimal
	numbers.  Octets are separated by colons.  The canonical
	representation uses lowercase characters.
	
	In the value set and its semantics, this type is equivalent
	to the PhysAddress textual convention of the SMIv2.
		"
    SYNTAX OCTET STRING 

IetfYangTypesTimestamp ::= TEXTUAL-CONVENTION
    STATUS current
    DESCRIPTION "The timestamp type represents the value of an associated
	timeticks schema node at which a specific occurrence
	happened.  The specific occurrence must be defined in the
	description of any schema node defined using this type.  When
	the specific occurrence occurred prior to the last time the
	associated timeticks attribute was zero, then the timestamp
	value is zero.  Note that this requires all timestamp values
	to be reset to zero when the value of the associated timeticks
	attribute reaches 497+ days and wraps around to zero.
	
	The associated timeticks schema node must be specified
	in the description of any schema node using this type.
	
	In the value set and its semantics, this type is equivalent
	to the TimeStamp textual convention of the SMIv2.
		"
    SYNTAX Unsigned32 

IetfYangTypesTimeticks ::= TEXTUAL-CONVENTION
    STATUS current
    DESCRIPTION "The timeticks type represents a non-negative integer that
	represents the time, modulo 2^32 (4294967296 decimal), in
	hundredths of a second between two epochs.  When a schema
	node is defined that uses this type, the description of
	the schema node identifies both of the reference epochs.
	
	In the value set and its semantics, this type is equivalent
	to the TimeTicks type of the SMIv2.
		"
    SYNTAX Unsigned32 

IetfYangTypesUuid ::= TEXTUAL-CONVENTION
    STATUS current
    DESCRIPTION "A Universally Unique IDentifier in the string representation
	defined in RFC 4122.  The canonical representation uses
	lowercase characters.
	
	The following is an example of a UUID in string representation:
	f81d4fae-7dec-11d0-a765-00a0c91e6bf6
	
		"
    SYNTAX OCTET STRING 

IetfYangTypesXpath10 ::= TEXTUAL-CONVENTION
    STATUS current
    DESCRIPTION "This type represents an XPATH 1.0 expression. 
	
	When a schema node is defined that uses this type, the
	description of the schema node MUST specify the XPath
	context in which the XPath expression is evaluated.
		"
    SYNTAX OCTET STRING 

IetfYangTypesYangIdentifier ::= TEXTUAL-CONVENTION
    STATUS current
    DESCRIPTION "A YANG identifier string as defined by the 'identifier'
	rule in Section 12 of RFC 6020.  An identifier must
	start with an alphabetic character or an underscore
	followed by an arbitrary sequence of alphabetic or
	numeric characters, underscores, hyphens, or dots.
	
	A YANG identifier MUST NOT start with any possible
	combination of the lowercase or uppercase character
	sequence 'xml'.
		"
    SYNTAX OCTET STRING  (SIZE (1..65535))

IetfYangTypesZeroBasedCounter32 ::= TEXTUAL-CONVENTION
    STATUS current
    DESCRIPTION "The zero-based-counter32 type represents a counter32
	that has the defined 'initial' value zero.
	
	A schema node of this type will be set to zero (0) on creation
	and will thereafter increase monotonically until it reaches
	a maximum value of 2^32-1 (4294967295 decimal), when it
	wraps around and starts increasing again from zero.
	
	Provided that an application discovers a new schema node
	of this type within the minimum time to wrap, it can use the
	'initial' value as a delta.  It is important for a management
	station to be aware of this minimum time and the actual time
	between polls, and to discard data if the actual time is too
	long or there is no defined minimum time.
	
	In the value set and its semantics, this type is equivalent
	to the ZeroBasedCounter32 textual convention of the SMIv2.
		"
    SYNTAX Unsigned32 

IetfYangTypesZeroBasedCounter64 ::= TEXTUAL-CONVENTION
    STATUS current
    DESCRIPTION "The zero-based-counter64 type represents a counter64 that
	has the defined 'initial' value zero. 
	
	
	
	
	A schema node of this type will be set to zero (0) on creation
	and will thereafter increase monotonically until it reaches
	a maximum value of 2^64-1 (18446744073709551615 decimal),
	when it wraps around and starts increasing again from zero.
	
	Provided that an application discovers a new schema node
	of this type within the minimum time to wrap, it can use the
	'initial' value as a delta.  It is important for a management
	station to be aware of this minimum time and the actual time
	between polls, and to discard data if the actual time is too
	long or there is no defined minimum time.
	
	In the value set and its semantics, this type is equivalent
	to the ZeroBasedCounter64 textual convention of the SMIv2.
		"
    SYNTAX OCTET STRING 

KeySyncSessionCertificateRef ::= TEXTUAL-CONVENTION
    STATUS current
    DESCRIPTION "certificate to be referred to.
		"
    SYNTAX OCTET STRING 

KeySyncSessionInterfaceRef ::= TEXTUAL-CONVENTION
    STATUS current
    DESCRIPTION "Interface to be referred to.
		"
    SYNTAX OCTET STRING 

LldpLldpSysCap ::= TEXTUAL-CONVENTION
    STATUS current
    DESCRIPTION "NULL
		"
    SYNTAX BITS  {
	 other (0),
	 repeater (1),
	 bridge (2),
	 wlanaccesspoint (3),
	 router (4),
	 telephone (5),
	 docsiscabledevice (6),
	 stationonly (7),
	 cvlancomponent (8),
	 svlancomponent (9),
	 twoportmacrelay (10)
	}

OpticalCommonSupportingPort ::= TEXTUAL-CONVENTION
    STATUS current
    DESCRIPTION "References one individual port, or no port at all
		"
    SYNTAX OCTET STRING 

OtdrOtdrIor ::= TEXTUAL-CONVENTION
    STATUS current
    DESCRIPTION "NULL
		"
    SYNTAX OCTET STRING 

OtdrOtdrPulseWidth ::= TEXTUAL-CONVENTION
    STATUS current
    DESCRIPTION "NULL
		"
    SYNTAX OCTET STRING 

OtdrOtdrRange ::= TEXTUAL-CONVENTION
    STATUS current
    DESCRIPTION "NULL
		"
    SYNTAX OCTET STRING 



coriant OBJECT IDENTIFIER ::= { enterprises  42229 }
products OBJECT IDENTIFIER ::= { coriant  1 }  
fault OBJECT IDENTIFIER ::= { groove 1 }
notificationInfo OBJECT IDENTIFIER ::= { fault 1 }
notificationObject OBJECT IDENTIFIER ::= { notificationInfo 1 }
notificationFmEntity OBJECT-TYPE
    SYNTAX DisplayString
    MAX-ACCESS read-only
    STATUS current
    DESCRIPTION "The management object instance which the alarm or condition is reported against.
		
		
		"
::= { notificationObject 1 }
notificationConditionType OBJECT-TYPE
    SYNTAX CoriantFmtypesConditionType 
    MAX-ACCESS read-only
    STATUS current
    DESCRIPTION "Identifies the current standing conditions which cause alarms and/or events.
		
		
		"
::= { notificationObject 2 }
notificationLocation OBJECT-TYPE
    SYNTAX CoriantTypesManagementLocation 
    MAX-ACCESS read-only
    STATUS current
    DESCRIPTION "
	Indicates if the alarm or event location is near end or far end.
	
		
		
		"
::= { notificationObject 3 }
notificationDirection OBJECT-TYPE
    SYNTAX CoriantTypesManagementDirection 
    MAX-ACCESS read-only
    STATUS current
    DESCRIPTION "
	Specifies the direction of an event/occurrence in the system, Ingress, Egress, NA.
	
		
		
		"
::= { notificationObject 4 }
notificationTimePeriod OBJECT-TYPE
    SYNTAX CoriantTypesManagementTimePeriod 
    MAX-ACCESS read-only
    STATUS current
    DESCRIPTION "
	Indicates the time-period increments during which PM data is collected.
	
		
		
		"
::= { notificationObject 5 }
notificationServiceAffect OBJECT-TYPE
    SYNTAX CoriantFmtypesServiceAffectFm 
    MAX-ACCESS read-only
    STATUS current
    DESCRIPTION "
	Indicates if an alarm is service affecting or non-service affecting.
	NSA indicates non-service affecting.
	SA indicates service affecting.
	
		
		
		"
::= { notificationObject 6 }
notificationSeverityLevel OBJECT-TYPE
    SYNTAX CoriantFmtypesSeverityLevel 
    MAX-ACCESS read-only
    STATUS current
    DESCRIPTION "
	Indicates the notification code (severity level) associated with the alarm type of service affecting.
	
		
		
		"
::= { notificationObject 7 }
notificationOccurrenceDateTime OBJECT-TYPE
    SYNTAX IetfYangTypesDateAndTime 
    MAX-ACCESS read-only
    STATUS current
    DESCRIPTION "Indicates the occurrence date and time of the alarm by the month of the year, the day of the month, hour of the day, the minute of the hour, and the second of the minute.
	
		
		
		"
::= { notificationObject 8 }
notificationConditionDescription OBJECT-TYPE
    SYNTAX OCTET STRING  (SIZE (0..255))
    MAX-ACCESS read-only
    STATUS current
    DESCRIPTION "
	Describes the condition that caused the alarm. 
	
		
		
		"
::= { notificationObject 9 }
notificationAlarmConditionType OBJECT-TYPE
    SYNTAX INTEGER  {
	 standing (1),
	 transient (2)
	}
    MAX-ACCESS read-only
    STATUS current
    DESCRIPTION "Alarm condition types, for example, standing or transient.
		
		
		"
::= { notificationObject 10 }
notificationLastSeverityLevel OBJECT-TYPE
    SYNTAX CoriantFmtypesSeverityLevel 
    MAX-ACCESS read-only
    STATUS current
    DESCRIPTION "
	Indicates the last severity level associated with the alarm type,
	which provides the info of alarm severity declared and cleared.
	
		
		
		"
::= { notificationObject 11 }
notificationExtensionDescription OBJECT-TYPE
    SYNTAX OCTET STRING  (SIZE (0..255))
    MAX-ACCESS read-only
    STATUS current
    DESCRIPTION "
	The description in alarm notification to provide additional information.
	
		
		
		"
::= { notificationObject 12 }
notificationFmEntityType OBJECT-TYPE
    SYNTAX CoriantFmtypesEntityTypeFm 
    MAX-ACCESS read-only
    STATUS current
    DESCRIPTION "
	Indicates the entity type the condition associated, which provides additional information for the object instance having the condition.
	entity type is not exactly same as MO. Entity type have smaller granularity referring to
	different service functions, e.g. 100GBase-R, 40GBase-R, 100GBase-R, ODU4, ODU2, ODU3, OTU4, OTUC2...
	Separate functions will have different entity types so that profile can be set differently for different
	service function which is more corresponding to user application.
	
		
		
		"
::= { notificationObject 13 }
notificationTrap OBJECT IDENTIFIER ::= { fault 2 }
alarmNotification NOTIFICATION-TYPE
    OBJECTS { notificationFmEntity,notificationConditionType,notificationLocation,notificationDirection,notificationTimePeriod,notificationServiceAffect,notificationSeverityLevel,notificationOccurrenceDateTime,notificationConditionDescription,notificationFmEntityType,notificationAlarmConditionType,notificationLastSeverityLevel,notificationExtensionDescription }
    STATUS current
    DESCRIPTION "<description>"
::= { notificationTrap 1 }
notAlarmedEventNotification NOTIFICATION-TYPE
    OBJECTS { notificationFmEntity,notificationConditionType,notificationLocation,notificationDirection,notificationTimePeriod,notificationServiceAffect,notificationSeverityLevel,notificationOccurrenceDateTime,notificationConditionDescription,notificationFmEntityType,notificationAlarmConditionType,notificationLastSeverityLevel,notificationExtensionDescription }
    STATUS current
    DESCRIPTION "<description>"
::= { notificationTrap 2 }
alarmProfile OBJECT IDENTIFIER ::= { fault 4 }
alarmProfileTable OBJECT-TYPE
    SYNTAX SEQUENCE OF AlarmProfileEntry
    MAX-ACCESS not-accessible
    STATUS current
    DESCRIPTION "Alarm profile defines the severity profile of alarm and event."
::= { alarmProfile 1 }
alarmProfileEntry OBJECT-TYPE
    SYNTAX AlarmProfileEntry
    MAX-ACCESS not-accessible
    STATUS current
    DESCRIPTION "Entry of alarmProfileTable" 
    INDEX { alarmProfileId }
::= { alarmProfileTable 1 }
AlarmProfileEntry ::= 
SEQUENCE {
	alarmProfileId Unsigned32
    }
alarmProfileId OBJECT-TYPE
    SYNTAX Unsigned32  (1..255)
    MAX-ACCESS read-only
    STATUS current
    DESCRIPTION "
	alarm profile identifier which uniquely specify alarm profile.
	alarm profile 1 is supported firstly and applicable to all entities implicitly.
	
		
		
		"
::= { alarmProfileEntry 1 }
alarmProfileENTR OBJECT IDENTIFIER ::= { fault 5 }
alarmProfileENTRTable OBJECT-TYPE
    SYNTAX SEQUENCE OF AlarmProfileENTREntry
    MAX-ACCESS not-accessible
    STATUS current
    DESCRIPTION "The list includes alarm/event entries of an alarm-profile."
::= { alarmProfileENTR 1 }
alarmProfileENTREntry OBJECT-TYPE
    SYNTAX AlarmProfileENTREntry
    MAX-ACCESS not-accessible
    STATUS current
    DESCRIPTION "Entry of alarmProfileENTRTable" 
    INDEX { alarmProfileId,alarmProfileENTRConditionType,alarmProfileENTRFmEntityType,alarmProfileENTRTimePeriod }
::= { alarmProfileENTRTable 1 }
AlarmProfileENTREntry ::= 
SEQUENCE {
	alarmProfileENTRConditionType CoriantFmtypesConditionType,
	alarmProfileENTRFmEntityType CoriantFmtypesEntityTypeFm,
	alarmProfileENTRTimePeriod CoriantTypesManagementTimePeriod,
	alarmProfileENTRSeverityLevelSa CoriantFmtypesSeverityLevel,
	alarmProfileENTRSeverityLevelNsa CoriantFmtypesSeverityLevel
    }
alarmProfileENTRConditionType OBJECT-TYPE
    SYNTAX CoriantFmtypesConditionType 
    MAX-ACCESS read-only
    STATUS current
    DESCRIPTION "
	Identifies the current standing conditions which cause conditions and/or events.
	
		
		
		"
::= { alarmProfileENTREntry 1 }
alarmProfileENTRFmEntityType OBJECT-TYPE
    SYNTAX CoriantFmtypesEntityTypeFm 
    MAX-ACCESS read-only
    STATUS current
    DESCRIPTION "
	Indicates the entity type the condition associated, which provides additional information for the object instance having the condition.
	entity type is not exactly same as MO. Entity type have smaller granularity referring to 
	different service functions, e.g. 100GBase-R, 40GBase-R, 100GBase-R, ODU4, ODU2, ODU3, OTU4, OTUC2...
	Separate functions will have different entity types so that profile can be set differently for different
	service function which is more corresponding to user application.
	
		
		
		"
::= { alarmProfileENTREntry 2 }
alarmProfileENTRTimePeriod OBJECT-TYPE
    SYNTAX CoriantTypesManagementTimePeriod 
    MAX-ACCESS read-only
    STATUS current
    DESCRIPTION "
	Indicates the time-period increments during which PM data is collected.
	
		
		
		"
::= { alarmProfileENTREntry 3 }
alarmProfileENTRSeverityLevelSa OBJECT-TYPE
    SYNTAX CoriantFmtypesSeverityLevel 
    MAX-ACCESS read-only
    STATUS current
    DESCRIPTION "
	Indicates the notification code (severity level) associated with the condition type of service affecting.
	
		
		
		"
::= { alarmProfileENTREntry 4 }
alarmProfileENTRSeverityLevelNsa OBJECT-TYPE
    SYNTAX CoriantFmtypesSeverityLevel 
    MAX-ACCESS read-only
    STATUS current
    DESCRIPTION "
	Indicates the notification code (severity level) associated with the condition type of non-service affecting.
	
		
		
		"
::= { alarmProfileENTREntry 5 }
standingCondition OBJECT IDENTIFIER ::= { fault 6 }
standingConditionTable OBJECT-TYPE
    SYNTAX SEQUENCE OF StandingConditionEntry
    MAX-ACCESS not-accessible
    STATUS current
    DESCRIPTION "The list includes active standing alarms."
::= { standingCondition 1 }
standingConditionEntry OBJECT-TYPE
    SYNTAX StandingConditionEntry
    MAX-ACCESS not-accessible
    STATUS current
    DESCRIPTION "Entry of standingConditionTable" 
    INDEX { standingConditionFmEntity,standingConditionConditionType,standingConditionLocation,standingConditionDirection,standingConditionTimePeriod }
::= { standingConditionTable 1 }
StandingConditionEntry ::= 
SEQUENCE {
	standingConditionFmEntity RowPointer,
	standingConditionConditionType CoriantFmtypesConditionType,
	standingConditionLocation CoriantTypesManagementLocation,
	standingConditionDirection CoriantTypesManagementDirection,
	standingConditionTimePeriod CoriantTypesManagementTimePeriod,
	standingConditionServiceAffect CoriantFmtypesServiceAffectFm,
	standingConditionSeverityLevel CoriantFmtypesSeverityLevel,
	standingConditionOccurrenceDateTime IetfYangTypesDateAndTime,
	standingConditionConditionDescription OCTET STRING,
	standingConditionFmEntityType CoriantFmtypesEntityTypeFm
    }
standingConditionFmEntity OBJECT-TYPE
    SYNTAX RowPointer 
    MAX-ACCESS read-only
    STATUS current
    DESCRIPTION "The management object instance which the alarm or condition is reported against.
		
		
		"
::= { standingConditionEntry 1 }
standingConditionConditionType OBJECT-TYPE
    SYNTAX CoriantFmtypesConditionType 
    MAX-ACCESS read-only
    STATUS current
    DESCRIPTION "Identifies the current standing conditions which cause alarms and/or events.
		
		
		"
::= { standingConditionEntry 2 }
standingConditionLocation OBJECT-TYPE
    SYNTAX CoriantTypesManagementLocation 
    MAX-ACCESS read-only
    STATUS current
    DESCRIPTION "
	Indicates if the alarm or event location is near end or far end.
	
		
		
		"
::= { standingConditionEntry 3 }
standingConditionDirection OBJECT-TYPE
    SYNTAX CoriantTypesManagementDirection 
    MAX-ACCESS read-only
    STATUS current
    DESCRIPTION "
	Specifies the direction of an event/occurrence in the system, Ingress, Egress, NA.
	
		
		
		"
::= { standingConditionEntry 4 }
standingConditionTimePeriod OBJECT-TYPE
    SYNTAX CoriantTypesManagementTimePeriod 
    MAX-ACCESS read-only
    STATUS current
    DESCRIPTION "
	Indicates the time-period increments during which PM data is collected.
	
		
		
		"
::= { standingConditionEntry 5 }
standingConditionServiceAffect OBJECT-TYPE
    SYNTAX CoriantFmtypesServiceAffectFm 
    MAX-ACCESS read-only
    STATUS current
    DESCRIPTION "
	Indicates if an alarm is service affecting or non-service affecting.
	NSA indicates non-service affecting.
	SA indicates service affecting.
	
		
		
		"
::= { standingConditionEntry 6 }
standingConditionSeverityLevel OBJECT-TYPE
    SYNTAX CoriantFmtypesSeverityLevel 
    MAX-ACCESS read-only
    STATUS current
    DESCRIPTION "
	Indicates the notification code (severity level) associated with the alarm type of service affecting.
	
		
		
		"
::= { standingConditionEntry 7 }
standingConditionOccurrenceDateTime OBJECT-TYPE
    SYNTAX IetfYangTypesDateAndTime 
    MAX-ACCESS read-only
    STATUS current
    DESCRIPTION "Indicates the occurrence date and time of the alarm by the month of the year, the day of the month, hour of the day, the minute of the hour, and the second of the minute.
	
		
		
		"
::= { standingConditionEntry 8 }
standingConditionConditionDescription OBJECT-TYPE
    SYNTAX OCTET STRING  (SIZE (0..255))
    MAX-ACCESS read-only
    STATUS current
    DESCRIPTION "
	Describes the condition that caused the alarm. 
	
		
		
		"
::= { standingConditionEntry 9 }
standingConditionFmEntityType OBJECT-TYPE
    SYNTAX CoriantFmtypesEntityTypeFm 
    MAX-ACCESS read-only
    STATUS current
    DESCRIPTION "
	Indicates the entity type the condition associated, which provides additional information for the object instance having the condition.
	entity type is not exactly same as MO. Entity type have smaller granularity referring to
	different service functions, e.g. 100GBase-R, 40GBase-R, 100GBase-R, ODU4, ODU2, ODU3, OTU4, OTUC2...
	Separate functions will have different entity types so that profile can be set differently for different
	service function which is more corresponding to user application.
	
		
		
		"
::= { standingConditionEntry 10 }
ne OBJECT IDENTIFIER ::= { groove 2 }
neInfo OBJECT IDENTIFIER ::= { ne 1 }
neId OBJECT-TYPE
    SYNTAX OCTET STRING  (SIZE (0..256))
    MAX-ACCESS read-only
    STATUS current
    DESCRIPTION "
	Network Element's system identification code. 
	Note that this is unique identifier for each NE.
	
		
		
		default value :"
::= { neInfo 1 }
neName OBJECT-TYPE
    SYNTAX OCTET STRING  (SIZE (0..256))
    MAX-ACCESS read-only
    STATUS current
    DESCRIPTION "
	Name assigned to this particular NE. 
	A readable name for the NE. It can be used for NE.
	But not expected to be used by NM for unique NE identification
	The different function from ne-id is that user can keep ne-id unchanged,
	which uniquely identifies the NE, and update ne-name if necessary.
	
		
		
		default value :"
::= { neInfo 2 }
neType OBJECT-TYPE
    SYNTAX OCTET STRING 
    MAX-ACCESS read-only
    STATUS current
    DESCRIPTION "Type of the NE
		
		
		default value :GROOVE_G30"
::= { neInfo 3 }
neLocation OBJECT-TYPE
    SYNTAX OCTET STRING  (SIZE (0..256))
    MAX-ACCESS read-only
    STATUS current
    DESCRIPTION "Name of the location of this particular NE
		
		
		"
::= { neInfo 4 }
neSite OBJECT-TYPE
    SYNTAX OCTET STRING  (SIZE (0..64))
    MAX-ACCESS read-only
    STATUS current
    DESCRIPTION "Name or CLLI of the site where this NE is located
		
		
		"
::= { neInfo 5 }
neAltitude OBJECT-TYPE
    SYNTAX INTEGER 
    MAX-ACCESS read-only
    STATUS current
    DESCRIPTION "The altitude of the Network Element in meters
		
		UNITS:meters
		"
::= { neInfo 6 }
neVendor OBJECT-TYPE
    SYNTAX OCTET STRING 
    MAX-ACCESS read-only
    STATUS current
    DESCRIPTION "Vendor name of this NE
		
		
		default value :Coriant"
::= { neInfo 7 }
neTemperature OBJECT-TYPE
    SYNTAX CoriantTypesTemperature 
    MAX-ACCESS read-only
    STATUS current
    DESCRIPTION "Ambient temperature sensed by the primary shelf for NE level
		
		
		"
::= { neInfo 8 }
system OBJECT IDENTIFIER ::= { ne 2 }
systemUnknownPluggableReport OBJECT-TYPE
    SYNTAX CoriantTypesEnableSwitch 
    MAX-ACCESS read-only
    STATUS current
    DESCRIPTION "
	The attribute will enable/disable the alarm reporting for unknown pluggables present on the NE.
	
		
		
		default value :enabled"
::= { system 1 }
systemPowerConsumptionCurrent OBJECT-TYPE
    SYNTAX CoriantTypesPower 
    MAX-ACCESS read-only
    STATUS current
    DESCRIPTION "Current power consumption of the system.
		
		
		"
::= { system 2 }
systemPowerConsumptionEstimatedMax OBJECT-TYPE
    SYNTAX CoriantTypesPower 
    MAX-ACCESS read-only
    STATUS current
    DESCRIPTION "Derived maximal power consumption around room temperature.
		
		
		"
::= { system 3 }
systemFactoryResetButton OBJECT-TYPE
    SYNTAX CoriantTypesEnableSwitch 
    MAX-ACCESS read-only
    STATUS current
    DESCRIPTION "
	The attribute will enable/disable factory reset button function on the NE.
	
		
		
		default value :enabled"
::= { system 4 }
console OBJECT IDENTIFIER ::= { ne 3 }
consoleBaudRate OBJECT-TYPE
    SYNTAX INTEGER  {
	 t9600 (6),
	 t19200 (7),
	 t38400 (8),
	 t57600 (11),
	 t115200 (12)
	}
    MAX-ACCESS read-only
    STATUS current
    DESCRIPTION "The baud rate of console port
		
		
		default value :9600"
::= { console 1 }
equipment OBJECT IDENTIFIER ::= { groove 3 }
shelf OBJECT IDENTIFIER ::= { equipment 1 }
shelfTable OBJECT-TYPE
    SYNTAX SEQUENCE OF ShelfEntry
    MAX-ACCESS not-accessible
    STATUS current
    DESCRIPTION "NULL"
::= { shelf 1 }
shelfEntry OBJECT-TYPE
    SYNTAX ShelfEntry
    MAX-ACCESS not-accessible
    STATUS current
    DESCRIPTION "Entry of shelfTable" 
    INDEX { shelfId }
::= { shelfTable 1 }
ShelfEntry ::= 
SEQUENCE {
	shelfId CoriantTypesShelfId,
	shelfLocation OCTET STRING,
	shelfInletTemperature CoriantTypesTemperature,
	shelfOutletTemperature CoriantTypesTemperature,
	shelfAdminStatus INTEGER,
	shelfOperStatus INTEGER,
	shelfAvailStatus BITS,
	shelfAliasName OCTET STRING
    }
shelfId OBJECT-TYPE
    SYNTAX CoriantTypesShelfId 
    MAX-ACCESS read-only
    STATUS current
    DESCRIPTION "
	Identifier of the shelf. 
	It shall be an integer number and assigned implicitly by the system or setting through coder on the shelf.
	
		
		
		"
::= { shelfEntry 1 }
shelfLocation OBJECT-TYPE
    SYNTAX OCTET STRING  (SIZE (0..64))
    MAX-ACCESS read-only
    STATUS current
    DESCRIPTION "Name of the location of this particular shelf.
		
		
		"
::= { shelfEntry 2 }
shelfInletTemperature OBJECT-TYPE
    SYNTAX CoriantTypesTemperature 
    MAX-ACCESS read-only
    STATUS current
    DESCRIPTION "shelf inlet temperature
		
		
		"
::= { shelfEntry 3 }
shelfOutletTemperature OBJECT-TYPE
    SYNTAX CoriantTypesTemperature 
    MAX-ACCESS read-only
    STATUS current
    DESCRIPTION "shelf outlet temperature
		
		
		"
::= { shelfEntry 4 }
shelfAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { shelfEntry 5 }
shelfOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { shelfEntry 6 }
shelfAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { shelfEntry 7 }
shelfAliasName OBJECT-TYPE
    SYNTAX OCTET STRING  (SIZE (0..256))
    MAX-ACCESS read-only
    STATUS current
    DESCRIPTION "User defined alias for this entity. Must be an alphanumeric string with dash or underscore
		
		
		"
::= { shelfEntry 8 }
slot OBJECT IDENTIFIER ::= { equipment 2 }
slotTable OBJECT-TYPE
    SYNTAX SEQUENCE OF SlotEntry
    MAX-ACCESS not-accessible
    STATUS current
    DESCRIPTION "NULL"
::= { slot 1 }
slotEntry OBJECT-TYPE
    SYNTAX SlotEntry
    MAX-ACCESS not-accessible
    STATUS current
    DESCRIPTION "Entry of slotTable" 
    INDEX { shelfId,slotId }
::= { slotTable 1 }
SlotEntry ::= 
SEQUENCE {
	slotId CoriantTypesSlotId,
	slotActualCardType CoriantTypesEquipmentType,
	slotPossibleCardTypes OCTET STRING,
	slotAdminStatus INTEGER,
	slotOperStatus INTEGER,
	slotAvailStatus BITS,
	slotAliasName OCTET STRING
    }
slotId OBJECT-TYPE
    SYNTAX CoriantTypesSlotId 
    MAX-ACCESS read-only
    STATUS current
    DESCRIPTION "
	Identifier of the slot. It shall be an integer number and assigned 
	implicitly by the system. 
	
		
		
		"
::= { slotEntry 1 }
slotActualCardType OBJECT-TYPE
    SYNTAX CoriantTypesEquipmentType 
    MAX-ACCESS read-only
    STATUS current
    DESCRIPTION "
	Equipment type for each slot/subslot according to the actually equipping. 
	Needs to be re-defined in the project specific model.
	
		
		
		default value :empty"
::= { slotEntry 2 }
slotPossibleCardTypes OBJECT-TYPE
    SYNTAX OCTET STRING 
    MAX-ACCESS read-only
    STATUS current
    DESCRIPTION "
	Defined all the equipment types which can be installed on the slot/subslot. 
	This is a leaf list, encode by some leafs.
		
		
		"
::= { slotEntry 3 }
slotAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { slotEntry 4 }
slotOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { slotEntry 5 }
slotAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { slotEntry 6 }
slotAliasName OBJECT-TYPE
    SYNTAX OCTET STRING  (SIZE (0..256))
    MAX-ACCESS read-only
    STATUS current
    DESCRIPTION "User defined alias for this entity. Must be an alphanumeric string with dash or underscore
		
		
		"
::= { slotEntry 7 }
card OBJECT IDENTIFIER ::= { equipment 3 }
cardTable OBJECT-TYPE
    SYNTAX SEQUENCE OF CardEntry
    MAX-ACCESS not-accessible
    STATUS current
    DESCRIPTION "Card is a container carried by a slot."
::= { card 1 }
cardEntry OBJECT-TYPE
    SYNTAX CardEntry
    MAX-ACCESS not-accessible
    STATUS current
    DESCRIPTION "Entry of cardTable" 
    INDEX { shelfId,slotId }
::= { cardTable 1 }
CardEntry ::= 
SEQUENCE {
	cardRequiredType CoriantTypesCardType,
	cardEquipmentName OCTET STRING,
	cardAdminStatus INTEGER,
	cardOperStatus INTEGER,
	cardAvailStatus BITS,
	cardAliasName OCTET STRING,
	cardFanSpeedRate CoriantTypesPercentage,
	cardSwitchingType INTEGER,
	cardTemperature CoriantTypesTemperature,
	cardMode INTEGER
    }
cardRequiredType OBJECT-TYPE
    SYNTAX CoriantTypesCardType 
    MAX-ACCESS read-only
    STATUS current
    DESCRIPTION "
	The attribute indicates the equipment type to identify the module. 
	Needs to be re-defined in the project specific model. 
	
		
		
		"
::= { cardEntry 1 }
cardEquipmentName OBJECT-TYPE
    SYNTAX OCTET STRING  (SIZE (0..64))
    MAX-ACCESS read-only
    STATUS current
    DESCRIPTION "
	The attribute indicates an additional field to identify the module. 
	
		
		
		"
::= { cardEntry 2 }
cardAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { cardEntry 3 }
cardOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { cardEntry 4 }
cardAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		default value :unknown"
::= { cardEntry 5 }
cardAliasName OBJECT-TYPE
    SYNTAX OCTET STRING  (SIZE (0..256))
    MAX-ACCESS read-only
    STATUS current
    DESCRIPTION "User defined alias for this entity. Must be an alphanumeric string with dash or underscore
		
		
		"
::= { cardEntry 6 }
cardFanSpeedRate OBJECT-TYPE
    SYNTAX CoriantTypesPercentage 
    MAX-ACCESS read-only
    STATUS current
    DESCRIPTION "The fan speed of percentage.
		Conditions:../required-type = 'FAN'
		
		"
::= { cardEntry 7 }
cardSwitchingType OBJECT-TYPE
    SYNTAX INTEGER  {
	 otn (0),
	 tdm (1),
	 optical (2),
	 packet (3)
	}
    MAX-ACCESS read-only
    STATUS current
    DESCRIPTION "The traffic switching type of card.
		Conditions:(../required-type != 'FAN') and (../required-type != 'PSU')
		
		default value :otn"
::= { cardEntry 8 }
cardTemperature OBJECT-TYPE
    SYNTAX CoriantTypesTemperature 
    MAX-ACCESS read-only
    STATUS current
    DESCRIPTION "Temperature at the monitoring point.
		
		
		"
::= { cardEntry 9 }
cardMode OBJECT-TYPE
    SYNTAX INTEGER  {
	 notApplicable (0),
	 normal (1),
	 regen (2)
	}
    MAX-ACCESS read-only
    STATUS current
    DESCRIPTION "Specify the card mode, e.g. normal or regen.
		
		
		default value :normal"
::= { cardEntry 10 }
subslot OBJECT IDENTIFIER ::= { equipment 4 }
subslotTable OBJECT-TYPE
    SYNTAX SEQUENCE OF SubslotEntry
    MAX-ACCESS not-accessible
    STATUS current
    DESCRIPTION "NULL"
::= { subslot 1 }
subslotEntry OBJECT-TYPE
    SYNTAX SubslotEntry
    MAX-ACCESS not-accessible
    STATUS current
    DESCRIPTION "Entry of subslotTable" 
    INDEX { shelfId,slotId,subslotId }
::= { subslotTable 1 }
SubslotEntry ::= 
SEQUENCE {
	subslotId CoriantTypesSlotId,
	subslotActualCardType CoriantTypesEquipmentType,
	subslotPossibleCardTypes OCTET STRING,
	subslotAdminStatus INTEGER,
	subslotOperStatus INTEGER,
	subslotAvailStatus BITS,
	subslotAliasName OCTET STRING
    }
subslotId OBJECT-TYPE
    SYNTAX CoriantTypesSlotId 
    MAX-ACCESS read-only
    STATUS current
    DESCRIPTION "
	Identifier of the subslot. 
	
		
		
		"
::= { subslotEntry 1 }
subslotActualCardType OBJECT-TYPE
    SYNTAX CoriantTypesEquipmentType 
    MAX-ACCESS read-only
    STATUS current
    DESCRIPTION "
	Equipment type for each slot/subslot according to the actually equipping. 
	Needs to be re-defined in the project specific model.
	
		
		
		default value :empty"
::= { subslotEntry 2 }
subslotPossibleCardTypes OBJECT-TYPE
    SYNTAX OCTET STRING 
    MAX-ACCESS read-only
    STATUS current
    DESCRIPTION "
	Defined all the equipment types which can be installed on the slot/subslot. 
	This is a leaf list, encode by some leafs.
		
		
		"
::= { subslotEntry 3 }
subslotAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { subslotEntry 4 }
subslotOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { subslotEntry 5 }
subslotAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { subslotEntry 6 }
subslotAliasName OBJECT-TYPE
    SYNTAX OCTET STRING  (SIZE (0..256))
    MAX-ACCESS read-only
    STATUS current
    DESCRIPTION "User defined alias for this entity. Must be an alphanumeric string with dash or underscore
		
		
		"
::= { subslotEntry 7 }
subcard OBJECT IDENTIFIER ::= { equipment 5 }
subcardTable OBJECT-TYPE
    SYNTAX SEQUENCE OF SubcardEntry
    MAX-ACCESS not-accessible
    STATUS current
    DESCRIPTION "Subcard is a container carried by a subslot."
::= { subcard 1 }
subcardEntry OBJECT-TYPE
    SYNTAX SubcardEntry
    MAX-ACCESS not-accessible
    STATUS current
    DESCRIPTION "Entry of subcardTable" 
    INDEX { shelfId,slotId,subslotId }
::= { subcardTable 1 }
SubcardEntry ::= 
SEQUENCE {
	subcardRequiredType CoriantTypesCardType,
	subcardEquipmentName OCTET STRING,
	subcardAdminStatus INTEGER,
	subcardOperStatus INTEGER,
	subcardAvailStatus BITS,
	subcardAliasName OCTET STRING,
	subcardTemperature CoriantTypesTemperature
    }
subcardRequiredType OBJECT-TYPE
    SYNTAX CoriantTypesCardType 
    MAX-ACCESS read-only
    STATUS current
    DESCRIPTION "
	The attribute indicates the equipment type to identify the module. 
	Needs to be re-defined in the project specific model. 
	
		
		
		"
::= { subcardEntry 1 }
subcardEquipmentName OBJECT-TYPE
    SYNTAX OCTET STRING  (SIZE (0..64))
    MAX-ACCESS read-only
    STATUS current
    DESCRIPTION "
	The attribute indicates an additional field to identify the module. 
	
		
		
		"
::= { subcardEntry 2 }
subcardAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { subcardEntry 3 }
subcardOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { subcardEntry 4 }
subcardAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		default value :unknown"
::= { subcardEntry 5 }
subcardAliasName OBJECT-TYPE
    SYNTAX OCTET STRING  (SIZE (0..256))
    MAX-ACCESS read-only
    STATUS current
    DESCRIPTION "User defined alias for this entity. Must be an alphanumeric string with dash or underscore
		
		
		"
::= { subcardEntry 6 }
subcardTemperature OBJECT-TYPE
    SYNTAX CoriantTypesTemperature 
    MAX-ACCESS read-only
    STATUS current
    DESCRIPTION "Temperature at the monitoring point.
		
		
		"
::= { subcardEntry 7 }
port OBJECT IDENTIFIER ::= { equipment 6 }
portTable OBJECT-TYPE
    SYNTAX SEQUENCE OF PortEntry
    MAX-ACCESS not-accessible
    STATUS current
    DESCRIPTION "NULL"
::= { port 1 }
portEntry OBJECT-TYPE
    SYNTAX PortEntry
    MAX-ACCESS not-accessible
    STATUS current
    DESCRIPTION "Entry of portTable" 
    INDEX { shelfId,slotId,subslotId,portId }
::= { portTable 1 }
PortEntry ::= 
SEQUENCE {
	portId CoriantTypesPortId,
	portPossiblePluggableTypes OCTET STRING,
	portActualPluggableType CoriantTypesEquipmentType,
	portRxOpticalPower CoriantTypesOpticalPower,
	portTxOpticalPower CoriantTypesOpticalPower,
	portRxOpticalPowerSelectedChannel CoriantTypesOpticalPower,
	portRxOpticalPowerLane1 CoriantTypesOpticalPower,
	portRxOpticalPowerLane2 CoriantTypesOpticalPower,
	portRxOpticalPowerLane3 CoriantTypesOpticalPower,
	portRxOpticalPowerLane4 CoriantTypesOpticalPower,
	portTxOpticalPowerLane1 CoriantTypesOpticalPower,
	portTxOpticalPowerLane2 CoriantTypesOpticalPower,
	portTxOpticalPowerLane3 CoriantTypesOpticalPower,
	portTxOpticalPowerLane4 CoriantTypesOpticalPower,
	portDirectionType CoriantTypesTypeOfDirection,
	portName CoriantTypesNameIdentifier,
	portType INTEGER,
	portMode CoriantTypesPortMode,
	portAdminStatus INTEGER,
	portOperStatus INTEGER,
	portAvailStatus BITS,
	portAliasName OCTET STRING,
	portServiceLabel OCTET STRING,
	portConnectedTo OCTET STRING,
	portArcConfig INTEGER,
	portArcState INTEGER,
	portArcSubState INTEGER,
	portArcTimer Unsigned32,
	portArcRemainingTime OCTET STRING,
	portExternalConnectivity CoriantTypesYesNo
    }
portId OBJECT-TYPE
    SYNTAX CoriantTypesPortId 
    MAX-ACCESS read-only
    STATUS current
    DESCRIPTION "The identifier is defined to uniquely identify the port.
		
		
		"
::= { portEntry 1 }
portPossiblePluggableTypes OBJECT-TYPE
    SYNTAX OCTET STRING 
    MAX-ACCESS read-only
    STATUS current
    DESCRIPTION "
	Defined all the pluggable types which can be equipped on the port. 
	Needs to be re-defined in the project specific model.
	This is a leaf list, encode by some leafs.
		Conditions:(../port-type != 'optical') and (../port-type != 'otdr') and (../port-type != 'optical-nomon')
		
		"
::= { portEntry 2 }
portActualPluggableType OBJECT-TYPE
    SYNTAX CoriantTypesEquipmentType 
    MAX-ACCESS read-only
    STATUS current
    DESCRIPTION "
	Pluggable type for each port according to the actually equipping. 
	Needs to be re-defined in the project specific model.
	
		Conditions:../port-type != 'optical'
		
		default value :empty"
::= { portEntry 3 }
portRxOpticalPower OBJECT-TYPE
    SYNTAX CoriantTypesOpticalPower 
    MAX-ACCESS read-only
    STATUS current
    DESCRIPTION "Received optical power
		
		
		"
::= { portEntry 4 }
portTxOpticalPower OBJECT-TYPE
    SYNTAX CoriantTypesOpticalPower 
    MAX-ACCESS read-only
    STATUS current
    DESCRIPTION "Transmitted optical power
		
		
		"
::= { portEntry 5 }
portRxOpticalPowerSelectedChannel OBJECT-TYPE
    SYNTAX CoriantTypesOpticalPower 
    MAX-ACCESS read-only
    STATUS current
    DESCRIPTION "Optical power of the selected channel on coherent receiver, 
	which will be different from the rx-optical-power when multiple channels input simultaneously.
		
		
		"
::= { portEntry 6 }
portRxOpticalPowerLane1 OBJECT-TYPE
    SYNTAX CoriantTypesOpticalPower 
    MAX-ACCESS read-only
    STATUS current
    DESCRIPTION "Received optical power of lane 1.
		
		
		"
::= { portEntry 7 }
portRxOpticalPowerLane2 OBJECT-TYPE
    SYNTAX CoriantTypesOpticalPower 
    MAX-ACCESS read-only
    STATUS current
    DESCRIPTION "Received optical power of lane 2.
		
		
		"
::= { portEntry 8 }
portRxOpticalPowerLane3 OBJECT-TYPE
    SYNTAX CoriantTypesOpticalPower 
    MAX-ACCESS read-only
    STATUS current
    DESCRIPTION "Received optical power of lane 3.
		
		
		"
::= { portEntry 9 }
portRxOpticalPowerLane4 OBJECT-TYPE
    SYNTAX CoriantTypesOpticalPower 
    MAX-ACCESS read-only
    STATUS current
    DESCRIPTION "Received optical power of lane 4.
		
		
		"
::= { portEntry 10 }
portTxOpticalPowerLane1 OBJECT-TYPE
    SYNTAX CoriantTypesOpticalPower 
    MAX-ACCESS read-only
    STATUS current
    DESCRIPTION "Transmitted optical power lane 1.
		
		
		"
::= { portEntry 11 }
portTxOpticalPowerLane2 OBJECT-TYPE
    SYNTAX CoriantTypesOpticalPower 
    MAX-ACCESS read-only
    STATUS current
    DESCRIPTION "Transmitted optical power lane 2.
		
		
		"
::= { portEntry 12 }
portTxOpticalPowerLane3 OBJECT-TYPE
    SYNTAX CoriantTypesOpticalPower 
    MAX-ACCESS read-only
    STATUS current
    DESCRIPTION "Transmitted optical power lane 3.
		
		
		"
::= { portEntry 13 }
portTxOpticalPowerLane4 OBJECT-TYPE
    SYNTAX CoriantTypesOpticalPower 
    MAX-ACCESS read-only
    STATUS current
    DESCRIPTION "Transmitted optical power lane 4.
		
		
		"
::= { portEntry 14 }
portDirectionType OBJECT-TYPE
    SYNTAX CoriantTypesTypeOfDirection 
    MAX-ACCESS read-only
    STATUS current
    DESCRIPTION "Supported direction of the optical port.
		
		
		"
::= { portEntry 15 }
portName OBJECT-TYPE
    SYNTAX CoriantTypesNameIdentifier 
    MAX-ACCESS read-only
    STATUS current
    DESCRIPTION "The name of the port.
		
		
		default value :unspecified"
::= { portEntry 16 }
portType OBJECT-TYPE
    SYNTAX INTEGER  {
	 client (1),
	 line (2),
	 clientSubport (3),
	 optical (4),
	 otdr (5),
	 opticalNomon (6)
	}
    MAX-ACCESS read-only
    STATUS current
    DESCRIPTION "The type of port. Needs to be provided upon Port creation
		
		
		"
::= { portEntry 17 }
portMode OBJECT-TYPE
    SYNTAX CoriantTypesPortMode 
    MAX-ACCESS read-only
    STATUS current
    DESCRIPTION "
	The working mode of port. 
	For client side:
	CHM1: applicable to port 3 to 6; possible values are: 100GBE, not-applicable.
	Default is 100GBE when card created.
	
	CHM2: applicable to port 3 to 11; possible values are: 40GBE, subport, not-applicable;
	applicable to subport 1 to 4; possible values are: 10GBE, not-applicable.
	Default is not-applicable.
						
	For Line side:
	CHM1/CHM2: possible values are: QPSK_100G, 16QAM_200G, 8QAM_300G.
	Default is 16QAM_200G.
	
	non applicable : there shall not be service created on the port or subport
	subport: the port shall create four subports under the port to support 4x10G.
	40GBE: 40GBE service shall be created on the port with default mapping GMP.
	10GBE: 10GBE service shall be created on the subport with default mapping BMP with fixed stuff.
	100GBE: 100GBE service shall be created on the subport with default mapping GMP.
	QPSK_100G: 100G OTU4 service with DP-QPSK coherent modulation format shall be created on the port.
	16QAM_200G: 200G OTUC2 service with DP-16QAM coherent modulation format shall be created on the port.
	8QAM_300G: 300G OTUC3 service with DP-8QAM coherent modulation format shall be created on the coupled two line ports.
	
	Note 4x10G is to create subport managed objects under the port. Each subport can support a 10G service.
						
	Restrictions:
	Changing Port mode shall be allowed only if the impacted port or subport object is administratively down.
	Changing a 'subport' port mode of a port to be other value shall only be allowed only if port-modes of all the subports under the port are 'not-applicable'.
	If there is explicitly cross-connection is created associated with the ODU of the port, change port mode of the port shall be denied.
	If the port mode is a coupled port mode, e.g. 8QAM_300G, port mode can only be edited on the lower number of port within the coupled ports. The other port (or ports if more than two) will have read-only port mode value same as this lowest number port.
	When port/subport is set to admin down, laser will be shutdown, ingress side will insert proper maintenance signal.
	
		Conditions:(../port-type != 'optical') and (../port-type != 'otdr') and (../port-type != 'optical-nomon')
		
		default value :not-applicable"
::= { portEntry 18 }
portAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { portEntry 19 }
portOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { portEntry 20 }
portAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { portEntry 21 }
portAliasName OBJECT-TYPE
    SYNTAX OCTET STRING  (SIZE (0..256))
    MAX-ACCESS read-only
    STATUS current
    DESCRIPTION "User defined alias for this entity. Must be an alphanumeric string with dash or underscore
		
		
		"
::= { portEntry 22 }
portServiceLabel OBJECT-TYPE
    SYNTAX OCTET STRING  (SIZE (0..128))
    MAX-ACCESS read-only
    STATUS current
    DESCRIPTION "Path/service name of cross-connection related facility.
		
		
		"
::= { portEntry 23 }
portConnectedTo OBJECT-TYPE
    SYNTAX OCTET STRING  (SIZE (0..128))
    MAX-ACCESS read-only
    STATUS current
    DESCRIPTION "Indicate neighbour port/facility entity to which the current port/facility is connected to.
		
		
		"
::= { portEntry 24 }
portArcConfig OBJECT-TYPE
    SYNTAX INTEGER  {
	 alm (1),
	 nalmQi (2),
	 nalm (3)
	}
    MAX-ACCESS read-only
    STATUS current
    DESCRIPTION "
	The configurable mode of the Alarm Report Control (ARC).
	
		
		
		default value :nalm-qi"
::= { portEntry 25 }
portArcState OBJECT-TYPE
    SYNTAX INTEGER  {
	 alm (1),
	 nalmQi (2),
	 nalm (3)
	}
    MAX-ACCESS read-only
    STATUS current
    DESCRIPTION "
	The current mode of the Alarm Report Control (ARC).
	
		
		
		"
::= { portEntry 26 }
portArcSubState OBJECT-TYPE
    SYNTAX INTEGER  {
	 notApplicable (0),
	 nalmCd (1),
	 nalmNr (2)
	}
    MAX-ACCESS read-only
    STATUS current
    DESCRIPTION "
	Additional information about the Alarm Report Control (ARC) when the main state is in the NALM-QI state 
	
		
		
		default value :nalm-nr"
::= { portEntry 27 }
portArcTimer OBJECT-TYPE
    SYNTAX Unsigned32  (0..10080)
    MAX-ACCESS read-only
    STATUS current
    DESCRIPTION "The holdoff timer value in minutes of the ARC.
	 Range is 0 - 10080 minutes 
		
		UNITS:minutes
		default value :1440"
::= { portEntry 28 }
portArcRemainingTime OBJECT-TYPE
    SYNTAX OCTET STRING 
    MAX-ACCESS read-only
    STATUS current
    DESCRIPTION "
	The remaining timer value (format: xxd-xxh:xxm:xxs) before the alarm is reported.
	
		
		
		"
::= { portEntry 29 }
portExternalConnectivity OBJECT-TYPE
    SYNTAX CoriantTypesYesNo 
    MAX-ACCESS read-only
    STATUS current
    DESCRIPTION "Indicates the port is connected externally or not.
		
		
		default value :no"
::= { portEntry 30 }
subport OBJECT IDENTIFIER ::= { equipment 7 }
subportTable OBJECT-TYPE
    SYNTAX SEQUENCE OF SubportEntry
    MAX-ACCESS not-accessible
    STATUS current
    DESCRIPTION "NULL"
::= { subport 1 }
subportEntry OBJECT-TYPE
    SYNTAX SubportEntry
    MAX-ACCESS not-accessible
    STATUS current
    DESCRIPTION "Entry of subportTable" 
    INDEX { shelfId,slotId,subslotId,portId,subportId }
::= { subportTable 1 }
SubportEntry ::= 
SEQUENCE {
	subportId CoriantTypesPortId,
	subportPortName CoriantTypesNameIdentifier,
	subportPortType INTEGER,
	subportPortMode CoriantTypesPortMode,
	subportAdminStatus INTEGER,
	subportOperStatus INTEGER,
	subportAvailStatus BITS,
	subportAliasName OCTET STRING,
	subportServiceLabel OCTET STRING,
	subportConnectedTo OCTET STRING,
	subportArcConfig INTEGER,
	subportArcState INTEGER,
	subportArcSubState INTEGER,
	subportArcTimer Unsigned32,
	subportArcRemainingTime OCTET STRING,
	subportRxOpticalPower CoriantTypesOpticalPower,
	subportTxOpticalPower CoriantTypesOpticalPower,
	subportExternalConnectivity CoriantTypesYesNo
    }
subportId OBJECT-TYPE
    SYNTAX CoriantTypesPortId 
    MAX-ACCESS read-only
    STATUS current
    DESCRIPTION "The identifier is defined to uniquely identify the subport.
		
		
		"
::= { subportEntry 1 }
subportPortName OBJECT-TYPE
    SYNTAX CoriantTypesNameIdentifier 
    MAX-ACCESS read-only
    STATUS current
    DESCRIPTION "The name of the port.
		
		
		default value :unspecified"
::= { subportEntry 2 }
subportPortType OBJECT-TYPE
    SYNTAX INTEGER  {
	 client (1),
	 line (2),
	 clientSubport (3),
	 optical (4),
	 otdr (5),
	 opticalNomon (6)
	}
    MAX-ACCESS read-only
    STATUS current
    DESCRIPTION "The type of port. Needs to be provided upon Port creation
		
		
		"
::= { subportEntry 3 }
subportPortMode OBJECT-TYPE
    SYNTAX CoriantTypesPortMode 
    MAX-ACCESS read-only
    STATUS current
    DESCRIPTION "
	The working mode of port. 
	For client side:
	CHM1: applicable to port 3 to 6; possible values are: 100GBE, not-applicable.
	Default is 100GBE when card created.
	
	CHM2: applicable to port 3 to 11; possible values are: 40GBE, subport, not-applicable;
	applicable to subport 1 to 4; possible values are: 10GBE, not-applicable.
	Default is not-applicable.
						
	For Line side:
	CHM1/CHM2: possible values are: QPSK_100G, 16QAM_200G, 8QAM_300G.
	Default is 16QAM_200G.
	
	non applicable : there shall not be service created on the port or subport
	subport: the port shall create four subports under the port to support 4x10G.
	40GBE: 40GBE service shall be created on the port with default mapping GMP.
	10GBE: 10GBE service shall be created on the subport with default mapping BMP with fixed stuff.
	100GBE: 100GBE service shall be created on the subport with default mapping GMP.
	QPSK_100G: 100G OTU4 service with DP-QPSK coherent modulation format shall be created on the port.
	16QAM_200G: 200G OTUC2 service with DP-16QAM coherent modulation format shall be created on the port.
	8QAM_300G: 300G OTUC3 service with DP-8QAM coherent modulation format shall be created on the coupled two line ports.
	
	Note 4x10G is to create subport managed objects under the port. Each subport can support a 10G service.
						
	Restrictions:
	Changing Port mode shall be allowed only if the impacted port or subport object is administratively down.
	Changing a 'subport' port mode of a port to be other value shall only be allowed only if port-modes of all the subports under the port are 'not-applicable'.
	If there is explicitly cross-connection is created associated with the ODU of the port, change port mode of the port shall be denied.
	If the port mode is a coupled port mode, e.g. 8QAM_300G, port mode can only be edited on the lower number of port within the coupled ports. The other port (or ports if more than two) will have read-only port mode value same as this lowest number port.
	When port/subport is set to admin down, laser will be shutdown, ingress side will insert proper maintenance signal.
	
		Conditions:(../port-type != 'optical') and (../port-type != 'otdr') and (../port-type != 'optical-nomon')
		
		default value :not-applicable"
::= { subportEntry 4 }
subportAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { subportEntry 5 }
subportOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { subportEntry 6 }
subportAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { subportEntry 7 }
subportAliasName OBJECT-TYPE
    SYNTAX OCTET STRING  (SIZE (0..256))
    MAX-ACCESS read-only
    STATUS current
    DESCRIPTION "User defined alias for this entity. Must be an alphanumeric string with dash or underscore
		
		
		"
::= { subportEntry 8 }
subportServiceLabel OBJECT-TYPE
    SYNTAX OCTET STRING  (SIZE (0..128))
    MAX-ACCESS read-only
    STATUS current
    DESCRIPTION "Path/service name of cross-connection related facility.
		
		
		"
::= { subportEntry 9 }
subportConnectedTo OBJECT-TYPE
    SYNTAX OCTET STRING  (SIZE (0..128))
    MAX-ACCESS read-only
    STATUS current
    DESCRIPTION "Indicate neighbour port/facility entity to which the current port/facility is connected to.
		
		
		"
::= { subportEntry 10 }
subportArcConfig OBJECT-TYPE
    SYNTAX INTEGER  {
	 alm (1),
	 nalmQi (2),
	 nalm (3)
	}
    MAX-ACCESS read-only
    STATUS current
    DESCRIPTION "
	The configurable mode of the Alarm Report Control (ARC).
	
		
		
		default value :nalm-qi"
::= { subportEntry 11 }
subportArcState OBJECT-TYPE
    SYNTAX INTEGER  {
	 alm (1),
	 nalmQi (2),
	 nalm (3)
	}
    MAX-ACCESS read-only
    STATUS current
    DESCRIPTION "
	The current mode of the Alarm Report Control (ARC).
	
		
		
		"
::= { subportEntry 12 }
subportArcSubState OBJECT-TYPE
    SYNTAX INTEGER  {
	 notApplicable (0),
	 nalmCd (1),
	 nalmNr (2)
	}
    MAX-ACCESS read-only
    STATUS current
    DESCRIPTION "
	Additional information about the Alarm Report Control (ARC) when the main state is in the NALM-QI state 
	
		
		
		default value :nalm-nr"
::= { subportEntry 13 }
subportArcTimer OBJECT-TYPE
    SYNTAX Unsigned32  (0..10080)
    MAX-ACCESS read-only
    STATUS current
    DESCRIPTION "The holdoff timer value in minutes of the ARC.
	 Range is 0 - 10080 minutes 
		
		UNITS:minutes
		default value :1440"
::= { subportEntry 14 }
subportArcRemainingTime OBJECT-TYPE
    SYNTAX OCTET STRING 
    MAX-ACCESS read-only
    STATUS current
    DESCRIPTION "
	The remaining timer value (format: xxd-xxh:xxm:xxs) before the alarm is reported.
	
		
		
		"
::= { subportEntry 15 }
subportRxOpticalPower OBJECT-TYPE
    SYNTAX CoriantTypesOpticalPower 
    MAX-ACCESS read-only
    STATUS current
    DESCRIPTION "Received optical power
		
		
		"
::= { subportEntry 16 }
subportTxOpticalPower OBJECT-TYPE
    SYNTAX CoriantTypesOpticalPower 
    MAX-ACCESS read-only
    STATUS current
    DESCRIPTION "Transmitted optical power
		
		
		"
::= { subportEntry 17 }
subportExternalConnectivity OBJECT-TYPE
    SYNTAX CoriantTypesYesNo 
    MAX-ACCESS read-only
    STATUS current
    DESCRIPTION "Indicates the port is connected externally or not.
		
		
		default value :no"
::= { subportEntry 18 }
pluggable OBJECT IDENTIFIER ::= { equipment 8 }
pluggableTable OBJECT-TYPE
    SYNTAX SEQUENCE OF PluggableEntry
    MAX-ACCESS not-accessible
    STATUS current
    DESCRIPTION "Represents the Pluggable object"
::= { pluggable 1 }
pluggableEntry OBJECT-TYPE
    SYNTAX PluggableEntry
    MAX-ACCESS not-accessible
    STATUS current
    DESCRIPTION "Entry of pluggableTable" 
    INDEX { shelfId,slotId,subslotId,portId }
::= { pluggableTable 1 }
PluggableEntry ::= 
SEQUENCE {
	pluggableRequiredType CoriantTypesPluggableType,
	pluggableFormFactor CoriantTypesPluggableFormFactor,
	pluggableInterfaceType OCTET STRING,
	pluggableLaserSource INTEGER,
	pluggableHwVersion OCTET STRING,
	pluggableVendor OCTET STRING,
	pluggableSerialNumber OCTET STRING,
	pluggableFwVersion OCTET STRING,
	pluggablePartNumber OCTET STRING,
	pluggableClei OCTET STRING,
	pluggableEquipmentName OCTET STRING,
	pluggableAdminStatus INTEGER,
	pluggableOperStatus INTEGER,
	pluggableAvailStatus BITS,
	pluggableAliasName OCTET STRING,
	pluggableTemperature CoriantTypesTemperature
    }
pluggableRequiredType OBJECT-TYPE
    SYNTAX CoriantTypesPluggableType 
    MAX-ACCESS read-only
    STATUS current
    DESCRIPTION "
	The attribute indicates the equipment type to identify the module. 
	Needs to be re-defined in the project specific model.
	
		
		
		"
::= { pluggableEntry 1 }
pluggableFormFactor OBJECT-TYPE
    SYNTAX CoriantTypesPluggableFormFactor 
    MAX-ACCESS read-only
    STATUS current
    DESCRIPTION "Indicating the exact form factor of the pluggable.
		
		
		default value :Unrecognized"
::= { pluggableEntry 2 }
pluggableInterfaceType OBJECT-TYPE
    SYNTAX OCTET STRING  (SIZE (0..64))
    MAX-ACCESS read-only
    STATUS current
    DESCRIPTION "Indicating interface type of the pluggable.
		
		
		default value :"
::= { pluggableEntry 3 }
pluggableLaserSource OBJECT-TYPE
    SYNTAX INTEGER  {
	 txLoShared (1),
	 txLoIndependent (2),
	 notAvailable (3)
	}
    MAX-ACCESS read-only
    STATUS current
    DESCRIPTION "
	The type of laser frequency. Only tx-lo-independent type support och-os rx-frequency working
	
		Conditions:../required-type = 'CFP2'
		
		default value :not-available"
::= { pluggableEntry 4 }
pluggableHwVersion OBJECT-TYPE
    SYNTAX OCTET STRING  (SIZE (0..20))
    MAX-ACCESS read-only
    STATUS current
    DESCRIPTION "
	The attribute Identifies the Hardware Version of the module that populates the slot. 
	
		
		
		"
::= { pluggableEntry 5 }
pluggableVendor OBJECT-TYPE
    SYNTAX OCTET STRING  (SIZE (0..64))
    MAX-ACCESS read-only
    STATUS current
    DESCRIPTION "
	Vendor information. 
	
		
		
		"
::= { pluggableEntry 6 }
pluggableSerialNumber OBJECT-TYPE
    SYNTAX OCTET STRING  (SIZE (0..18))
    MAX-ACCESS read-only
    STATUS current
    DESCRIPTION "
	This is the value of serial number stored in EEPROM of the equipment. 
	
		
		
		"
::= { pluggableEntry 7 }
pluggableFwVersion OBJECT-TYPE
    SYNTAX OCTET STRING  (SIZE (0..20))
    MAX-ACCESS read-only
    STATUS current
    DESCRIPTION "
	Current Firmware (FW) version on the equipment. 
	
		
		
		"
::= { pluggableEntry 8 }
pluggablePartNumber OBJECT-TYPE
    SYNTAX OCTET STRING  (SIZE (0..18))
    MAX-ACCESS read-only
    STATUS current
    DESCRIPTION "
	Identifies the Part Number of the equipment. 
	
		
		
		"
::= { pluggableEntry 9 }
pluggableClei OBJECT-TYPE
    SYNTAX OCTET STRING  (SIZE (0..18))
    MAX-ACCESS read-only
    STATUS current
    DESCRIPTION "
	Identifies the CLEI code number of the equipment. 
	The CLEI code is a 10-character code that identifies
	communications equipment. It describes product type, features,
	source document, and associated drawings and vintages.
	
		
		
		"
::= { pluggableEntry 10 }
pluggableEquipmentName OBJECT-TYPE
    SYNTAX OCTET STRING  (SIZE (0..64))
    MAX-ACCESS read-only
    STATUS current
    DESCRIPTION "
	The attribute indicates an additional field to identify the module. 
	
		
		
		"
::= { pluggableEntry 11 }
pluggableAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { pluggableEntry 12 }
pluggableOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { pluggableEntry 13 }
pluggableAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		default value :unknown"
::= { pluggableEntry 14 }
pluggableAliasName OBJECT-TYPE
    SYNTAX OCTET STRING  (SIZE (0..256))
    MAX-ACCESS read-only
    STATUS current
    DESCRIPTION "User defined alias for this entity. Must be an alphanumeric string with dash or underscore
		
		
		"
::= { pluggableEntry 15 }
pluggableTemperature OBJECT-TYPE
    SYNTAX CoriantTypesTemperature 
    MAX-ACCESS read-only
    STATUS current
    DESCRIPTION "Temperature at the monitoring point.
		
		
		"
::= { pluggableEntry 16 }
amplifier OBJECT IDENTIFIER ::= { equipment 9 }
amplifierTable OBJECT-TYPE
    SYNTAX SEQUENCE OF AmplifierEntry
    MAX-ACCESS not-accessible
    STATUS current
    DESCRIPTION "The list of optical amplifier on an equipment."
::= { amplifier 1 }
amplifierEntry OBJECT-TYPE
    SYNTAX AmplifierEntry
    MAX-ACCESS not-accessible
    STATUS current
    DESCRIPTION "Entry of amplifierTable" 
    INDEX { shelfId,slotId,subslotId,amplifierName }
::= { amplifierTable 1 }
AmplifierEntry ::= 
SEQUENCE {
	amplifierName CoriantTypesNameIdentifier,
	amplifierSupportingInputPort RowPointer,
	amplifierSupportingOutputPort RowPointer,
	amplifierAdminStatus INTEGER,
	amplifierOperStatus INTEGER,
	amplifierAvailStatus BITS,
	amplifierAliasName OCTET STRING,
	amplifierEnable CoriantTypesEnableSwitch,
	amplifierInputLosShutdown CoriantTypesEnableSwitch,
	amplifierControlMode INTEGER,
	amplifierMode INTEGER,
	amplifierType INTEGER,
	amplifierTargetGain CoriantTypesOpticalDB,
	amplifierOperatingGain CoriantTypesOpticalDB,
	amplifierGainAdjustment CoriantTypesOpticalDB,
	amplifierGainRangeMin CoriantTypesOpticalDB,
	amplifierGainRangeMax CoriantTypesOpticalPower,
	amplifierOutputPowerMon CoriantTypesOpticalPower,
	amplifierOutputPowerMonWithAse CoriantTypesOpticalPower,
	amplifierInputPowerMon CoriantTypesOpticalPower,
	amplifierOutputVoa CoriantTypesOpticalDB,
	amplifierPowerBeforeOutputVoa CoriantTypesOpticalPower
    }
amplifierName OBJECT-TYPE
    SYNTAX CoriantTypesNameIdentifier 
    MAX-ACCESS read-only
    STATUS current
    DESCRIPTION "User-defined name assigned to identify a specific amplifier in the device
		
		
		"
::= { amplifierEntry 1 }
amplifierSupportingInputPort OBJECT-TYPE
    SYNTAX RowPointer 
    MAX-ACCESS read-only
    STATUS current
    DESCRIPTION "Identifier of the supporting input port.
		
		
		"
::= { amplifierEntry 2 }
amplifierSupportingOutputPort OBJECT-TYPE
    SYNTAX RowPointer 
    MAX-ACCESS read-only
    STATUS current
    DESCRIPTION "Identifier of the supporting output port.
		
		
		"
::= { amplifierEntry 3 }
amplifierAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { amplifierEntry 4 }
amplifierOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { amplifierEntry 5 }
amplifierAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { amplifierEntry 6 }
amplifierAliasName OBJECT-TYPE
    SYNTAX OCTET STRING  (SIZE (0..256))
    MAX-ACCESS read-only
    STATUS current
    DESCRIPTION "User defined alias for this entity. Must be an alphanumeric string with dash or underscore
		
		
		"
::= { amplifierEntry 7 }
amplifierEnable OBJECT-TYPE
    SYNTAX CoriantTypesEnableSwitch 
    MAX-ACCESS read-only
    STATUS current
    DESCRIPTION "Configuration for enable or disable the amplifier.
		
		
		default value :disabled"
::= { amplifierEntry 8 }
amplifierInputLosShutdown OBJECT-TYPE
    SYNTAX CoriantTypesEnableSwitch 
    MAX-ACCESS read-only
    STATUS current
    DESCRIPTION "Enable or disable the function of automatic shutdown per input LOS.
		
		
		default value :enabled"
::= { amplifierEntry 9 }
amplifierControlMode OBJECT-TYPE
    SYNTAX INTEGER  {
	 manual (1),
	 auto (2)
	}
    MAX-ACCESS read-only
    STATUS current
    DESCRIPTION "Control mode of the amplifier.
		
		
		default value :auto"
::= { amplifierEntry 10 }
amplifierMode OBJECT-TYPE
    SYNTAX INTEGER  {
	 constantPower (1),
	 constantGain (2)
	}
    MAX-ACCESS read-only
    STATUS current
    DESCRIPTION "The operating mode of the amplifier
		
		
		default value :constant-gain"
::= { amplifierEntry 11 }
amplifierType OBJECT-TYPE
    SYNTAX INTEGER  {
	 fixedGainEdfa (1),
	 variableGainEdfa (2)
	}
    MAX-ACCESS read-only
    STATUS current
    DESCRIPTION "Type of the amplifier.
		
		
		default value :variable-gain-EDFA"
::= { amplifierEntry 12 }
amplifierTargetGain OBJECT-TYPE
    SYNTAX CoriantTypesOpticalDB 
    MAX-ACCESS read-only
    STATUS current
    DESCRIPTION "Setting gain to the amplifier for constant-gain mode in manual control mode.
		
		
		"
::= { amplifierEntry 13 }
amplifierOperatingGain OBJECT-TYPE
    SYNTAX CoriantTypesOpticalDB 
    MAX-ACCESS read-only
    STATUS current
    DESCRIPTION "Operating gain of the amplifier, which is the actually configured gain on the amplifier.
		
		
		"
::= { amplifierEntry 14 }
amplifierGainAdjustment OBJECT-TYPE
    SYNTAX CoriantTypesOpticalDB 
    MAX-ACCESS read-only
    STATUS current
    DESCRIPTION "The value is used for adjustment of gain when the amplifier in automatic control mode, 
	  the automatically caculated gain will include offset of this attribute.
		
		
		default value :0.0"
::= { amplifierEntry 15 }
amplifierGainRangeMin OBJECT-TYPE
    SYNTAX CoriantTypesOpticalDB 
    MAX-ACCESS read-only
    STATUS current
    DESCRIPTION "The minimum of settable gain.
		
		
		"
::= { amplifierEntry 16 }
amplifierGainRangeMax OBJECT-TYPE
    SYNTAX CoriantTypesOpticalPower 
    MAX-ACCESS read-only
    STATUS current
    DESCRIPTION "The maximum of settable gain.
		
		UNITS:dB
		"
::= { amplifierEntry 17 }
amplifierOutputPowerMon OBJECT-TYPE
    SYNTAX CoriantTypesOpticalPower 
    MAX-ACCESS read-only
    STATUS current
    DESCRIPTION "Monitored aggregation signal output power.
		
		UNITS:dBm
		"
::= { amplifierEntry 18 }
amplifierOutputPowerMonWithAse OBJECT-TYPE
    SYNTAX CoriantTypesOpticalPower 
    MAX-ACCESS read-only
    STATUS current
    DESCRIPTION "Monitored aggregation total output power including both signal and ASE.
		
		UNITS:dBm
		"
::= { amplifierEntry 19 }
amplifierInputPowerMon OBJECT-TYPE
    SYNTAX CoriantTypesOpticalPower 
    MAX-ACCESS read-only
    STATUS current
    DESCRIPTION "Monitored aggregation input power.
		
		UNITS:dBm
		"
::= { amplifierEntry 20 }
amplifierOutputVoa OBJECT-TYPE
    SYNTAX CoriantTypesOpticalDB 
    MAX-ACCESS read-only
    STATUS current
    DESCRIPTION "Configurable optical attenuation at output of the amplifier.
		
		
		default value :0.0"
::= { amplifierEntry 21 }
amplifierPowerBeforeOutputVoa OBJECT-TYPE
    SYNTAX CoriantTypesOpticalPower 
    MAX-ACCESS read-only
    STATUS current
    DESCRIPTION "Monitored optical power after output VOA.
		
		UNITS:dBm
		"
::= { amplifierEntry 22 }
tdc OBJECT IDENTIFIER ::= { equipment 10 }
tdcTable OBJECT-TYPE
    SYNTAX SEQUENCE OF TdcEntry
    MAX-ACCESS not-accessible
    STATUS current
    DESCRIPTION "The list of optical tdc on an equipment."
::= { tdc 1 }
tdcEntry OBJECT-TYPE
    SYNTAX TdcEntry
    MAX-ACCESS not-accessible
    STATUS current
    DESCRIPTION "Entry of tdcTable" 
    INDEX { shelfId,slotId,subslotId,tdcName }
::= { tdcTable 1 }
TdcEntry ::= 
SEQUENCE {
	tdcName CoriantTypesNameIdentifier,
	tdcSupportingInputPort RowPointer,
	tdcSupportingOutputPort RowPointer,
	tdcAdminStatus INTEGER,
	tdcOperStatus INTEGER,
	tdcAvailStatus BITS,
	tdcAliasName OCTET STRING,
	tdcMode INTEGER,
	tdcReferenceFrequency CoriantTypesFreq,
	tdcActualReferenceFrequency Unsigned32,
	tdcFrequencyRangeMin Unsigned32,
	tdcFrequencyRangeMax Unsigned32,
	tdcChromaticDispersion INTEGER,
	tdcChromaticDispersionAdjustment INTEGER,
	tdcActualChromaticDispersion INTEGER,
	tdcCdRangeMin INTEGER,
	tdcCdRangeMax INTEGER
    }
tdcName OBJECT-TYPE
    SYNTAX CoriantTypesNameIdentifier 
    MAX-ACCESS read-only
    STATUS current
    DESCRIPTION "User-defined name assigned to identify a specific tdc in the device
		
		
		"
::= { tdcEntry 1 }
tdcSupportingInputPort OBJECT-TYPE
    SYNTAX RowPointer 
    MAX-ACCESS read-only
    STATUS current
    DESCRIPTION "Identifier of the supporting input port.
		
		
		"
::= { tdcEntry 2 }
tdcSupportingOutputPort OBJECT-TYPE
    SYNTAX RowPointer 
    MAX-ACCESS read-only
    STATUS current
    DESCRIPTION "Identifier of the supporting output port.
		
		
		"
::= { tdcEntry 3 }
tdcAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { tdcEntry 4 }
tdcOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { tdcEntry 5 }
tdcAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { tdcEntry 6 }
tdcAliasName OBJECT-TYPE
    SYNTAX OCTET STRING  (SIZE (0..256))
    MAX-ACCESS read-only
    STATUS current
    DESCRIPTION "User defined alias for this entity. Must be an alphanumeric string with dash or underscore
		
		
		"
::= { tdcEntry 7 }
tdcMode OBJECT-TYPE
    SYNTAX INTEGER  {
	 manual (1),
	 auto (2)
	}
    MAX-ACCESS read-only
    STATUS current
    DESCRIPTION "Control mode of the tunable dispersion compensation; Manual: CD value will be decided per configured CD value; 
	Auto: system will automatically decide the CD value per measured chromatic dispersion in the span.                    
	
		
		
		default value :auto"
::= { tdcEntry 8 }
tdcReferenceFrequency OBJECT-TYPE
    SYNTAX CoriantTypesFreq 
    MAX-ACCESS read-only
    STATUS current
    DESCRIPTION " Indicating the reference wavelength of the TDC.
		
		UNITS:MHz
		"
::= { tdcEntry 9 }
tdcActualReferenceFrequency OBJECT-TYPE
    SYNTAX Unsigned32 
    MAX-ACCESS read-only
    STATUS current
    DESCRIPTION " Indicating the actual reference wavelength of the TDC.
		
		UNITS:MHz
		"
::= { tdcEntry 10 }
tdcFrequencyRangeMin OBJECT-TYPE
    SYNTAX Unsigned32 
    MAX-ACCESS read-only
    STATUS current
    DESCRIPTION "The minimum of supported wavelength.
		
		UNITS:MHz
		"
::= { tdcEntry 11 }
tdcFrequencyRangeMax OBJECT-TYPE
    SYNTAX Unsigned32 
    MAX-ACCESS read-only
    STATUS current
    DESCRIPTION "The maximum of supported wavelength.
		
		UNITS:MHz
		"
::= { tdcEntry 12 }
tdcChromaticDispersion OBJECT-TYPE
    SYNTAX INTEGER 
    MAX-ACCESS read-only
    STATUS current
    DESCRIPTION "The setting value of Chromatic Dispersion.
		
		UNITS:ps/nm
		default value :0"
::= { tdcEntry 13 }
tdcChromaticDispersionAdjustment OBJECT-TYPE
    SYNTAX INTEGER 
    MAX-ACCESS read-only
    STATUS current
    DESCRIPTION "The value will be used to adjust target chromatic dispersion by adding the value with auto decided dispersion in auto tdc mode.
		
		UNITS:ps/nm
		"
::= { tdcEntry 14 }
tdcActualChromaticDispersion OBJECT-TYPE
    SYNTAX INTEGER 
    MAX-ACCESS read-only
    STATUS current
    DESCRIPTION "The actual value of Chromatic Dispersion.
		
		UNITS:ps/nm
		"
::= { tdcEntry 15 }
tdcCdRangeMin OBJECT-TYPE
    SYNTAX INTEGER 
    MAX-ACCESS read-only
    STATUS current
    DESCRIPTION "The minimum of supported chromatic dispersion.
		
		UNITS:ps/nm
		"
::= { tdcEntry 16 }
tdcCdRangeMax OBJECT-TYPE
    SYNTAX INTEGER 
    MAX-ACCESS read-only
    STATUS current
    DESCRIPTION "The maximum of supported chromatic dispersion.
		
		UNITS:ps/nm
		"
::= { tdcEntry 17 }
inventory OBJECT IDENTIFIER ::= { equipment 12 }
inventoryTable OBJECT-TYPE
    SYNTAX SEQUENCE OF InventoryEntry
    MAX-ACCESS not-accessible
    STATUS current
    DESCRIPTION "NULL"
::= { inventory 1 }
inventoryEntry OBJECT-TYPE
    SYNTAX InventoryEntry
    MAX-ACCESS not-accessible
    STATUS current
    DESCRIPTION "Entry of inventoryTable" 
    INDEX { inventoryEquipmentType,inventoryShelfId,inventorySlotId,inventorySubslotId,inventoryPortId }
::= { inventoryTable 1 }
InventoryEntry ::= 
SEQUENCE {
	inventoryEquipmentType INTEGER,
	inventoryShelfId CoriantTypesShelfId,
	inventorySlotId CoriantTypesSlotId,
	inventorySubslotId CoriantTypesSlotId,
	inventoryPortId CoriantTypesPortId,
	inventoryEquipmentVersion OCTET STRING,
	inventoryModuleType OCTET STRING,
	inventoryVendor OCTET STRING,
	inventorySerialNumber OCTET STRING,
	inventoryFwVersion OCTET STRING,
	inventoryPartNumber OCTET STRING,
	inventoryClei OCTET STRING,
	inventoryInterfaceType OCTET STRING,
	inventoryManufactureDate OCTET STRING,
	inventoryManufacturerNumber OCTET STRING
    }
inventoryEquipmentType OBJECT-TYPE
    SYNTAX INTEGER  {
	 shelf (1),
	 slot (2),
	 card (3),
	 port (4),
	 pluggable (5),
	 subslot (6),
	 subcard (7)
	}
    MAX-ACCESS read-only
    STATUS current
    DESCRIPTION "The equipment type that the inventory data refers to
		
		
		"
::= { inventoryEntry 1 }
inventoryShelfId OBJECT-TYPE
    SYNTAX CoriantTypesShelfId 
    MAX-ACCESS read-only
    STATUS current
    DESCRIPTION "Identifier of the shelf.
		
		
		"
::= { inventoryEntry 2 }
inventorySlotId OBJECT-TYPE
    SYNTAX CoriantTypesSlotId 
    MAX-ACCESS read-only
    STATUS current
    DESCRIPTION "Identifier of the slot.
		
		
		"
::= { inventoryEntry 3 }
inventorySubslotId OBJECT-TYPE
    SYNTAX CoriantTypesSlotId 
    MAX-ACCESS read-only
    STATUS current
    DESCRIPTION "Identifier of the subslot.
		
		
		"
::= { inventoryEntry 4 }
inventoryPortId OBJECT-TYPE
    SYNTAX CoriantTypesPortId 
    MAX-ACCESS read-only
    STATUS current
    DESCRIPTION "Identifier of the port.
		
		
		"
::= { inventoryEntry 5 }
inventoryEquipmentVersion OBJECT-TYPE
    SYNTAX OCTET STRING  (SIZE (0..20))
    MAX-ACCESS read-only
    STATUS current
    DESCRIPTION "The attribute Identifies the Hardware Version of the module that populates the slot.
		
		
		"
::= { inventoryEntry 6 }
inventoryModuleType OBJECT-TYPE
    SYNTAX OCTET STRING  (SIZE (0..18))
    MAX-ACCESS read-only
    STATUS current
    DESCRIPTION "This is the value of module type stored in EEPROM of the equipment.
		
		
		"
::= { inventoryEntry 7 }
inventoryVendor OBJECT-TYPE
    SYNTAX OCTET STRING  (SIZE (0..64))
    MAX-ACCESS read-only
    STATUS current
    DESCRIPTION "Vendor information.
		
		
		"
::= { inventoryEntry 8 }
inventorySerialNumber OBJECT-TYPE
    SYNTAX OCTET STRING  (SIZE (0..20))
    MAX-ACCESS read-only
    STATUS current
    DESCRIPTION "This is the value of serial number stored in EEPROM of the equipment.
		
		
		"
::= { inventoryEntry 9 }
inventoryFwVersion OBJECT-TYPE
    SYNTAX OCTET STRING  (SIZE (0..20))
    MAX-ACCESS read-only
    STATUS current
    DESCRIPTION "Current Firmware (FW) version on the equipment.
		
		
		"
::= { inventoryEntry 10 }
inventoryPartNumber OBJECT-TYPE
    SYNTAX OCTET STRING  (SIZE (0..18))
    MAX-ACCESS read-only
    STATUS current
    DESCRIPTION "Identifies the Part Number of the equipment.
		
		
		"
::= { inventoryEntry 11 }
inventoryClei OBJECT-TYPE
    SYNTAX OCTET STRING  (SIZE (0..18))
    MAX-ACCESS read-only
    STATUS current
    DESCRIPTION "
	Identifies the CLEI code number of the equipment.
	The CLEI code is a 10-character code that identifies
	communications equipment. It describes product type, features,
	source document, and associated drawings and vintages.
	CLEI codes have 4 data elements:
	- Characters 1 to 4: Define family or subfamily of product.
	- Characters 5 to 7: Define features.
	- Character 8: Manufacturer and System ID.
	- Characters 9 and 10: Identifies version, issue, and release #.
	
		
		
		"
::= { inventoryEntry 12 }
inventoryInterfaceType OBJECT-TYPE
    SYNTAX OCTET STRING  (SIZE (0..64))
    MAX-ACCESS read-only
    STATUS current
    DESCRIPTION "Indicating interface type of the pluggable.
		
		
		default value :"
::= { inventoryEntry 13 }
inventoryManufactureDate OBJECT-TYPE
    SYNTAX OCTET STRING 
    MAX-ACCESS read-only
    STATUS current
    DESCRIPTION "The equipment manufacture date get from equipment. 
	format is mm/dd/yyyy. When there is no date information show nothing
		Conditions:(../equipment-type = 'shelf') or (../equipment-type = 'card') or (../equipment-type = 'subcard') or (../equipment-type = 'pluggable')
		
		default value :"
::= { inventoryEntry 14 }
inventoryManufacturerNumber OBJECT-TYPE
    SYNTAX OCTET STRING  (SIZE (0..18))
    MAX-ACCESS read-only
    STATUS current
    DESCRIPTION "This is the value of manufacturer number stored in EEPROM of the equipment.
		
		
		"
::= { inventoryEntry 16 }
led OBJECT IDENTIFIER ::= { equipment 14 }
ledTable OBJECT-TYPE
    SYNTAX SEQUENCE OF LedEntry
    MAX-ACCESS not-accessible
    STATUS current
    DESCRIPTION "
	Attributes related with LED
	Applicable to Shelf, FAN, PSU, CHM1, CHM2, CHM1G, OCC2 in DCI.
	"
::= { led 1 }
ledEntry OBJECT-TYPE
    SYNTAX LedEntry
    MAX-ACCESS not-accessible
    STATUS current
    DESCRIPTION "Entry of ledTable" 
    INDEX { ledEquipmentType,ledShelfId,ledSlotId,ledSubslotId,ledName }
::= { ledTable 1 }
LedEntry ::= 
SEQUENCE {
	ledEquipmentType OCTET STRING,
	ledShelfId CoriantTypesShelfId,
	ledSlotId CoriantTypesSlotId,
	ledName OCTET STRING,
	ledStatus INTEGER,
	ledSubslotId CoriantTypesSubslotId
    }
ledEquipmentType OBJECT-TYPE
    SYNTAX OCTET STRING  (SIZE (0..16))
    MAX-ACCESS read-only
    STATUS current
    DESCRIPTION "
	The attribute indicates the equipment type to identify the module. 
	for example, if the card is CHM1, 'CHM1' shall be used.
	DCI supporting LEDs:
	CHM1, CHM2, SHELF, FAN
	
		
		
		"
::= { ledEntry 1 }
ledShelfId OBJECT-TYPE
    SYNTAX CoriantTypesShelfId 
    MAX-ACCESS read-only
    STATUS current
    DESCRIPTION "
	Identifier of the shelf. 
	
		
		
		"
::= { ledEntry 2 }
ledSlotId OBJECT-TYPE
    SYNTAX CoriantTypesSlotId 
    MAX-ACCESS read-only
    STATUS current
    DESCRIPTION "
	Identifier of the slot. 
	
		
		
		"
::= { ledEntry 3 }
ledName OBJECT-TYPE
    SYNTAX OCTET STRING  (SIZE (0..16))
    MAX-ACCESS read-only
    STATUS current
    DESCRIPTION "
	The functional name of LED. 
	DCI NE:
	location_led
	port(n)_led   (CHM1: n = 1 to 6, CHM2 n = 1 to 12, e.g. Port12)
	active_led
	power_led
	fault_led
	status_led
	subslot(n)_led
	
		
		
		"
::= { ledEntry 4 }
ledStatus OBJECT-TYPE
    SYNTAX INTEGER  {
	 notAvailable (1),
	 off (2),
	 blink (3),
	 red (4),
	 redBlink (5),
	 green (6),
	 greenBlink (7),
	 amber (8),
	 amberBlink (9)
	}
    MAX-ACCESS read-only
    STATUS current
    DESCRIPTION "
	Current LED status. 
	DCI NE:
	For Location_LED: OFF, BLINK
	For others:
	red, red-blink,green,green-blink,amber,amber-blink,off,notAvailable
	
		
		
		"
::= { ledEntry 5 }
ledSubslotId OBJECT-TYPE
    SYNTAX CoriantTypesSubslotId 
    MAX-ACCESS read-only
    STATUS current
    DESCRIPTION "
	Identifier of the subslot. 
	
		
		
		"
::= { ledEntry 6 }
temperatureDetails OBJECT IDENTIFIER ::= { equipment 15 }
temperatureDetailsTable OBJECT-TYPE
    SYNTAX SEQUENCE OF TemperatureDetailsEntry
    MAX-ACCESS not-accessible
    STATUS current
    DESCRIPTION "The detailed information of temperature in each monitoring-point of current module"
::= { temperatureDetails 1 }
temperatureDetailsEntry OBJECT-TYPE
    SYNTAX TemperatureDetailsEntry
    MAX-ACCESS not-accessible
    STATUS current
    DESCRIPTION "Entry of temperatureDetailsTable" 
    INDEX { shelfId,slotId,temperatureDetailsMonitoringPoint }
::= { temperatureDetailsTable 1 }
TemperatureDetailsEntry ::= 
SEQUENCE {
	temperatureDetailsMonitoringPoint OCTET STRING,
	temperatureDetailsTemperature CoriantTypesTemperature,
	temperatureDetailsTemperatureRangeLow CoriantTypesTemperature,
	temperatureDetailsTemperatureRangeHigh CoriantTypesTemperature
    }
temperatureDetailsMonitoringPoint OBJECT-TYPE
    SYNTAX OCTET STRING  (SIZE (1..64))
    MAX-ACCESS read-only
    STATUS current
    DESCRIPTION "The point of temperature monitoring. It could be the sensor or chip internal.
		
		
		"
::= { temperatureDetailsEntry 1 }
temperatureDetailsTemperature OBJECT-TYPE
    SYNTAX CoriantTypesTemperature 
    MAX-ACCESS read-only
    STATUS current
    DESCRIPTION "Temperature at the monitoring point.
		
		
		"
::= { temperatureDetailsEntry 2 }
temperatureDetailsTemperatureRangeLow OBJECT-TYPE
    SYNTAX CoriantTypesTemperature 
    MAX-ACCESS read-only
    STATUS current
    DESCRIPTION "The lowest temperature threshold of this monitoring point in working mode.
		
		
		"
::= { temperatureDetailsEntry 3 }
temperatureDetailsTemperatureRangeHigh OBJECT-TYPE
    SYNTAX CoriantTypesTemperature 
    MAX-ACCESS read-only
    STATUS current
    DESCRIPTION "The highest temperature threshold of this monitoring point in working mode.
		
		
		"
::= { temperatureDetailsEntry 4 }
otdr OBJECT IDENTIFIER ::= { equipment 16 }
otdrTable OBJECT-TYPE
    SYNTAX SEQUENCE OF OtdrEntry
    MAX-ACCESS not-accessible
    STATUS current
    DESCRIPTION "Container of OTDR."
::= { otdr 1 }
otdrEntry OBJECT-TYPE
    SYNTAX OtdrEntry
    MAX-ACCESS not-accessible
    STATUS current
    DESCRIPTION "Entry of otdrTable" 
    INDEX { shelfId,slotId,subslotId }
::= { otdrTable 1 }
OtdrEntry ::= 
SEQUENCE {
	otdrState INTEGER,
	otdrMeasurementTime Unsigned32,
	otdrError OCTET STRING,
	otdrLaserStatus INTEGER,
	otdrMeasurementPort Unsigned32
    }
otdrState OBJECT-TYPE
    SYNTAX INTEGER  {
	 notAvailable (0),
	 idle (1),
	 measuring (2),
	 finished (3),
	 fail (4)
	}
    MAX-ACCESS read-only
    STATUS current
    DESCRIPTION "
	Indicating the current status of the OTDR. 
	
		
		
		default value :not-available"
::= { otdrEntry 1 }
otdrMeasurementTime OBJECT-TYPE
    SYNTAX Unsigned32 
    MAX-ACCESS read-only
    STATUS current
    DESCRIPTION "
	Indicating the time remaining in current measurement running. 
	
		
		UNITS:second
		default value :0"
::= { otdrEntry 2 }
otdrError OBJECT-TYPE
    SYNTAX OCTET STRING  (SIZE (0..64))
    MAX-ACCESS read-only
    STATUS current
    DESCRIPTION "Error message produced when the measurement ends with error.
		
		
		"
::= { otdrEntry 3 }
otdrLaserStatus OBJECT-TYPE
    SYNTAX INTEGER  {
	 notAvailable (0),
	 enabled (1),
	 disabled (2)
	}
    MAX-ACCESS read-only
    STATUS current
    DESCRIPTION "
	Indicating the current status of the OTDR laser. 
	
		
		
		default value :not-available"
::= { otdrEntry 4 }
otdrMeasurementPort OBJECT-TYPE
    SYNTAX Unsigned32 
    MAX-ACCESS read-only
    STATUS current
    DESCRIPTION "0 indicates that the card is not measuring any port; 
	non-zero indicates the OTDR port number where a measurement is currently taking place.
		
		
		default value :0"
::= { otdrEntry 5 }
otdrPort OBJECT IDENTIFIER ::= { equipment 18 }
otdrPortTable OBJECT-TYPE
    SYNTAX SEQUENCE OF OtdrPortEntry
    MAX-ACCESS not-accessible
    STATUS current
    DESCRIPTION "Containing attributes of OTDR port."
::= { otdrPort 1 }
otdrPortEntry OBJECT-TYPE
    SYNTAX OtdrPortEntry
    MAX-ACCESS not-accessible
    STATUS current
    DESCRIPTION "Entry of otdrPortTable" 
    INDEX { shelfId,slotId,subslotId,portId }
::= { otdrPortTable 1 }
OtdrPortEntry ::= 
SEQUENCE {
	otdrPortOtdrRange OtdrOtdrRange,
	otdrPortOtdrPulseWidth OtdrOtdrPulseWidth,
	otdrPortOtdrMeasurementSpeed INTEGER,
	otdrPortOtdrIor OtdrOtdrIor,
	otdrPortOtdrFiberType INTEGER,
	otdrPortOtdrLastMeasurement IetfYangTypesDateAndTime,
	otdrPortOtdrResolution OCTET STRING
    }
otdrPortOtdrRange OBJECT-TYPE
    SYNTAX OtdrOtdrRange 
    MAX-ACCESS read-only
    STATUS current
    DESCRIPTION " OTDR measurement range. 
		
		UNITS:km
		default value :auto"
::= { otdrPortEntry 1 }
otdrPortOtdrPulseWidth OBJECT-TYPE
    SYNTAX OtdrOtdrPulseWidth 
    MAX-ACCESS read-only
    STATUS current
    DESCRIPTION "
	Indicates pulse width to be used in otdr measurement. 
	
		
		UNITS:nano-second
		default value :auto"
::= { otdrPortEntry 2 }
otdrPortOtdrMeasurementSpeed OBJECT-TYPE
    SYNTAX INTEGER  {
	 fast (1),
	 medium (3),
	 slow (4),
	 precision (5),
	 auto (6)
	}
    MAX-ACCESS read-only
    STATUS current
    DESCRIPTION "
	Indicating OTDR measurement speed. 
	
		
		
		default value :auto"
::= { otdrPortEntry 3 }
otdrPortOtdrIor OBJECT-TYPE
    SYNTAX OtdrOtdrIor 
    MAX-ACCESS read-only
    STATUS current
    DESCRIPTION "
	Specifies the group index of refraction (IOR) of the fiber to be measured. 
	
		
		
		default value :auto"
::= { otdrPortEntry 4 }
otdrPortOtdrFiberType OBJECT-TYPE
    SYNTAX INTEGER  {
	 unknown (0),
	 ssmf (1),
	 leaf (2),
	 twrs (3),
	 twc (4),
	 allwave (5),
	 dsf (6),
	 ls (7),
	 puresilica (8),
	 twreach (9),
	 vistacor (10),
	 teralight (11),
	 drakall (12),
	 twplus (13),
	 twminus (14),
	 pslc (15),
	 auto (16)
	}
    MAX-ACCESS read-only
    STATUS current
    DESCRIPTION "
	Indicating fiber type to be measured. 
	
		
		
		default value :auto"
::= { otdrPortEntry 5 }
otdrPortOtdrLastMeasurement OBJECT-TYPE
    SYNTAX IetfYangTypesDateAndTime 
    MAX-ACCESS read-only
    STATUS current
    DESCRIPTION "Indicates the last otdr measurement date and time on the port.
		
		
		default value :0000-00-00T00:00:00Z"
::= { otdrPortEntry 6 }
otdrPortOtdrResolution OBJECT-TYPE
    SYNTAX OCTET STRING 
    MAX-ACCESS read-only
    STATUS current
    DESCRIPTION "
	Specifies the OTDR data sampling resolution. 
	
		
		UNITS:meter
		default value :auto"
::= { otdrPortEntry 7 }
ops OBJECT IDENTIFIER ::= { equipment 20 }
opsTable OBJECT-TYPE
    SYNTAX SEQUENCE OF OpsEntry
    MAX-ACCESS not-accessible
    STATUS current
    DESCRIPTION "The list of optical protection switch (ops) on an equipment."
::= { ops 1 }
opsEntry OBJECT-TYPE
    SYNTAX OpsEntry
    MAX-ACCESS not-accessible
    STATUS current
    DESCRIPTION "Entry of opsTable" 
    INDEX { shelfId,slotId,subslotId,opsName }
::= { opsTable 1 }
OpsEntry ::= 
SEQUENCE {
	opsName CoriantTypesNameIdentifier,
	opsWorkingEntity RowPointer,
	opsProtectionEntity RowPointer,
	opsAdminStatus INTEGER,
	opsOperStatus INTEGER,
	opsAvailStatus BITS,
	opsAliasName OCTET STRING,
	opsProtectionStatus INTEGER,
	opsActivePath INTEGER,
	opsRevertive CoriantTypesYesNo,
	opsWaitToRestore Unsigned32,
	opsWorkingSwitchThreshold CoriantTypesOpticalPower,
	opsProtectionSwitchThreshold CoriantTypesOpticalPower,
	opsWorkingLosThreshold CoriantTypesOpticalPower,
	opsProtectionLosThreshold CoriantTypesOpticalPower,
	opsHoldoffTimer Unsigned32,
	opsWavelengthBand INTEGER
    }
opsName OBJECT-TYPE
    SYNTAX CoriantTypesNameIdentifier 
    MAX-ACCESS read-only
    STATUS current
    DESCRIPTION "The name assigned to identify a specific ops in the device
		
		
		"
::= { opsEntry 1 }
opsWorkingEntity OBJECT-TYPE
    SYNTAX RowPointer 
    MAX-ACCESS read-only
    STATUS current
    DESCRIPTION "Identifier of the working port of the OPS.
		
		
		"
::= { opsEntry 2 }
opsProtectionEntity OBJECT-TYPE
    SYNTAX RowPointer 
    MAX-ACCESS read-only
    STATUS current
    DESCRIPTION "Identifier of the protection port of the OPS
		
		
		"
::= { opsEntry 3 }
opsAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { opsEntry 4 }
opsOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { opsEntry 5 }
opsAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { opsEntry 6 }
opsAliasName OBJECT-TYPE
    SYNTAX OCTET STRING  (SIZE (0..256))
    MAX-ACCESS read-only
    STATUS current
    DESCRIPTION "User defined alias for this entity. Must be an alphanumeric string with dash or underscore
		
		
		"
::= { opsEntry 7 }
opsProtectionStatus OBJECT-TYPE
    SYNTAX INTEGER  {
	 notApplicable (0),
	 manualSwitchToProtection (1),
	 manualSwitchToWorking (2),
	 forceSwitchToProtection (3),
	 forceSwitchToWorking (4),
	 lockoutOfProtection (5),
	 signalFailureOnWorking (6),
	 signalFailureOnProtection (7),
	 signalDegradeOnWorking (8),
	 signalDegradeOnProtection (9),
	 doNotRevert (10),
	 noRequest (11),
	 waitToRestore (12)
	}
    MAX-ACCESS read-only
    STATUS current
    DESCRIPTION "Indicates the status of the protection switch.
	
		
		
		"
::= { opsEntry 8 }
opsActivePath OBJECT-TYPE
    SYNTAX INTEGER  {
	 working (1),
	 protection (2),
	 unknown (3)
	}
    MAX-ACCESS read-only
    STATUS current
    DESCRIPTION "Indicating the active port of the protection switch.
	
		
		
		default value :unknown"
::= { opsEntry 9 }
opsRevertive OBJECT-TYPE
    SYNTAX CoriantTypesYesNo 
    MAX-ACCESS read-only
    STATUS current
    DESCRIPTION "Revertive behavior of the aps.
	If True, then automatically revert after protection switch
	once the fault is restored.
		
		
		default value :no"
::= { opsEntry 10 }
opsWaitToRestore OBJECT-TYPE
    SYNTAX Unsigned32  (0..3600)
    MAX-ACCESS read-only
    STATUS current
    DESCRIPTION "Wait To Restore, valid values: 0-3600 seconds. A value of zero will switch back immediately,
	after expiration of the timer, the working is restored and a norequest state is transmitted.
		
		UNITS:second
		default value :300"
::= { opsEntry 11 }
opsWorkingSwitchThreshold OBJECT-TYPE
    SYNTAX CoriantTypesOpticalPower 
    MAX-ACCESS read-only
    STATUS current
    DESCRIPTION "The switching threshold of the working port which indicates the optical power threshold of signal degrade.
		
		
		default value :-18.0"
::= { opsEntry 12 }
opsProtectionSwitchThreshold OBJECT-TYPE
    SYNTAX CoriantTypesOpticalPower 
    MAX-ACCESS read-only
    STATUS current
    DESCRIPTION "The switching threshold of the protection port which indicates the optical power threshold of signal degrade.
		
		
		default value :-18.0"
::= { opsEntry 13 }
opsWorkingLosThreshold OBJECT-TYPE
    SYNTAX CoriantTypesOpticalPower 
    MAX-ACCESS read-only
    STATUS current
    DESCRIPTION "The switching threshold of the working port, power level below it will lead to loss of signal.
		
		
		default value :-23.0"
::= { opsEntry 14 }
opsProtectionLosThreshold OBJECT-TYPE
    SYNTAX CoriantTypesOpticalPower 
    MAX-ACCESS read-only
    STATUS current
    DESCRIPTION "The switching threshold of the protection port, power level below it will lead to loss of signal.
		
		
		default value :-23.0"
::= { opsEntry 15 }
opsHoldoffTimer OBJECT-TYPE
    SYNTAX Unsigned32  (0..1000)
    MAX-ACCESS read-only
    STATUS current
    DESCRIPTION "
	The hold off time of the protection switch.
	
		
		UNITS:milliseconds
		default value :0"
::= { opsEntry 16 }
opsWavelengthBand OBJECT-TYPE
    SYNTAX INTEGER  {
	 t1550 (1),
	 t1310 (2)
	}
    MAX-ACCESS read-only
    STATUS current
    DESCRIPTION "Specifies the band of the signal going through the optical protection switch unit.
	
		
		UNITS:nm
		default value :1550"
::= { opsEntry 17 }
subportStatistics OBJECT IDENTIFIER ::= { equipment 25 }
subportStatisticsTable OBJECT-TYPE
    SYNTAX SEQUENCE OF SubportStatisticsEntry
    MAX-ACCESS not-accessible
    STATUS current
    DESCRIPTION "NULL"
::= { subportStatistics 1 }
subportStatisticsEntry OBJECT-TYPE
    SYNTAX SubportStatisticsEntry
    MAX-ACCESS not-accessible
    STATUS current
    DESCRIPTION "Entry of subportStatisticsTable" 
    INDEX { shelfId,slotId,subslotId,portId,subportId }
::= { subportStatisticsTable 1 }
SubportStatisticsEntry ::= 
SEQUENCE {
	subportStatisticsEntryLastClear IetfYangTypesDateAndTime
    }
subportStatisticsEntryLastClear OBJECT-TYPE
    SYNTAX IetfYangTypesDateAndTime 
    MAX-ACCESS read-only
    STATUS current
    DESCRIPTION "The start time of statistics monitor
		
		
		default value :0000-00-00T00:00:00.000Z"
::= { subportStatisticsEntry 1 }
portStatistics OBJECT IDENTIFIER ::= { equipment 26 }
portStatisticsTable OBJECT-TYPE
    SYNTAX SEQUENCE OF PortStatisticsEntry
    MAX-ACCESS not-accessible
    STATUS current
    DESCRIPTION "NULL"
::= { portStatistics 1 }
portStatisticsEntry OBJECT-TYPE
    SYNTAX PortStatisticsEntry
    MAX-ACCESS not-accessible
    STATUS current
    DESCRIPTION "Entry of portStatisticsTable" 
    INDEX { shelfId,slotId,subslotId,portId }
::= { portStatisticsTable 1 }
PortStatisticsEntry ::= 
SEQUENCE {
	portStatisticsEntryLastClear IetfYangTypesDateAndTime
    }
portStatisticsEntryLastClear OBJECT-TYPE
    SYNTAX IetfYangTypesDateAndTime 
    MAX-ACCESS read-only
    STATUS current
    DESCRIPTION "The start time of statistics monitor
		
		
		default value :0000-00-00T00:00:00.000Z"
::= { portStatisticsEntry 1 }
subcardStatistics OBJECT IDENTIFIER ::= { equipment 27 }
subcardStatisticsTable OBJECT-TYPE
    SYNTAX SEQUENCE OF SubcardStatisticsEntry
    MAX-ACCESS not-accessible
    STATUS current
    DESCRIPTION "NULL"
::= { subcardStatistics 1 }
subcardStatisticsEntry OBJECT-TYPE
    SYNTAX SubcardStatisticsEntry
    MAX-ACCESS not-accessible
    STATUS current
    DESCRIPTION "Entry of subcardStatisticsTable" 
    INDEX { shelfId,slotId,subslotId }
::= { subcardStatisticsTable 1 }
SubcardStatisticsEntry ::= 
SEQUENCE {
	subcardStatisticsEntryLastClear IetfYangTypesDateAndTime
    }
subcardStatisticsEntryLastClear OBJECT-TYPE
    SYNTAX IetfYangTypesDateAndTime 
    MAX-ACCESS read-only
    STATUS current
    DESCRIPTION "The start time of statistics monitor
		
		
		default value :0000-00-00T00:00:00.000Z"
::= { subcardStatisticsEntry 1 }
cardStatistics OBJECT IDENTIFIER ::= { equipment 28 }
cardStatisticsTable OBJECT-TYPE
    SYNTAX SEQUENCE OF CardStatisticsEntry
    MAX-ACCESS not-accessible
    STATUS current
    DESCRIPTION "NULL"
::= { cardStatistics 1 }
cardStatisticsEntry OBJECT-TYPE
    SYNTAX CardStatisticsEntry
    MAX-ACCESS not-accessible
    STATUS current
    DESCRIPTION "Entry of cardStatisticsTable" 
    INDEX { shelfId,slotId }
::= { cardStatisticsTable 1 }
CardStatisticsEntry ::= 
SEQUENCE {
	cardStatisticsEntryLastClear IetfYangTypesDateAndTime
    }
cardStatisticsEntryLastClear OBJECT-TYPE
    SYNTAX IetfYangTypesDateAndTime 
    MAX-ACCESS read-only
    STATUS current
    DESCRIPTION "The start time of statistics monitor
		
		
		default value :0000-00-00T00:00:00.000Z"
::= { cardStatisticsEntry 1 }
shelfStatistics OBJECT IDENTIFIER ::= { equipment 29 }
shelfStatisticsTable OBJECT-TYPE
    SYNTAX SEQUENCE OF ShelfStatisticsEntry
    MAX-ACCESS not-accessible
    STATUS current
    DESCRIPTION "NULL"
::= { shelfStatistics 1 }
shelfStatisticsEntry OBJECT-TYPE
    SYNTAX ShelfStatisticsEntry
    MAX-ACCESS not-accessible
    STATUS current
    DESCRIPTION "Entry of shelfStatisticsTable" 
    INDEX { shelfId }
::= { shelfStatisticsTable 1 }
ShelfStatisticsEntry ::= 
SEQUENCE {
	shelfStatisticsEntryLastClear IetfYangTypesDateAndTime
    }
shelfStatisticsEntryLastClear OBJECT-TYPE
    SYNTAX IetfYangTypesDateAndTime 
    MAX-ACCESS read-only
    STATUS current
    DESCRIPTION "The start time of statistics monitor
		
		
		default value :0000-00-00T00:00:00.000Z"
::= { shelfStatisticsEntry 1 }
services OBJECT IDENTIFIER ::= { groove 4 }
otn OBJECT IDENTIFIER ::= { services 1 }
eth10g OBJECT IDENTIFIER ::= { otn 1 }
eth10gTable OBJECT-TYPE
    SYNTAX SEQUENCE OF Eth10gEntry
    MAX-ACCESS not-accessible
    STATUS current
    DESCRIPTION "
	Represents the 10GBE object.
	"
::= { eth10g 1 }
eth10gEntry OBJECT-TYPE
    SYNTAX Eth10gEntry
    MAX-ACCESS not-accessible
    STATUS current
    DESCRIPTION "Entry of eth10gTable" 
    INDEX { shelfId,slotId,subslotId,portId,subportId }
::= { eth10gTable 1 }
Eth10gEntry ::= 
SEQUENCE {
	eth10gEthFecType CoriantTypesEthFec,
	eth10gEthFecTypeState CoriantTypesEthFec,
	eth10gTransmitInterpacketgap Unsigned32,
	eth10gGfpPayloadFcs CoriantTypesEnableSwitch,
	eth10gMappingMode INTEGER,
	eth10gAdminStatus INTEGER,
	eth10gOperStatus INTEGER,
	eth10gAvailStatus BITS,
	eth10gAliasName OCTET STRING,
	eth10gClientShutdown CoriantTypesYesNo,
	eth10gClientShutdownHoldoffTimer Unsigned32,
	eth10gNearEndAls CoriantTypesYesNo,
	eth10gAlsDegradeMode CoriantTypesEnableSwitch,
	eth10gLoopbackEnable CoriantTypesEnableSwitch,
	eth10gLoopbackType INTEGER,
	eth10gTestSignalType CoriantTypesTestSignalType,
	eth10gTestSignalEnable CoriantTypesTestSignalConfig,
	eth10gServiceLabel OCTET STRING,
	eth10gLldpStatusIf INTEGER,
	eth10gUpiValue INTEGER,
	eth10gHoldoffSignal CoriantTypesYesNo
    }
eth10gEthFecType OBJECT-TYPE
    SYNTAX CoriantTypesEthFec 
    MAX-ACCESS read-only
    STATUS current
    DESCRIPTION "
	The FEC working type of etyn port.
	
		
		
		default value :auto"
::= { eth10gEntry 1 }
eth10gEthFecTypeState OBJECT-TYPE
    SYNTAX CoriantTypesEthFec 
    MAX-ACCESS read-only
    STATUS current
    DESCRIPTION "
	The FEC working state of etyn port.
	
		
		
		default value :disabled"
::= { eth10gEntry 2 }
eth10gTransmitInterpacketgap OBJECT-TYPE
    SYNTAX Unsigned32  (8..12)
    MAX-ACCESS read-only
    STATUS current
    DESCRIPTION "
	Specifies the minimum transmit IPG value.
	
		
		
		default value :8"
::= { eth10gEntry 3 }
eth10gGfpPayloadFcs OBJECT-TYPE
    SYNTAX CoriantTypesEnableSwitch 
    MAX-ACCESS read-only
    STATUS current
    DESCRIPTION "
	Enabled: GFP payload FCS will be used, Ethernet frame FCS will be removed; 
	Disabled: GFP payload FCS will not be inserted, Ethernet frame FCS will be used.
	
		
		
		default value :disabled"
::= { eth10gEntry 4 }
eth10gMappingMode OBJECT-TYPE
    SYNTAX INTEGER  {
	 notApplicable (0),
	 gmp (1),
	 gfpF (2),
	 t40gbmpOdu2e (3),
	 preamble (4),
	 bmpFixedstuff (5),
	 bmp (6),
	 amp (7)
	}
    MAX-ACCESS read-only
    STATUS current
    DESCRIPTION "The mapping mode of client port packets into ODUk.
		
		
		default value :not-applicable"
::= { eth10gEntry 5 }
eth10gAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { eth10gEntry 6 }
eth10gOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { eth10gEntry 7 }
eth10gAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { eth10gEntry 8 }
eth10gAliasName OBJECT-TYPE
    SYNTAX OCTET STRING  (SIZE (0..256))
    MAX-ACCESS read-only
    STATUS current
    DESCRIPTION "User defined alias for this entity. Must be an alphanumeric string with dash or underscore
		
		
		"
::= { eth10gEntry 9 }
eth10gClientShutdown OBJECT-TYPE
    SYNTAX CoriantTypesYesNo 
    MAX-ACCESS read-only
    STATUS current
    DESCRIPTION "The switching of client-shutdown.
		
		
		default value :no"
::= { eth10gEntry 10 }
eth10gClientShutdownHoldoffTimer OBJECT-TYPE
    SYNTAX Unsigned32  (0..1000)
    MAX-ACCESS read-only
    STATUS current
    DESCRIPTION "The hold off time of client shutdown or replacement siganl at egress direction.
		
		UNITS:milliseconds
		default value :0"
::= { eth10gEntry 11 }
eth10gNearEndAls OBJECT-TYPE
    SYNTAX CoriantTypesYesNo 
    MAX-ACCESS read-only
    STATUS current
    DESCRIPTION "The switching of near end ALS.
		
		
		default value :no"
::= { eth10gEntry 12 }
eth10gAlsDegradeMode OBJECT-TYPE
    SYNTAX CoriantTypesEnableSwitch 
    MAX-ACCESS read-only
    STATUS current
    DESCRIPTION "The switching of defect BERSD-ODU trig ALS
		
		
		default value :disabled"
::= { eth10gEntry 13 }
eth10gLoopbackEnable OBJECT-TYPE
    SYNTAX CoriantTypesEnableSwitch 
    MAX-ACCESS read-only
    STATUS current
    DESCRIPTION "The enable switching of loopback function.
		
		
		default value :disabled"
::= { eth10gEntry 14 }
eth10gLoopbackType OBJECT-TYPE
    SYNTAX INTEGER  {
	 none (0),
	 terminal (1),
	 facility (2)
	}
    MAX-ACCESS read-only
    STATUS current
    DESCRIPTION "The type mode of loopback function
		
		
		default value :none"
::= { eth10gEntry 15 }
eth10gTestSignalType OBJECT-TYPE
    SYNTAX CoriantTypesTestSignalType 
    MAX-ACCESS read-only
    STATUS current
    DESCRIPTION "The type mode of test signal.
		
		
		default value :NONE"
::= { eth10gEntry 16 }
eth10gTestSignalEnable OBJECT-TYPE
    SYNTAX CoriantTypesTestSignalConfig 
    MAX-ACCESS read-only
    STATUS current
    DESCRIPTION "The enable switching of test signal function
		
		
		default value :NONE"
::= { eth10gEntry 17 }
eth10gServiceLabel OBJECT-TYPE
    SYNTAX OCTET STRING  (SIZE (0..128))
    MAX-ACCESS read-only
    STATUS current
    DESCRIPTION "Path/service name of cross-connection related facility.
		
		
		"
::= { eth10gEntry 18 }
eth10gLldpStatusIf OBJECT-TYPE
    SYNTAX INTEGER  {
	 notApplicable (0),
	 rxonly (2),
	 disabled (4)
	}
    MAX-ACCESS read-only
    STATUS current
    DESCRIPTION "
	Port level lldp control. 
	Value of 'rxonly', then the LLDP agent will receive lldp,
	when lldp-status-ne is also enabled. 
	                    
	Value of 'disabled', then LLDP agent will not filter and
	receive LLDP frames on this port.  If there is remote systems
	information which is received on this port and stored in
	the system before the lldp-status   becomes disabled, 
	then the information will naturally age out.    
	
	Note: txOnly and txAndRx modes are not supported.
	                    
	
		
		
		default value :disabled"
::= { eth10gEntry 19 }
eth10gUpiValue OBJECT-TYPE
    SYNTAX INTEGER  {
	 notApplicable (0),
	 g709 (1),
	 gsupp43 (2)
	}
    MAX-ACCESS read-only
    STATUS current
    DESCRIPTION "
	The value of ODU2 upi in PREAMBLE mapping mode.
	
		
		
		default value :not-applicable"
::= { eth10gEntry 20 }
eth10gHoldoffSignal OBJECT-TYPE
    SYNTAX CoriantTypesYesNo 
    MAX-ACCESS read-only
    STATUS current
    DESCRIPTION "Specify if specific signal will be sent out during hold off time
	which avoid downstream equipment consequent action in the duration.
		
		
		default value :no"
::= { eth10gEntry 21 }
testSignalFacilityStatus OBJECT IDENTIFIER ::= { otn 2 }
testSignalFacilityStatusTable OBJECT-TYPE
    SYNTAX SEQUENCE OF TestSignalFacilityStatusEntry
    MAX-ACCESS not-accessible
    STATUS current
    DESCRIPTION "Test signal status for current facility."
::= { testSignalFacilityStatus 1 }
testSignalFacilityStatusEntry OBJECT-TYPE
    SYNTAX TestSignalFacilityStatusEntry
    MAX-ACCESS not-accessible
    STATUS current
    DESCRIPTION "Entry of testSignalFacilityStatusTable" 
    INDEX { shelfId,slotId,subslotId,portId,subportId }
::= { testSignalFacilityStatusTable 1 }
TestSignalFacilityStatusEntry ::= 
SEQUENCE {
	testSignalFacilityStatusPrbsSync INTEGER,
	testSignalFacilityStatusTestTimeDuration Unsigned32,
	testSignalFacilityStatusPrbsBitErrorCount IetfYangTypesGauge64
    }
testSignalFacilityStatusPrbsSync OBJECT-TYPE
    SYNTAX INTEGER  {
	 notApplicable (0),
	 inSync (1),
	 outSync (2),
	 errSync (3)
	}
    MAX-ACCESS read-only
    STATUS current
    DESCRIPTION "The test result of PRBS Synchronization
		
		
		default value :not-applicable"
::= { testSignalFacilityStatusEntry 1 }
testSignalFacilityStatusTestTimeDuration OBJECT-TYPE
    SYNTAX Unsigned32 
    MAX-ACCESS read-only
    STATUS current
    DESCRIPTION "The time duration of signal test
		
		UNITS:seconds
		"
::= { testSignalFacilityStatusEntry 2 }
testSignalFacilityStatusPrbsBitErrorCount OBJECT-TYPE
    SYNTAX IetfYangTypesGauge64 
    MAX-ACCESS read-only
    STATUS current
    DESCRIPTION "The counting of bit error by PRBS Synchronization
		
		
		"
::= { testSignalFacilityStatusEntry 3 }
lldpRemoteSystem OBJECT IDENTIFIER ::= { otn 3 }
lldpRemoteSystemTable OBJECT-TYPE
    SYNTAX SEQUENCE OF LldpRemoteSystemEntry
    MAX-ACCESS not-accessible
    STATUS current
    DESCRIPTION "List of LLDP neighbors."
::= { lldpRemoteSystem 1 }
lldpRemoteSystemEntry OBJECT-TYPE
    SYNTAX LldpRemoteSystemEntry
    MAX-ACCESS not-accessible
    STATUS current
    DESCRIPTION "Entry of lldpRemoteSystemTable" 
    INDEX { shelfId,slotId,subslotId,portId,subportId,lldpRemoteSystemLldpRemoteIndex }
::= { lldpRemoteSystemTable 1 }
LldpRemoteSystemEntry ::= 
SEQUENCE {
	lldpRemoteSystemLldpRemoteIndex Unsigned32,
	lldpRemoteSystemRemoteChassisIdSubtype INTEGER,
	lldpRemoteSystemRemoteChassisId OCTET STRING,
	lldpRemoteSystemRemotePortIdSubtype INTEGER,
	lldpRemoteSystemRemotePortId OCTET STRING,
	lldpRemoteSystemRemotePortDesc OCTET STRING,
	lldpRemoteSystemRemoteSysName OCTET STRING,
	lldpRemoteSystemRemoteSysDesc OCTET STRING,
	lldpRemoteSystemRemoteSysCapSupported LldpLldpSysCap,
	lldpRemoteSystemRemoteSysCapEnabled LldpLldpSysCap
    }
lldpRemoteSystemLldpRemoteIndex OBJECT-TYPE
    SYNTAX Unsigned32 
    MAX-ACCESS read-only
    STATUS current
    DESCRIPTION "
	This attribute represents an arbitrary local integer value used
	by this agent to identify a particular connection instance,
	unique only for the indicated remote system. 
	
		
		
		"
::= { lldpRemoteSystemEntry 1 }
lldpRemoteSystemRemoteChassisIdSubtype OBJECT-TYPE
    SYNTAX INTEGER  {
	 chassiscomponent (1),
	 interfacealias (2),
	 portcomponent (3),
	 macaddress (4),
	 networkaddress (5),
	 interfacename (6),
	 local (7)
	}
    MAX-ACCESS read-only
    STATUS current
    DESCRIPTION "
	This attribute describes the source of a chassis identifier. 
	
	The enumeration 'chassisComponent(1)' represents a chassis
	identifier based on the value of entPhysicalAlias object
	(defined in IETF RFC 2737) for a chassis component (i.e.,
	an entPhysicalClass value of 'chassis(3)').
	
	The enumeration 'interfaceAlias(2)' represents a chassis
	identifier based on the value of ifAlias object (defined in
	IETF RFC 2863) for an interface on the containing chassis.
	
	The enumeration 'portComponent(3)' represents a chassis
	identifier based on the value of entPhysicalAlias object
	(defined in IETF RFC 2737) for a port or backplane
	component (i.e., entPhysicalClass value of 'port(10)' or
	'backplane(4)'), within the containing chassis.
	
	The enumeration 'macAddress(4)' represents a chassis
	identifier based on the value of a unicast source address
	(encoded in network byte order and IEEE 802.3 canonical bit
	order), of a port on the containing chassis as defined in
	IEEE Std 802-2001.
	
	The enumeration 'networkAddress(5)' represents a chassis
	identifier based on a network address, associated with
	a particular chassis.  The encoded address is actually
	composed of two fields.  The first field is a single octet,
	representing the IANA AddressFamilyNumbers value for the
	specific address type, and the second field is the network
	address value.
	
	The enumeration 'interfaceName(6)' represents a chassis
	identifier based on the value of ifName object (defined in
	IETF RFC 2863) for an interface on the containing chassis.
	
	The enumeration 'local(7)' represents a chassis identifier
	based on a locally defined value.
	
		
		
		"
::= { lldpRemoteSystemEntry 2 }
lldpRemoteSystemRemoteChassisId OBJECT-TYPE
    SYNTAX OCTET STRING  (SIZE (0..255))
    MAX-ACCESS read-only
    STATUS current
    DESCRIPTION "
	This attribute describes the format of a chassis identifier string. 
	Objects of this type are always used with an associated
	LldpChassisIdSubtype object, which identifies the format of
	the particular LldpChassisId object instance.
	
	If the associated LldpChassisIdSubtype object has a value of
	'chassisComponent(1)', then the octet string identifies
	a particular instance of the entPhysicalAlias object
	(defined in IETF RFC 2737) for a chassis component (i.e.,
	an entPhysicalClass value of 'chassis(3)').
	
	If the associated LldpChassisIdSubtype object has a value
	of 'interfaceAlias(2)', then the octet string identifies
	a particular instance of the ifAlias object (defined in
	IETF RFC 2863) for an interface on the containing chassis.
	If the particular ifAlias object does not contain any values,
	another chassis identifier type should be used.
	
	If the associated LldpChassisIdSubtype object has a value
	of 'portComponent(3)', then the octet string identifies a
	particular instance of the entPhysicalAlias object (defined
	in IETF RFC 2737) for a port or backplane component within
	the containing chassis.
	
	If the associated LldpChassisIdSubtype object has a value of
	'macAddress(4)', then this string identifies a particular
	unicast source address (encoded in network byte order and
	IEEE 802.3 canonical bit order), of a port on the containing
	chassis as defined in IEEE Std 802-2001.
	
	If the associated LldpChassisIdSubtype object has a value of
	'networkAddress(5)', then this string identifies a particular
	network address, encoded in network byte order, associated
	with one or more ports on the containing chassis.  The first
	octet contains the IANA Address Family Numbers enumeration
	value for the specific address type, and octets 2 through
	N contain the network address value in network byte order.
	
	If the associated LldpChassisIdSubtype object has a value
	of 'interfaceName(6)', then the octet string identifies
	a particular instance of the ifName object (defined in
	IETF RFC 2863) for an interface on the containing chassis.
	If the particular ifName object does not contain any values,
	another chassis identifier type should be used.
	
	If the associated LldpChassisIdSubtype object has a value of
	'local(7)', then this string identifies a locally assigned
	Chassis ID.                 
	
		
		
		"
::= { lldpRemoteSystemEntry 3 }
lldpRemoteSystemRemotePortIdSubtype OBJECT-TYPE
    SYNTAX INTEGER  {
	 interfacealias (1),
	 portcomponent (2),
	 macaddress (3),
	 networkaddress (4),
	 interfacename (5),
	 agentcircuitid (6),
	 local (7)
	}
    MAX-ACCESS read-only
    STATUS current
    DESCRIPTION "
	This attribute describes the format of a port identifier string. 
	Objects of this type are always used with an associated
	LldpPortIdSubtype object, which identifies the format of the
	particular LldpPortId object instance.
	
	If the associated LldpPortIdSubtype object has a value of
	'interfaceAlias(1)', then the octet string identifies a
	particular instance of the ifAlias object (defined in IETF
	RFC 2863).  If the particular ifAlias object does not contain
	any values, another port identifier type should be used.
	
	If the associated LldpPortIdSubtype object has a value of
	'portComponent(2)', then the octet string identifies a
	particular instance of the entPhysicalAlias object (defined
	in IETF RFC 2737) for a port or backplane component.
	
	If the associated LldpPortIdSubtype object has a value of
	'macAddress(3)', then this string identifies a particular
	unicast source address (encoded in network byte order
	and IEEE 802.3 canonical bit order) associated with the port
	(IEEE Std 802-2001).
	
	If the associated LldpPortIdSubtype object has a value of
	'networkAddress(4)', then this string identifies a network
	address associated with the port.  The first octet contains
	the IANA AddressFamilyNumbers enumeration value for the
	specific address type, and octets 2 through N contain the
	networkAddress address value in network byte order.
	
	If the associated LldpPortIdSubtype object has a value of
	'interfaceName(5)', then the octet string identifies a
	particular instance of the ifName object (defined in IETF
	RFC 2863).  If the particular ifName object does not contain
	any values, another port identifier type should be used.
	
	If the associated LldpPortIdSubtype object has a value of
	'agentCircuitId(6)', then this string identifies an agent-local
	identifier of the circuit (defined in RFC 3046).
	
	If the associated LldpPortIdSubtype object has a value of
	'local(7)', then this string identifies a locally
	assigned port ID.   
	
		
		
		"
::= { lldpRemoteSystemEntry 4 }
lldpRemoteSystemRemotePortId OBJECT-TYPE
    SYNTAX OCTET STRING  (SIZE (0..255))
    MAX-ACCESS read-only
    STATUS current
    DESCRIPTION "
	This attribute describes the format of a port identifier string. 
	Objects of this type are always used with an associated
	LldpPortIdSubtype object, which identifies the format of the
	particular LldpPortId object instance. 
	
	If the associated LldpPortIdSubtype object has a value of
	'interfaceAlias(1)', then the octet string identifies a
	particular instance of the ifAlias object (defined in IETF
	RFC 2863).  If the particular ifAlias object does not contain
	any values, another port identifier type should be used.
	
	If the associated LldpPortIdSubtype object has a value of
	'portComponent(2)', then the octet string identifies a
	particular instance of the entPhysicalAlias object (defined
	in IETF RFC 2737) for a port or backplane component.
	
	If the associated LldpPortIdSubtype object has a value of
	'macAddress(3)', then this string identifies a particular
	unicast source address (encoded in network byte order
	and IEEE 802.3 canonical bit order) associated with the port
	(IEEE Std 802-2001).
	
	If the associated LldpPortIdSubtype object has a value of
	'networkAddress(4)', then this string identifies a network
	address associated with the port.  The first octet contains
	the IANA AddressFamilyNumbers enumeration value for the
	specific address type, and octets 2 through N contain the
	networkAddress address value in network byte order.
	
	If the associated LldpPortIdSubtype object has a value of
	'interfaceName(5)', then the octet string identifies a
	particular instance of the ifName object (defined in IETF
	RFC 2863).  If the particular ifName object does not contain
	any values, another port identifier type should be used.
	
	If the associated LldpPortIdSubtype object has a value of
	'agentCircuitId(6)', then this string identifies an agent-local
	identifier of the circuit (defined in RFC 3046).
	
	If the associated LldpPortIdSubtype object has a value of
	'local(7)', then this string identifies a locally
	assigned port ID.               
	
		
		
		"
::= { lldpRemoteSystemEntry 5 }
lldpRemoteSystemRemotePortDesc OBJECT-TYPE
    SYNTAX OCTET STRING  (SIZE (0..255))
    MAX-ACCESS read-only
    STATUS current
    DESCRIPTION "
	The string value used to identify the description of
	the given port associated with the remote system.
	
		
		
		"
::= { lldpRemoteSystemEntry 6 }
lldpRemoteSystemRemoteSysName OBJECT-TYPE
    SYNTAX OCTET STRING  (SIZE (0..255))
    MAX-ACCESS read-only
    STATUS current
    DESCRIPTION "
	The string value used to identify the system name of the
	remote system. 
	sys-name: system name                        
	
		
		
		"
::= { lldpRemoteSystemEntry 7 }
lldpRemoteSystemRemoteSysDesc OBJECT-TYPE
    SYNTAX OCTET STRING  (SIZE (0..255))
    MAX-ACCESS read-only
    STATUS current
    DESCRIPTION "
	The string value used to identify the system description
	of the remote system. 
	sys-desc: system description                         
	
		
		
		"
::= { lldpRemoteSystemEntry 8 }
lldpRemoteSystemRemoteSysCapSupported OBJECT-TYPE
    SYNTAX LldpLldpSysCap 
    MAX-ACCESS read-only
    STATUS current
    DESCRIPTION "
	This attribute describes the system capabilities. 
	The bit 'other(0)' indicates that the system has capabilities
	other than those listed below.
	The bit 'repeater(1)' indicates that the system has repeater
	capability.
	The bit 'bridge(2)' indicates that the system has bridge
	capability.
	The bit 'wlanAccessPoint(3)' indicates that the system has 
	WLAN access point capability.
	The bit 'router(4)' indicates that the system has router
	capability.
	The bit 'telephone(5)' indicates that the system has telephone
	capability.
	The bit 'docsisCableDevice(6)' indicates that the system has
	DOCSIS Cable Device capability (IETF RFC 2669 & 2670).
	The bit 'stationOnly(7)' indicates that the system has only
	station capability and nothing else.
	The bit 'cVLANComponent(8)' indicates that the system has
	C-VLAN component functionality.
	The bit 'sVLANComponent(9)' indicates that the system  has
	S-VLAN component functionality.
	The bit 'twoPortMACRelay(10)' indicates that the system has
	Two-port MAC Relay (TPMR) functionality.  
	sys-cap-supported: supported system capability                        
	
		
		
		"
::= { lldpRemoteSystemEntry 9 }
lldpRemoteSystemRemoteSysCapEnabled OBJECT-TYPE
    SYNTAX LldpLldpSysCap 
    MAX-ACCESS read-only
    STATUS current
    DESCRIPTION "This attribute describes the system capabilities. 
	The bit 'other(0)' indicates that the system has capabilities
	other than those listed below.
	The bit 'repeater(1)' indicates that the system has repeater
	capability.
	The bit 'bridge(2)' indicates that the system has bridge
	capability.
	The bit 'wlanAccessPoint(3)' indicates that the system has 
	WLAN access point capability.
	The bit 'router(4)' indicates that the system has router
	capability.
	The bit 'telephone(5)' indicates that the system has telephone
	capability.
	The bit 'docsisCableDevice(6)' indicates that the system has
	DOCSIS Cable Device capability (IETF RFC 2669 & 2670).
	The bit 'stationOnly(7)' indicates that the system has only
	station capability and nothing else.
	The bit 'cVLANComponent(8)' indicates that the system has
	C-VLAN component functionality.
	The bit 'sVLANComponent(9)' indicates that the system  has
	S-VLAN component functionality.
	The bit 'twoPortMACRelay(10)' indicates that the system has
	Two-port MAC Relay (TPMR) functionality.                        
	
		
		
		"
::= { lldpRemoteSystemEntry 10 }
remoteManAddresses OBJECT IDENTIFIER ::= { otn 4 }
remoteManAddressesTable OBJECT-TYPE
    SYNTAX SEQUENCE OF RemoteManAddressesEntry
    MAX-ACCESS not-accessible
    STATUS current
    DESCRIPTION "
	List of management addresses of LLDP neighbor. 
	man:managment, remote management addresses
	"
::= { remoteManAddresses 1 }
remoteManAddressesEntry OBJECT-TYPE
    SYNTAX RemoteManAddressesEntry
    MAX-ACCESS not-accessible
    STATUS current
    DESCRIPTION "Entry of remoteManAddressesTable" 
    INDEX { shelfId,slotId,subslotId,portId,subportId,lldpRemoteSystemLldpRemoteIndex,remoteManAddressesRemoteManAddrSubtype,remoteManAddressesRemoteManAddr }
::= { remoteManAddressesTable 1 }
RemoteManAddressesEntry ::= 
SEQUENCE {
	remoteManAddressesRemoteManAddrSubtype Unsigned32,
	remoteManAddressesRemoteManAddr OCTET STRING,
	remoteManAddressesRemoteManAddrIfSubtype Unsigned32,
	remoteManAddressesRemoteManAddrIfId Unsigned32,
	remoteManAddressesRemoteManAddrOid OCTET STRING
    }
remoteManAddressesRemoteManAddrSubtype OBJECT-TYPE
    SYNTAX Unsigned32 
    MAX-ACCESS read-only
    STATUS current
    DESCRIPTION "
	The type of management address identifier encoding used in
	the associated 'lldpLocManagmentAddr' object. 
	
		
		
		"
::= { remoteManAddressesEntry 1 }
remoteManAddressesRemoteManAddr OBJECT-TYPE
    SYNTAX OCTET STRING  (SIZE (0..62))
    MAX-ACCESS read-only
    STATUS current
    DESCRIPTION "
	The string value used to identify the management address
	component associated with the remote system.  The purpose
	of this address is to contact the management entity. 
	man: management
	addr: address                            
	
		
		
		"
::= { remoteManAddressesEntry 2 }
remoteManAddressesRemoteManAddrIfSubtype OBJECT-TYPE
    SYNTAX Unsigned32 
    MAX-ACCESS read-only
    STATUS current
    DESCRIPTION "
	This attribute describes the basis of a particular type of
	interface associated with the management address. 
	
	The enumeration 'unknown(1)' represents the case where the
	interface is not known.
	
	The enumeration 'ifIndex(2)' represents interface identifier
	based on the ifIndex MIB object.
	
	The enumeration 'systemPortNumber(3)' represents interface
	identifier based on the system port numbering convention.
	man: management
	addr: address                             
	
		
		
		"
::= { remoteManAddressesEntry 3 }
remoteManAddressesRemoteManAddrIfId OBJECT-TYPE
    SYNTAX Unsigned32 
    MAX-ACCESS read-only
    STATUS current
    DESCRIPTION "
	The integer value used to identify the interface number
	regarding the management address component associated with
	the remote system.                          
	man: management
	addr: address                             
	
		
		
		"
::= { remoteManAddressesEntry 4 }
remoteManAddressesRemoteManAddrOid OBJECT-TYPE
    SYNTAX OCTET STRING  (SIZE (0..128))
    MAX-ACCESS read-only
    STATUS current
    DESCRIPTION "
	The OID value used to identify the type of hardware component
	or protocol entity associated with the management address
	advertised by the remote system agent. 
	man: management
	addr: address
	oid: object identifier                            
	
		
		
		"
::= { remoteManAddressesEntry 5 }
odu OBJECT IDENTIFIER ::= { otn 5 }
oduTable OBJECT-TYPE
    SYNTAX SEQUENCE OF OduEntry
    MAX-ACCESS not-accessible
    STATUS current
    DESCRIPTION "NULL"
::= { odu 1 }
oduEntry OBJECT-TYPE
    SYNTAX OduEntry
    MAX-ACCESS not-accessible
    STATUS current
    DESCRIPTION "Entry of oduTable" 
    INDEX { shelfId,slotId,subslotId,portId,subportId,odutypeL1,oduidL1,odutypeL2,oduidL2,odutypeL3,oduidL3,odutypeL4,oduidL4 }
::= { oduTable 1 }
OduEntry ::= 
SEQUENCE {
	odutypeL1 CoriantTypesOduType,
	oduidL1 Unsigned32,
	odutypeL2 CoriantTypesOduType,
	oduidL2 Unsigned32,
	odutypeL3 CoriantTypesOduType,
	oduidL3 Unsigned32,
	odutypeL4 CoriantTypesOduType,
	oduidL4 Unsigned32,
	oduAdminStatus INTEGER,
	oduOperStatus INTEGER,
	oduAvailStatus BITS,
	oduAliasName OCTET STRING,
	oduServiceLabel OCTET STRING,
	oduTribSlot CoriantTypesNumberList,
	oduRxPayloadType OCTET STRING,
	oduTxPayloadType OCTET STRING,
	oduNimEnable CoriantTypesEnableSwitch,
	oduDelayMeasurementEnable CoriantTypesEnableSwitch,
	oduOpuConfigActual INTEGER,
	oduClientSignalType INTEGER,
	oduExpSapi OCTET STRING,
	oduExpDapi OCTET STRING,
	oduExpOperator OCTET STRING,
	oduTxSapi OCTET STRING,
	oduTxDapi OCTET STRING,
	oduTxOperator OCTET STRING,
	oduTimDefectMode CoriantTypesTimMode,
	oduTimAct CoriantTypesEnableSwitch,
	oduRxSapi OCTET STRING,
	oduRxDapi OCTET STRING,
	oduRxOperator OCTET STRING,
	oduDegradeInterval Unsigned32,
	oduDegradeThreshold Unsigned32,
	oduTestSignalType CoriantTypesTestSignalType,
	oduTestSignalEnable CoriantTypesTestSignalConfig,
	oduTerminationMode INTEGER
    }
odutypeL1 OBJECT-TYPE
    SYNTAX CoriantTypesOduType 
    MAX-ACCESS read-only
    STATUS current
    DESCRIPTION "Level 1 ODU type
		
		
		"
::= { oduEntry 1 }
oduidL1 OBJECT-TYPE
    SYNTAX Unsigned32 
    MAX-ACCESS read-only
    STATUS current
    DESCRIPTION "Identifier of level 1 ODU
		
		
		"
::= { oduEntry 2 }
odutypeL2 OBJECT-TYPE
    SYNTAX CoriantTypesOduType 
    MAX-ACCESS read-only
    STATUS current
    DESCRIPTION "Level 2 ODU type
		
		
		"
::= { oduEntry 3 }
oduidL2 OBJECT-TYPE
    SYNTAX Unsigned32 
    MAX-ACCESS read-only
    STATUS current
    DESCRIPTION "Identifier of level 2 ODU
		
		
		"
::= { oduEntry 4 }
odutypeL3 OBJECT-TYPE
    SYNTAX CoriantTypesOduType 
    MAX-ACCESS read-only
    STATUS current
    DESCRIPTION "Level 3 ODU type
		
		
		"
::= { oduEntry 5 }
oduidL3 OBJECT-TYPE
    SYNTAX Unsigned32 
    MAX-ACCESS read-only
    STATUS current
    DESCRIPTION "Identifier of level 3 ODU
		
		
		"
::= { oduEntry 6 }
odutypeL4 OBJECT-TYPE
    SYNTAX CoriantTypesOduType 
    MAX-ACCESS read-only
    STATUS current
    DESCRIPTION "Level 4 ODU type
		
		
		"
::= { oduEntry 7 }
oduidL4 OBJECT-TYPE
    SYNTAX Unsigned32 
    MAX-ACCESS read-only
    STATUS current
    DESCRIPTION "Identifier of level 4 ODU
		
		
		"
::= { oduEntry 8 }
oduAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { oduEntry 9 }
oduOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { oduEntry 10 }
oduAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { oduEntry 11 }
oduAliasName OBJECT-TYPE
    SYNTAX OCTET STRING  (SIZE (0..256))
    MAX-ACCESS read-only
    STATUS current
    DESCRIPTION "User defined alias for this entity. Must be an alphanumeric string with dash or underscore
		
		
		"
::= { oduEntry 12 }
oduServiceLabel OBJECT-TYPE
    SYNTAX OCTET STRING  (SIZE (0..128))
    MAX-ACCESS read-only
    STATUS current
    DESCRIPTION "Path/service name of cross-connection related facility.
		
		
		"
::= { oduEntry 13 }
oduTribSlot OBJECT-TYPE
    SYNTAX CoriantTypesNumberList 
    MAX-ACCESS read-only
    STATUS current
    DESCRIPTION "Tributary slots of ODU, range 1 to 80
		
		
		"
::= { oduEntry 14 }
oduRxPayloadType OBJECT-TYPE
    SYNTAX OCTET STRING  (SIZE (0|4))
    MAX-ACCESS read-only
    STATUS current
    DESCRIPTION "Received payload-type of ODU
		
		
		"
::= { oduEntry 15 }
oduTxPayloadType OBJECT-TYPE
    SYNTAX OCTET STRING  (SIZE (0|4))
    MAX-ACCESS read-only
    STATUS current
    DESCRIPTION "Transmitter payload-type of ODU
		
		
		"
::= { oduEntry 16 }
oduNimEnable OBJECT-TYPE
    SYNTAX CoriantTypesEnableSwitch 
    MAX-ACCESS read-only
    STATUS current
    DESCRIPTION "The enable switching of nim function
		
		
		default value :enabled"
::= { oduEntry 17 }
oduDelayMeasurementEnable OBJECT-TYPE
    SYNTAX CoriantTypesEnableSwitch 
    MAX-ACCESS read-only
    STATUS current
    DESCRIPTION "The enable switching of delay-measurement function
		
		
		default value :disabled"
::= { oduEntry 18 }
oduOpuConfigActual OBJECT-TYPE
    SYNTAX INTEGER  {
	 notApplicable (0),
	 intact (1),
	 client (2),
	 mux (3)
	}
    MAX-ACCESS read-only
    STATUS current
    DESCRIPTION "The actual opu configuration type
		
		
		default value :not-applicable"
::= { oduEntry 19 }
oduClientSignalType OBJECT-TYPE
    SYNTAX INTEGER  {
	 notApplicable (0),
	 fc8g (1),
	 fc16g (2)
	}
    MAX-ACCESS read-only
    STATUS current
    DESCRIPTION "The ODUflex rate for special signal type
		
		
		default value :not-applicable"
::= { oduEntry 20 }
oduExpSapi OBJECT-TYPE
    SYNTAX OCTET STRING  (SIZE (0..15))
    MAX-ACCESS read-only
    STATUS current
    DESCRIPTION "The expected sapi(Source Access Point Identifier)
		
		
		"
::= { oduEntry 21 }
oduExpDapi OBJECT-TYPE
    SYNTAX OCTET STRING  (SIZE (0..15))
    MAX-ACCESS read-only
    STATUS current
    DESCRIPTION "The expected dapi(Destination Access Point Identifier)
		
		
		"
::= { oduEntry 22 }
oduExpOperator OBJECT-TYPE
    SYNTAX OCTET STRING  (SIZE (0..32))
    MAX-ACCESS read-only
    STATUS current
    DESCRIPTION "The expected operator TTI
		
		
		"
::= { oduEntry 23 }
oduTxSapi OBJECT-TYPE
    SYNTAX OCTET STRING  (SIZE (0..15))
    MAX-ACCESS read-only
    STATUS current
    DESCRIPTION "The transmitter sapi(Source Access Point Identifier)
		
		
		"
::= { oduEntry 24 }
oduTxDapi OBJECT-TYPE
    SYNTAX OCTET STRING  (SIZE (0..15))
    MAX-ACCESS read-only
    STATUS current
    DESCRIPTION "The transmitter dapi(Destination Access Point Identifier)
		
		
		"
::= { oduEntry 25 }
oduTxOperator OBJECT-TYPE
    SYNTAX OCTET STRING  (SIZE (0..32))
    MAX-ACCESS read-only
    STATUS current
    DESCRIPTION "The transmitter operator TTI
		
		
		"
::= { oduEntry 26 }
oduTimDefectMode OBJECT-TYPE
    SYNTAX CoriantTypesTimMode 
    MAX-ACCESS read-only
    STATUS current
    DESCRIPTION "The tim defect selection mode
		
		
		default value :NONE"
::= { oduEntry 27 }
oduTimAct OBJECT-TYPE
    SYNTAX CoriantTypesEnableSwitch 
    MAX-ACCESS read-only
    STATUS current
    DESCRIPTION "The enable switching of inserting AIS by tim function
		
		
		default value :disabled"
::= { oduEntry 28 }
oduRxSapi OBJECT-TYPE
    SYNTAX OCTET STRING  (SIZE (0..15))
    MAX-ACCESS read-only
    STATUS current
    DESCRIPTION "The received sapi(Source Access Point Identifier)
		
		
		"
::= { oduEntry 29 }
oduRxDapi OBJECT-TYPE
    SYNTAX OCTET STRING  (SIZE (0..15))
    MAX-ACCESS read-only
    STATUS current
    DESCRIPTION "The received dapi(Destination Access Point Identifier)
		
		
		"
::= { oduEntry 30 }
oduRxOperator OBJECT-TYPE
    SYNTAX OCTET STRING  (SIZE (0..32))
    MAX-ACCESS read-only
    STATUS current
    DESCRIPTION "The received operator TTI
		
		
		"
::= { oduEntry 31 }
oduDegradeInterval OBJECT-TYPE
    SYNTAX Unsigned32  (2..10)
    MAX-ACCESS read-only
    STATUS current
    DESCRIPTION "The consecutive number of 1s intervals with the number of detected block errors exceeding the block error threshold for each of those seconds for the purposes of SDBER detection.
		
		
		default value :7"
::= { oduEntry 32 }
oduDegradeThreshold OBJECT-TYPE
    SYNTAX Unsigned32  (1..2590845)
    MAX-ACCESS read-only
    STATUS current
    DESCRIPTION "The threshold number of block errors at which a 1s interval will be considered degraded for the purposes of SDBER detection.
		
		
		default value :1"
::= { oduEntry 33 }
oduTestSignalType OBJECT-TYPE
    SYNTAX CoriantTypesTestSignalType 
    MAX-ACCESS read-only
    STATUS current
    DESCRIPTION "The type mode of test signal.
		
		
		default value :NONE"
::= { oduEntry 34 }
oduTestSignalEnable OBJECT-TYPE
    SYNTAX CoriantTypesTestSignalConfig 
    MAX-ACCESS read-only
    STATUS current
    DESCRIPTION "The enable switching of test signal function
		
		
		default value :NONE"
::= { oduEntry 35 }
oduTerminationMode OBJECT-TYPE
    SYNTAX INTEGER  {
	 terminated (0),
	 nonTerminated (1)
	}
    MAX-ACCESS read-only
    STATUS current
    DESCRIPTION "Termination mode for ODU. It works for trace label, nim , Delay Measurement and test signal function validation
		
		
		default value :terminated"
::= { oduEntry 36 }
oduEncryption OBJECT IDENTIFIER ::= { otn 6 }
oduEncryptionTable OBJECT-TYPE
    SYNTAX SEQUENCE OF OduEncryptionEntry
    MAX-ACCESS not-accessible
    STATUS current
    DESCRIPTION "Encryption function for the ODU channel."
::= { oduEncryption 1 }
oduEncryptionEntry OBJECT-TYPE
    SYNTAX OduEncryptionEntry
    MAX-ACCESS not-accessible
    STATUS current
    DESCRIPTION "Entry of oduEncryptionTable" 
    INDEX { shelfId,slotId,subslotId,portId,subportId,odutypeL1,oduidL1,odutypeL2,oduidL2,odutypeL3,oduidL3,odutypeL4,oduidL4 }
::= { oduEncryptionTable 1 }
OduEncryptionEntry ::= 
SEQUENCE {
	oduEncryptionEncryptionEnable INTEGER,
	oduEncryptionBlockCipherMode INTEGER,
	oduEncryptionEncryptionInterval Unsigned32,
	oduEncryptionEncryptionTxStatus CoriantCommonOtnEncryStatusEnum,
	oduEncryptionEncryptionRxStatus CoriantCommonOtnEncryStatusEnum,
	oduEncryptionOduKeySyncSession CoriantCommonOtnKeySyncSession,
	oduEncryptionEncryptionTxChannelId OCTET STRING,
	oduEncryptionTimeToNextKey Unsigned32
    }
oduEncryptionEncryptionEnable OBJECT-TYPE
    SYNTAX INTEGER  {
	 enabled (1),
	 disabled (2),
	 enabledNonRevertive (3)
	}
    MAX-ACCESS read-only
    STATUS current
    DESCRIPTION "Setting AES-256 encryption on OTN
		
		
		default value :disabled"
::= { oduEncryptionEntry 1 }
oduEncryptionBlockCipherMode OBJECT-TYPE
    SYNTAX INTEGER  {
	 ctr (1),
	 gcm (2)
	}
    MAX-ACCESS read-only
    STATUS current
    DESCRIPTION "Specifies the block cipher mode of operation.
		
		
		default value :CTR"
::= { oduEncryptionEntry 2 }
oduEncryptionEncryptionInterval OBJECT-TYPE
    SYNTAX Unsigned32  (10..1440)
    MAX-ACCESS read-only
    STATUS current
    DESCRIPTION "The encryption key rotation interval (in minutes)
		
		UNITS:minutes
		default value :30"
::= { oduEncryptionEntry 3 }
oduEncryptionEncryptionTxStatus OBJECT-TYPE
    SYNTAX CoriantCommonOtnEncryStatusEnum 
    MAX-ACCESS read-only
    STATUS current
    DESCRIPTION "The encryption status at transmit side of the ODU,
	which reflects the status of both encryption data and communication sessions.
		
		
		"
::= { oduEncryptionEntry 4 }
oduEncryptionEncryptionRxStatus OBJECT-TYPE
    SYNTAX CoriantCommonOtnEncryStatusEnum 
    MAX-ACCESS read-only
    STATUS current
    DESCRIPTION "The encryption status at receive side of the ODU,
	which reflects the status of both encryption data and communication sessions.
		
		
		"
::= { oduEncryptionEntry 5 }
oduEncryptionOduKeySyncSession OBJECT-TYPE
    SYNTAX CoriantCommonOtnKeySyncSession 
    MAX-ACCESS read-only
    STATUS current
    DESCRIPTION "Indicate the associated session for the ODU channel to synchronize keys.
		
		
		default value :none"
::= { oduEncryptionEntry 6 }
oduEncryptionEncryptionTxChannelId OBJECT-TYPE
    SYNTAX OCTET STRING  (SIZE (0..32))
    MAX-ACCESS read-only
    STATUS current
    DESCRIPTION "Specify channel identifier of the encrypted ODU, which shall be unique within the NE.
		
		
		"
::= { oduEncryptionEntry 7 }
oduEncryptionTimeToNextKey OBJECT-TYPE
    SYNTAX Unsigned32 
    MAX-ACCESS read-only
    STATUS current
    DESCRIPTION "The time left to rotate the ODU encryption key.
		
		UNITS:seconds
		default value :0"
::= { oduEncryptionEntry 8 }
testSignalStatus OBJECT IDENTIFIER ::= { otn 7 }
testSignalStatusTable OBJECT-TYPE
    SYNTAX SEQUENCE OF TestSignalStatusEntry
    MAX-ACCESS not-accessible
    STATUS current
    DESCRIPTION "Test signal status on ODU"
::= { testSignalStatus 1 }
testSignalStatusEntry OBJECT-TYPE
    SYNTAX TestSignalStatusEntry
    MAX-ACCESS not-accessible
    STATUS current
    DESCRIPTION "Entry of testSignalStatusTable" 
    INDEX { shelfId,slotId,subslotId,portId,subportId,odutypeL1,oduidL1,odutypeL2,oduidL2,odutypeL3,oduidL3,odutypeL4,oduidL4 }
::= { testSignalStatusTable 1 }
TestSignalStatusEntry ::= 
SEQUENCE {
	testSignalStatusPrbsSync INTEGER,
	testSignalStatusTestTimeDuration Unsigned32,
	testSignalStatusPrbsBitErrorCount IetfYangTypesGauge64
    }
testSignalStatusPrbsSync OBJECT-TYPE
    SYNTAX INTEGER  {
	 notApplicable (0),
	 inSync (1),
	 outSync (2),
	 errSync (3)
	}
    MAX-ACCESS read-only
    STATUS current
    DESCRIPTION "The test result of PRBS Synchronization
		
		
		default value :not-applicable"
::= { testSignalStatusEntry 1 }
testSignalStatusTestTimeDuration OBJECT-TYPE
    SYNTAX Unsigned32 
    MAX-ACCESS read-only
    STATUS current
    DESCRIPTION "The time duration of signal test
		
		UNITS:seconds
		"
::= { testSignalStatusEntry 2 }
testSignalStatusPrbsBitErrorCount OBJECT-TYPE
    SYNTAX IetfYangTypesGauge64 
    MAX-ACCESS read-only
    STATUS current
    DESCRIPTION "The counting of bit error by PRBS Synchronization
		
		
		"
::= { testSignalStatusEntry 3 }
eth40g OBJECT IDENTIFIER ::= { otn 8 }
eth40gTable OBJECT-TYPE
    SYNTAX SEQUENCE OF Eth40gEntry
    MAX-ACCESS not-accessible
    STATUS current
    DESCRIPTION "
	Represents the 40GBE object.
	"
::= { eth40g 1 }
eth40gEntry OBJECT-TYPE
    SYNTAX Eth40gEntry
    MAX-ACCESS not-accessible
    STATUS current
    DESCRIPTION "Entry of eth40gTable" 
    INDEX { shelfId,slotId,subslotId,portId,subportId }
::= { eth40gTable 1 }
Eth40gEntry ::= 
SEQUENCE {
	eth40gEthFecType CoriantTypesEthFec,
	eth40gEthFecTypeState CoriantTypesEthFec,
	eth40gTransmitInterpacketgap Unsigned32,
	eth40gGfpPayloadFcs CoriantTypesEnableSwitch,
	eth40gMappingMode INTEGER,
	eth40gAdminStatus INTEGER,
	eth40gOperStatus INTEGER,
	eth40gAvailStatus BITS,
	eth40gAliasName OCTET STRING,
	eth40gClientShutdown CoriantTypesYesNo,
	eth40gClientShutdownHoldoffTimer Unsigned32,
	eth40gNearEndAls CoriantTypesYesNo,
	eth40gAlsDegradeMode CoriantTypesEnableSwitch,
	eth40gLoopbackEnable CoriantTypesEnableSwitch,
	eth40gLoopbackType INTEGER,
	eth40gTestSignalType CoriantTypesTestSignalType,
	eth40gTestSignalEnable CoriantTypesTestSignalConfig,
	eth40gServiceLabel OCTET STRING,
	eth40gLldpStatusIf INTEGER,
	eth40gHoldoffSignal CoriantTypesYesNo
    }
eth40gEthFecType OBJECT-TYPE
    SYNTAX CoriantTypesEthFec 
    MAX-ACCESS read-only
    STATUS current
    DESCRIPTION "
	The FEC working type of etyn port.
	
		
		
		default value :auto"
::= { eth40gEntry 1 }
eth40gEthFecTypeState OBJECT-TYPE
    SYNTAX CoriantTypesEthFec 
    MAX-ACCESS read-only
    STATUS current
    DESCRIPTION "
	The FEC working state of etyn port.
	
		
		
		default value :disabled"
::= { eth40gEntry 2 }
eth40gTransmitInterpacketgap OBJECT-TYPE
    SYNTAX Unsigned32  (8..12)
    MAX-ACCESS read-only
    STATUS current
    DESCRIPTION "
	Specifies the minimum transmit IPG value.
	
		
		
		default value :8"
::= { eth40gEntry 3 }
eth40gGfpPayloadFcs OBJECT-TYPE
    SYNTAX CoriantTypesEnableSwitch 
    MAX-ACCESS read-only
    STATUS current
    DESCRIPTION "
	Enabled: GFP payload FCS will be used, Ethernet frame FCS will be removed; 
	Disabled: GFP payload FCS will not be inserted, Ethernet frame FCS will be used.
	
		
		
		default value :disabled"
::= { eth40gEntry 4 }
eth40gMappingMode OBJECT-TYPE
    SYNTAX INTEGER  {
	 notApplicable (0),
	 gmp (1),
	 gfpF (2),
	 t40gbmpOdu2e (3),
	 preamble (4),
	 bmpFixedstuff (5),
	 bmp (6),
	 amp (7)
	}
    MAX-ACCESS read-only
    STATUS current
    DESCRIPTION "The mapping mode of client port packets into ODUk.
		
		
		default value :not-applicable"
::= { eth40gEntry 5 }
eth40gAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { eth40gEntry 6 }
eth40gOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { eth40gEntry 7 }
eth40gAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { eth40gEntry 8 }
eth40gAliasName OBJECT-TYPE
    SYNTAX OCTET STRING  (SIZE (0..256))
    MAX-ACCESS read-only
    STATUS current
    DESCRIPTION "User defined alias for this entity. Must be an alphanumeric string with dash or underscore
		
		
		"
::= { eth40gEntry 9 }
eth40gClientShutdown OBJECT-TYPE
    SYNTAX CoriantTypesYesNo 
    MAX-ACCESS read-only
    STATUS current
    DESCRIPTION "The switching of client-shutdown.
		
		
		default value :no"
::= { eth40gEntry 10 }
eth40gClientShutdownHoldoffTimer OBJECT-TYPE
    SYNTAX Unsigned32  (0..1000)
    MAX-ACCESS read-only
    STATUS current
    DESCRIPTION "The hold off time of client shutdown or replacement siganl at egress direction.
		
		UNITS:milliseconds
		default value :0"
::= { eth40gEntry 11 }
eth40gNearEndAls OBJECT-TYPE
    SYNTAX CoriantTypesYesNo 
    MAX-ACCESS read-only
    STATUS current
    DESCRIPTION "The switching of near end ALS.
		
		
		default value :no"
::= { eth40gEntry 12 }
eth40gAlsDegradeMode OBJECT-TYPE
    SYNTAX CoriantTypesEnableSwitch 
    MAX-ACCESS read-only
    STATUS current
    DESCRIPTION "The switching of defect BERSD-ODU trig ALS
		
		
		default value :disabled"
::= { eth40gEntry 13 }
eth40gLoopbackEnable OBJECT-TYPE
    SYNTAX CoriantTypesEnableSwitch 
    MAX-ACCESS read-only
    STATUS current
    DESCRIPTION "The enable switching of loopback function.
		
		
		default value :disabled"
::= { eth40gEntry 14 }
eth40gLoopbackType OBJECT-TYPE
    SYNTAX INTEGER  {
	 none (0),
	 terminal (1),
	 facility (2)
	}
    MAX-ACCESS read-only
    STATUS current
    DESCRIPTION "The type mode of loopback function
		
		
		default value :none"
::= { eth40gEntry 15 }
eth40gTestSignalType OBJECT-TYPE
    SYNTAX CoriantTypesTestSignalType 
    MAX-ACCESS read-only
    STATUS current
    DESCRIPTION "The type mode of test signal.
		
		
		default value :NONE"
::= { eth40gEntry 16 }
eth40gTestSignalEnable OBJECT-TYPE
    SYNTAX CoriantTypesTestSignalConfig 
    MAX-ACCESS read-only
    STATUS current
    DESCRIPTION "The enable switching of test signal function
		
		
		default value :NONE"
::= { eth40gEntry 17 }
eth40gServiceLabel OBJECT-TYPE
    SYNTAX OCTET STRING  (SIZE (0..128))
    MAX-ACCESS read-only
    STATUS current
    DESCRIPTION "Path/service name of cross-connection related facility.
		
		
		"
::= { eth40gEntry 18 }
eth40gLldpStatusIf OBJECT-TYPE
    SYNTAX INTEGER  {
	 notApplicable (0),
	 rxonly (2),
	 disabled (4)
	}
    MAX-ACCESS read-only
    STATUS current
    DESCRIPTION "
	Port level lldp control. 
	Value of 'rxonly', then the LLDP agent will receive lldp,
	when lldp-status-ne is also enabled. 
	                    
	Value of 'disabled', then LLDP agent will not filter and
	receive LLDP frames on this port.  If there is remote systems
	information which is received on this port and stored in
	the system before the lldp-status   becomes disabled, 
	then the information will naturally age out.    
	
	Note: txOnly and txAndRx modes are not supported.
	                    
	
		
		
		default value :disabled"
::= { eth40gEntry 19 }
eth40gHoldoffSignal OBJECT-TYPE
    SYNTAX CoriantTypesYesNo 
    MAX-ACCESS read-only
    STATUS current
    DESCRIPTION "Specify if specific signal will be sent out during hold off time
	which avoid downstream equipment consequent action in the duration.
		
		
		default value :no"
::= { eth40gEntry 20 }
eth100g OBJECT IDENTIFIER ::= { otn 9 }
eth100gTable OBJECT-TYPE
    SYNTAX SEQUENCE OF Eth100gEntry
    MAX-ACCESS not-accessible
    STATUS current
    DESCRIPTION "Represents the 100GBE object."
::= { eth100g 1 }
eth100gEntry OBJECT-TYPE
    SYNTAX Eth100gEntry
    MAX-ACCESS not-accessible
    STATUS current
    DESCRIPTION "Entry of eth100gTable" 
    INDEX { shelfId,slotId,subslotId,portId,subportId }
::= { eth100gTable 1 }
Eth100gEntry ::= 
SEQUENCE {
	eth100gEthFecType CoriantTypesEthFec,
	eth100gEthFecTypeState CoriantTypesEthFec,
	eth100gTransmitInterpacketgap Unsigned32,
	eth100gGfpPayloadFcs CoriantTypesEnableSwitch,
	eth100gMappingMode INTEGER,
	eth100gAdminStatus INTEGER,
	eth100gOperStatus INTEGER,
	eth100gAvailStatus BITS,
	eth100gAliasName OCTET STRING,
	eth100gClientShutdown CoriantTypesYesNo,
	eth100gClientShutdownHoldoffTimer Unsigned32,
	eth100gNearEndAls CoriantTypesYesNo,
	eth100gAlsDegradeMode CoriantTypesEnableSwitch,
	eth100gLoopbackEnable CoriantTypesEnableSwitch,
	eth100gLoopbackType INTEGER,
	eth100gTestSignalType CoriantTypesTestSignalType,
	eth100gTestSignalEnable CoriantTypesTestSignalConfig,
	eth100gServiceLabel OCTET STRING,
	eth100gLldpStatusIf INTEGER,
	eth100gHoldoffSignal CoriantTypesYesNo
    }
eth100gEthFecType OBJECT-TYPE
    SYNTAX CoriantTypesEthFec 
    MAX-ACCESS read-only
    STATUS current
    DESCRIPTION "
	The FEC working type of etyn port.
	
		
		
		default value :auto"
::= { eth100gEntry 1 }
eth100gEthFecTypeState OBJECT-TYPE
    SYNTAX CoriantTypesEthFec 
    MAX-ACCESS read-only
    STATUS current
    DESCRIPTION "
	The FEC working state of etyn port.
	
		
		
		default value :disabled"
::= { eth100gEntry 2 }
eth100gTransmitInterpacketgap OBJECT-TYPE
    SYNTAX Unsigned32  (8..12)
    MAX-ACCESS read-only
    STATUS current
    DESCRIPTION "
	Specifies the minimum transmit IPG value.
	
		
		
		default value :8"
::= { eth100gEntry 3 }
eth100gGfpPayloadFcs OBJECT-TYPE
    SYNTAX CoriantTypesEnableSwitch 
    MAX-ACCESS read-only
    STATUS current
    DESCRIPTION "
	Enabled: GFP payload FCS will be used, Ethernet frame FCS will be removed; 
	Disabled: GFP payload FCS will not be inserted, Ethernet frame FCS will be used.
	
		
		
		default value :disabled"
::= { eth100gEntry 4 }
eth100gMappingMode OBJECT-TYPE
    SYNTAX INTEGER  {
	 notApplicable (0),
	 gmp (1),
	 gfpF (2),
	 t40gbmpOdu2e (3),
	 preamble (4),
	 bmpFixedstuff (5),
	 bmp (6),
	 amp (7)
	}
    MAX-ACCESS read-only
    STATUS current
    DESCRIPTION "The mapping mode of client port packets into ODUk.
		
		
		default value :not-applicable"
::= { eth100gEntry 5 }
eth100gAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { eth100gEntry 6 }
eth100gOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { eth100gEntry 7 }
eth100gAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { eth100gEntry 8 }
eth100gAliasName OBJECT-TYPE
    SYNTAX OCTET STRING  (SIZE (0..256))
    MAX-ACCESS read-only
    STATUS current
    DESCRIPTION "User defined alias for this entity. Must be an alphanumeric string with dash or underscore
		
		
		"
::= { eth100gEntry 9 }
eth100gClientShutdown OBJECT-TYPE
    SYNTAX CoriantTypesYesNo 
    MAX-ACCESS read-only
    STATUS current
    DESCRIPTION "The switching of client-shutdown.
		
		
		default value :no"
::= { eth100gEntry 10 }
eth100gClientShutdownHoldoffTimer OBJECT-TYPE
    SYNTAX Unsigned32  (0..1000)
    MAX-ACCESS read-only
    STATUS current
    DESCRIPTION "The hold off time of client shutdown or replacement siganl at egress direction.
		
		UNITS:milliseconds
		default value :0"
::= { eth100gEntry 11 }
eth100gNearEndAls OBJECT-TYPE
    SYNTAX CoriantTypesYesNo 
    MAX-ACCESS read-only
    STATUS current
    DESCRIPTION "The switching of near end ALS.
		
		
		default value :no"
::= { eth100gEntry 12 }
eth100gAlsDegradeMode OBJECT-TYPE
    SYNTAX CoriantTypesEnableSwitch 
    MAX-ACCESS read-only
    STATUS current
    DESCRIPTION "The switching of defect BERSD-ODU trig ALS
		
		
		default value :disabled"
::= { eth100gEntry 13 }
eth100gLoopbackEnable OBJECT-TYPE
    SYNTAX CoriantTypesEnableSwitch 
    MAX-ACCESS read-only
    STATUS current
    DESCRIPTION "The enable switching of loopback function.
		
		
		default value :disabled"
::= { eth100gEntry 14 }
eth100gLoopbackType OBJECT-TYPE
    SYNTAX INTEGER  {
	 none (0),
	 terminal (1),
	 facility (2)
	}
    MAX-ACCESS read-only
    STATUS current
    DESCRIPTION "The type mode of loopback function
		
		
		default value :none"
::= { eth100gEntry 15 }
eth100gTestSignalType OBJECT-TYPE
    SYNTAX CoriantTypesTestSignalType 
    MAX-ACCESS read-only
    STATUS current
    DESCRIPTION "The type mode of test signal.
		
		
		default value :NONE"
::= { eth100gEntry 16 }
eth100gTestSignalEnable OBJECT-TYPE
    SYNTAX CoriantTypesTestSignalConfig 
    MAX-ACCESS read-only
    STATUS current
    DESCRIPTION "The enable switching of test signal function
		
		
		default value :NONE"
::= { eth100gEntry 17 }
eth100gServiceLabel OBJECT-TYPE
    SYNTAX OCTET STRING  (SIZE (0..128))
    MAX-ACCESS read-only
    STATUS current
    DESCRIPTION "Path/service name of cross-connection related facility.
		
		
		"
::= { eth100gEntry 18 }
eth100gLldpStatusIf OBJECT-TYPE
    SYNTAX INTEGER  {
	 notApplicable (0),
	 rxonly (2),
	 disabled (4)
	}
    MAX-ACCESS read-only
    STATUS current
    DESCRIPTION "
	Port level lldp control. 
	Value of 'rxonly', then the LLDP agent will receive lldp,
	when lldp-status-ne is also enabled. 
	                    
	Value of 'disabled', then LLDP agent will not filter and
	receive LLDP frames on this port.  If there is remote systems
	information which is received on this port and stored in
	the system before the lldp-status   becomes disabled, 
	then the information will naturally age out.    
	
	Note: txOnly and txAndRx modes are not supported.
	                    
	
		
		
		default value :disabled"
::= { eth100gEntry 19 }
eth100gHoldoffSignal OBJECT-TYPE
    SYNTAX CoriantTypesYesNo 
    MAX-ACCESS read-only
    STATUS current
    DESCRIPTION "Specify if specific signal will be sent out during hold off time
	which avoid downstream equipment consequent action in the duration.
		
		
		default value :no"
::= { eth100gEntry 20 }
otu4 OBJECT IDENTIFIER ::= { otn 10 }
otu4Table OBJECT-TYPE
    SYNTAX SEQUENCE OF Otu4Entry
    MAX-ACCESS not-accessible
    STATUS current
    DESCRIPTION "Represents the otu4 object"
::= { otu4 1 }
otu4Entry OBJECT-TYPE
    SYNTAX Otu4Entry
    MAX-ACCESS not-accessible
    STATUS current
    DESCRIPTION "Entry of otu4Table" 
    INDEX { shelfId,slotId,subslotId,portId,subportId }
::= { otu4Table 1 }
Otu4Entry ::= 
SEQUENCE {
	otu4FecType CoriantTypesOtukFec,
	otu4AdminStatus INTEGER,
	otu4OperStatus INTEGER,
	otu4AvailStatus BITS,
	otu4AliasName OCTET STRING,
	otu4ServiceLabel OCTET STRING,
	otu4ExpSapi OCTET STRING,
	otu4ExpDapi OCTET STRING,
	otu4ExpOperator OCTET STRING,
	otu4TxSapi OCTET STRING,
	otu4TxDapi OCTET STRING,
	otu4TxOperator OCTET STRING,
	otu4TimDefectMode CoriantTypesTimMode,
	otu4TimAct CoriantTypesEnableSwitch,
	otu4RxSapi OCTET STRING,
	otu4RxDapi OCTET STRING,
	otu4RxOperator OCTET STRING,
	otu4DegradeInterval Unsigned32,
	otu4DegradeThreshold Unsigned32,
	otu4LoopbackEnable CoriantTypesEnableSwitch,
	otu4LoopbackType INTEGER,
	otu4ClientShutdown CoriantTypesYesNo,
	otu4ClientShutdownHoldoffTimer Unsigned32,
	otu4HoldoffSignal CoriantTypesYesNo,
	otu4NearEndAls CoriantTypesYesNo,
	otu4AlsDegradeMode CoriantTypesEnableSwitch
    }
otu4FecType OBJECT-TYPE
    SYNTAX CoriantTypesOtukFec 
    MAX-ACCESS read-only
    STATUS current
    DESCRIPTION "
	The FEC type of client OTUk.
	
		Conditions:(ancestor::port/port-type = 'client') or (ancestor::port/port-type = 'client-subport')
		
		default value :G709"
::= { otu4Entry 1 }
otu4AdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { otu4Entry 2 }
otu4OperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { otu4Entry 3 }
otu4AvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { otu4Entry 4 }
otu4AliasName OBJECT-TYPE
    SYNTAX OCTET STRING  (SIZE (0..256))
    MAX-ACCESS read-only
    STATUS current
    DESCRIPTION "User defined alias for this entity. Must be an alphanumeric string with dash or underscore
		
		
		"
::= { otu4Entry 5 }
otu4ServiceLabel OBJECT-TYPE
    SYNTAX OCTET STRING  (SIZE (0..128))
    MAX-ACCESS read-only
    STATUS current
    DESCRIPTION "Path/service name of cross-connection related facility.
		
		
		"
::= { otu4Entry 6 }
otu4ExpSapi OBJECT-TYPE
    SYNTAX OCTET STRING  (SIZE (0..15))
    MAX-ACCESS read-only
    STATUS current
    DESCRIPTION "The expected sapi(Source Access Point Identifier)
		
		
		"
::= { otu4Entry 7 }
otu4ExpDapi OBJECT-TYPE
    SYNTAX OCTET STRING  (SIZE (0..15))
    MAX-ACCESS read-only
    STATUS current
    DESCRIPTION "The expected dapi(Destination Access Point Identifier)
		
		
		"
::= { otu4Entry 8 }
otu4ExpOperator OBJECT-TYPE
    SYNTAX OCTET STRING  (SIZE (0..32))
    MAX-ACCESS read-only
    STATUS current
    DESCRIPTION "The expected operator TTI
		
		
		"
::= { otu4Entry 9 }
otu4TxSapi OBJECT-TYPE
    SYNTAX OCTET STRING  (SIZE (0..15))
    MAX-ACCESS read-only
    STATUS current
    DESCRIPTION "The transmitter sapi(Source Access Point Identifier)
		
		
		"
::= { otu4Entry 10 }
otu4TxDapi OBJECT-TYPE
    SYNTAX OCTET STRING  (SIZE (0..15))
    MAX-ACCESS read-only
    STATUS current
    DESCRIPTION "The transmitter dapi(Destination Access Point Identifier)
		
		
		"
::= { otu4Entry 11 }
otu4TxOperator OBJECT-TYPE
    SYNTAX OCTET STRING  (SIZE (0..32))
    MAX-ACCESS read-only
    STATUS current
    DESCRIPTION "The transmitter operator TTI
		
		
		"
::= { otu4Entry 12 }
otu4TimDefectMode OBJECT-TYPE
    SYNTAX CoriantTypesTimMode 
    MAX-ACCESS read-only
    STATUS current
    DESCRIPTION "The tim defect selection mode
		
		
		default value :NONE"
::= { otu4Entry 13 }
otu4TimAct OBJECT-TYPE
    SYNTAX CoriantTypesEnableSwitch 
    MAX-ACCESS read-only
    STATUS current
    DESCRIPTION "The enable switching of inserting AIS by tim function
		
		
		default value :disabled"
::= { otu4Entry 14 }
otu4RxSapi OBJECT-TYPE
    SYNTAX OCTET STRING  (SIZE (0..15))
    MAX-ACCESS read-only
    STATUS current
    DESCRIPTION "The received sapi(Source Access Point Identifier)
		
		
		"
::= { otu4Entry 15 }
otu4RxDapi OBJECT-TYPE
    SYNTAX OCTET STRING  (SIZE (0..15))
    MAX-ACCESS read-only
    STATUS current
    DESCRIPTION "The received dapi(Destination Access Point Identifier)
		
		
		"
::= { otu4Entry 16 }
otu4RxOperator OBJECT-TYPE
    SYNTAX OCTET STRING  (SIZE (0..32))
    MAX-ACCESS read-only
    STATUS current
    DESCRIPTION "The received operator TTI
		
		
		"
::= { otu4Entry 17 }
otu4DegradeInterval OBJECT-TYPE
    SYNTAX Unsigned32  (2..10)
    MAX-ACCESS read-only
    STATUS current
    DESCRIPTION "The consecutive number of 1s intervals with the number of detected block errors exceeding the block error threshold for each of those seconds for the purposes of SDBER detection.
		
		
		default value :7"
::= { otu4Entry 18 }
otu4DegradeThreshold OBJECT-TYPE
    SYNTAX Unsigned32  (1..2590845)
    MAX-ACCESS read-only
    STATUS current
    DESCRIPTION "The threshold number of block errors at which a 1s interval will be considered degraded for the purposes of SDBER detection.
		
		
		default value :1"
::= { otu4Entry 19 }
otu4LoopbackEnable OBJECT-TYPE
    SYNTAX CoriantTypesEnableSwitch 
    MAX-ACCESS read-only
    STATUS current
    DESCRIPTION "The enable switching of loopback function.
		
		
		default value :disabled"
::= { otu4Entry 20 }
otu4LoopbackType OBJECT-TYPE
    SYNTAX INTEGER  {
	 none (0),
	 terminal (1),
	 facility (2)
	}
    MAX-ACCESS read-only
    STATUS current
    DESCRIPTION "The type mode of loopback function
		
		
		default value :none"
::= { otu4Entry 21 }
otu4ClientShutdown OBJECT-TYPE
    SYNTAX CoriantTypesYesNo 
    MAX-ACCESS read-only
    STATUS current
    DESCRIPTION "The switching of client-shutdown.
		
		
		default value :no"
::= { otu4Entry 22 }
otu4ClientShutdownHoldoffTimer OBJECT-TYPE
    SYNTAX Unsigned32  (0..1000)
    MAX-ACCESS read-only
    STATUS current
    DESCRIPTION "The hold off time of client shutdown or replacement siganl at egress direction.
		
		UNITS:milliseconds
		default value :0"
::= { otu4Entry 23 }
otu4HoldoffSignal OBJECT-TYPE
    SYNTAX CoriantTypesYesNo 
    MAX-ACCESS read-only
    STATUS current
    DESCRIPTION "Specify if specific signal will be sent out during hold off time
	which avoid downstream equipment consequent action in the duration.
		
		
		default value :no"
::= { otu4Entry 24 }
otu4NearEndAls OBJECT-TYPE
    SYNTAX CoriantTypesYesNo 
    MAX-ACCESS read-only
    STATUS current
    DESCRIPTION "The switching of near end ALS.
		
		
		default value :no"
::= { otu4Entry 25 }
otu4AlsDegradeMode OBJECT-TYPE
    SYNTAX CoriantTypesEnableSwitch 
    MAX-ACCESS read-only
    STATUS current
    DESCRIPTION "The switching of defect BERSD-ODU trig ALS
		
		
		default value :disabled"
::= { otu4Entry 26 }
otu2 OBJECT IDENTIFIER ::= { otn 11 }
otu2Table OBJECT-TYPE
    SYNTAX SEQUENCE OF Otu2Entry
    MAX-ACCESS not-accessible
    STATUS current
    DESCRIPTION "Represents the otu2 object"
::= { otu2 1 }
otu2Entry OBJECT-TYPE
    SYNTAX Otu2Entry
    MAX-ACCESS not-accessible
    STATUS current
    DESCRIPTION "Entry of otu2Table" 
    INDEX { shelfId,slotId,subslotId,portId,subportId }
::= { otu2Table 1 }
Otu2Entry ::= 
SEQUENCE {
	otu2FecType CoriantTypesOtukFec,
	otu2AdminStatus INTEGER,
	otu2OperStatus INTEGER,
	otu2AvailStatus BITS,
	otu2AliasName OCTET STRING,
	otu2ServiceLabel OCTET STRING,
	otu2ExpSapi OCTET STRING,
	otu2ExpDapi OCTET STRING,
	otu2ExpOperator OCTET STRING,
	otu2TxSapi OCTET STRING,
	otu2TxDapi OCTET STRING,
	otu2TxOperator OCTET STRING,
	otu2TimDefectMode CoriantTypesTimMode,
	otu2TimAct CoriantTypesEnableSwitch,
	otu2RxSapi OCTET STRING,
	otu2RxDapi OCTET STRING,
	otu2RxOperator OCTET STRING,
	otu2DegradeInterval Unsigned32,
	otu2DegradeThreshold Unsigned32,
	otu2LoopbackEnable CoriantTypesEnableSwitch,
	otu2LoopbackType INTEGER
    }
otu2FecType OBJECT-TYPE
    SYNTAX CoriantTypesOtukFec 
    MAX-ACCESS read-only
    STATUS current
    DESCRIPTION "
	The FEC type of client OTUk.
	
		Conditions:(ancestor::port/port-type = 'client') or (ancestor::port/port-type = 'client-subport')
		
		default value :G709"
::= { otu2Entry 1 }
otu2AdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { otu2Entry 2 }
otu2OperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { otu2Entry 3 }
otu2AvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { otu2Entry 4 }
otu2AliasName OBJECT-TYPE
    SYNTAX OCTET STRING  (SIZE (0..256))
    MAX-ACCESS read-only
    STATUS current
    DESCRIPTION "User defined alias for this entity. Must be an alphanumeric string with dash or underscore
		
		
		"
::= { otu2Entry 5 }
otu2ServiceLabel OBJECT-TYPE
    SYNTAX OCTET STRING  (SIZE (0..128))
    MAX-ACCESS read-only
    STATUS current
    DESCRIPTION "Path/service name of cross-connection related facility.
		
		
		"
::= { otu2Entry 6 }
otu2ExpSapi OBJECT-TYPE
    SYNTAX OCTET STRING  (SIZE (0..15))
    MAX-ACCESS read-only
    STATUS current
    DESCRIPTION "The expected sapi(Source Access Point Identifier)
		
		
		"
::= { otu2Entry 7 }
otu2ExpDapi OBJECT-TYPE
    SYNTAX OCTET STRING  (SIZE (0..15))
    MAX-ACCESS read-only
    STATUS current
    DESCRIPTION "The expected dapi(Destination Access Point Identifier)
		
		
		"
::= { otu2Entry 8 }
otu2ExpOperator OBJECT-TYPE
    SYNTAX OCTET STRING  (SIZE (0..32))
    MAX-ACCESS read-only
    STATUS current
    DESCRIPTION "The expected operator TTI
		
		
		"
::= { otu2Entry 9 }
otu2TxSapi OBJECT-TYPE
    SYNTAX OCTET STRING  (SIZE (0..15))
    MAX-ACCESS read-only
    STATUS current
    DESCRIPTION "The transmitter sapi(Source Access Point Identifier)
		
		
		"
::= { otu2Entry 10 }
otu2TxDapi OBJECT-TYPE
    SYNTAX OCTET STRING  (SIZE (0..15))
    MAX-ACCESS read-only
    STATUS current
    DESCRIPTION "The transmitter dapi(Destination Access Point Identifier)
		
		
		"
::= { otu2Entry 11 }
otu2TxOperator OBJECT-TYPE
    SYNTAX OCTET STRING  (SIZE (0..32))
    MAX-ACCESS read-only
    STATUS current
    DESCRIPTION "The transmitter operator TTI
		
		
		"
::= { otu2Entry 12 }
otu2TimDefectMode OBJECT-TYPE
    SYNTAX CoriantTypesTimMode 
    MAX-ACCESS read-only
    STATUS current
    DESCRIPTION "The tim defect selection mode
		
		
		default value :NONE"
::= { otu2Entry 13 }
otu2TimAct OBJECT-TYPE
    SYNTAX CoriantTypesEnableSwitch 
    MAX-ACCESS read-only
    STATUS current
    DESCRIPTION "The enable switching of inserting AIS by tim function
		
		
		default value :disabled"
::= { otu2Entry 14 }
otu2RxSapi OBJECT-TYPE
    SYNTAX OCTET STRING  (SIZE (0..15))
    MAX-ACCESS read-only
    STATUS current
    DESCRIPTION "The received sapi(Source Access Point Identifier)
		
		
		"
::= { otu2Entry 15 }
otu2RxDapi OBJECT-TYPE
    SYNTAX OCTET STRING  (SIZE (0..15))
    MAX-ACCESS read-only
    STATUS current
    DESCRIPTION "The received dapi(Destination Access Point Identifier)
		
		
		"
::= { otu2Entry 16 }
otu2RxOperator OBJECT-TYPE
    SYNTAX OCTET STRING  (SIZE (0..32))
    MAX-ACCESS read-only
    STATUS current
    DESCRIPTION "The received operator TTI
		
		
		"
::= { otu2Entry 17 }
otu2DegradeInterval OBJECT-TYPE
    SYNTAX Unsigned32  (2..10)
    MAX-ACCESS read-only
    STATUS current
    DESCRIPTION "The consecutive number of 1s intervals with the number of detected block errors exceeding the block error threshold for each of those seconds for the purposes of SDBER detection.
		
		
		default value :7"
::= { otu2Entry 18 }
otu2DegradeThreshold OBJECT-TYPE
    SYNTAX Unsigned32  (1..2590845)
    MAX-ACCESS read-only
    STATUS current
    DESCRIPTION "The threshold number of block errors at which a 1s interval will be considered degraded for the purposes of SDBER detection.
		
		
		default value :1"
::= { otu2Entry 19 }
otu2LoopbackEnable OBJECT-TYPE
    SYNTAX CoriantTypesEnableSwitch 
    MAX-ACCESS read-only
    STATUS current
    DESCRIPTION "The enable switching of loopback function.
		
		
		default value :disabled"
::= { otu2Entry 20 }
otu2LoopbackType OBJECT-TYPE
    SYNTAX INTEGER  {
	 none (0),
	 terminal (1),
	 facility (2)
	}
    MAX-ACCESS read-only
    STATUS current
    DESCRIPTION "The type mode of loopback function
		
		
		default value :none"
::= { otu2Entry 21 }
otu2e OBJECT IDENTIFIER ::= { otn 12 }
otu2eTable OBJECT-TYPE
    SYNTAX SEQUENCE OF Otu2eEntry
    MAX-ACCESS not-accessible
    STATUS current
    DESCRIPTION "Represents the otu2e object"
::= { otu2e 1 }
otu2eEntry OBJECT-TYPE
    SYNTAX Otu2eEntry
    MAX-ACCESS not-accessible
    STATUS current
    DESCRIPTION "Entry of otu2eTable" 
    INDEX { shelfId,slotId,subslotId,portId,subportId }
::= { otu2eTable 1 }
Otu2eEntry ::= 
SEQUENCE {
	otu2eFecType CoriantTypesOtukFec,
	otu2eAdminStatus INTEGER,
	otu2eOperStatus INTEGER,
	otu2eAvailStatus BITS,
	otu2eAliasName OCTET STRING,
	otu2eServiceLabel OCTET STRING,
	otu2eExpSapi OCTET STRING,
	otu2eExpDapi OCTET STRING,
	otu2eExpOperator OCTET STRING,
	otu2eTxSapi OCTET STRING,
	otu2eTxDapi OCTET STRING,
	otu2eTxOperator OCTET STRING,
	otu2eTimDefectMode CoriantTypesTimMode,
	otu2eTimAct CoriantTypesEnableSwitch,
	otu2eRxSapi OCTET STRING,
	otu2eRxDapi OCTET STRING,
	otu2eRxOperator OCTET STRING,
	otu2eDegradeInterval Unsigned32,
	otu2eDegradeThreshold Unsigned32,
	otu2eLoopbackEnable CoriantTypesEnableSwitch,
	otu2eLoopbackType INTEGER
    }
otu2eFecType OBJECT-TYPE
    SYNTAX CoriantTypesOtukFec 
    MAX-ACCESS read-only
    STATUS current
    DESCRIPTION "
	The FEC type of client OTUk.
	
		Conditions:(ancestor::port/port-type = 'client') or (ancestor::port/port-type = 'client-subport')
		
		default value :G709"
::= { otu2eEntry 1 }
otu2eAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { otu2eEntry 2 }
otu2eOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { otu2eEntry 3 }
otu2eAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { otu2eEntry 4 }
otu2eAliasName OBJECT-TYPE
    SYNTAX OCTET STRING  (SIZE (0..256))
    MAX-ACCESS read-only
    STATUS current
    DESCRIPTION "User defined alias for this entity. Must be an alphanumeric string with dash or underscore
		
		
		"
::= { otu2eEntry 5 }
otu2eServiceLabel OBJECT-TYPE
    SYNTAX OCTET STRING  (SIZE (0..128))
    MAX-ACCESS read-only
    STATUS current
    DESCRIPTION "Path/service name of cross-connection related facility.
		
		
		"
::= { otu2eEntry 6 }
otu2eExpSapi OBJECT-TYPE
    SYNTAX OCTET STRING  (SIZE (0..15))
    MAX-ACCESS read-only
    STATUS current
    DESCRIPTION "The expected sapi(Source Access Point Identifier)
		
		
		"
::= { otu2eEntry 7 }
otu2eExpDapi OBJECT-TYPE
    SYNTAX OCTET STRING  (SIZE (0..15))
    MAX-ACCESS read-only
    STATUS current
    DESCRIPTION "The expected dapi(Destination Access Point Identifier)
		
		
		"
::= { otu2eEntry 8 }
otu2eExpOperator OBJECT-TYPE
    SYNTAX OCTET STRING  (SIZE (0..32))
    MAX-ACCESS read-only
    STATUS current
    DESCRIPTION "The expected operator TTI
		
		
		"
::= { otu2eEntry 9 }
otu2eTxSapi OBJECT-TYPE
    SYNTAX OCTET STRING  (SIZE (0..15))
    MAX-ACCESS read-only
    STATUS current
    DESCRIPTION "The transmitter sapi(Source Access Point Identifier)
		
		
		"
::= { otu2eEntry 10 }
otu2eTxDapi OBJECT-TYPE
    SYNTAX OCTET STRING  (SIZE (0..15))
    MAX-ACCESS read-only
    STATUS current
    DESCRIPTION "The transmitter dapi(Destination Access Point Identifier)
		
		
		"
::= { otu2eEntry 11 }
otu2eTxOperator OBJECT-TYPE
    SYNTAX OCTET STRING  (SIZE (0..32))
    MAX-ACCESS read-only
    STATUS current
    DESCRIPTION "The transmitter operator TTI
		
		
		"
::= { otu2eEntry 12 }
otu2eTimDefectMode OBJECT-TYPE
    SYNTAX CoriantTypesTimMode 
    MAX-ACCESS read-only
    STATUS current
    DESCRIPTION "The tim defect selection mode
		
		
		default value :NONE"
::= { otu2eEntry 13 }
otu2eTimAct OBJECT-TYPE
    SYNTAX CoriantTypesEnableSwitch 
    MAX-ACCESS read-only
    STATUS current
    DESCRIPTION "The enable switching of inserting AIS by tim function
		
		
		default value :disabled"
::= { otu2eEntry 14 }
otu2eRxSapi OBJECT-TYPE
    SYNTAX OCTET STRING  (SIZE (0..15))
    MAX-ACCESS read-only
    STATUS current
    DESCRIPTION "The received sapi(Source Access Point Identifier)
		
		
		"
::= { otu2eEntry 15 }
otu2eRxDapi OBJECT-TYPE
    SYNTAX OCTET STRING  (SIZE (0..15))
    MAX-ACCESS read-only
    STATUS current
    DESCRIPTION "The received dapi(Destination Access Point Identifier)
		
		
		"
::= { otu2eEntry 16 }
otu2eRxOperator OBJECT-TYPE
    SYNTAX OCTET STRING  (SIZE (0..32))
    MAX-ACCESS read-only
    STATUS current
    DESCRIPTION "The received operator TTI
		
		
		"
::= { otu2eEntry 17 }
otu2eDegradeInterval OBJECT-TYPE
    SYNTAX Unsigned32  (2..10)
    MAX-ACCESS read-only
    STATUS current
    DESCRIPTION "The consecutive number of 1s intervals with the number of detected block errors exceeding the block error threshold for each of those seconds for the purposes of SDBER detection.
		
		
		default value :7"
::= { otu2eEntry 18 }
otu2eDegradeThreshold OBJECT-TYPE
    SYNTAX Unsigned32  (1..2590845)
    MAX-ACCESS read-only
    STATUS current
    DESCRIPTION "The threshold number of block errors at which a 1s interval will be considered degraded for the purposes of SDBER detection.
		
		
		default value :1"
::= { otu2eEntry 19 }
otu2eLoopbackEnable OBJECT-TYPE
    SYNTAX CoriantTypesEnableSwitch 
    MAX-ACCESS read-only
    STATUS current
    DESCRIPTION "The enable switching of loopback function.
		
		
		default value :disabled"
::= { otu2eEntry 20 }
otu2eLoopbackType OBJECT-TYPE
    SYNTAX INTEGER  {
	 none (0),
	 terminal (1),
	 facility (2)
	}
    MAX-ACCESS read-only
    STATUS current
    DESCRIPTION "The type mode of loopback function
		
		
		default value :none"
::= { otu2eEntry 21 }
fc8g OBJECT IDENTIFIER ::= { otn 13 }
fc8gTable OBJECT-TYPE
    SYNTAX SEQUENCE OF Fc8gEntry
    MAX-ACCESS not-accessible
    STATUS current
    DESCRIPTION "
	Represents the FC8G object.
	"
::= { fc8g 1 }
fc8gEntry OBJECT-TYPE
    SYNTAX Fc8gEntry
    MAX-ACCESS not-accessible
    STATUS current
    DESCRIPTION "Entry of fc8gTable" 
    INDEX { shelfId,slotId,subslotId,portId,subportId }
::= { fc8gTable 1 }
Fc8gEntry ::= 
SEQUENCE {
	fc8gMappingMode INTEGER,
	fc8gAdminStatus INTEGER,
	fc8gOperStatus INTEGER,
	fc8gAvailStatus BITS,
	fc8gAliasName OCTET STRING,
	fc8gClientShutdown CoriantTypesYesNo,
	fc8gClientShutdownHoldoffTimer Unsigned32,
	fc8gNearEndAls CoriantTypesYesNo,
	fc8gAlsDegradeMode CoriantTypesEnableSwitch,
	fc8gLoopbackEnable CoriantTypesEnableSwitch,
	fc8gLoopbackType INTEGER,
	fc8gTestSignalType CoriantTypesTestSignalType,
	fc8gTestSignalEnable CoriantTypesTestSignalConfig,
	fc8gServiceLabel OCTET STRING,
	fc8gHoldoffSignal CoriantTypesYesNo
    }
fc8gMappingMode OBJECT-TYPE
    SYNTAX INTEGER  {
	 notApplicable (0),
	 gmp (1),
	 gfpF (2),
	 t40gbmpOdu2e (3),
	 preamble (4),
	 bmpFixedstuff (5),
	 bmp (6),
	 amp (7)
	}
    MAX-ACCESS read-only
    STATUS current
    DESCRIPTION "The mapping mode of client port packets into ODUk.
		
		
		default value :not-applicable"
::= { fc8gEntry 1 }
fc8gAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { fc8gEntry 2 }
fc8gOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { fc8gEntry 3 }
fc8gAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { fc8gEntry 4 }
fc8gAliasName OBJECT-TYPE
    SYNTAX OCTET STRING  (SIZE (0..256))
    MAX-ACCESS read-only
    STATUS current
    DESCRIPTION "User defined alias for this entity. Must be an alphanumeric string with dash or underscore
		
		
		"
::= { fc8gEntry 5 }
fc8gClientShutdown OBJECT-TYPE
    SYNTAX CoriantTypesYesNo 
    MAX-ACCESS read-only
    STATUS current
    DESCRIPTION "The switching of client-shutdown.
		
		
		default value :no"
::= { fc8gEntry 6 }
fc8gClientShutdownHoldoffTimer OBJECT-TYPE
    SYNTAX Unsigned32  (0..1000)
    MAX-ACCESS read-only
    STATUS current
    DESCRIPTION "The hold off time of client shutdown or replacement siganl at egress direction.
		
		UNITS:milliseconds
		default value :0"
::= { fc8gEntry 7 }
fc8gNearEndAls OBJECT-TYPE
    SYNTAX CoriantTypesYesNo 
    MAX-ACCESS read-only
    STATUS current
    DESCRIPTION "The switching of near end ALS.
		
		
		default value :no"
::= { fc8gEntry 8 }
fc8gAlsDegradeMode OBJECT-TYPE
    SYNTAX CoriantTypesEnableSwitch 
    MAX-ACCESS read-only
    STATUS current
    DESCRIPTION "The switching of defect BERSD-ODU trig ALS
		
		
		default value :disabled"
::= { fc8gEntry 9 }
fc8gLoopbackEnable OBJECT-TYPE
    SYNTAX CoriantTypesEnableSwitch 
    MAX-ACCESS read-only
    STATUS current
    DESCRIPTION "The enable switching of loopback function.
		
		
		default value :disabled"
::= { fc8gEntry 10 }
fc8gLoopbackType OBJECT-TYPE
    SYNTAX INTEGER  {
	 none (0),
	 terminal (1),
	 facility (2)
	}
    MAX-ACCESS read-only
    STATUS current
    DESCRIPTION "The type mode of loopback function
		
		
		default value :none"
::= { fc8gEntry 11 }
fc8gTestSignalType OBJECT-TYPE
    SYNTAX CoriantTypesTestSignalType 
    MAX-ACCESS read-only
    STATUS current
    DESCRIPTION "The type mode of test signal.
		
		
		default value :NONE"
::= { fc8gEntry 12 }
fc8gTestSignalEnable OBJECT-TYPE
    SYNTAX CoriantTypesTestSignalConfig 
    MAX-ACCESS read-only
    STATUS current
    DESCRIPTION "The enable switching of test signal function
		
		
		default value :NONE"
::= { fc8gEntry 13 }
fc8gServiceLabel OBJECT-TYPE
    SYNTAX OCTET STRING  (SIZE (0..128))
    MAX-ACCESS read-only
    STATUS current
    DESCRIPTION "Path/service name of cross-connection related facility.
		
		
		"
::= { fc8gEntry 14 }
fc8gHoldoffSignal OBJECT-TYPE
    SYNTAX CoriantTypesYesNo 
    MAX-ACCESS read-only
    STATUS current
    DESCRIPTION "Specify if specific signal will be sent out during hold off time
	which avoid downstream equipment consequent action in the duration.
		
		
		default value :no"
::= { fc8gEntry 15 }
fc16g OBJECT IDENTIFIER ::= { otn 14 }
fc16gTable OBJECT-TYPE
    SYNTAX SEQUENCE OF Fc16gEntry
    MAX-ACCESS not-accessible
    STATUS current
    DESCRIPTION "
	Represents the FC16G object.
	"
::= { fc16g 1 }
fc16gEntry OBJECT-TYPE
    SYNTAX Fc16gEntry
    MAX-ACCESS not-accessible
    STATUS current
    DESCRIPTION "Entry of fc16gTable" 
    INDEX { shelfId,slotId,subslotId,portId,subportId }
::= { fc16gTable 1 }
Fc16gEntry ::= 
SEQUENCE {
	fc16gMappingMode INTEGER,
	fc16gAdminStatus INTEGER,
	fc16gOperStatus INTEGER,
	fc16gAvailStatus BITS,
	fc16gAliasName OCTET STRING,
	fc16gClientShutdown CoriantTypesYesNo,
	fc16gClientShutdownHoldoffTimer Unsigned32,
	fc16gNearEndAls CoriantTypesYesNo,
	fc16gAlsDegradeMode CoriantTypesEnableSwitch,
	fc16gLoopbackEnable CoriantTypesEnableSwitch,
	fc16gLoopbackType INTEGER,
	fc16gTestSignalType CoriantTypesTestSignalType,
	fc16gTestSignalEnable CoriantTypesTestSignalConfig,
	fc16gServiceLabel OCTET STRING,
	fc16gHoldoffSignal CoriantTypesYesNo
    }
fc16gMappingMode OBJECT-TYPE
    SYNTAX INTEGER  {
	 notApplicable (0),
	 gmp (1),
	 gfpF (2),
	 t40gbmpOdu2e (3),
	 preamble (4),
	 bmpFixedstuff (5),
	 bmp (6),
	 amp (7)
	}
    MAX-ACCESS read-only
    STATUS current
    DESCRIPTION "The mapping mode of client port packets into ODUk.
		
		
		default value :not-applicable"
::= { fc16gEntry 1 }
fc16gAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { fc16gEntry 2 }
fc16gOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { fc16gEntry 3 }
fc16gAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { fc16gEntry 4 }
fc16gAliasName OBJECT-TYPE
    SYNTAX OCTET STRING  (SIZE (0..256))
    MAX-ACCESS read-only
    STATUS current
    DESCRIPTION "User defined alias for this entity. Must be an alphanumeric string with dash or underscore
		
		
		"
::= { fc16gEntry 5 }
fc16gClientShutdown OBJECT-TYPE
    SYNTAX CoriantTypesYesNo 
    MAX-ACCESS read-only
    STATUS current
    DESCRIPTION "The switching of client-shutdown.
		
		
		default value :no"
::= { fc16gEntry 6 }
fc16gClientShutdownHoldoffTimer OBJECT-TYPE
    SYNTAX Unsigned32  (0..1000)
    MAX-ACCESS read-only
    STATUS current
    DESCRIPTION "The hold off time of client shutdown or replacement siganl at egress direction.
		
		UNITS:milliseconds
		default value :0"
::= { fc16gEntry 7 }
fc16gNearEndAls OBJECT-TYPE
    SYNTAX CoriantTypesYesNo 
    MAX-ACCESS read-only
    STATUS current
    DESCRIPTION "The switching of near end ALS.
		
		
		default value :no"
::= { fc16gEntry 8 }
fc16gAlsDegradeMode OBJECT-TYPE
    SYNTAX CoriantTypesEnableSwitch 
    MAX-ACCESS read-only
    STATUS current
    DESCRIPTION "The switching of defect BERSD-ODU trig ALS
		
		
		default value :disabled"
::= { fc16gEntry 9 }
fc16gLoopbackEnable OBJECT-TYPE
    SYNTAX CoriantTypesEnableSwitch 
    MAX-ACCESS read-only
    STATUS current
    DESCRIPTION "The enable switching of loopback function.
		
		
		default value :disabled"
::= { fc16gEntry 10 }
fc16gLoopbackType OBJECT-TYPE
    SYNTAX INTEGER  {
	 none (0),
	 terminal (1),
	 facility (2)
	}
    MAX-ACCESS read-only
    STATUS current
    DESCRIPTION "The type mode of loopback function
		
		
		default value :none"
::= { fc16gEntry 11 }
fc16gTestSignalType OBJECT-TYPE
    SYNTAX CoriantTypesTestSignalType 
    MAX-ACCESS read-only
    STATUS current
    DESCRIPTION "The type mode of test signal.
		
		
		default value :NONE"
::= { fc16gEntry 12 }
fc16gTestSignalEnable OBJECT-TYPE
    SYNTAX CoriantTypesTestSignalConfig 
    MAX-ACCESS read-only
    STATUS current
    DESCRIPTION "The enable switching of test signal function
		
		
		default value :NONE"
::= { fc16gEntry 13 }
fc16gServiceLabel OBJECT-TYPE
    SYNTAX OCTET STRING  (SIZE (0..128))
    MAX-ACCESS read-only
    STATUS current
    DESCRIPTION "Path/service name of cross-connection related facility.
		
		
		"
::= { fc16gEntry 14 }
fc16gHoldoffSignal OBJECT-TYPE
    SYNTAX CoriantTypesYesNo 
    MAX-ACCESS read-only
    STATUS current
    DESCRIPTION "Specify if specific signal will be sent out during hold off time
	which avoid downstream equipment consequent action in the duration.
		
		
		default value :no"
::= { fc16gEntry 15 }
oc192 OBJECT IDENTIFIER ::= { otn 15 }
oc192Table OBJECT-TYPE
    SYNTAX SEQUENCE OF Oc192Entry
    MAX-ACCESS not-accessible
    STATUS current
    DESCRIPTION "
	Represents the OC192 object.
	"
::= { oc192 1 }
oc192Entry OBJECT-TYPE
    SYNTAX Oc192Entry
    MAX-ACCESS not-accessible
    STATUS current
    DESCRIPTION "Entry of oc192Table" 
    INDEX { shelfId,slotId,subslotId,portId,subportId }
::= { oc192Table 1 }
Oc192Entry ::= 
SEQUENCE {
	oc192MappingMode INTEGER,
	oc192AdminStatus INTEGER,
	oc192OperStatus INTEGER,
	oc192AvailStatus BITS,
	oc192AliasName OCTET STRING,
	oc192ClientShutdown CoriantTypesYesNo,
	oc192ClientShutdownHoldoffTimer Unsigned32,
	oc192NearEndAls CoriantTypesYesNo,
	oc192AlsDegradeMode CoriantTypesEnableSwitch,
	oc192LoopbackEnable CoriantTypesEnableSwitch,
	oc192LoopbackType INTEGER,
	oc192TestSignalType CoriantTypesTestSignalType,
	oc192TestSignalEnable CoriantTypesTestSignalConfig,
	oc192ServiceLabel OCTET STRING,
	oc192ExpTrc OCTET STRING,
	oc192TxTrc OCTET STRING,
	oc192RxTrc OCTET STRING,
	oc192TimAct CoriantTypesEnableSwitch,
	oc192TimMonitor CoriantTypesEnableSwitch,
	oc192AisType INTEGER,
	oc192HoldoffSignal CoriantTypesYesNo
    }
oc192MappingMode OBJECT-TYPE
    SYNTAX INTEGER  {
	 notApplicable (0),
	 gmp (1),
	 gfpF (2),
	 t40gbmpOdu2e (3),
	 preamble (4),
	 bmpFixedstuff (5),
	 bmp (6),
	 amp (7)
	}
    MAX-ACCESS read-only
    STATUS current
    DESCRIPTION "The mapping mode of client port packets into ODUk.
		
		
		default value :not-applicable"
::= { oc192Entry 1 }
oc192AdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { oc192Entry 2 }
oc192OperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { oc192Entry 3 }
oc192AvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { oc192Entry 4 }
oc192AliasName OBJECT-TYPE
    SYNTAX OCTET STRING  (SIZE (0..256))
    MAX-ACCESS read-only
    STATUS current
    DESCRIPTION "User defined alias for this entity. Must be an alphanumeric string with dash or underscore
		
		
		"
::= { oc192Entry 5 }
oc192ClientShutdown OBJECT-TYPE
    SYNTAX CoriantTypesYesNo 
    MAX-ACCESS read-only
    STATUS current
    DESCRIPTION "The switching of client-shutdown.
		
		
		default value :no"
::= { oc192Entry 6 }
oc192ClientShutdownHoldoffTimer OBJECT-TYPE
    SYNTAX Unsigned32  (0..1000)
    MAX-ACCESS read-only
    STATUS current
    DESCRIPTION "The hold off time of client shutdown or replacement siganl at egress direction.
		
		UNITS:milliseconds
		default value :0"
::= { oc192Entry 7 }
oc192NearEndAls OBJECT-TYPE
    SYNTAX CoriantTypesYesNo 
    MAX-ACCESS read-only
    STATUS current
    DESCRIPTION "The switching of near end ALS.
		
		
		default value :no"
::= { oc192Entry 8 }
oc192AlsDegradeMode OBJECT-TYPE
    SYNTAX CoriantTypesEnableSwitch 
    MAX-ACCESS read-only
    STATUS current
    DESCRIPTION "The switching of defect BERSD-ODU trig ALS
		
		
		default value :disabled"
::= { oc192Entry 9 }
oc192LoopbackEnable OBJECT-TYPE
    SYNTAX CoriantTypesEnableSwitch 
    MAX-ACCESS read-only
    STATUS current
    DESCRIPTION "The enable switching of loopback function.
		
		
		default value :disabled"
::= { oc192Entry 10 }
oc192LoopbackType OBJECT-TYPE
    SYNTAX INTEGER  {
	 none (0),
	 terminal (1),
	 facility (2)
	}
    MAX-ACCESS read-only
    STATUS current
    DESCRIPTION "The type mode of loopback function
		
		
		default value :none"
::= { oc192Entry 11 }
oc192TestSignalType OBJECT-TYPE
    SYNTAX CoriantTypesTestSignalType 
    MAX-ACCESS read-only
    STATUS current
    DESCRIPTION "The type mode of test signal.
		
		
		default value :NONE"
::= { oc192Entry 12 }
oc192TestSignalEnable OBJECT-TYPE
    SYNTAX CoriantTypesTestSignalConfig 
    MAX-ACCESS read-only
    STATUS current
    DESCRIPTION "The enable switching of test signal function
		
		
		default value :NONE"
::= { oc192Entry 13 }
oc192ServiceLabel OBJECT-TYPE
    SYNTAX OCTET STRING  (SIZE (0..128))
    MAX-ACCESS read-only
    STATUS current
    DESCRIPTION "Path/service name of cross-connection related facility.
		
		
		"
::= { oc192Entry 14 }
oc192ExpTrc OBJECT-TYPE
    SYNTAX OCTET STRING  (SIZE (0..15))
    MAX-ACCESS read-only
    STATUS current
    DESCRIPTION "The expected trc(trail trace identification)
		
		
		"
::= { oc192Entry 15 }
oc192TxTrc OBJECT-TYPE
    SYNTAX OCTET STRING  (SIZE (0..15))
    MAX-ACCESS read-only
    STATUS current
    DESCRIPTION "The transmitter trc(trail trace identification)
		Conditions:ancestor::card/switching-type = 'tdm'
		
		"
::= { oc192Entry 16 }
oc192RxTrc OBJECT-TYPE
    SYNTAX OCTET STRING  (SIZE (0..15))
    MAX-ACCESS read-only
    STATUS current
    DESCRIPTION "The received trc(trail trace identification)
		
		
		"
::= { oc192Entry 17 }
oc192TimAct OBJECT-TYPE
    SYNTAX CoriantTypesEnableSwitch 
    MAX-ACCESS read-only
    STATUS current
    DESCRIPTION "The enable switching of inserting AIS by tim function
		
		
		default value :disabled"
::= { oc192Entry 18 }
oc192TimMonitor OBJECT-TYPE
    SYNTAX CoriantTypesEnableSwitch 
    MAX-ACCESS read-only
    STATUS current
    DESCRIPTION "The enable switching of tim defect monitor mode
		
		
		default value :disabled"
::= { oc192Entry 19 }
oc192AisType OBJECT-TYPE
    SYNTAX INTEGER  {
	 genericAis (0),
	 msAis (1),
	 aisL (2)
	}
    MAX-ACCESS read-only
    STATUS current
    DESCRIPTION "NULL
		
		
		default value :Generic-AIS"
::= { oc192Entry 20 }
oc192HoldoffSignal OBJECT-TYPE
    SYNTAX CoriantTypesYesNo 
    MAX-ACCESS read-only
    STATUS current
    DESCRIPTION "Specify if specific signal will be sent out during hold off time
	which avoid downstream equipment consequent action in the duration.
		
		
		default value :no"
::= { oc192Entry 21 }
stm64 OBJECT IDENTIFIER ::= { otn 16 }
stm64Table OBJECT-TYPE
    SYNTAX SEQUENCE OF Stm64Entry
    MAX-ACCESS not-accessible
    STATUS current
    DESCRIPTION "
	Represents the STM64 object.
	"
::= { stm64 1 }
stm64Entry OBJECT-TYPE
    SYNTAX Stm64Entry
    MAX-ACCESS not-accessible
    STATUS current
    DESCRIPTION "Entry of stm64Table" 
    INDEX { shelfId,slotId,subslotId,portId,subportId }
::= { stm64Table 1 }
Stm64Entry ::= 
SEQUENCE {
	stm64MappingMode INTEGER,
	stm64AdminStatus INTEGER,
	stm64OperStatus INTEGER,
	stm64AvailStatus BITS,
	stm64AliasName OCTET STRING,
	stm64ClientShutdown CoriantTypesYesNo,
	stm64ClientShutdownHoldoffTimer Unsigned32,
	stm64NearEndAls CoriantTypesYesNo,
	stm64AlsDegradeMode CoriantTypesEnableSwitch,
	stm64LoopbackEnable CoriantTypesEnableSwitch,
	stm64LoopbackType INTEGER,
	stm64TestSignalType CoriantTypesTestSignalType,
	stm64TestSignalEnable CoriantTypesTestSignalConfig,
	stm64ServiceLabel OCTET STRING,
	stm64ExpTrc OCTET STRING,
	stm64TxTrc OCTET STRING,
	stm64RxTrc OCTET STRING,
	stm64TimAct CoriantTypesEnableSwitch,
	stm64TimMonitor CoriantTypesEnableSwitch,
	stm64AisType INTEGER,
	stm64HoldoffSignal CoriantTypesYesNo
    }
stm64MappingMode OBJECT-TYPE
    SYNTAX INTEGER  {
	 notApplicable (0),
	 gmp (1),
	 gfpF (2),
	 t40gbmpOdu2e (3),
	 preamble (4),
	 bmpFixedstuff (5),
	 bmp (6),
	 amp (7)
	}
    MAX-ACCESS read-only
    STATUS current
    DESCRIPTION "The mapping mode of client port packets into ODUk.
		
		
		default value :not-applicable"
::= { stm64Entry 1 }
stm64AdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { stm64Entry 2 }
stm64OperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { stm64Entry 3 }
stm64AvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { stm64Entry 4 }
stm64AliasName OBJECT-TYPE
    SYNTAX OCTET STRING  (SIZE (0..256))
    MAX-ACCESS read-only
    STATUS current
    DESCRIPTION "User defined alias for this entity. Must be an alphanumeric string with dash or underscore
		
		
		"
::= { stm64Entry 5 }
stm64ClientShutdown OBJECT-TYPE
    SYNTAX CoriantTypesYesNo 
    MAX-ACCESS read-only
    STATUS current
    DESCRIPTION "The switching of client-shutdown.
		
		
		default value :no"
::= { stm64Entry 6 }
stm64ClientShutdownHoldoffTimer OBJECT-TYPE
    SYNTAX Unsigned32  (0..1000)
    MAX-ACCESS read-only
    STATUS current
    DESCRIPTION "The hold off time of client shutdown or replacement siganl at egress direction.
		
		UNITS:milliseconds
		default value :0"
::= { stm64Entry 7 }
stm64NearEndAls OBJECT-TYPE
    SYNTAX CoriantTypesYesNo 
    MAX-ACCESS read-only
    STATUS current
    DESCRIPTION "The switching of near end ALS.
		
		
		default value :no"
::= { stm64Entry 8 }
stm64AlsDegradeMode OBJECT-TYPE
    SYNTAX CoriantTypesEnableSwitch 
    MAX-ACCESS read-only
    STATUS current
    DESCRIPTION "The switching of defect BERSD-ODU trig ALS
		
		
		default value :disabled"
::= { stm64Entry 9 }
stm64LoopbackEnable OBJECT-TYPE
    SYNTAX CoriantTypesEnableSwitch 
    MAX-ACCESS read-only
    STATUS current
    DESCRIPTION "The enable switching of loopback function.
		
		
		default value :disabled"
::= { stm64Entry 10 }
stm64LoopbackType OBJECT-TYPE
    SYNTAX INTEGER  {
	 none (0),
	 terminal (1),
	 facility (2)
	}
    MAX-ACCESS read-only
    STATUS current
    DESCRIPTION "The type mode of loopback function
		
		
		default value :none"
::= { stm64Entry 11 }
stm64TestSignalType OBJECT-TYPE
    SYNTAX CoriantTypesTestSignalType 
    MAX-ACCESS read-only
    STATUS current
    DESCRIPTION "The type mode of test signal.
		
		
		default value :NONE"
::= { stm64Entry 12 }
stm64TestSignalEnable OBJECT-TYPE
    SYNTAX CoriantTypesTestSignalConfig 
    MAX-ACCESS read-only
    STATUS current
    DESCRIPTION "The enable switching of test signal function
		
		
		default value :NONE"
::= { stm64Entry 13 }
stm64ServiceLabel OBJECT-TYPE
    SYNTAX OCTET STRING  (SIZE (0..128))
    MAX-ACCESS read-only
    STATUS current
    DESCRIPTION "Path/service name of cross-connection related facility.
		
		
		"
::= { stm64Entry 14 }
stm64ExpTrc OBJECT-TYPE
    SYNTAX OCTET STRING  (SIZE (0..15))
    MAX-ACCESS read-only
    STATUS current
    DESCRIPTION "The expected trc(trail trace identification)
		
		
		"
::= { stm64Entry 15 }
stm64TxTrc OBJECT-TYPE
    SYNTAX OCTET STRING  (SIZE (0..15))
    MAX-ACCESS read-only
    STATUS current
    DESCRIPTION "The transmitter trc(trail trace identification)
		Conditions:ancestor::card/switching-type = 'tdm'
		
		"
::= { stm64Entry 16 }
stm64RxTrc OBJECT-TYPE
    SYNTAX OCTET STRING  (SIZE (0..15))
    MAX-ACCESS read-only
    STATUS current
    DESCRIPTION "The received trc(trail trace identification)
		
		
		"
::= { stm64Entry 17 }
stm64TimAct OBJECT-TYPE
    SYNTAX CoriantTypesEnableSwitch 
    MAX-ACCESS read-only
    STATUS current
    DESCRIPTION "The enable switching of inserting AIS by tim function
		
		
		default value :disabled"
::= { stm64Entry 18 }
stm64TimMonitor OBJECT-TYPE
    SYNTAX CoriantTypesEnableSwitch 
    MAX-ACCESS read-only
    STATUS current
    DESCRIPTION "The enable switching of tim defect monitor mode
		
		
		default value :disabled"
::= { stm64Entry 19 }
stm64AisType OBJECT-TYPE
    SYNTAX INTEGER  {
	 genericAis (0),
	 msAis (1),
	 aisL (2)
	}
    MAX-ACCESS read-only
    STATUS current
    DESCRIPTION "NULL
		
		
		default value :Generic-AIS"
::= { stm64Entry 20 }
stm64HoldoffSignal OBJECT-TYPE
    SYNTAX CoriantTypesYesNo 
    MAX-ACCESS read-only
    STATUS current
    DESCRIPTION "Specify if specific signal will be sent out during hold off time
	which avoid downstream equipment consequent action in the duration.
		
		
		default value :no"
::= { stm64Entry 21 }
otuc2 OBJECT IDENTIFIER ::= { otn 17 }
otuc2Table OBJECT-TYPE
    SYNTAX SEQUENCE OF Otuc2Entry
    MAX-ACCESS not-accessible
    STATUS current
    DESCRIPTION "Represents the otuc2 object"
::= { otuc2 1 }
otuc2Entry OBJECT-TYPE
    SYNTAX Otuc2Entry
    MAX-ACCESS not-accessible
    STATUS current
    DESCRIPTION "Entry of otuc2Table" 
    INDEX { shelfId,slotId,subslotId,portId,subportId }
::= { otuc2Table 1 }
Otuc2Entry ::= 
SEQUENCE {
	otuc2FecType CoriantTypesOtukFec,
	otuc2AdminStatus INTEGER,
	otuc2OperStatus INTEGER,
	otuc2AvailStatus BITS,
	otuc2AliasName OCTET STRING,
	otuc2ServiceLabel OCTET STRING,
	otuc2ExpSapi OCTET STRING,
	otuc2ExpDapi OCTET STRING,
	otuc2ExpOperator OCTET STRING,
	otuc2TxSapi OCTET STRING,
	otuc2TxDapi OCTET STRING,
	otuc2TxOperator OCTET STRING,
	otuc2TimDefectMode CoriantTypesTimMode,
	otuc2TimAct CoriantTypesEnableSwitch,
	otuc2RxSapi OCTET STRING,
	otuc2RxDapi OCTET STRING,
	otuc2RxOperator OCTET STRING,
	otuc2DegradeInterval Unsigned32,
	otuc2DegradeThreshold Unsigned32
    }
otuc2FecType OBJECT-TYPE
    SYNTAX CoriantTypesOtukFec 
    MAX-ACCESS read-only
    STATUS current
    DESCRIPTION "
	The FEC type of client OTUk.
	
		Conditions:(ancestor::port/port-type = 'client') or (ancestor::port/port-type = 'client-subport')
		
		default value :G709"
::= { otuc2Entry 1 }
otuc2AdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { otuc2Entry 2 }
otuc2OperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { otuc2Entry 3 }
otuc2AvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { otuc2Entry 4 }
otuc2AliasName OBJECT-TYPE
    SYNTAX OCTET STRING  (SIZE (0..256))
    MAX-ACCESS read-only
    STATUS current
    DESCRIPTION "User defined alias for this entity. Must be an alphanumeric string with dash or underscore
		
		
		"
::= { otuc2Entry 5 }
otuc2ServiceLabel OBJECT-TYPE
    SYNTAX OCTET STRING  (SIZE (0..128))
    MAX-ACCESS read-only
    STATUS current
    DESCRIPTION "Path/service name of cross-connection related facility.
		
		
		"
::= { otuc2Entry 6 }
otuc2ExpSapi OBJECT-TYPE
    SYNTAX OCTET STRING  (SIZE (0..15))
    MAX-ACCESS read-only
    STATUS current
    DESCRIPTION "The expected sapi(Source Access Point Identifier)
		
		
		"
::= { otuc2Entry 7 }
otuc2ExpDapi OBJECT-TYPE
    SYNTAX OCTET STRING  (SIZE (0..15))
    MAX-ACCESS read-only
    STATUS current
    DESCRIPTION "The expected dapi(Destination Access Point Identifier)
		
		
		"
::= { otuc2Entry 8 }
otuc2ExpOperator OBJECT-TYPE
    SYNTAX OCTET STRING  (SIZE (0..32))
    MAX-ACCESS read-only
    STATUS current
    DESCRIPTION "The expected operator TTI
		
		
		"
::= { otuc2Entry 9 }
otuc2TxSapi OBJECT-TYPE
    SYNTAX OCTET STRING  (SIZE (0..15))
    MAX-ACCESS read-only
    STATUS current
    DESCRIPTION "The transmitter sapi(Source Access Point Identifier)
		
		
		"
::= { otuc2Entry 10 }
otuc2TxDapi OBJECT-TYPE
    SYNTAX OCTET STRING  (SIZE (0..15))
    MAX-ACCESS read-only
    STATUS current
    DESCRIPTION "The transmitter dapi(Destination Access Point Identifier)
		
		
		"
::= { otuc2Entry 11 }
otuc2TxOperator OBJECT-TYPE
    SYNTAX OCTET STRING  (SIZE (0..32))
    MAX-ACCESS read-only
    STATUS current
    DESCRIPTION "The transmitter operator TTI
		
		
		"
::= { otuc2Entry 12 }
otuc2TimDefectMode OBJECT-TYPE
    SYNTAX CoriantTypesTimMode 
    MAX-ACCESS read-only
    STATUS current
    DESCRIPTION "The tim defect selection mode
		
		
		default value :NONE"
::= { otuc2Entry 13 }
otuc2TimAct OBJECT-TYPE
    SYNTAX CoriantTypesEnableSwitch 
    MAX-ACCESS read-only
    STATUS current
    DESCRIPTION "The enable switching of inserting AIS by tim function
		
		
		default value :disabled"
::= { otuc2Entry 14 }
otuc2RxSapi OBJECT-TYPE
    SYNTAX OCTET STRING  (SIZE (0..15))
    MAX-ACCESS read-only
    STATUS current
    DESCRIPTION "The received sapi(Source Access Point Identifier)
		
		
		"
::= { otuc2Entry 15 }
otuc2RxDapi OBJECT-TYPE
    SYNTAX OCTET STRING  (SIZE (0..15))
    MAX-ACCESS read-only
    STATUS current
    DESCRIPTION "The received dapi(Destination Access Point Identifier)
		
		
		"
::= { otuc2Entry 16 }
otuc2RxOperator OBJECT-TYPE
    SYNTAX OCTET STRING  (SIZE (0..32))
    MAX-ACCESS read-only
    STATUS current
    DESCRIPTION "The received operator TTI
		
		
		"
::= { otuc2Entry 17 }
otuc2DegradeInterval OBJECT-TYPE
    SYNTAX Unsigned32  (2..10)
    MAX-ACCESS read-only
    STATUS current
    DESCRIPTION "The consecutive number of 1s intervals with the number of detected block errors exceeding the block error threshold for each of those seconds for the purposes of SDBER detection.
		
		
		default value :7"
::= { otuc2Entry 18 }
otuc2DegradeThreshold OBJECT-TYPE
    SYNTAX Unsigned32  (1..2590845)
    MAX-ACCESS read-only
    STATUS current
    DESCRIPTION "The threshold number of block errors at which a 1s interval will be considered degraded for the purposes of SDBER detection.
		
		
		default value :1"
::= { otuc2Entry 19 }
otuc3 OBJECT IDENTIFIER ::= { otn 18 }
otuc3Table OBJECT-TYPE
    SYNTAX SEQUENCE OF Otuc3Entry
    MAX-ACCESS not-accessible
    STATUS current
    DESCRIPTION "Represents the otuc3 object"
::= { otuc3 1 }
otuc3Entry OBJECT-TYPE
    SYNTAX Otuc3Entry
    MAX-ACCESS not-accessible
    STATUS current
    DESCRIPTION "Entry of otuc3Table" 
    INDEX { shelfId,slotId,subslotId,portId,subportId }
::= { otuc3Table 1 }
Otuc3Entry ::= 
SEQUENCE {
	otuc3FecType CoriantTypesOtukFec,
	otuc3AdminStatus INTEGER,
	otuc3OperStatus INTEGER,
	otuc3AvailStatus BITS,
	otuc3AliasName OCTET STRING,
	otuc3ServiceLabel OCTET STRING,
	otuc3ExpSapi OCTET STRING,
	otuc3ExpDapi OCTET STRING,
	otuc3ExpOperator OCTET STRING,
	otuc3TxSapi OCTET STRING,
	otuc3TxDapi OCTET STRING,
	otuc3TxOperator OCTET STRING,
	otuc3TimDefectMode CoriantTypesTimMode,
	otuc3TimAct CoriantTypesEnableSwitch,
	otuc3RxSapi OCTET STRING,
	otuc3RxDapi OCTET STRING,
	otuc3RxOperator OCTET STRING,
	otuc3DegradeInterval Unsigned32,
	otuc3DegradeThreshold Unsigned32
    }
otuc3FecType OBJECT-TYPE
    SYNTAX CoriantTypesOtukFec 
    MAX-ACCESS read-only
    STATUS current
    DESCRIPTION "
	The FEC type of client OTUk.
	
		Conditions:(ancestor::port/port-type = 'client') or (ancestor::port/port-type = 'client-subport')
		
		default value :G709"
::= { otuc3Entry 1 }
otuc3AdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { otuc3Entry 2 }
otuc3OperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { otuc3Entry 3 }
otuc3AvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { otuc3Entry 4 }
otuc3AliasName OBJECT-TYPE
    SYNTAX OCTET STRING  (SIZE (0..256))
    MAX-ACCESS read-only
    STATUS current
    DESCRIPTION "User defined alias for this entity. Must be an alphanumeric string with dash or underscore
		
		
		"
::= { otuc3Entry 5 }
otuc3ServiceLabel OBJECT-TYPE
    SYNTAX OCTET STRING  (SIZE (0..128))
    MAX-ACCESS read-only
    STATUS current
    DESCRIPTION "Path/service name of cross-connection related facility.
		
		
		"
::= { otuc3Entry 6 }
otuc3ExpSapi OBJECT-TYPE
    SYNTAX OCTET STRING  (SIZE (0..15))
    MAX-ACCESS read-only
    STATUS current
    DESCRIPTION "The expected sapi(Source Access Point Identifier)
		
		
		"
::= { otuc3Entry 7 }
otuc3ExpDapi OBJECT-TYPE
    SYNTAX OCTET STRING  (SIZE (0..15))
    MAX-ACCESS read-only
    STATUS current
    DESCRIPTION "The expected dapi(Destination Access Point Identifier)
		
		
		"
::= { otuc3Entry 8 }
otuc3ExpOperator OBJECT-TYPE
    SYNTAX OCTET STRING  (SIZE (0..32))
    MAX-ACCESS read-only
    STATUS current
    DESCRIPTION "The expected operator TTI
		
		
		"
::= { otuc3Entry 9 }
otuc3TxSapi OBJECT-TYPE
    SYNTAX OCTET STRING  (SIZE (0..15))
    MAX-ACCESS read-only
    STATUS current
    DESCRIPTION "The transmitter sapi(Source Access Point Identifier)
		
		
		"
::= { otuc3Entry 10 }
otuc3TxDapi OBJECT-TYPE
    SYNTAX OCTET STRING  (SIZE (0..15))
    MAX-ACCESS read-only
    STATUS current
    DESCRIPTION "The transmitter dapi(Destination Access Point Identifier)
		
		
		"
::= { otuc3Entry 11 }
otuc3TxOperator OBJECT-TYPE
    SYNTAX OCTET STRING  (SIZE (0..32))
    MAX-ACCESS read-only
    STATUS current
    DESCRIPTION "The transmitter operator TTI
		
		
		"
::= { otuc3Entry 12 }
otuc3TimDefectMode OBJECT-TYPE
    SYNTAX CoriantTypesTimMode 
    MAX-ACCESS read-only
    STATUS current
    DESCRIPTION "The tim defect selection mode
		
		
		default value :NONE"
::= { otuc3Entry 13 }
otuc3TimAct OBJECT-TYPE
    SYNTAX CoriantTypesEnableSwitch 
    MAX-ACCESS read-only
    STATUS current
    DESCRIPTION "The enable switching of inserting AIS by tim function
		
		
		default value :disabled"
::= { otuc3Entry 14 }
otuc3RxSapi OBJECT-TYPE
    SYNTAX OCTET STRING  (SIZE (0..15))
    MAX-ACCESS read-only
    STATUS current
    DESCRIPTION "The received sapi(Source Access Point Identifier)
		
		
		"
::= { otuc3Entry 15 }
otuc3RxDapi OBJECT-TYPE
    SYNTAX OCTET STRING  (SIZE (0..15))
    MAX-ACCESS read-only
    STATUS current
    DESCRIPTION "The received dapi(Destination Access Point Identifier)
		
		
		"
::= { otuc3Entry 16 }
otuc3RxOperator OBJECT-TYPE
    SYNTAX OCTET STRING  (SIZE (0..32))
    MAX-ACCESS read-only
    STATUS current
    DESCRIPTION "The received operator TTI
		
		
		"
::= { otuc3Entry 17 }
otuc3DegradeInterval OBJECT-TYPE
    SYNTAX Unsigned32  (2..10)
    MAX-ACCESS read-only
    STATUS current
    DESCRIPTION "The consecutive number of 1s intervals with the number of detected block errors exceeding the block error threshold for each of those seconds for the purposes of SDBER detection.
		
		
		default value :7"
::= { otuc3Entry 18 }
otuc3DegradeThreshold OBJECT-TYPE
    SYNTAX Unsigned32  (1..2590845)
    MAX-ACCESS read-only
    STATUS current
    DESCRIPTION "The threshold number of block errors at which a 1s interval will be considered degraded for the purposes of SDBER detection.
		
		
		default value :1"
::= { otuc3Entry 19 }
ochOs OBJECT IDENTIFIER ::= { otn 19 }
ochOsTable OBJECT-TYPE
    SYNTAX SEQUENCE OF OchOsEntry
    MAX-ACCESS not-accessible
    STATUS current
    DESCRIPTION "Represents the och-os MO"
::= { ochOs 1 }
ochOsEntry OBJECT-TYPE
    SYNTAX OchOsEntry
    MAX-ACCESS not-accessible
    STATUS current
    DESCRIPTION "Entry of ochOsTable" 
    INDEX { shelfId,slotId,subslotId,portId }
::= { ochOsTable 1 }
OchOsEntry ::= 
SEQUENCE {
	ochOsModulationFormat INTEGER,
	ochOsLineEncoding INTEGER,
	ochOsFrequency CoriantTypesFreq,
	ochOsActualFrequency CoriantTypesFreq,
	ochOsRxFrequency CoriantTypesFreq,
	ochOsActualRxFrequency CoriantTypesFreq,
	ochOsLaserEnable CoriantTypesEnableSwitch,
	ochOsRequiredTxOpticalPower CoriantTypesOpticalPower,
	ochOsActualTxOpticalPower CoriantTypesOpticalPower,
	ochOsFecType CoriantTypesOtukFec,
	ochOsRxAttenuation CoriantTypesOpticalDB,
	ochOsTxFilterRollOff OCTET STRING,
	ochOsPreemphasis CoriantTypesEnableSwitch,
	ochOsPreemphasisValue OCTET STRING,
	ochOsAdminStatus INTEGER,
	ochOsOperStatus INTEGER,
	ochOsAvailStatus BITS,
	ochOsAliasName OCTET STRING,
	ochOsLoopbackEnable CoriantTypesEnableSwitch,
	ochOsLoopbackType INTEGER,
	ochOsServiceLabel OCTET STRING,
	ochOsDGD Unsigned32,
	ochOsCD INTEGER,
	ochOsOSNR CoriantTypesOpticalDB,
	ochOsQFactor CoriantTypesOpticalDB,
	ochOsPreFecBer OCTET STRING,
	ochOsCdRangeLow INTEGER,
	ochOsCdRangeHigh INTEGER,
	ochOsPropagateShutdown CoriantTypesYesNo,
	ochOsFastSopMode CoriantTypesEnableSwitch
    }
ochOsModulationFormat OBJECT-TYPE
    SYNTAX INTEGER  {
	 notApplicable (0),
	 dpQpsk (1),
	 dp16qam (2),
	 dp8qam (3),
	 nrz (6)
	}
    MAX-ACCESS read-only
    STATUS current
    DESCRIPTION "
	Currently och-os modulation format
	
		
		
		"
::= { ochOsEntry 1 }
ochOsLineEncoding OBJECT-TYPE
    SYNTAX INTEGER  {
	 nonDifferential (1),
	 differential (2)
	}
    MAX-ACCESS read-only
    STATUS current
    DESCRIPTION "
	Currently line-encoding mode
	
		
		
		"
::= { ochOsEntry 2 }
ochOsFrequency OBJECT-TYPE
    SYNTAX CoriantTypesFreq 
    MAX-ACCESS read-only
    STATUS current
    DESCRIPTION "
	The laser frequency. For tx-lo-independent laser-type, it set the tx laser frequency only.
	
		
		UNITS:MHz
		default value :0"
::= { ochOsEntry 3 }
ochOsActualFrequency OBJECT-TYPE
    SYNTAX CoriantTypesFreq 
    MAX-ACCESS read-only
    STATUS current
    DESCRIPTION "
	The actual laser frequency.
	If rx-frequency is 0, it reflects both Rx and Tx frequency for coherent interface.
	
		
		UNITS:MHz
		default value :0"
::= { ochOsEntry 4 }
ochOsRxFrequency OBJECT-TYPE
    SYNTAX CoriantTypesFreq 
    MAX-ACCESS read-only
    STATUS current
    DESCRIPTION "
	The rx laser frequency. Special for 0 means it is same as tx laser frequency.
	
		Conditions:../../possible-pluggable-types != 'SFP+'
		UNITS:MHz
		default value :0"
::= { ochOsEntry 5 }
ochOsActualRxFrequency OBJECT-TYPE
    SYNTAX CoriantTypesFreq 
    MAX-ACCESS read-only
    STATUS current
    DESCRIPTION "
	The actual rx laser frequency for coherent interface with separating Lo laser from Tx.
	0 means Lo and Tx share the same laser where 'frequency' attriute will indicate both Tx and Rx.
	
		Conditions:../../possible-pluggable-types != 'SFP+'
		UNITS:MHz
		default value :0"
::= { ochOsEntry 6 }
ochOsLaserEnable OBJECT-TYPE
    SYNTAX CoriantTypesEnableSwitch 
    MAX-ACCESS read-only
    STATUS current
    DESCRIPTION "
	The enable switching of output laser.
	
		
		
		default value :disabled"
::= { ochOsEntry 7 }
ochOsRequiredTxOpticalPower OBJECT-TYPE
    SYNTAX CoriantTypesOpticalPower 
    MAX-ACCESS read-only
    STATUS current
    DESCRIPTION "
	This is to support adjustable optical power of Line side.
	
		
		
		default value :1.0"
::= { ochOsEntry 8 }
ochOsActualTxOpticalPower OBJECT-TYPE
    SYNTAX CoriantTypesOpticalPower 
    MAX-ACCESS read-only
    STATUS current
    DESCRIPTION "
	This is the actual transmitting optical power of Line side.
	
		
		
		default value :-99.0"
::= { ochOsEntry 9 }
ochOsFecType OBJECT-TYPE
    SYNTAX CoriantTypesOtukFec 
    MAX-ACCESS read-only
    STATUS current
    DESCRIPTION "The FEC type of och-os
		
		
		default value :SDFEC25"
::= { ochOsEntry 10 }
ochOsRxAttenuation OBJECT-TYPE
    SYNTAX CoriantTypesOpticalDB 
    MAX-ACCESS read-only
    STATUS current
    DESCRIPTION "
	This is to support configurable optical attenuation at receiver side which is based on the hardware capability on the port.
	
		
		
		default value :0.0"
::= { ochOsEntry 11 }
ochOsTxFilterRollOff OBJECT-TYPE
    SYNTAX OCTET STRING 
    MAX-ACCESS read-only
    STATUS current
    DESCRIPTION "Transmitter filter roll off factor.
		
		
		default value :0.2"
::= { ochOsEntry 12 }
ochOsPreemphasis OBJECT-TYPE
    SYNTAX CoriantTypesEnableSwitch 
    MAX-ACCESS read-only
    STATUS current
    DESCRIPTION "Preemphasis of transmitted signal.
		
		
		default value :enabled"
::= { ochOsEntry 13 }
ochOsPreemphasisValue OBJECT-TYPE
    SYNTAX OCTET STRING 
    MAX-ACCESS read-only
    STATUS current
    DESCRIPTION "Preemphasis of transmitted signal.
		
		
		default value :1.0"
::= { ochOsEntry 14 }
ochOsAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { ochOsEntry 15 }
ochOsOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { ochOsEntry 16 }
ochOsAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { ochOsEntry 17 }
ochOsAliasName OBJECT-TYPE
    SYNTAX OCTET STRING  (SIZE (0..256))
    MAX-ACCESS read-only
    STATUS current
    DESCRIPTION "User defined alias for this entity. Must be an alphanumeric string with dash or underscore
		
		
		"
::= { ochOsEntry 18 }
ochOsLoopbackEnable OBJECT-TYPE
    SYNTAX CoriantTypesEnableSwitch 
    MAX-ACCESS read-only
    STATUS current
    DESCRIPTION "The enable switching of loopback function.
		
		
		default value :disabled"
::= { ochOsEntry 19 }
ochOsLoopbackType OBJECT-TYPE
    SYNTAX INTEGER  {
	 none (0),
	 terminal (1),
	 facility (2)
	}
    MAX-ACCESS read-only
    STATUS current
    DESCRIPTION "The type mode of loopback function
		
		
		default value :none"
::= { ochOsEntry 20 }
ochOsServiceLabel OBJECT-TYPE
    SYNTAX OCTET STRING  (SIZE (0..128))
    MAX-ACCESS read-only
    STATUS current
    DESCRIPTION "Path/service name of cross-connection related facility.
		
		
		"
::= { ochOsEntry 21 }
ochOsDGD OBJECT-TYPE
    SYNTAX Unsigned32 
    MAX-ACCESS read-only
    STATUS current
    DESCRIPTION "Value of Differential Group Delay
		
		UNITS:ps
		"
::= { ochOsEntry 22 }
ochOsCD OBJECT-TYPE
    SYNTAX INTEGER 
    MAX-ACCESS read-only
    STATUS current
    DESCRIPTION "Value of Chromatic Dispersion
		
		UNITS:ps/nm
		"
::= { ochOsEntry 23 }
ochOsOSNR OBJECT-TYPE
    SYNTAX CoriantTypesOpticalDB 
    MAX-ACCESS read-only
    STATUS current
    DESCRIPTION "
	Current value of OSNR.
	The result could be OSNR value with dB
		
		
		"
::= { ochOsEntry 24 }
ochOsQFactor OBJECT-TYPE
    SYNTAX CoriantTypesOpticalDB 
    MAX-ACCESS read-only
    STATUS current
    DESCRIPTION "
	Current value of Q-factor
	
		
		
		"
::= { ochOsEntry 25 }
ochOsPreFecBer OBJECT-TYPE
    SYNTAX OCTET STRING 
    MAX-ACCESS read-only
    STATUS current
    DESCRIPTION "Current value of PreFEC Bit Error Ratio.
		
		
		default value :-99.0"
::= { ochOsEntry 26 }
ochOsCdRangeLow OBJECT-TYPE
    SYNTAX INTEGER 
    MAX-ACCESS read-only
    STATUS current
    DESCRIPTION "low value of chromatic dispersion search range.
		
		UNITS:ps/nm
		default value :-45000"
::= { ochOsEntry 27 }
ochOsCdRangeHigh OBJECT-TYPE
    SYNTAX INTEGER 
    MAX-ACCESS read-only
    STATUS current
    DESCRIPTION "high value of chromatic dispersion search range.
		
		UNITS:ps/nm
		default value :45000"
::= { ochOsEntry 28 }
ochOsPropagateShutdown OBJECT-TYPE
    SYNTAX CoriantTypesYesNo 
    MAX-ACCESS read-only
    STATUS current
    DESCRIPTION "When the attribute value is set to yes, the transmit laser will
	be shutdown if the whole service of the direction has signal failure,
	the function mainly used in regeneration node to propagate signal failure as LOS.
		
		
		default value :no"
::= { ochOsEntry 29 }
ochOsFastSopMode OBJECT-TYPE
    SYNTAX CoriantTypesEnableSwitch 
    MAX-ACCESS read-only
    STATUS current
    DESCRIPTION "Specify if enable fast SOP (state of polarization) change tracking; if enabled, the interface 
	   will tolerate very fast SOP and transient.
		
		
		default value :disabled"
::= { ochOsEntry 31 }
wan10gSonet OBJECT IDENTIFIER ::= { otn 30 }
wan10gSonetTable OBJECT-TYPE
    SYNTAX SEQUENCE OF Wan10gSonetEntry
    MAX-ACCESS not-accessible
    STATUS current
    DESCRIPTION "
	Represents the 10GWAN_SONET object.
	"
::= { wan10gSonet 1 }
wan10gSonetEntry OBJECT-TYPE
    SYNTAX Wan10gSonetEntry
    MAX-ACCESS not-accessible
    STATUS current
    DESCRIPTION "Entry of wan10gSonetTable" 
    INDEX { shelfId,slotId,subslotId,portId,subportId }
::= { wan10gSonetTable 1 }
Wan10gSonetEntry ::= 
SEQUENCE {
	wan10gSonetMappingMode INTEGER,
	wan10gSonetAdminStatus INTEGER,
	wan10gSonetOperStatus INTEGER,
	wan10gSonetAvailStatus BITS,
	wan10gSonetAliasName OCTET STRING,
	wan10gSonetClientShutdown CoriantTypesYesNo,
	wan10gSonetClientShutdownHoldoffTimer Unsigned32,
	wan10gSonetHoldoffSignal CoriantTypesYesNo,
	wan10gSonetNearEndAls CoriantTypesYesNo,
	wan10gSonetAlsDegradeMode CoriantTypesEnableSwitch,
	wan10gSonetLoopbackEnable CoriantTypesEnableSwitch,
	wan10gSonetLoopbackType INTEGER,
	wan10gSonetTestSignalType CoriantTypesTestSignalType,
	wan10gSonetTestSignalEnable CoriantTypesTestSignalConfig,
	wan10gSonetServiceLabel OCTET STRING,
	wan10gSonetExpTrc OCTET STRING,
	wan10gSonetTxTrc OCTET STRING,
	wan10gSonetRxTrc OCTET STRING,
	wan10gSonetTimAct CoriantTypesEnableSwitch,
	wan10gSonetTimMonitor CoriantTypesEnableSwitch,
	wan10gSonetAisType INTEGER
    }
wan10gSonetMappingMode OBJECT-TYPE
    SYNTAX INTEGER  {
	 notApplicable (0),
	 gmp (1),
	 gfpF (2),
	 t40gbmpOdu2e (3),
	 preamble (4),
	 bmpFixedstuff (5),
	 bmp (6),
	 amp (7)
	}
    MAX-ACCESS read-only
    STATUS current
    DESCRIPTION "The mapping mode of client port packets into ODUk.
		
		
		default value :not-applicable"
::= { wan10gSonetEntry 1 }
wan10gSonetAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { wan10gSonetEntry 2 }
wan10gSonetOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { wan10gSonetEntry 3 }
wan10gSonetAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { wan10gSonetEntry 4 }
wan10gSonetAliasName OBJECT-TYPE
    SYNTAX OCTET STRING  (SIZE (0..256))
    MAX-ACCESS read-only
    STATUS current
    DESCRIPTION "User defined alias for this entity. Must be an alphanumeric string with dash or underscore
		
		
		"
::= { wan10gSonetEntry 5 }
wan10gSonetClientShutdown OBJECT-TYPE
    SYNTAX CoriantTypesYesNo 
    MAX-ACCESS read-only
    STATUS current
    DESCRIPTION "The switching of client-shutdown.
		
		
		default value :no"
::= { wan10gSonetEntry 6 }
wan10gSonetClientShutdownHoldoffTimer OBJECT-TYPE
    SYNTAX Unsigned32  (0..1000)
    MAX-ACCESS read-only
    STATUS current
    DESCRIPTION "The hold off time of client shutdown or replacement siganl at egress direction.
		
		UNITS:milliseconds
		default value :0"
::= { wan10gSonetEntry 7 }
wan10gSonetHoldoffSignal OBJECT-TYPE
    SYNTAX CoriantTypesYesNo 
    MAX-ACCESS read-only
    STATUS current
    DESCRIPTION "Specify if specific signal will be sent out during hold off time
	which avoid downstream equipment consequent action in the duration.
		
		
		default value :no"
::= { wan10gSonetEntry 8 }
wan10gSonetNearEndAls OBJECT-TYPE
    SYNTAX CoriantTypesYesNo 
    MAX-ACCESS read-only
    STATUS current
    DESCRIPTION "The switching of near end ALS.
		
		
		default value :no"
::= { wan10gSonetEntry 9 }
wan10gSonetAlsDegradeMode OBJECT-TYPE
    SYNTAX CoriantTypesEnableSwitch 
    MAX-ACCESS read-only
    STATUS current
    DESCRIPTION "The switching of defect BERSD-ODU trig ALS
		
		
		default value :disabled"
::= { wan10gSonetEntry 10 }
wan10gSonetLoopbackEnable OBJECT-TYPE
    SYNTAX CoriantTypesEnableSwitch 
    MAX-ACCESS read-only
    STATUS current
    DESCRIPTION "The enable switching of loopback function.
		
		
		default value :disabled"
::= { wan10gSonetEntry 11 }
wan10gSonetLoopbackType OBJECT-TYPE
    SYNTAX INTEGER  {
	 none (0),
	 terminal (1),
	 facility (2)
	}
    MAX-ACCESS read-only
    STATUS current
    DESCRIPTION "The type mode of loopback function
		
		
		default value :none"
::= { wan10gSonetEntry 12 }
wan10gSonetTestSignalType OBJECT-TYPE
    SYNTAX CoriantTypesTestSignalType 
    MAX-ACCESS read-only
    STATUS current
    DESCRIPTION "The type mode of test signal.
		
		
		default value :NONE"
::= { wan10gSonetEntry 13 }
wan10gSonetTestSignalEnable OBJECT-TYPE
    SYNTAX CoriantTypesTestSignalConfig 
    MAX-ACCESS read-only
    STATUS current
    DESCRIPTION "The enable switching of test signal function
		
		
		default value :NONE"
::= { wan10gSonetEntry 14 }
wan10gSonetServiceLabel OBJECT-TYPE
    SYNTAX OCTET STRING  (SIZE (0..128))
    MAX-ACCESS read-only
    STATUS current
    DESCRIPTION "Path/service name of cross-connection related facility.
		
		
		"
::= { wan10gSonetEntry 15 }
wan10gSonetExpTrc OBJECT-TYPE
    SYNTAX OCTET STRING  (SIZE (0..15))
    MAX-ACCESS read-only
    STATUS current
    DESCRIPTION "The expected trc(trail trace identification)
		
		
		"
::= { wan10gSonetEntry 16 }
wan10gSonetTxTrc OBJECT-TYPE
    SYNTAX OCTET STRING  (SIZE (0..15))
    MAX-ACCESS read-only
    STATUS current
    DESCRIPTION "The transmitter trc(trail trace identification)
		Conditions:ancestor::card/switching-type = 'tdm'
		
		"
::= { wan10gSonetEntry 17 }
wan10gSonetRxTrc OBJECT-TYPE
    SYNTAX OCTET STRING  (SIZE (0..15))
    MAX-ACCESS read-only
    STATUS current
    DESCRIPTION "The received trc(trail trace identification)
		
		
		"
::= { wan10gSonetEntry 18 }
wan10gSonetTimAct OBJECT-TYPE
    SYNTAX CoriantTypesEnableSwitch 
    MAX-ACCESS read-only
    STATUS current
    DESCRIPTION "The enable switching of inserting AIS by tim function
		
		
		default value :disabled"
::= { wan10gSonetEntry 19 }
wan10gSonetTimMonitor OBJECT-TYPE
    SYNTAX CoriantTypesEnableSwitch 
    MAX-ACCESS read-only
    STATUS current
    DESCRIPTION "The enable switching of tim defect monitor mode
		
		
		default value :disabled"
::= { wan10gSonetEntry 20 }
wan10gSonetAisType OBJECT-TYPE
    SYNTAX INTEGER  {
	 genericAis (0),
	 msAis (1),
	 aisL (2)
	}
    MAX-ACCESS read-only
    STATUS current
    DESCRIPTION "NULL
		
		
		default value :Generic-AIS"
::= { wan10gSonetEntry 21 }
wan10gSdh OBJECT IDENTIFIER ::= { otn 31 }
wan10gSdhTable OBJECT-TYPE
    SYNTAX SEQUENCE OF Wan10gSdhEntry
    MAX-ACCESS not-accessible
    STATUS current
    DESCRIPTION "
	Represents the 10GWAN_SDH object.
	"
::= { wan10gSdh 1 }
wan10gSdhEntry OBJECT-TYPE
    SYNTAX Wan10gSdhEntry
    MAX-ACCESS not-accessible
    STATUS current
    DESCRIPTION "Entry of wan10gSdhTable" 
    INDEX { shelfId,slotId,subslotId,portId,subportId }
::= { wan10gSdhTable 1 }
Wan10gSdhEntry ::= 
SEQUENCE {
	wan10gSdhMappingMode INTEGER,
	wan10gSdhAdminStatus INTEGER,
	wan10gSdhOperStatus INTEGER,
	wan10gSdhAvailStatus BITS,
	wan10gSdhAliasName OCTET STRING,
	wan10gSdhClientShutdown CoriantTypesYesNo,
	wan10gSdhClientShutdownHoldoffTimer Unsigned32,
	wan10gSdhHoldoffSignal CoriantTypesYesNo,
	wan10gSdhNearEndAls CoriantTypesYesNo,
	wan10gSdhAlsDegradeMode CoriantTypesEnableSwitch,
	wan10gSdhLoopbackEnable CoriantTypesEnableSwitch,
	wan10gSdhLoopbackType INTEGER,
	wan10gSdhTestSignalType CoriantTypesTestSignalType,
	wan10gSdhTestSignalEnable CoriantTypesTestSignalConfig,
	wan10gSdhServiceLabel OCTET STRING,
	wan10gSdhExpTrc OCTET STRING,
	wan10gSdhTxTrc OCTET STRING,
	wan10gSdhRxTrc OCTET STRING,
	wan10gSdhTimAct CoriantTypesEnableSwitch,
	wan10gSdhTimMonitor CoriantTypesEnableSwitch,
	wan10gSdhAisType INTEGER
    }
wan10gSdhMappingMode OBJECT-TYPE
    SYNTAX INTEGER  {
	 notApplicable (0),
	 gmp (1),
	 gfpF (2),
	 t40gbmpOdu2e (3),
	 preamble (4),
	 bmpFixedstuff (5),
	 bmp (6),
	 amp (7)
	}
    MAX-ACCESS read-only
    STATUS current
    DESCRIPTION "The mapping mode of client port packets into ODUk.
		
		
		default value :not-applicable"
::= { wan10gSdhEntry 1 }
wan10gSdhAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { wan10gSdhEntry 2 }
wan10gSdhOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { wan10gSdhEntry 3 }
wan10gSdhAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { wan10gSdhEntry 4 }
wan10gSdhAliasName OBJECT-TYPE
    SYNTAX OCTET STRING  (SIZE (0..256))
    MAX-ACCESS read-only
    STATUS current
    DESCRIPTION "User defined alias for this entity. Must be an alphanumeric string with dash or underscore
		
		
		"
::= { wan10gSdhEntry 5 }
wan10gSdhClientShutdown OBJECT-TYPE
    SYNTAX CoriantTypesYesNo 
    MAX-ACCESS read-only
    STATUS current
    DESCRIPTION "The switching of client-shutdown.
		
		
		default value :no"
::= { wan10gSdhEntry 6 }
wan10gSdhClientShutdownHoldoffTimer OBJECT-TYPE
    SYNTAX Unsigned32  (0..1000)
    MAX-ACCESS read-only
    STATUS current
    DESCRIPTION "The hold off time of client shutdown or replacement siganl at egress direction.
		
		UNITS:milliseconds
		default value :0"
::= { wan10gSdhEntry 7 }
wan10gSdhHoldoffSignal OBJECT-TYPE
    SYNTAX CoriantTypesYesNo 
    MAX-ACCESS read-only
    STATUS current
    DESCRIPTION "Specify if specific signal will be sent out during hold off time
	which avoid downstream equipment consequent action in the duration.
		
		
		default value :no"
::= { wan10gSdhEntry 8 }
wan10gSdhNearEndAls OBJECT-TYPE
    SYNTAX CoriantTypesYesNo 
    MAX-ACCESS read-only
    STATUS current
    DESCRIPTION "The switching of near end ALS.
		
		
		default value :no"
::= { wan10gSdhEntry 9 }
wan10gSdhAlsDegradeMode OBJECT-TYPE
    SYNTAX CoriantTypesEnableSwitch 
    MAX-ACCESS read-only
    STATUS current
    DESCRIPTION "The switching of defect BERSD-ODU trig ALS
		
		
		default value :disabled"
::= { wan10gSdhEntry 10 }
wan10gSdhLoopbackEnable OBJECT-TYPE
    SYNTAX CoriantTypesEnableSwitch 
    MAX-ACCESS read-only
    STATUS current
    DESCRIPTION "The enable switching of loopback function.
		
		
		default value :disabled"
::= { wan10gSdhEntry 11 }
wan10gSdhLoopbackType OBJECT-TYPE
    SYNTAX INTEGER  {
	 none (0),
	 terminal (1),
	 facility (2)
	}
    MAX-ACCESS read-only
    STATUS current
    DESCRIPTION "The type mode of loopback function
		
		
		default value :none"
::= { wan10gSdhEntry 12 }
wan10gSdhTestSignalType OBJECT-TYPE
    SYNTAX CoriantTypesTestSignalType 
    MAX-ACCESS read-only
    STATUS current
    DESCRIPTION "The type mode of test signal.
		
		
		default value :NONE"
::= { wan10gSdhEntry 13 }
wan10gSdhTestSignalEnable OBJECT-TYPE
    SYNTAX CoriantTypesTestSignalConfig 
    MAX-ACCESS read-only
    STATUS current
    DESCRIPTION "The enable switching of test signal function
		
		
		default value :NONE"
::= { wan10gSdhEntry 14 }
wan10gSdhServiceLabel OBJECT-TYPE
    SYNTAX OCTET STRING  (SIZE (0..128))
    MAX-ACCESS read-only
    STATUS current
    DESCRIPTION "Path/service name of cross-connection related facility.
		
		
		"
::= { wan10gSdhEntry 15 }
wan10gSdhExpTrc OBJECT-TYPE
    SYNTAX OCTET STRING  (SIZE (0..15))
    MAX-ACCESS read-only
    STATUS current
    DESCRIPTION "The expected trc(trail trace identification)
		
		
		"
::= { wan10gSdhEntry 16 }
wan10gSdhTxTrc OBJECT-TYPE
    SYNTAX OCTET STRING  (SIZE (0..15))
    MAX-ACCESS read-only
    STATUS current
    DESCRIPTION "The transmitter trc(trail trace identification)
		Conditions:ancestor::card/switching-type = 'tdm'
		
		"
::= { wan10gSdhEntry 17 }
wan10gSdhRxTrc OBJECT-TYPE
    SYNTAX OCTET STRING  (SIZE (0..15))
    MAX-ACCESS read-only
    STATUS current
    DESCRIPTION "The received trc(trail trace identification)
		
		
		"
::= { wan10gSdhEntry 18 }
wan10gSdhTimAct OBJECT-TYPE
    SYNTAX CoriantTypesEnableSwitch 
    MAX-ACCESS read-only
    STATUS current
    DESCRIPTION "The enable switching of inserting AIS by tim function
		
		
		default value :disabled"
::= { wan10gSdhEntry 19 }
wan10gSdhTimMonitor OBJECT-TYPE
    SYNTAX CoriantTypesEnableSwitch 
    MAX-ACCESS read-only
    STATUS current
    DESCRIPTION "The enable switching of tim defect monitor mode
		
		
		default value :disabled"
::= { wan10gSdhEntry 20 }
wan10gSdhAisType OBJECT-TYPE
    SYNTAX INTEGER  {
	 genericAis (0),
	 msAis (1),
	 aisL (2)
	}
    MAX-ACCESS read-only
    STATUS current
    DESCRIPTION "NULL
		
		
		default value :Generic-AIS"
::= { wan10gSdhEntry 21 }
eth10gStatistics OBJECT IDENTIFIER ::= { otn 32 }
eth10gStatisticsTable OBJECT-TYPE
    SYNTAX SEQUENCE OF Eth10gStatisticsEntry
    MAX-ACCESS not-accessible
    STATUS current
    DESCRIPTION "NULL"
::= { eth10gStatistics 1 }
eth10gStatisticsEntry OBJECT-TYPE
    SYNTAX Eth10gStatisticsEntry
    MAX-ACCESS not-accessible
    STATUS current
    DESCRIPTION "Entry of eth10gStatisticsTable" 
    INDEX { shelfId,slotId,subslotId,portId,subportId }
::= { eth10gStatisticsTable 1 }
Eth10gStatisticsEntry ::= 
SEQUENCE {
	eth10gStatisticsEntryLastClear IetfYangTypesDateAndTime,
	eth10gStatisticsEntryLossOfSignalSeconds OCTET STRING,
	eth10gStatisticsEntryBitErrorFec OCTET STRING,
	eth10gStatisticsEntryUncorrectedBlockErrorFec OCTET STRING,
	eth10gStatisticsEntryInSymbolErrors OCTET STRING,
	eth10gStatisticsEntryInDropEvents OCTET STRING,
	eth10gStatisticsEntryInOctets OCTET STRING,
	eth10gStatisticsEntryInPackets OCTET STRING,
	eth10gStatisticsEntryInBroadcastPackets OCTET STRING,
	eth10gStatisticsEntryInMulticastPackets OCTET STRING,
	eth10gStatisticsEntryInCrcAlignErrors OCTET STRING,
	eth10gStatisticsEntryInUndersizePackets OCTET STRING,
	eth10gStatisticsEntryInOversizePackets OCTET STRING,
	eth10gStatisticsEntryInFragments OCTET STRING,
	eth10gStatisticsEntryInJabbers OCTET STRING,
	eth10gStatisticsEntryInPackets64octets OCTET STRING,
	eth10gStatisticsEntryInPackets65to127octets OCTET STRING,
	eth10gStatisticsEntryInPackets128to255octets OCTET STRING,
	eth10gStatisticsEntryInPackets256to511octets OCTET STRING,
	eth10gStatisticsEntryInPackets512to1023octets OCTET STRING,
	eth10gStatisticsEntryInPackets1024to1518octets OCTET STRING,
	eth10gStatisticsEntryOutSymbolErrors OCTET STRING,
	eth10gStatisticsEntryOutDropEvents OCTET STRING,
	eth10gStatisticsEntryOutOctets OCTET STRING,
	eth10gStatisticsEntryOutPackets OCTET STRING,
	eth10gStatisticsEntryOutBroadcastPackets OCTET STRING,
	eth10gStatisticsEntryOutMulticastPackets OCTET STRING,
	eth10gStatisticsEntryOutCrcAlignErrors OCTET STRING,
	eth10gStatisticsEntryOutUndersizePackets OCTET STRING,
	eth10gStatisticsEntryOutOversizePackets OCTET STRING,
	eth10gStatisticsEntryOutFragments OCTET STRING,
	eth10gStatisticsEntryOutJabbers OCTET STRING,
	eth10gStatisticsEntryOutPackets64octets OCTET STRING,
	eth10gStatisticsEntryOutPackets65to127octets OCTET STRING,
	eth10gStatisticsEntryOutPackets128to255octets OCTET STRING,
	eth10gStatisticsEntryOutPackets256to511octets OCTET STRING,
	eth10gStatisticsEntryOutPackets512to1023octets OCTET STRING,
	eth10gStatisticsEntryOutPackets1024to1518octets OCTET STRING
    }
eth10gStatisticsEntryLastClear OBJECT-TYPE
    SYNTAX IetfYangTypesDateAndTime 
    MAX-ACCESS read-only
    STATUS current
    DESCRIPTION "The start time of statistics monitor
		
		
		default value :0000-00-00T00:00:00.000Z"
::= { eth10gStatisticsEntry 1 }
eth10gStatisticsEntryLossOfSignalSeconds OBJECT-TYPE
    SYNTAX OCTET STRING 
    MAX-ACCESS read-only
    STATUS current
    DESCRIPTION "the statistics seconds counting for signal loss
		
		UNITS:seconds
		"
::= { eth10gStatisticsEntry 2 }
eth10gStatisticsEntryBitErrorFec OBJECT-TYPE
    SYNTAX OCTET STRING 
    MAX-ACCESS read-only
    STATUS current
    DESCRIPTION "the statistics bits counting for error bit forward error correction
		
		UNITS:bits
		"
::= { eth10gStatisticsEntry 3 }
eth10gStatisticsEntryUncorrectedBlockErrorFec OBJECT-TYPE
    SYNTAX OCTET STRING 
    MAX-ACCESS read-only
    STATUS current
    DESCRIPTION "the statistics blocks counting for uncorrected block error forward error correction
		
		UNITS:blocks
		"
::= { eth10gStatisticsEntry 4 }
eth10gStatisticsEntryInSymbolErrors OBJECT-TYPE
    SYNTAX OCTET STRING 
    MAX-ACCESS read-only
    STATUS current
    DESCRIPTION "the statistics Times counting for input signal symbol errors
		
		UNITS:Events
		"
::= { eth10gStatisticsEntry 5 }
eth10gStatisticsEntryInDropEvents OBJECT-TYPE
    SYNTAX OCTET STRING 
    MAX-ACCESS read-only
    STATUS current
    DESCRIPTION "the statistics counting for input signal drop events
		
		UNITS:events
		"
::= { eth10gStatisticsEntry 6 }
eth10gStatisticsEntryInOctets OBJECT-TYPE
    SYNTAX OCTET STRING 
    MAX-ACCESS read-only
    STATUS current
    DESCRIPTION "the statistics counting for input signal octets
		
		UNITS:octets
		"
::= { eth10gStatisticsEntry 7 }
eth10gStatisticsEntryInPackets OBJECT-TYPE
    SYNTAX OCTET STRING 
    MAX-ACCESS read-only
    STATUS current
    DESCRIPTION "the statistics counting for input signal packets
		
		UNITS:packets
		"
::= { eth10gStatisticsEntry 8 }
eth10gStatisticsEntryInBroadcastPackets OBJECT-TYPE
    SYNTAX OCTET STRING 
    MAX-ACCESS read-only
    STATUS current
    DESCRIPTION "the statistics counting for input broadcast packets
		
		UNITS:packets
		"
::= { eth10gStatisticsEntry 9 }
eth10gStatisticsEntryInMulticastPackets OBJECT-TYPE
    SYNTAX OCTET STRING 
    MAX-ACCESS read-only
    STATUS current
    DESCRIPTION "the statistics counting for input multicast packets
		
		UNITS:packets
		"
::= { eth10gStatisticsEntry 10 }
eth10gStatisticsEntryInCrcAlignErrors OBJECT-TYPE
    SYNTAX OCTET STRING 
    MAX-ACCESS read-only
    STATUS current
    DESCRIPTION "the statistics counting for input CRC error packets
		
		UNITS:packets
		"
::= { eth10gStatisticsEntry 11 }
eth10gStatisticsEntryInUndersizePackets OBJECT-TYPE
    SYNTAX OCTET STRING 
    MAX-ACCESS read-only
    STATUS current
    DESCRIPTION "the statistics counting for input undersize packets
		
		UNITS:packets
		"
::= { eth10gStatisticsEntry 12 }
eth10gStatisticsEntryInOversizePackets OBJECT-TYPE
    SYNTAX OCTET STRING 
    MAX-ACCESS read-only
    STATUS current
    DESCRIPTION "the statistics counting for input oversize packets
		
		UNITS:packets
		"
::= { eth10gStatisticsEntry 13 }
eth10gStatisticsEntryInFragments OBJECT-TYPE
    SYNTAX OCTET STRING 
    MAX-ACCESS read-only
    STATUS current
    DESCRIPTION "the statistics counting for input fragment packets
		
		UNITS:packets
		"
::= { eth10gStatisticsEntry 14 }
eth10gStatisticsEntryInJabbers OBJECT-TYPE
    SYNTAX OCTET STRING 
    MAX-ACCESS read-only
    STATUS current
    DESCRIPTION "the statistics counting for input jabber packets
		
		UNITS:packets
		"
::= { eth10gStatisticsEntry 15 }
eth10gStatisticsEntryInPackets64octets OBJECT-TYPE
    SYNTAX OCTET STRING 
    MAX-ACCESS read-only
    STATUS current
    DESCRIPTION "the statistics counting for input 64 octets packets
		
		UNITS:packets
		"
::= { eth10gStatisticsEntry 16 }
eth10gStatisticsEntryInPackets65to127octets OBJECT-TYPE
    SYNTAX OCTET STRING 
    MAX-ACCESS read-only
    STATUS current
    DESCRIPTION "the statistics counting for input 65 to 127 octets packets
		
		UNITS:packets
		"
::= { eth10gStatisticsEntry 17 }
eth10gStatisticsEntryInPackets128to255octets OBJECT-TYPE
    SYNTAX OCTET STRING 
    MAX-ACCESS read-only
    STATUS current
    DESCRIPTION "the statistics counting for input 128 to 255 octets packets
		
		UNITS:packets
		"
::= { eth10gStatisticsEntry 18 }
eth10gStatisticsEntryInPackets256to511octets OBJECT-TYPE
    SYNTAX OCTET STRING 
    MAX-ACCESS read-only
    STATUS current
    DESCRIPTION "the statistics counting for input 256 to 511 octets packets
		
		UNITS:packets
		"
::= { eth10gStatisticsEntry 19 }
eth10gStatisticsEntryInPackets512to1023octets OBJECT-TYPE
    SYNTAX OCTET STRING 
    MAX-ACCESS read-only
    STATUS current
    DESCRIPTION "the statistics counting for input 512 to 1023 octets packets
		
		UNITS:packets
		"
::= { eth10gStatisticsEntry 20 }
eth10gStatisticsEntryInPackets1024to1518octets OBJECT-TYPE
    SYNTAX OCTET STRING 
    MAX-ACCESS read-only
    STATUS current
    DESCRIPTION "the statistics counting for input 1024 to 1518 octets packets
		
		UNITS:packets
		"
::= { eth10gStatisticsEntry 21 }
eth10gStatisticsEntryOutSymbolErrors OBJECT-TYPE
    SYNTAX OCTET STRING 
    MAX-ACCESS read-only
    STATUS current
    DESCRIPTION "the statistics Times counting for output signal symbol errors
		
		UNITS:Events
		"
::= { eth10gStatisticsEntry 22 }
eth10gStatisticsEntryOutDropEvents OBJECT-TYPE
    SYNTAX OCTET STRING 
    MAX-ACCESS read-only
    STATUS current
    DESCRIPTION "the statistics counting for output signal drop events
		
		UNITS:events
		"
::= { eth10gStatisticsEntry 23 }
eth10gStatisticsEntryOutOctets OBJECT-TYPE
    SYNTAX OCTET STRING 
    MAX-ACCESS read-only
    STATUS current
    DESCRIPTION "the statistics counting for output signal octets
		
		UNITS:octets
		"
::= { eth10gStatisticsEntry 24 }
eth10gStatisticsEntryOutPackets OBJECT-TYPE
    SYNTAX OCTET STRING 
    MAX-ACCESS read-only
    STATUS current
    DESCRIPTION "the statistics counting for output signal packets
		
		UNITS:packets
		"
::= { eth10gStatisticsEntry 25 }
eth10gStatisticsEntryOutBroadcastPackets OBJECT-TYPE
    SYNTAX OCTET STRING 
    MAX-ACCESS read-only
    STATUS current
    DESCRIPTION "the statistics counting for output broadcast packets
		
		UNITS:packets
		"
::= { eth10gStatisticsEntry 26 }
eth10gStatisticsEntryOutMulticastPackets OBJECT-TYPE
    SYNTAX OCTET STRING 
    MAX-ACCESS read-only
    STATUS current
    DESCRIPTION "the statistics counting for output multicast packets
		
		UNITS:packets
		"
::= { eth10gStatisticsEntry 27 }
eth10gStatisticsEntryOutCrcAlignErrors OBJECT-TYPE
    SYNTAX OCTET STRING 
    MAX-ACCESS read-only
    STATUS current
    DESCRIPTION "the statistics counting for output CRC error packets
		
		UNITS:packets
		"
::= { eth10gStatisticsEntry 28 }
eth10gStatisticsEntryOutUndersizePackets OBJECT-TYPE
    SYNTAX OCTET STRING 
    MAX-ACCESS read-only
    STATUS current
    DESCRIPTION "the statistics counting for output undersize packets
		
		UNITS:packets
		"
::= { eth10gStatisticsEntry 29 }
eth10gStatisticsEntryOutOversizePackets OBJECT-TYPE
    SYNTAX OCTET STRING 
    MAX-ACCESS read-only
    STATUS current
    DESCRIPTION "the statistics counting for output oversize packets
		
		UNITS:packets
		"
::= { eth10gStatisticsEntry 30 }
eth10gStatisticsEntryOutFragments OBJECT-TYPE
    SYNTAX OCTET STRING 
    MAX-ACCESS read-only
    STATUS current
    DESCRIPTION "the statistics counting for output fragment packets
		
		UNITS:packets
		"
::= { eth10gStatisticsEntry 31 }
eth10gStatisticsEntryOutJabbers OBJECT-TYPE
    SYNTAX OCTET STRING 
    MAX-ACCESS read-only
    STATUS current
    DESCRIPTION "the statistics counting for output jabber packets
		
		UNITS:packets
		"
::= { eth10gStatisticsEntry 32 }
eth10gStatisticsEntryOutPackets64octets OBJECT-TYPE
    SYNTAX OCTET STRING 
    MAX-ACCESS read-only
    STATUS current
    DESCRIPTION "the statistics counting for output 64 octets packets
		
		UNITS:packets
		"
::= { eth10gStatisticsEntry 33 }
eth10gStatisticsEntryOutPackets65to127octets OBJECT-TYPE
    SYNTAX OCTET STRING 
    MAX-ACCESS read-only
    STATUS current
    DESCRIPTION "the statistics counting for output 65 to 127 octets packets
		
		UNITS:packets
		"
::= { eth10gStatisticsEntry 34 }
eth10gStatisticsEntryOutPackets128to255octets OBJECT-TYPE
    SYNTAX OCTET STRING 
    MAX-ACCESS read-only
    STATUS current
    DESCRIPTION "the statistics counting for output 128 to 255 octets packets
		
		UNITS:packets
		"
::= { eth10gStatisticsEntry 35 }
eth10gStatisticsEntryOutPackets256to511octets OBJECT-TYPE
    SYNTAX OCTET STRING 
    MAX-ACCESS read-only
    STATUS current
    DESCRIPTION "the statistics counting for output 256 to 511 octets packets
		
		UNITS:packets
		"
::= { eth10gStatisticsEntry 36 }
eth10gStatisticsEntryOutPackets512to1023octets OBJECT-TYPE
    SYNTAX OCTET STRING 
    MAX-ACCESS read-only
    STATUS current
    DESCRIPTION "the statistics counting for output 512 to 1023 octets packets
		
		UNITS:packets
		"
::= { eth10gStatisticsEntry 37 }
eth10gStatisticsEntryOutPackets1024to1518octets OBJECT-TYPE
    SYNTAX OCTET STRING 
    MAX-ACCESS read-only
    STATUS current
    DESCRIPTION "the statistics counting for output 1024 to 1518 octets packets
		
		UNITS:packets
		"
::= { eth10gStatisticsEntry 38 }
oduStatistics OBJECT IDENTIFIER ::= { otn 33 }
oduStatisticsTable OBJECT-TYPE
    SYNTAX SEQUENCE OF OduStatisticsEntry
    MAX-ACCESS not-accessible
    STATUS current
    DESCRIPTION "NULL"
::= { oduStatistics 1 }
oduStatisticsEntry OBJECT-TYPE
    SYNTAX OduStatisticsEntry
    MAX-ACCESS not-accessible
    STATUS current
    DESCRIPTION "Entry of oduStatisticsTable" 
    INDEX { shelfId,slotId,subslotId,portId,subportId,odutypeL1,oduidL1,odutypeL2,oduidL2,odutypeL3,oduidL3,odutypeL4,oduidL4 }
::= { oduStatisticsTable 1 }
OduStatisticsEntry ::= 
SEQUENCE {
	oduStatisticsEntryLastClear IetfYangTypesDateAndTime,
	oduStatisticsEntryErroredBlocks OCTET STRING,
	oduStatisticsEntryErroredSeconds OCTET STRING,
	oduStatisticsEntrySeverelyErroredSeconds OCTET STRING,
	oduStatisticsEntryUnavailableSeconds OCTET STRING,
	oduStatisticsEntryEncryptionFailRx OCTET STRING
    }
oduStatisticsEntryLastClear OBJECT-TYPE
    SYNTAX IetfYangTypesDateAndTime 
    MAX-ACCESS read-only
    STATUS current
    DESCRIPTION "The start time of statistics monitor
		
		
		default value :0000-00-00T00:00:00.000Z"
::= { oduStatisticsEntry 1 }
oduStatisticsEntryErroredBlocks OBJECT-TYPE
    SYNTAX OCTET STRING 
    MAX-ACCESS read-only
    STATUS current
    DESCRIPTION "the statistics counting for errored blocks
		
		UNITS:blocks
		"
::= { oduStatisticsEntry 2 }
oduStatisticsEntryErroredSeconds OBJECT-TYPE
    SYNTAX OCTET STRING 
    MAX-ACCESS read-only
    STATUS current
    DESCRIPTION "the statistics seconds counting for errored signal
		
		UNITS:seconds
		"
::= { oduStatisticsEntry 3 }
oduStatisticsEntrySeverelyErroredSeconds OBJECT-TYPE
    SYNTAX OCTET STRING 
    MAX-ACCESS read-only
    STATUS current
    DESCRIPTION "the statistics seconds counting for severely errored signal
		
		UNITS:seconds
		"
::= { oduStatisticsEntry 4 }
oduStatisticsEntryUnavailableSeconds OBJECT-TYPE
    SYNTAX OCTET STRING 
    MAX-ACCESS read-only
    STATUS current
    DESCRIPTION "the statistics seconds counting for unavailable signal
		
		UNITS:seconds
		"
::= { oduStatisticsEntry 5 }
oduStatisticsEntryEncryptionFailRx OBJECT-TYPE
    SYNTAX OCTET STRING 
    MAX-ACCESS read-only
    STATUS current
    DESCRIPTION "Failed Encryption Frames of Receive side
		
		UNITS:frames
		"
::= { oduStatisticsEntry 6 }
eth40gStatistics OBJECT IDENTIFIER ::= { otn 34 }
eth40gStatisticsTable OBJECT-TYPE
    SYNTAX SEQUENCE OF Eth40gStatisticsEntry
    MAX-ACCESS not-accessible
    STATUS current
    DESCRIPTION "NULL"
::= { eth40gStatistics 1 }
eth40gStatisticsEntry OBJECT-TYPE
    SYNTAX Eth40gStatisticsEntry
    MAX-ACCESS not-accessible
    STATUS current
    DESCRIPTION "Entry of eth40gStatisticsTable" 
    INDEX { shelfId,slotId,subslotId,portId,subportId }
::= { eth40gStatisticsTable 1 }
Eth40gStatisticsEntry ::= 
SEQUENCE {
	eth40gStatisticsEntryLastClear IetfYangTypesDateAndTime,
	eth40gStatisticsEntryLossOfSignalSeconds OCTET STRING,
	eth40gStatisticsEntryBitErrorFec OCTET STRING,
	eth40gStatisticsEntryUncorrectedBlockErrorFec OCTET STRING,
	eth40gStatisticsEntryInSymbolErrors OCTET STRING,
	eth40gStatisticsEntryInDropEvents OCTET STRING,
	eth40gStatisticsEntryInOctets OCTET STRING,
	eth40gStatisticsEntryInPackets OCTET STRING,
	eth40gStatisticsEntryInBroadcastPackets OCTET STRING,
	eth40gStatisticsEntryInMulticastPackets OCTET STRING,
	eth40gStatisticsEntryInCrcAlignErrors OCTET STRING,
	eth40gStatisticsEntryInUndersizePackets OCTET STRING,
	eth40gStatisticsEntryInOversizePackets OCTET STRING,
	eth40gStatisticsEntryInFragments OCTET STRING,
	eth40gStatisticsEntryInJabbers OCTET STRING,
	eth40gStatisticsEntryInPackets64octets OCTET STRING,
	eth40gStatisticsEntryInPackets65to127octets OCTET STRING,
	eth40gStatisticsEntryInPackets128to255octets OCTET STRING,
	eth40gStatisticsEntryInPackets256to511octets OCTET STRING,
	eth40gStatisticsEntryInPackets512to1023octets OCTET STRING,
	eth40gStatisticsEntryInPackets1024to1518octets OCTET STRING,
	eth40gStatisticsEntryOutSymbolErrors OCTET STRING,
	eth40gStatisticsEntryOutDropEvents OCTET STRING,
	eth40gStatisticsEntryOutOctets OCTET STRING,
	eth40gStatisticsEntryOutPackets OCTET STRING,
	eth40gStatisticsEntryOutBroadcastPackets OCTET STRING,
	eth40gStatisticsEntryOutMulticastPackets OCTET STRING,
	eth40gStatisticsEntryOutCrcAlignErrors OCTET STRING,
	eth40gStatisticsEntryOutUndersizePackets OCTET STRING,
	eth40gStatisticsEntryOutOversizePackets OCTET STRING,
	eth40gStatisticsEntryOutFragments OCTET STRING,
	eth40gStatisticsEntryOutJabbers OCTET STRING,
	eth40gStatisticsEntryOutPackets64octets OCTET STRING,
	eth40gStatisticsEntryOutPackets65to127octets OCTET STRING,
	eth40gStatisticsEntryOutPackets128to255octets OCTET STRING,
	eth40gStatisticsEntryOutPackets256to511octets OCTET STRING,
	eth40gStatisticsEntryOutPackets512to1023octets OCTET STRING,
	eth40gStatisticsEntryOutPackets1024to1518octets OCTET STRING
    }
eth40gStatisticsEntryLastClear OBJECT-TYPE
    SYNTAX IetfYangTypesDateAndTime 
    MAX-ACCESS read-only
    STATUS current
    DESCRIPTION "The start time of statistics monitor
		
		
		default value :0000-00-00T00:00:00.000Z"
::= { eth40gStatisticsEntry 1 }
eth40gStatisticsEntryLossOfSignalSeconds OBJECT-TYPE
    SYNTAX OCTET STRING 
    MAX-ACCESS read-only
    STATUS current
    DESCRIPTION "the statistics seconds counting for signal loss
		
		UNITS:seconds
		"
::= { eth40gStatisticsEntry 2 }
eth40gStatisticsEntryBitErrorFec OBJECT-TYPE
    SYNTAX OCTET STRING 
    MAX-ACCESS read-only
    STATUS current
    DESCRIPTION "the statistics bits counting for error bit forward error correction
		
		UNITS:bits
		"
::= { eth40gStatisticsEntry 3 }
eth40gStatisticsEntryUncorrectedBlockErrorFec OBJECT-TYPE
    SYNTAX OCTET STRING 
    MAX-ACCESS read-only
    STATUS current
    DESCRIPTION "the statistics blocks counting for uncorrected block error forward error correction
		
		UNITS:blocks
		"
::= { eth40gStatisticsEntry 4 }
eth40gStatisticsEntryInSymbolErrors OBJECT-TYPE
    SYNTAX OCTET STRING 
    MAX-ACCESS read-only
    STATUS current
    DESCRIPTION "the statistics Times counting for input signal symbol errors
		
		UNITS:Events
		"
::= { eth40gStatisticsEntry 5 }
eth40gStatisticsEntryInDropEvents OBJECT-TYPE
    SYNTAX OCTET STRING 
    MAX-ACCESS read-only
    STATUS current
    DESCRIPTION "the statistics counting for input signal drop events
		
		UNITS:events
		"
::= { eth40gStatisticsEntry 6 }
eth40gStatisticsEntryInOctets OBJECT-TYPE
    SYNTAX OCTET STRING 
    MAX-ACCESS read-only
    STATUS current
    DESCRIPTION "the statistics counting for input signal octets
		
		UNITS:octets
		"
::= { eth40gStatisticsEntry 7 }
eth40gStatisticsEntryInPackets OBJECT-TYPE
    SYNTAX OCTET STRING 
    MAX-ACCESS read-only
    STATUS current
    DESCRIPTION "the statistics counting for input signal packets
		
		UNITS:packets
		"
::= { eth40gStatisticsEntry 8 }
eth40gStatisticsEntryInBroadcastPackets OBJECT-TYPE
    SYNTAX OCTET STRING 
    MAX-ACCESS read-only
    STATUS current
    DESCRIPTION "the statistics counting for input broadcast packets
		
		UNITS:packets
		"
::= { eth40gStatisticsEntry 9 }
eth40gStatisticsEntryInMulticastPackets OBJECT-TYPE
    SYNTAX OCTET STRING 
    MAX-ACCESS read-only
    STATUS current
    DESCRIPTION "the statistics counting for input multicast packets
		
		UNITS:packets
		"
::= { eth40gStatisticsEntry 10 }
eth40gStatisticsEntryInCrcAlignErrors OBJECT-TYPE
    SYNTAX OCTET STRING 
    MAX-ACCESS read-only
    STATUS current
    DESCRIPTION "the statistics counting for input CRC error packets
		
		UNITS:packets
		"
::= { eth40gStatisticsEntry 11 }
eth40gStatisticsEntryInUndersizePackets OBJECT-TYPE
    SYNTAX OCTET STRING 
    MAX-ACCESS read-only
    STATUS current
    DESCRIPTION "the statistics counting for input undersize packets
		
		UNITS:packets
		"
::= { eth40gStatisticsEntry 12 }
eth40gStatisticsEntryInOversizePackets OBJECT-TYPE
    SYNTAX OCTET STRING 
    MAX-ACCESS read-only
    STATUS current
    DESCRIPTION "the statistics counting for input oversize packets
		
		UNITS:packets
		"
::= { eth40gStatisticsEntry 13 }
eth40gStatisticsEntryInFragments OBJECT-TYPE
    SYNTAX OCTET STRING 
    MAX-ACCESS read-only
    STATUS current
    DESCRIPTION "the statistics counting for input fragment packets
		
		UNITS:packets
		"
::= { eth40gStatisticsEntry 14 }
eth40gStatisticsEntryInJabbers OBJECT-TYPE
    SYNTAX OCTET STRING 
    MAX-ACCESS read-only
    STATUS current
    DESCRIPTION "the statistics counting for input jabber packets
		
		UNITS:packets
		"
::= { eth40gStatisticsEntry 15 }
eth40gStatisticsEntryInPackets64octets OBJECT-TYPE
    SYNTAX OCTET STRING 
    MAX-ACCESS read-only
    STATUS current
    DESCRIPTION "the statistics counting for input 64 octets packets
		
		UNITS:packets
		"
::= { eth40gStatisticsEntry 16 }
eth40gStatisticsEntryInPackets65to127octets OBJECT-TYPE
    SYNTAX OCTET STRING 
    MAX-ACCESS read-only
    STATUS current
    DESCRIPTION "the statistics counting for input 65 to 127 octets packets
		
		UNITS:packets
		"
::= { eth40gStatisticsEntry 17 }
eth40gStatisticsEntryInPackets128to255octets OBJECT-TYPE
    SYNTAX OCTET STRING 
    MAX-ACCESS read-only
    STATUS current
    DESCRIPTION "the statistics counting for input 128 to 255 octets packets
		
		UNITS:packets
		"
::= { eth40gStatisticsEntry 18 }
eth40gStatisticsEntryInPackets256to511octets OBJECT-TYPE
    SYNTAX OCTET STRING 
    MAX-ACCESS read-only
    STATUS current
    DESCRIPTION "the statistics counting for input 256 to 511 octets packets
		
		UNITS:packets
		"
::= { eth40gStatisticsEntry 19 }
eth40gStatisticsEntryInPackets512to1023octets OBJECT-TYPE
    SYNTAX OCTET STRING 
    MAX-ACCESS read-only
    STATUS current
    DESCRIPTION "the statistics counting for input 512 to 1023 octets packets
		
		UNITS:packets
		"
::= { eth40gStatisticsEntry 20 }
eth40gStatisticsEntryInPackets1024to1518octets OBJECT-TYPE
    SYNTAX OCTET STRING 
    MAX-ACCESS read-only
    STATUS current
    DESCRIPTION "the statistics counting for input 1024 to 1518 octets packets
		
		UNITS:packets
		"
::= { eth40gStatisticsEntry 21 }
eth40gStatisticsEntryOutSymbolErrors OBJECT-TYPE
    SYNTAX OCTET STRING 
    MAX-ACCESS read-only
    STATUS current
    DESCRIPTION "the statistics Times counting for output signal symbol errors
		
		UNITS:Events
		"
::= { eth40gStatisticsEntry 22 }
eth40gStatisticsEntryOutDropEvents OBJECT-TYPE
    SYNTAX OCTET STRING 
    MAX-ACCESS read-only
    STATUS current
    DESCRIPTION "the statistics counting for output signal drop events
		
		UNITS:events
		"
::= { eth40gStatisticsEntry 23 }
eth40gStatisticsEntryOutOctets OBJECT-TYPE
    SYNTAX OCTET STRING 
    MAX-ACCESS read-only
    STATUS current
    DESCRIPTION "the statistics counting for output signal octets
		
		UNITS:octets
		"
::= { eth40gStatisticsEntry 24 }
eth40gStatisticsEntryOutPackets OBJECT-TYPE
    SYNTAX OCTET STRING 
    MAX-ACCESS read-only
    STATUS current
    DESCRIPTION "the statistics counting for output signal packets
		
		UNITS:packets
		"
::= { eth40gStatisticsEntry 25 }
eth40gStatisticsEntryOutBroadcastPackets OBJECT-TYPE
    SYNTAX OCTET STRING 
    MAX-ACCESS read-only
    STATUS current
    DESCRIPTION "the statistics counting for output broadcast packets
		
		UNITS:packets
		"
::= { eth40gStatisticsEntry 26 }
eth40gStatisticsEntryOutMulticastPackets OBJECT-TYPE
    SYNTAX OCTET STRING 
    MAX-ACCESS read-only
    STATUS current
    DESCRIPTION "the statistics counting for output multicast packets
		
		UNITS:packets
		"
::= { eth40gStatisticsEntry 27 }
eth40gStatisticsEntryOutCrcAlignErrors OBJECT-TYPE
    SYNTAX OCTET STRING 
    MAX-ACCESS read-only
    STATUS current
    DESCRIPTION "the statistics counting for output CRC error packets
		
		UNITS:packets
		"
::= { eth40gStatisticsEntry 28 }
eth40gStatisticsEntryOutUndersizePackets OBJECT-TYPE
    SYNTAX OCTET STRING 
    MAX-ACCESS read-only
    STATUS current
    DESCRIPTION "the statistics counting for output undersize packets
		
		UNITS:packets
		"
::= { eth40gStatisticsEntry 29 }
eth40gStatisticsEntryOutOversizePackets OBJECT-TYPE
    SYNTAX OCTET STRING 
    MAX-ACCESS read-only
    STATUS current
    DESCRIPTION "the statistics counting for output oversize packets
		
		UNITS:packets
		"
::= { eth40gStatisticsEntry 30 }
eth40gStatisticsEntryOutFragments OBJECT-TYPE
    SYNTAX OCTET STRING 
    MAX-ACCESS read-only
    STATUS current
    DESCRIPTION "the statistics counting for output fragment packets
		
		UNITS:packets
		"
::= { eth40gStatisticsEntry 31 }
eth40gStatisticsEntryOutJabbers OBJECT-TYPE
    SYNTAX OCTET STRING 
    MAX-ACCESS read-only
    STATUS current
    DESCRIPTION "the statistics counting for output jabber packets
		
		UNITS:packets
		"
::= { eth40gStatisticsEntry 32 }
eth40gStatisticsEntryOutPackets64octets OBJECT-TYPE
    SYNTAX OCTET STRING 
    MAX-ACCESS read-only
    STATUS current
    DESCRIPTION "the statistics counting for output 64 octets packets
		
		UNITS:packets
		"
::= { eth40gStatisticsEntry 33 }
eth40gStatisticsEntryOutPackets65to127octets OBJECT-TYPE
    SYNTAX OCTET STRING 
    MAX-ACCESS read-only
    STATUS current
    DESCRIPTION "the statistics counting for output 65 to 127 octets packets
		
		UNITS:packets
		"
::= { eth40gStatisticsEntry 34 }
eth40gStatisticsEntryOutPackets128to255octets OBJECT-TYPE
    SYNTAX OCTET STRING 
    MAX-ACCESS read-only
    STATUS current
    DESCRIPTION "the statistics counting for output 128 to 255 octets packets
		
		UNITS:packets
		"
::= { eth40gStatisticsEntry 35 }
eth40gStatisticsEntryOutPackets256to511octets OBJECT-TYPE
    SYNTAX OCTET STRING 
    MAX-ACCESS read-only
    STATUS current
    DESCRIPTION "the statistics counting for output 256 to 511 octets packets
		
		UNITS:packets
		"
::= { eth40gStatisticsEntry 36 }
eth40gStatisticsEntryOutPackets512to1023octets OBJECT-TYPE
    SYNTAX OCTET STRING 
    MAX-ACCESS read-only
    STATUS current
    DESCRIPTION "the statistics counting for output 512 to 1023 octets packets
		
		UNITS:packets
		"
::= { eth40gStatisticsEntry 37 }
eth40gStatisticsEntryOutPackets1024to1518octets OBJECT-TYPE
    SYNTAX OCTET STRING 
    MAX-ACCESS read-only
    STATUS current
    DESCRIPTION "the statistics counting for output 1024 to 1518 octets packets
		
		UNITS:packets
		"
::= { eth40gStatisticsEntry 38 }
eth100gStatistics OBJECT IDENTIFIER ::= { otn 35 }
eth100gStatisticsTable OBJECT-TYPE
    SYNTAX SEQUENCE OF Eth100gStatisticsEntry
    MAX-ACCESS not-accessible
    STATUS current
    DESCRIPTION "NULL"
::= { eth100gStatistics 1 }
eth100gStatisticsEntry OBJECT-TYPE
    SYNTAX Eth100gStatisticsEntry
    MAX-ACCESS not-accessible
    STATUS current
    DESCRIPTION "Entry of eth100gStatisticsTable" 
    INDEX { shelfId,slotId,subslotId,portId,subportId }
::= { eth100gStatisticsTable 1 }
Eth100gStatisticsEntry ::= 
SEQUENCE {
	eth100gStatisticsEntryLastClear IetfYangTypesDateAndTime,
	eth100gStatisticsEntryLossOfSignalSeconds OCTET STRING,
	eth100gStatisticsEntryBitErrorFec OCTET STRING,
	eth100gStatisticsEntryUncorrectedBlockErrorFec OCTET STRING,
	eth100gStatisticsEntryInSymbolErrors OCTET STRING,
	eth100gStatisticsEntryInDropEvents OCTET STRING,
	eth100gStatisticsEntryInOctets OCTET STRING,
	eth100gStatisticsEntryInPackets OCTET STRING,
	eth100gStatisticsEntryInBroadcastPackets OCTET STRING,
	eth100gStatisticsEntryInMulticastPackets OCTET STRING,
	eth100gStatisticsEntryInCrcAlignErrors OCTET STRING,
	eth100gStatisticsEntryInUndersizePackets OCTET STRING,
	eth100gStatisticsEntryInOversizePackets OCTET STRING,
	eth100gStatisticsEntryInFragments OCTET STRING,
	eth100gStatisticsEntryInJabbers OCTET STRING,
	eth100gStatisticsEntryInPackets64octets OCTET STRING,
	eth100gStatisticsEntryInPackets65to127octets OCTET STRING,
	eth100gStatisticsEntryInPackets128to255octets OCTET STRING,
	eth100gStatisticsEntryInPackets256to511octets OCTET STRING,
	eth100gStatisticsEntryInPackets512to1023octets OCTET STRING,
	eth100gStatisticsEntryInPackets1024to1518octets OCTET STRING,
	eth100gStatisticsEntryOutSymbolErrors OCTET STRING,
	eth100gStatisticsEntryOutDropEvents OCTET STRING,
	eth100gStatisticsEntryOutOctets OCTET STRING,
	eth100gStatisticsEntryOutPackets OCTET STRING,
	eth100gStatisticsEntryOutBroadcastPackets OCTET STRING,
	eth100gStatisticsEntryOutMulticastPackets OCTET STRING,
	eth100gStatisticsEntryOutCrcAlignErrors OCTET STRING,
	eth100gStatisticsEntryOutUndersizePackets OCTET STRING,
	eth100gStatisticsEntryOutOversizePackets OCTET STRING,
	eth100gStatisticsEntryOutFragments OCTET STRING,
	eth100gStatisticsEntryOutJabbers OCTET STRING,
	eth100gStatisticsEntryOutPackets64octets OCTET STRING,
	eth100gStatisticsEntryOutPackets65to127octets OCTET STRING,
	eth100gStatisticsEntryOutPackets128to255octets OCTET STRING,
	eth100gStatisticsEntryOutPackets256to511octets OCTET STRING,
	eth100gStatisticsEntryOutPackets512to1023octets OCTET STRING,
	eth100gStatisticsEntryOutPackets1024to1518octets OCTET STRING
    }
eth100gStatisticsEntryLastClear OBJECT-TYPE
    SYNTAX IetfYangTypesDateAndTime 
    MAX-ACCESS read-only
    STATUS current
    DESCRIPTION "The start time of statistics monitor
		
		
		default value :0000-00-00T00:00:00.000Z"
::= { eth100gStatisticsEntry 1 }
eth100gStatisticsEntryLossOfSignalSeconds OBJECT-TYPE
    SYNTAX OCTET STRING 
    MAX-ACCESS read-only
    STATUS current
    DESCRIPTION "the statistics seconds counting for signal loss
		
		UNITS:seconds
		"
::= { eth100gStatisticsEntry 2 }
eth100gStatisticsEntryBitErrorFec OBJECT-TYPE
    SYNTAX OCTET STRING 
    MAX-ACCESS read-only
    STATUS current
    DESCRIPTION "the statistics bits counting for error bit forward error correction
		
		UNITS:bits
		"
::= { eth100gStatisticsEntry 3 }
eth100gStatisticsEntryUncorrectedBlockErrorFec OBJECT-TYPE
    SYNTAX OCTET STRING 
    MAX-ACCESS read-only
    STATUS current
    DESCRIPTION "the statistics blocks counting for uncorrected block error forward error correction
		
		UNITS:blocks
		"
::= { eth100gStatisticsEntry 4 }
eth100gStatisticsEntryInSymbolErrors OBJECT-TYPE
    SYNTAX OCTET STRING 
    MAX-ACCESS read-only
    STATUS current
    DESCRIPTION "the statistics Times counting for input signal symbol errors
		
		UNITS:Events
		"
::= { eth100gStatisticsEntry 5 }
eth100gStatisticsEntryInDropEvents OBJECT-TYPE
    SYNTAX OCTET STRING 
    MAX-ACCESS read-only
    STATUS current
    DESCRIPTION "the statistics counting for input signal drop events
		
		UNITS:events
		"
::= { eth100gStatisticsEntry 6 }
eth100gStatisticsEntryInOctets OBJECT-TYPE
    SYNTAX OCTET STRING 
    MAX-ACCESS read-only
    STATUS current
    DESCRIPTION "the statistics counting for input signal octets
		
		UNITS:octets
		"
::= { eth100gStatisticsEntry 7 }
eth100gStatisticsEntryInPackets OBJECT-TYPE
    SYNTAX OCTET STRING 
    MAX-ACCESS read-only
    STATUS current
    DESCRIPTION "the statistics counting for input signal packets
		
		UNITS:packets
		"
::= { eth100gStatisticsEntry 8 }
eth100gStatisticsEntryInBroadcastPackets OBJECT-TYPE
    SYNTAX OCTET STRING 
    MAX-ACCESS read-only
    STATUS current
    DESCRIPTION "the statistics counting for input broadcast packets
		
		UNITS:packets
		"
::= { eth100gStatisticsEntry 9 }
eth100gStatisticsEntryInMulticastPackets OBJECT-TYPE
    SYNTAX OCTET STRING 
    MAX-ACCESS read-only
    STATUS current
    DESCRIPTION "the statistics counting for input multicast packets
		
		UNITS:packets
		"
::= { eth100gStatisticsEntry 10 }
eth100gStatisticsEntryInCrcAlignErrors OBJECT-TYPE
    SYNTAX OCTET STRING 
    MAX-ACCESS read-only
    STATUS current
    DESCRIPTION "the statistics counting for input CRC error packets
		
		UNITS:packets
		"
::= { eth100gStatisticsEntry 11 }
eth100gStatisticsEntryInUndersizePackets OBJECT-TYPE
    SYNTAX OCTET STRING 
    MAX-ACCESS read-only
    STATUS current
    DESCRIPTION "the statistics counting for input undersize packets
		
		UNITS:packets
		"
::= { eth100gStatisticsEntry 12 }
eth100gStatisticsEntryInOversizePackets OBJECT-TYPE
    SYNTAX OCTET STRING 
    MAX-ACCESS read-only
    STATUS current
    DESCRIPTION "the statistics counting for input oversize packets
		
		UNITS:packets
		"
::= { eth100gStatisticsEntry 13 }
eth100gStatisticsEntryInFragments OBJECT-TYPE
    SYNTAX OCTET STRING 
    MAX-ACCESS read-only
    STATUS current
    DESCRIPTION "the statistics counting for input fragment packets
		
		UNITS:packets
		"
::= { eth100gStatisticsEntry 14 }
eth100gStatisticsEntryInJabbers OBJECT-TYPE
    SYNTAX OCTET STRING 
    MAX-ACCESS read-only
    STATUS current
    DESCRIPTION "the statistics counting for input jabber packets
		
		UNITS:packets
		"
::= { eth100gStatisticsEntry 15 }
eth100gStatisticsEntryInPackets64octets OBJECT-TYPE
    SYNTAX OCTET STRING 
    MAX-ACCESS read-only
    STATUS current
    DESCRIPTION "the statistics counting for input 64 octets packets
		
		UNITS:packets
		"
::= { eth100gStatisticsEntry 16 }
eth100gStatisticsEntryInPackets65to127octets OBJECT-TYPE
    SYNTAX OCTET STRING 
    MAX-ACCESS read-only
    STATUS current
    DESCRIPTION "the statistics counting for input 65 to 127 octets packets
		
		UNITS:packets
		"
::= { eth100gStatisticsEntry 17 }
eth100gStatisticsEntryInPackets128to255octets OBJECT-TYPE
    SYNTAX OCTET STRING 
    MAX-ACCESS read-only
    STATUS current
    DESCRIPTION "the statistics counting for input 128 to 255 octets packets
		
		UNITS:packets
		"
::= { eth100gStatisticsEntry 18 }
eth100gStatisticsEntryInPackets256to511octets OBJECT-TYPE
    SYNTAX OCTET STRING 
    MAX-ACCESS read-only
    STATUS current
    DESCRIPTION "the statistics counting for input 256 to 511 octets packets
		
		UNITS:packets
		"
::= { eth100gStatisticsEntry 19 }
eth100gStatisticsEntryInPackets512to1023octets OBJECT-TYPE
    SYNTAX OCTET STRING 
    MAX-ACCESS read-only
    STATUS current
    DESCRIPTION "the statistics counting for input 512 to 1023 octets packets
		
		UNITS:packets
		"
::= { eth100gStatisticsEntry 20 }
eth100gStatisticsEntryInPackets1024to1518octets OBJECT-TYPE
    SYNTAX OCTET STRING 
    MAX-ACCESS read-only
    STATUS current
    DESCRIPTION "the statistics counting for input 1024 to 1518 octets packets
		
		UNITS:packets
		"
::= { eth100gStatisticsEntry 21 }
eth100gStatisticsEntryOutSymbolErrors OBJECT-TYPE
    SYNTAX OCTET STRING 
    MAX-ACCESS read-only
    STATUS current
    DESCRIPTION "the statistics Times counting for output signal symbol errors
		
		UNITS:Events
		"
::= { eth100gStatisticsEntry 22 }
eth100gStatisticsEntryOutDropEvents OBJECT-TYPE
    SYNTAX OCTET STRING 
    MAX-ACCESS read-only
    STATUS current
    DESCRIPTION "the statistics counting for output signal drop events
		
		UNITS:events
		"
::= { eth100gStatisticsEntry 23 }
eth100gStatisticsEntryOutOctets OBJECT-TYPE
    SYNTAX OCTET STRING 
    MAX-ACCESS read-only
    STATUS current
    DESCRIPTION "the statistics counting for output signal octets
		
		UNITS:octets
		"
::= { eth100gStatisticsEntry 24 }
eth100gStatisticsEntryOutPackets OBJECT-TYPE
    SYNTAX OCTET STRING 
    MAX-ACCESS read-only
    STATUS current
    DESCRIPTION "the statistics counting for output signal packets
		
		UNITS:packets
		"
::= { eth100gStatisticsEntry 25 }
eth100gStatisticsEntryOutBroadcastPackets OBJECT-TYPE
    SYNTAX OCTET STRING 
    MAX-ACCESS read-only
    STATUS current
    DESCRIPTION "the statistics counting for output broadcast packets
		
		UNITS:packets
		"
::= { eth100gStatisticsEntry 26 }
eth100gStatisticsEntryOutMulticastPackets OBJECT-TYPE
    SYNTAX OCTET STRING 
    MAX-ACCESS read-only
    STATUS current
    DESCRIPTION "the statistics counting for output multicast packets
		
		UNITS:packets
		"
::= { eth100gStatisticsEntry 27 }
eth100gStatisticsEntryOutCrcAlignErrors OBJECT-TYPE
    SYNTAX OCTET STRING 
    MAX-ACCESS read-only
    STATUS current
    DESCRIPTION "the statistics counting for output CRC error packets
		
		UNITS:packets
		"
::= { eth100gStatisticsEntry 28 }
eth100gStatisticsEntryOutUndersizePackets OBJECT-TYPE
    SYNTAX OCTET STRING 
    MAX-ACCESS read-only
    STATUS current
    DESCRIPTION "the statistics counting for output undersize packets
		
		UNITS:packets
		"
::= { eth100gStatisticsEntry 29 }
eth100gStatisticsEntryOutOversizePackets OBJECT-TYPE
    SYNTAX OCTET STRING 
    MAX-ACCESS read-only
    STATUS current
    DESCRIPTION "the statistics counting for output oversize packets
		
		UNITS:packets
		"
::= { eth100gStatisticsEntry 30 }
eth100gStatisticsEntryOutFragments OBJECT-TYPE
    SYNTAX OCTET STRING 
    MAX-ACCESS read-only
    STATUS current
    DESCRIPTION "the statistics counting for output fragment packets
		
		UNITS:packets
		"
::= { eth100gStatisticsEntry 31 }
eth100gStatisticsEntryOutJabbers OBJECT-TYPE
    SYNTAX OCTET STRING 
    MAX-ACCESS read-only
    STATUS current
    DESCRIPTION "the statistics counting for output jabber packets
		
		UNITS:packets
		"
::= { eth100gStatisticsEntry 32 }
eth100gStatisticsEntryOutPackets64octets OBJECT-TYPE
    SYNTAX OCTET STRING 
    MAX-ACCESS read-only
    STATUS current
    DESCRIPTION "the statistics counting for output 64 octets packets
		
		UNITS:packets
		"
::= { eth100gStatisticsEntry 33 }
eth100gStatisticsEntryOutPackets65to127octets OBJECT-TYPE
    SYNTAX OCTET STRING 
    MAX-ACCESS read-only
    STATUS current
    DESCRIPTION "the statistics counting for output 65 to 127 octets packets
		
		UNITS:packets
		"
::= { eth100gStatisticsEntry 34 }
eth100gStatisticsEntryOutPackets128to255octets OBJECT-TYPE
    SYNTAX OCTET STRING 
    MAX-ACCESS read-only
    STATUS current
    DESCRIPTION "the statistics counting for output 128 to 255 octets packets
		
		UNITS:packets
		"
::= { eth100gStatisticsEntry 35 }
eth100gStatisticsEntryOutPackets256to511octets OBJECT-TYPE
    SYNTAX OCTET STRING 
    MAX-ACCESS read-only
    STATUS current
    DESCRIPTION "the statistics counting for output 256 to 511 octets packets
		
		UNITS:packets
		"
::= { eth100gStatisticsEntry 36 }
eth100gStatisticsEntryOutPackets512to1023octets OBJECT-TYPE
    SYNTAX OCTET STRING 
    MAX-ACCESS read-only
    STATUS current
    DESCRIPTION "the statistics counting for output 512 to 1023 octets packets
		
		UNITS:packets
		"
::= { eth100gStatisticsEntry 37 }
eth100gStatisticsEntryOutPackets1024to1518octets OBJECT-TYPE
    SYNTAX OCTET STRING 
    MAX-ACCESS read-only
    STATUS current
    DESCRIPTION "the statistics counting for output 1024 to 1518 octets packets
		
		UNITS:packets
		"
::= { eth100gStatisticsEntry 38 }
otu4Statistics OBJECT IDENTIFIER ::= { otn 36 }
otu4StatisticsTable OBJECT-TYPE
    SYNTAX SEQUENCE OF Otu4StatisticsEntry
    MAX-ACCESS not-accessible
    STATUS current
    DESCRIPTION "NULL"
::= { otu4Statistics 1 }
otu4StatisticsEntry OBJECT-TYPE
    SYNTAX Otu4StatisticsEntry
    MAX-ACCESS not-accessible
    STATUS current
    DESCRIPTION "Entry of otu4StatisticsTable" 
    INDEX { shelfId,slotId,subslotId,portId,subportId }
::= { otu4StatisticsTable 1 }
Otu4StatisticsEntry ::= 
SEQUENCE {
	otu4StatisticsEntryLastClear IetfYangTypesDateAndTime,
	otu4StatisticsEntryLossOfSignalSeconds OCTET STRING,
	otu4StatisticsEntryBitErrorFec OCTET STRING,
	otu4StatisticsEntryUncorrectedBlockErrorFec OCTET STRING,
	otu4StatisticsEntryErroredBlocks OCTET STRING,
	otu4StatisticsEntryErroredSeconds OCTET STRING,
	otu4StatisticsEntrySeverelyErroredSeconds OCTET STRING,
	otu4StatisticsEntryUnavailableSeconds OCTET STRING
    }
otu4StatisticsEntryLastClear OBJECT-TYPE
    SYNTAX IetfYangTypesDateAndTime 
    MAX-ACCESS read-only
    STATUS current
    DESCRIPTION "The start time of statistics monitor
		
		
		default value :0000-00-00T00:00:00.000Z"
::= { otu4StatisticsEntry 1 }
otu4StatisticsEntryLossOfSignalSeconds OBJECT-TYPE
    SYNTAX OCTET STRING 
    MAX-ACCESS read-only
    STATUS current
    DESCRIPTION "the statistics seconds counting for signal loss
		
		UNITS:seconds
		"
::= { otu4StatisticsEntry 2 }
otu4StatisticsEntryBitErrorFec OBJECT-TYPE
    SYNTAX OCTET STRING 
    MAX-ACCESS read-only
    STATUS current
    DESCRIPTION "the statistics bits counting for error bit forward error correction
		
		UNITS:bits
		"
::= { otu4StatisticsEntry 3 }
otu4StatisticsEntryUncorrectedBlockErrorFec OBJECT-TYPE
    SYNTAX OCTET STRING 
    MAX-ACCESS read-only
    STATUS current
    DESCRIPTION "the statistics blocks counting for uncorrected block error forward error correction
		
		UNITS:blocks
		"
::= { otu4StatisticsEntry 4 }
otu4StatisticsEntryErroredBlocks OBJECT-TYPE
    SYNTAX OCTET STRING 
    MAX-ACCESS read-only
    STATUS current
    DESCRIPTION "the statistics counting for errored blocks
		
		UNITS:blocks
		"
::= { otu4StatisticsEntry 5 }
otu4StatisticsEntryErroredSeconds OBJECT-TYPE
    SYNTAX OCTET STRING 
    MAX-ACCESS read-only
    STATUS current
    DESCRIPTION "the statistics seconds counting for errored signal
		
		UNITS:seconds
		"
::= { otu4StatisticsEntry 6 }
otu4StatisticsEntrySeverelyErroredSeconds OBJECT-TYPE
    SYNTAX OCTET STRING 
    MAX-ACCESS read-only
    STATUS current
    DESCRIPTION "the statistics seconds counting for severely errored signal
		
		UNITS:seconds
		"
::= { otu4StatisticsEntry 7 }
otu4StatisticsEntryUnavailableSeconds OBJECT-TYPE
    SYNTAX OCTET STRING 
    MAX-ACCESS read-only
    STATUS current
    DESCRIPTION "the statistics seconds counting for unavailable signal
		
		UNITS:seconds
		"
::= { otu4StatisticsEntry 8 }
otu2Statistics OBJECT IDENTIFIER ::= { otn 37 }
otu2StatisticsTable OBJECT-TYPE
    SYNTAX SEQUENCE OF Otu2StatisticsEntry
    MAX-ACCESS not-accessible
    STATUS current
    DESCRIPTION "NULL"
::= { otu2Statistics 1 }
otu2StatisticsEntry OBJECT-TYPE
    SYNTAX Otu2StatisticsEntry
    MAX-ACCESS not-accessible
    STATUS current
    DESCRIPTION "Entry of otu2StatisticsTable" 
    INDEX { shelfId,slotId,subslotId,portId,subportId }
::= { otu2StatisticsTable 1 }
Otu2StatisticsEntry ::= 
SEQUENCE {
	otu2StatisticsEntryLastClear IetfYangTypesDateAndTime,
	otu2StatisticsEntryLossOfSignalSeconds OCTET STRING,
	otu2StatisticsEntryBitErrorFec OCTET STRING,
	otu2StatisticsEntryUncorrectedBlockErrorFec OCTET STRING,
	otu2StatisticsEntryErroredBlocks OCTET STRING,
	otu2StatisticsEntryErroredSeconds OCTET STRING,
	otu2StatisticsEntrySeverelyErroredSeconds OCTET STRING,
	otu2StatisticsEntryUnavailableSeconds OCTET STRING
    }
otu2StatisticsEntryLastClear OBJECT-TYPE
    SYNTAX IetfYangTypesDateAndTime 
    MAX-ACCESS read-only
    STATUS current
    DESCRIPTION "The start time of statistics monitor
		
		
		default value :0000-00-00T00:00:00.000Z"
::= { otu2StatisticsEntry 1 }
otu2StatisticsEntryLossOfSignalSeconds OBJECT-TYPE
    SYNTAX OCTET STRING 
    MAX-ACCESS read-only
    STATUS current
    DESCRIPTION "the statistics seconds counting for signal loss
		
		UNITS:seconds
		"
::= { otu2StatisticsEntry 2 }
otu2StatisticsEntryBitErrorFec OBJECT-TYPE
    SYNTAX OCTET STRING 
    MAX-ACCESS read-only
    STATUS current
    DESCRIPTION "the statistics bits counting for error bit forward error correction
		
		UNITS:bits
		"
::= { otu2StatisticsEntry 3 }
otu2StatisticsEntryUncorrectedBlockErrorFec OBJECT-TYPE
    SYNTAX OCTET STRING 
    MAX-ACCESS read-only
    STATUS current
    DESCRIPTION "the statistics blocks counting for uncorrected block error forward error correction
		
		UNITS:blocks
		"
::= { otu2StatisticsEntry 4 }
otu2StatisticsEntryErroredBlocks OBJECT-TYPE
    SYNTAX OCTET STRING 
    MAX-ACCESS read-only
    STATUS current
    DESCRIPTION "the statistics counting for errored blocks
		
		UNITS:blocks
		"
::= { otu2StatisticsEntry 5 }
otu2StatisticsEntryErroredSeconds OBJECT-TYPE
    SYNTAX OCTET STRING 
    MAX-ACCESS read-only
    STATUS current
    DESCRIPTION "the statistics seconds counting for errored signal
		
		UNITS:seconds
		"
::= { otu2StatisticsEntry 6 }
otu2StatisticsEntrySeverelyErroredSeconds OBJECT-TYPE
    SYNTAX OCTET STRING 
    MAX-ACCESS read-only
    STATUS current
    DESCRIPTION "the statistics seconds counting for severely errored signal
		
		UNITS:seconds
		"
::= { otu2StatisticsEntry 7 }
otu2StatisticsEntryUnavailableSeconds OBJECT-TYPE
    SYNTAX OCTET STRING 
    MAX-ACCESS read-only
    STATUS current
    DESCRIPTION "the statistics seconds counting for unavailable signal
		
		UNITS:seconds
		"
::= { otu2StatisticsEntry 8 }
otu2eStatistics OBJECT IDENTIFIER ::= { otn 38 }
otu2eStatisticsTable OBJECT-TYPE
    SYNTAX SEQUENCE OF Otu2eStatisticsEntry
    MAX-ACCESS not-accessible
    STATUS current
    DESCRIPTION "NULL"
::= { otu2eStatistics 1 }
otu2eStatisticsEntry OBJECT-TYPE
    SYNTAX Otu2eStatisticsEntry
    MAX-ACCESS not-accessible
    STATUS current
    DESCRIPTION "Entry of otu2eStatisticsTable" 
    INDEX { shelfId,slotId,subslotId,portId,subportId }
::= { otu2eStatisticsTable 1 }
Otu2eStatisticsEntry ::= 
SEQUENCE {
	otu2eStatisticsEntryLastClear IetfYangTypesDateAndTime,
	otu2eStatisticsEntryLossOfSignalSeconds OCTET STRING,
	otu2eStatisticsEntryBitErrorFec OCTET STRING,
	otu2eStatisticsEntryUncorrectedBlockErrorFec OCTET STRING,
	otu2eStatisticsEntryErroredBlocks OCTET STRING,
	otu2eStatisticsEntryErroredSeconds OCTET STRING,
	otu2eStatisticsEntrySeverelyErroredSeconds OCTET STRING,
	otu2eStatisticsEntryUnavailableSeconds OCTET STRING
    }
otu2eStatisticsEntryLastClear OBJECT-TYPE
    SYNTAX IetfYangTypesDateAndTime 
    MAX-ACCESS read-only
    STATUS current
    DESCRIPTION "The start time of statistics monitor
		
		
		default value :0000-00-00T00:00:00.000Z"
::= { otu2eStatisticsEntry 1 }
otu2eStatisticsEntryLossOfSignalSeconds OBJECT-TYPE
    SYNTAX OCTET STRING 
    MAX-ACCESS read-only
    STATUS current
    DESCRIPTION "the statistics seconds counting for signal loss
		
		UNITS:seconds
		"
::= { otu2eStatisticsEntry 2 }
otu2eStatisticsEntryBitErrorFec OBJECT-TYPE
    SYNTAX OCTET STRING 
    MAX-ACCESS read-only
    STATUS current
    DESCRIPTION "the statistics bits counting for error bit forward error correction
		
		UNITS:bits
		"
::= { otu2eStatisticsEntry 3 }
otu2eStatisticsEntryUncorrectedBlockErrorFec OBJECT-TYPE
    SYNTAX OCTET STRING 
    MAX-ACCESS read-only
    STATUS current
    DESCRIPTION "the statistics blocks counting for uncorrected block error forward error correction
		
		UNITS:blocks
		"
::= { otu2eStatisticsEntry 4 }
otu2eStatisticsEntryErroredBlocks OBJECT-TYPE
    SYNTAX OCTET STRING 
    MAX-ACCESS read-only
    STATUS current
    DESCRIPTION "the statistics counting for errored blocks
		
		UNITS:blocks
		"
::= { otu2eStatisticsEntry 5 }
otu2eStatisticsEntryErroredSeconds OBJECT-TYPE
    SYNTAX OCTET STRING 
    MAX-ACCESS read-only
    STATUS current
    DESCRIPTION "the statistics seconds counting for errored signal
		
		UNITS:seconds
		"
::= { otu2eStatisticsEntry 6 }
otu2eStatisticsEntrySeverelyErroredSeconds OBJECT-TYPE
    SYNTAX OCTET STRING 
    MAX-ACCESS read-only
    STATUS current
    DESCRIPTION "the statistics seconds counting for severely errored signal
		
		UNITS:seconds
		"
::= { otu2eStatisticsEntry 7 }
otu2eStatisticsEntryUnavailableSeconds OBJECT-TYPE
    SYNTAX OCTET STRING 
    MAX-ACCESS read-only
    STATUS current
    DESCRIPTION "the statistics seconds counting for unavailable signal
		
		UNITS:seconds
		"
::= { otu2eStatisticsEntry 8 }
oc192Statistics OBJECT IDENTIFIER ::= { otn 39 }
oc192StatisticsTable OBJECT-TYPE
    SYNTAX SEQUENCE OF Oc192StatisticsEntry
    MAX-ACCESS not-accessible
    STATUS current
    DESCRIPTION "NULL"
::= { oc192Statistics 1 }
oc192StatisticsEntry OBJECT-TYPE
    SYNTAX Oc192StatisticsEntry
    MAX-ACCESS not-accessible
    STATUS current
    DESCRIPTION "Entry of oc192StatisticsTable" 
    INDEX { shelfId,slotId,subslotId,portId,subportId }
::= { oc192StatisticsTable 1 }
Oc192StatisticsEntry ::= 
SEQUENCE {
	oc192StatisticsEntryLastClear IetfYangTypesDateAndTime,
	oc192StatisticsEntryLossOfSignalSeconds OCTET STRING,
	oc192StatisticsEntryInCodingViolation OCTET STRING,
	oc192StatisticsEntryInErroredSeconds OCTET STRING,
	oc192StatisticsEntryInSeverelyErroredSeconds OCTET STRING,
	oc192StatisticsEntryInUnavailableSeconds OCTET STRING,
	oc192StatisticsEntryInSeverelyErroredFrameSecond OCTET STRING
    }
oc192StatisticsEntryLastClear OBJECT-TYPE
    SYNTAX IetfYangTypesDateAndTime 
    MAX-ACCESS read-only
    STATUS current
    DESCRIPTION "The start time of statistics monitor
		
		
		default value :0000-00-00T00:00:00.000Z"
::= { oc192StatisticsEntry 1 }
oc192StatisticsEntryLossOfSignalSeconds OBJECT-TYPE
    SYNTAX OCTET STRING 
    MAX-ACCESS read-only
    STATUS current
    DESCRIPTION "the statistics seconds counting for signal loss
		
		UNITS:seconds
		"
::= { oc192StatisticsEntry 2 }
oc192StatisticsEntryInCodingViolation OBJECT-TYPE
    SYNTAX OCTET STRING 
    MAX-ACCESS read-only
    STATUS current
    DESCRIPTION "the statistics bits counting for ingress coding violation
		
		UNITS:bits
		"
::= { oc192StatisticsEntry 3 }
oc192StatisticsEntryInErroredSeconds OBJECT-TYPE
    SYNTAX OCTET STRING 
    MAX-ACCESS read-only
    STATUS current
    DESCRIPTION "the statistics seconds counting for RX errored signal
		
		UNITS:seconds
		"
::= { oc192StatisticsEntry 4 }
oc192StatisticsEntryInSeverelyErroredSeconds OBJECT-TYPE
    SYNTAX OCTET STRING 
    MAX-ACCESS read-only
    STATUS current
    DESCRIPTION "the statistics seconds counting for RX severely errored signal
		
		UNITS:seconds
		"
::= { oc192StatisticsEntry 5 }
oc192StatisticsEntryInUnavailableSeconds OBJECT-TYPE
    SYNTAX OCTET STRING 
    MAX-ACCESS read-only
    STATUS current
    DESCRIPTION "the statistics seconds counting for RX unavailable signal
		
		UNITS:seconds
		"
::= { oc192StatisticsEntry 6 }
oc192StatisticsEntryInSeverelyErroredFrameSecond OBJECT-TYPE
    SYNTAX OCTET STRING 
    MAX-ACCESS read-only
    STATUS current
    DESCRIPTION "the statistics seconds counting for ingress signal frame severely errored
		
		UNITS:seconds
		"
::= { oc192StatisticsEntry 7 }
stm64Statistics OBJECT IDENTIFIER ::= { otn 40 }
stm64StatisticsTable OBJECT-TYPE
    SYNTAX SEQUENCE OF Stm64StatisticsEntry
    MAX-ACCESS not-accessible
    STATUS current
    DESCRIPTION "NULL"
::= { stm64Statistics 1 }
stm64StatisticsEntry OBJECT-TYPE
    SYNTAX Stm64StatisticsEntry
    MAX-ACCESS not-accessible
    STATUS current
    DESCRIPTION "Entry of stm64StatisticsTable" 
    INDEX { shelfId,slotId,subslotId,portId,subportId }
::= { stm64StatisticsTable 1 }
Stm64StatisticsEntry ::= 
SEQUENCE {
	stm64StatisticsEntryLastClear IetfYangTypesDateAndTime,
	stm64StatisticsEntryLossOfSignalSeconds OCTET STRING,
	stm64StatisticsEntryInBackgroundBlockError OCTET STRING,
	stm64StatisticsEntryInErroredSeconds OCTET STRING,
	stm64StatisticsEntryInSeverelyErroredSeconds OCTET STRING,
	stm64StatisticsEntryInUnavailableSeconds OCTET STRING,
	stm64StatisticsEntryInOutOfFrameSeconds OCTET STRING
    }
stm64StatisticsEntryLastClear OBJECT-TYPE
    SYNTAX IetfYangTypesDateAndTime 
    MAX-ACCESS read-only
    STATUS current
    DESCRIPTION "The start time of statistics monitor
		
		
		default value :0000-00-00T00:00:00.000Z"
::= { stm64StatisticsEntry 1 }
stm64StatisticsEntryLossOfSignalSeconds OBJECT-TYPE
    SYNTAX OCTET STRING 
    MAX-ACCESS read-only
    STATUS current
    DESCRIPTION "the statistics seconds counting for signal loss
		
		UNITS:seconds
		"
::= { stm64StatisticsEntry 2 }
stm64StatisticsEntryInBackgroundBlockError OBJECT-TYPE
    SYNTAX OCTET STRING 
    MAX-ACCESS read-only
    STATUS current
    DESCRIPTION "the statistics counting for ingress errored blocks
		
		UNITS:blocks
		"
::= { stm64StatisticsEntry 3 }
stm64StatisticsEntryInErroredSeconds OBJECT-TYPE
    SYNTAX OCTET STRING 
    MAX-ACCESS read-only
    STATUS current
    DESCRIPTION "the statistics seconds counting for RX errored signal
		
		UNITS:seconds
		"
::= { stm64StatisticsEntry 4 }
stm64StatisticsEntryInSeverelyErroredSeconds OBJECT-TYPE
    SYNTAX OCTET STRING 
    MAX-ACCESS read-only
    STATUS current
    DESCRIPTION "the statistics seconds counting for RX severely errored signal
		
		UNITS:seconds
		"
::= { stm64StatisticsEntry 5 }
stm64StatisticsEntryInUnavailableSeconds OBJECT-TYPE
    SYNTAX OCTET STRING 
    MAX-ACCESS read-only
    STATUS current
    DESCRIPTION "the statistics seconds counting for RX unavailable signal
		
		UNITS:seconds
		"
::= { stm64StatisticsEntry 6 }
stm64StatisticsEntryInOutOfFrameSeconds OBJECT-TYPE
    SYNTAX OCTET STRING 
    MAX-ACCESS read-only
    STATUS current
    DESCRIPTION "the statistics seconds counting for ingress signal lose of frame
		
		UNITS:seconds
		"
::= { stm64StatisticsEntry 7 }
wan10gSonetStatistics OBJECT IDENTIFIER ::= { otn 41 }
wan10gSonetStatisticsTable OBJECT-TYPE
    SYNTAX SEQUENCE OF Wan10gSonetStatisticsEntry
    MAX-ACCESS not-accessible
    STATUS current
    DESCRIPTION "NULL"
::= { wan10gSonetStatistics 1 }
wan10gSonetStatisticsEntry OBJECT-TYPE
    SYNTAX Wan10gSonetStatisticsEntry
    MAX-ACCESS not-accessible
    STATUS current
    DESCRIPTION "Entry of wan10gSonetStatisticsTable" 
    INDEX { shelfId,slotId,subslotId,portId,subportId }
::= { wan10gSonetStatisticsTable 1 }
Wan10gSonetStatisticsEntry ::= 
SEQUENCE {
	wan10gSonetStatisticsEntryLastClear IetfYangTypesDateAndTime,
	wan10gSonetStatisticsEntryLossOfSignalSeconds OCTET STRING,
	wan10gSonetStatisticsEntryInCodingViolation OCTET STRING,
	wan10gSonetStatisticsEntryInErroredSeconds OCTET STRING,
	wan10gSonetStatisticsEntryInSeverelyErroredSeconds OCTET STRING,
	wan10gSonetStatisticsEntryInUnavailableSeconds OCTET STRING,
	wan10gSonetStatisticsEntryInSeverelyErroredFrameSecond OCTET STRING
    }
wan10gSonetStatisticsEntryLastClear OBJECT-TYPE
    SYNTAX IetfYangTypesDateAndTime 
    MAX-ACCESS read-only
    STATUS current
    DESCRIPTION "The start time of statistics monitor
		
		
		default value :0000-00-00T00:00:00.000Z"
::= { wan10gSonetStatisticsEntry 1 }
wan10gSonetStatisticsEntryLossOfSignalSeconds OBJECT-TYPE
    SYNTAX OCTET STRING 
    MAX-ACCESS read-only
    STATUS current
    DESCRIPTION "the statistics seconds counting for signal loss
		
		UNITS:seconds
		"
::= { wan10gSonetStatisticsEntry 2 }
wan10gSonetStatisticsEntryInCodingViolation OBJECT-TYPE
    SYNTAX OCTET STRING 
    MAX-ACCESS read-only
    STATUS current
    DESCRIPTION "the statistics bits counting for ingress coding violation
		
		UNITS:bits
		"
::= { wan10gSonetStatisticsEntry 3 }
wan10gSonetStatisticsEntryInErroredSeconds OBJECT-TYPE
    SYNTAX OCTET STRING 
    MAX-ACCESS read-only
    STATUS current
    DESCRIPTION "the statistics seconds counting for RX errored signal
		
		UNITS:seconds
		"
::= { wan10gSonetStatisticsEntry 4 }
wan10gSonetStatisticsEntryInSeverelyErroredSeconds OBJECT-TYPE
    SYNTAX OCTET STRING 
    MAX-ACCESS read-only
    STATUS current
    DESCRIPTION "the statistics seconds counting for RX severely errored signal
		
		UNITS:seconds
		"
::= { wan10gSonetStatisticsEntry 5 }
wan10gSonetStatisticsEntryInUnavailableSeconds OBJECT-TYPE
    SYNTAX OCTET STRING 
    MAX-ACCESS read-only
    STATUS current
    DESCRIPTION "the statistics seconds counting for RX unavailable signal
		
		UNITS:seconds
		"
::= { wan10gSonetStatisticsEntry 6 }
wan10gSonetStatisticsEntryInSeverelyErroredFrameSecond OBJECT-TYPE
    SYNTAX OCTET STRING 
    MAX-ACCESS read-only
    STATUS current
    DESCRIPTION "the statistics seconds counting for ingress signal frame severely errored
		
		UNITS:seconds
		"
::= { wan10gSonetStatisticsEntry 7 }
wan10gSdhStatistics OBJECT IDENTIFIER ::= { otn 42 }
wan10gSdhStatisticsTable OBJECT-TYPE
    SYNTAX SEQUENCE OF Wan10gSdhStatisticsEntry
    MAX-ACCESS not-accessible
    STATUS current
    DESCRIPTION "NULL"
::= { wan10gSdhStatistics 1 }
wan10gSdhStatisticsEntry OBJECT-TYPE
    SYNTAX Wan10gSdhStatisticsEntry
    MAX-ACCESS not-accessible
    STATUS current
    DESCRIPTION "Entry of wan10gSdhStatisticsTable" 
    INDEX { shelfId,slotId,subslotId,portId,subportId }
::= { wan10gSdhStatisticsTable 1 }
Wan10gSdhStatisticsEntry ::= 
SEQUENCE {
	wan10gSdhStatisticsEntryLastClear IetfYangTypesDateAndTime,
	wan10gSdhStatisticsEntryLossOfSignalSeconds OCTET STRING,
	wan10gSdhStatisticsEntryInBackgroundBlockError OCTET STRING,
	wan10gSdhStatisticsEntryInErroredSeconds OCTET STRING,
	wan10gSdhStatisticsEntryInSeverelyErroredSeconds OCTET STRING,
	wan10gSdhStatisticsEntryInUnavailableSeconds OCTET STRING,
	wan10gSdhStatisticsEntryInOutOfFrameSeconds OCTET STRING
    }
wan10gSdhStatisticsEntryLastClear OBJECT-TYPE
    SYNTAX IetfYangTypesDateAndTime 
    MAX-ACCESS read-only
    STATUS current
    DESCRIPTION "The start time of statistics monitor
		
		
		default value :0000-00-00T00:00:00.000Z"
::= { wan10gSdhStatisticsEntry 1 }
wan10gSdhStatisticsEntryLossOfSignalSeconds OBJECT-TYPE
    SYNTAX OCTET STRING 
    MAX-ACCESS read-only
    STATUS current
    DESCRIPTION "the statistics seconds counting for signal loss
		
		UNITS:seconds
		"
::= { wan10gSdhStatisticsEntry 2 }
wan10gSdhStatisticsEntryInBackgroundBlockError OBJECT-TYPE
    SYNTAX OCTET STRING 
    MAX-ACCESS read-only
    STATUS current
    DESCRIPTION "the statistics counting for ingress errored blocks
		
		UNITS:blocks
		"
::= { wan10gSdhStatisticsEntry 3 }
wan10gSdhStatisticsEntryInErroredSeconds OBJECT-TYPE
    SYNTAX OCTET STRING 
    MAX-ACCESS read-only
    STATUS current
    DESCRIPTION "the statistics seconds counting for RX errored signal
		
		UNITS:seconds
		"
::= { wan10gSdhStatisticsEntry 4 }
wan10gSdhStatisticsEntryInSeverelyErroredSeconds OBJECT-TYPE
    SYNTAX OCTET STRING 
    MAX-ACCESS read-only
    STATUS current
    DESCRIPTION "the statistics seconds counting for RX severely errored signal
		
		UNITS:seconds
		"
::= { wan10gSdhStatisticsEntry 5 }
wan10gSdhStatisticsEntryInUnavailableSeconds OBJECT-TYPE
    SYNTAX OCTET STRING 
    MAX-ACCESS read-only
    STATUS current
    DESCRIPTION "the statistics seconds counting for RX unavailable signal
		
		UNITS:seconds
		"
::= { wan10gSdhStatisticsEntry 6 }
wan10gSdhStatisticsEntryInOutOfFrameSeconds OBJECT-TYPE
    SYNTAX OCTET STRING 
    MAX-ACCESS read-only
    STATUS current
    DESCRIPTION "the statistics seconds counting for ingress signal lose of frame
		
		UNITS:seconds
		"
::= { wan10gSdhStatisticsEntry 7 }
fc8gStatistics OBJECT IDENTIFIER ::= { otn 43 }
fc8gStatisticsTable OBJECT-TYPE
    SYNTAX SEQUENCE OF Fc8gStatisticsEntry
    MAX-ACCESS not-accessible
    STATUS current
    DESCRIPTION "NULL"
::= { fc8gStatistics 1 }
fc8gStatisticsEntry OBJECT-TYPE
    SYNTAX Fc8gStatisticsEntry
    MAX-ACCESS not-accessible
    STATUS current
    DESCRIPTION "Entry of fc8gStatisticsTable" 
    INDEX { shelfId,slotId,subslotId,portId,subportId }
::= { fc8gStatisticsTable 1 }
Fc8gStatisticsEntry ::= 
SEQUENCE {
	fc8gStatisticsEntryLastClear IetfYangTypesDateAndTime,
	fc8gStatisticsEntryLossOfSignalSeconds OCTET STRING,
	fc8gStatisticsEntryInSymbolErrors OCTET STRING
    }
fc8gStatisticsEntryLastClear OBJECT-TYPE
    SYNTAX IetfYangTypesDateAndTime 
    MAX-ACCESS read-only
    STATUS current
    DESCRIPTION "The start time of statistics monitor
		
		
		default value :0000-00-00T00:00:00.000Z"
::= { fc8gStatisticsEntry 1 }
fc8gStatisticsEntryLossOfSignalSeconds OBJECT-TYPE
    SYNTAX OCTET STRING 
    MAX-ACCESS read-only
    STATUS current
    DESCRIPTION "the statistics seconds counting for signal loss
		
		UNITS:seconds
		"
::= { fc8gStatisticsEntry 2 }
fc8gStatisticsEntryInSymbolErrors OBJECT-TYPE
    SYNTAX OCTET STRING 
    MAX-ACCESS read-only
    STATUS current
    DESCRIPTION "the statistics Times counting for signal symbol errors
		
		UNITS:Events
		"
::= { fc8gStatisticsEntry 3 }
fc16gStatistics OBJECT IDENTIFIER ::= { otn 44 }
fc16gStatisticsTable OBJECT-TYPE
    SYNTAX SEQUENCE OF Fc16gStatisticsEntry
    MAX-ACCESS not-accessible
    STATUS current
    DESCRIPTION "NULL"
::= { fc16gStatistics 1 }
fc16gStatisticsEntry OBJECT-TYPE
    SYNTAX Fc16gStatisticsEntry
    MAX-ACCESS not-accessible
    STATUS current
    DESCRIPTION "Entry of fc16gStatisticsTable" 
    INDEX { shelfId,slotId,subslotId,portId,subportId }
::= { fc16gStatisticsTable 1 }
Fc16gStatisticsEntry ::= 
SEQUENCE {
	fc16gStatisticsEntryLastClear IetfYangTypesDateAndTime,
	fc16gStatisticsEntryLossOfSignalSeconds OCTET STRING,
	fc16gStatisticsEntryInSymbolErrors OCTET STRING
    }
fc16gStatisticsEntryLastClear OBJECT-TYPE
    SYNTAX IetfYangTypesDateAndTime 
    MAX-ACCESS read-only
    STATUS current
    DESCRIPTION "The start time of statistics monitor
		
		
		default value :0000-00-00T00:00:00.000Z"
::= { fc16gStatisticsEntry 1 }
fc16gStatisticsEntryLossOfSignalSeconds OBJECT-TYPE
    SYNTAX OCTET STRING 
    MAX-ACCESS read-only
    STATUS current
    DESCRIPTION "the statistics seconds counting for signal loss
		
		UNITS:seconds
		"
::= { fc16gStatisticsEntry 2 }
fc16gStatisticsEntryInSymbolErrors OBJECT-TYPE
    SYNTAX OCTET STRING 
    MAX-ACCESS read-only
    STATUS current
    DESCRIPTION "the statistics Times counting for signal symbol errors
		
		UNITS:Events
		"
::= { fc16gStatisticsEntry 3 }
otuc2Statistics OBJECT IDENTIFIER ::= { otn 45 }
otuc2StatisticsTable OBJECT-TYPE
    SYNTAX SEQUENCE OF Otuc2StatisticsEntry
    MAX-ACCESS not-accessible
    STATUS current
    DESCRIPTION "NULL"
::= { otuc2Statistics 1 }
otuc2StatisticsEntry OBJECT-TYPE
    SYNTAX Otuc2StatisticsEntry
    MAX-ACCESS not-accessible
    STATUS current
    DESCRIPTION "Entry of otuc2StatisticsTable" 
    INDEX { shelfId,slotId,subslotId,portId,subportId }
::= { otuc2StatisticsTable 1 }
Otuc2StatisticsEntry ::= 
SEQUENCE {
	otuc2StatisticsEntryLastClear IetfYangTypesDateAndTime,
	otuc2StatisticsEntryLossOfSignalSeconds OCTET STRING,
	otuc2StatisticsEntryBitErrorFec OCTET STRING,
	otuc2StatisticsEntryUncorrectedBlockErrorFec OCTET STRING,
	otuc2StatisticsEntryErroredBlocks OCTET STRING,
	otuc2StatisticsEntryErroredSeconds OCTET STRING,
	otuc2StatisticsEntrySeverelyErroredSeconds OCTET STRING,
	otuc2StatisticsEntryUnavailableSeconds OCTET STRING
    }
otuc2StatisticsEntryLastClear OBJECT-TYPE
    SYNTAX IetfYangTypesDateAndTime 
    MAX-ACCESS read-only
    STATUS current
    DESCRIPTION "The start time of statistics monitor
		
		
		default value :0000-00-00T00:00:00.000Z"
::= { otuc2StatisticsEntry 1 }
otuc2StatisticsEntryLossOfSignalSeconds OBJECT-TYPE
    SYNTAX OCTET STRING 
    MAX-ACCESS read-only
    STATUS current
    DESCRIPTION "the statistics seconds counting for signal loss
		
		UNITS:seconds
		"
::= { otuc2StatisticsEntry 2 }
otuc2StatisticsEntryBitErrorFec OBJECT-TYPE
    SYNTAX OCTET STRING 
    MAX-ACCESS read-only
    STATUS current
    DESCRIPTION "the statistics bits counting for error bit forward error correction
		
		UNITS:bits
		"
::= { otuc2StatisticsEntry 3 }
otuc2StatisticsEntryUncorrectedBlockErrorFec OBJECT-TYPE
    SYNTAX OCTET STRING 
    MAX-ACCESS read-only
    STATUS current
    DESCRIPTION "the statistics blocks counting for uncorrected block error forward error correction
		
		UNITS:blocks
		"
::= { otuc2StatisticsEntry 4 }
otuc2StatisticsEntryErroredBlocks OBJECT-TYPE
    SYNTAX OCTET STRING 
    MAX-ACCESS read-only
    STATUS current
    DESCRIPTION "the statistics counting for errored blocks
		
		UNITS:blocks
		"
::= { otuc2StatisticsEntry 5 }
otuc2StatisticsEntryErroredSeconds OBJECT-TYPE
    SYNTAX OCTET STRING 
    MAX-ACCESS read-only
    STATUS current
    DESCRIPTION "the statistics seconds counting for errored signal
		
		UNITS:seconds
		"
::= { otuc2StatisticsEntry 6 }
otuc2StatisticsEntrySeverelyErroredSeconds OBJECT-TYPE
    SYNTAX OCTET STRING 
    MAX-ACCESS read-only
    STATUS current
    DESCRIPTION "the statistics seconds counting for severely errored signal
		
		UNITS:seconds
		"
::= { otuc2StatisticsEntry 7 }
otuc2StatisticsEntryUnavailableSeconds OBJECT-TYPE
    SYNTAX OCTET STRING 
    MAX-ACCESS read-only
    STATUS current
    DESCRIPTION "the statistics seconds counting for unavailable signal
		
		UNITS:seconds
		"
::= { otuc2StatisticsEntry 8 }
otuc3Statistics OBJECT IDENTIFIER ::= { otn 46 }
otuc3StatisticsTable OBJECT-TYPE
    SYNTAX SEQUENCE OF Otuc3StatisticsEntry
    MAX-ACCESS not-accessible
    STATUS current
    DESCRIPTION "NULL"
::= { otuc3Statistics 1 }
otuc3StatisticsEntry OBJECT-TYPE
    SYNTAX Otuc3StatisticsEntry
    MAX-ACCESS not-accessible
    STATUS current
    DESCRIPTION "Entry of otuc3StatisticsTable" 
    INDEX { shelfId,slotId,subslotId,portId,subportId }
::= { otuc3StatisticsTable 1 }
Otuc3StatisticsEntry ::= 
SEQUENCE {
	otuc3StatisticsEntryLastClear IetfYangTypesDateAndTime,
	otuc3StatisticsEntryLossOfSignalSeconds OCTET STRING,
	otuc3StatisticsEntryBitErrorFec OCTET STRING,
	otuc3StatisticsEntryUncorrectedBlockErrorFec OCTET STRING,
	otuc3StatisticsEntryErroredBlocks OCTET STRING,
	otuc3StatisticsEntryErroredSeconds OCTET STRING,
	otuc3StatisticsEntrySeverelyErroredSeconds OCTET STRING,
	otuc3StatisticsEntryUnavailableSeconds OCTET STRING
    }
otuc3StatisticsEntryLastClear OBJECT-TYPE
    SYNTAX IetfYangTypesDateAndTime 
    MAX-ACCESS read-only
    STATUS current
    DESCRIPTION "The start time of statistics monitor
		
		
		default value :0000-00-00T00:00:00.000Z"
::= { otuc3StatisticsEntry 1 }
otuc3StatisticsEntryLossOfSignalSeconds OBJECT-TYPE
    SYNTAX OCTET STRING 
    MAX-ACCESS read-only
    STATUS current
    DESCRIPTION "the statistics seconds counting for signal loss
		
		UNITS:seconds
		"
::= { otuc3StatisticsEntry 2 }
otuc3StatisticsEntryBitErrorFec OBJECT-TYPE
    SYNTAX OCTET STRING 
    MAX-ACCESS read-only
    STATUS current
    DESCRIPTION "the statistics bits counting for error bit forward error correction
		
		UNITS:bits
		"
::= { otuc3StatisticsEntry 3 }
otuc3StatisticsEntryUncorrectedBlockErrorFec OBJECT-TYPE
    SYNTAX OCTET STRING 
    MAX-ACCESS read-only
    STATUS current
    DESCRIPTION "the statistics blocks counting for uncorrected block error forward error correction
		
		UNITS:blocks
		"
::= { otuc3StatisticsEntry 4 }
otuc3StatisticsEntryErroredBlocks OBJECT-TYPE
    SYNTAX OCTET STRING 
    MAX-ACCESS read-only
    STATUS current
    DESCRIPTION "the statistics counting for errored blocks
		
		UNITS:blocks
		"
::= { otuc3StatisticsEntry 5 }
otuc3StatisticsEntryErroredSeconds OBJECT-TYPE
    SYNTAX OCTET STRING 
    MAX-ACCESS read-only
    STATUS current
    DESCRIPTION "the statistics seconds counting for errored signal
		
		UNITS:seconds
		"
::= { otuc3StatisticsEntry 6 }
otuc3StatisticsEntrySeverelyErroredSeconds OBJECT-TYPE
    SYNTAX OCTET STRING 
    MAX-ACCESS read-only
    STATUS current
    DESCRIPTION "the statistics seconds counting for severely errored signal
		
		UNITS:seconds
		"
::= { otuc3StatisticsEntry 7 }
otuc3StatisticsEntryUnavailableSeconds OBJECT-TYPE
    SYNTAX OCTET STRING 
    MAX-ACCESS read-only
    STATUS current
    DESCRIPTION "the statistics seconds counting for unavailable signal
		
		UNITS:seconds
		"
::= { otuc3StatisticsEntry 8 }
ochOsStatistics OBJECT IDENTIFIER ::= { otn 47 }
ochOsStatisticsTable OBJECT-TYPE
    SYNTAX SEQUENCE OF OchOsStatisticsEntry
    MAX-ACCESS not-accessible
    STATUS current
    DESCRIPTION "NULL"
::= { ochOsStatistics 1 }
ochOsStatisticsEntry OBJECT-TYPE
    SYNTAX OchOsStatisticsEntry
    MAX-ACCESS not-accessible
    STATUS current
    DESCRIPTION "Entry of ochOsStatisticsTable" 
    INDEX { shelfId,slotId,subslotId,portId }
::= { ochOsStatisticsTable 1 }
OchOsStatisticsEntry ::= 
SEQUENCE {
	ochOsStatisticsEntryLastClear IetfYangTypesDateAndTime,
	ochOsStatisticsEntryLossOfSignalSeconds OCTET STRING,
	ochOsStatisticsEntryBitErrorFec OCTET STRING,
	ochOsStatisticsEntryUncorrectedBlockErrorFec OCTET STRING
    }
ochOsStatisticsEntryLastClear OBJECT-TYPE
    SYNTAX IetfYangTypesDateAndTime 
    MAX-ACCESS read-only
    STATUS current
    DESCRIPTION "The start time of statistics monitor
		
		
		default value :0000-00-00T00:00:00.000Z"
::= { ochOsStatisticsEntry 1 }
ochOsStatisticsEntryLossOfSignalSeconds OBJECT-TYPE
    SYNTAX OCTET STRING 
    MAX-ACCESS read-only
    STATUS current
    DESCRIPTION "the statistics seconds counting for signal loss
		
		UNITS:seconds
		"
::= { ochOsStatisticsEntry 2 }
ochOsStatisticsEntryBitErrorFec OBJECT-TYPE
    SYNTAX OCTET STRING 
    MAX-ACCESS read-only
    STATUS current
    DESCRIPTION "the statistics bits counting for error bit forward error correction
		
		UNITS:bits
		"
::= { ochOsStatisticsEntry 3 }
ochOsStatisticsEntryUncorrectedBlockErrorFec OBJECT-TYPE
    SYNTAX OCTET STRING 
    MAX-ACCESS read-only
    STATUS current
    DESCRIPTION "the statistics blocks counting for uncorrected block error forward error correction
		
		UNITS:blocks
		"
::= { ochOsStatisticsEntry 4 }
cRS OBJECT IDENTIFIER ::= { services 3 }
cRSTable OBJECT-TYPE
    SYNTAX SEQUENCE OF CRSEntry
    MAX-ACCESS not-accessible
    STATUS current
    DESCRIPTION "
	Cross connection table. 
	"
::= { cRS 1 }
cRSEntry OBJECT-TYPE
    SYNTAX CRSEntry
    MAX-ACCESS not-accessible
    STATUS current
    DESCRIPTION "Entry of cRSTable" 
    INDEX { cRSSrcTp,cRSDstTp }
::= { cRSTable 1 }
CRSEntry ::= 
SEQUENCE {
	cRSSrcTp RowPointer,
	cRSDstTp RowPointer,
	cRSServiceLabel OCTET STRING,
	cRSManagedBy INTEGER,
	cRSAliasName OCTET STRING
    }
cRSSrcTp OBJECT-TYPE
    SYNTAX RowPointer 
    MAX-ACCESS read-only
    STATUS current
    DESCRIPTION "
	Source tp of cross connection. 
	
		
		
		"
::= { cRSEntry 1 }
cRSDstTp OBJECT-TYPE
    SYNTAX RowPointer 
    MAX-ACCESS read-only
    STATUS current
    DESCRIPTION "
	Destination tp of cross connection.
	
		
		
		"
::= { cRSEntry 2 }
cRSServiceLabel OBJECT-TYPE
    SYNTAX OCTET STRING  (SIZE (0..128))
    MAX-ACCESS read-only
    STATUS current
    DESCRIPTION "Path/service name of cross-connection.
		
		
		"
::= { cRSEntry 3 }
cRSManagedBy OBJECT-TYPE
    SYNTAX INTEGER  {
	 system (1),
	 user (2)
	}
    MAX-ACCESS read-only
    STATUS current
    DESCRIPTION "Describes whether this CRS was system created or not. 
	A system created CRS implies a HW cross connection, that is not 
	manageable by the user.
		
		
		default value :user"
::= { cRSEntry 4 }
cRSAliasName OBJECT-TYPE
    SYNTAX OCTET STRING  (SIZE (0..256))
    MAX-ACCESS read-only
    STATUS current
    DESCRIPTION "User defined alias for this entity. Must be an alphanumeric string with dash or underscore
		
		
		"
::= { cRSEntry 5 }
fiberConnection OBJECT IDENTIFIER ::= { services 4 }
fiberConnectionTable OBJECT-TYPE
    SYNTAX SEQUENCE OF FiberConnectionEntry
    MAX-ACCESS not-accessible
    STATUS current
    DESCRIPTION "
	Fiber connection table which will be user managed and be explicitly provisioned by user. 
	Fiber Connection indicates the physical fiber connection between physical ports or subports.
	"
::= { fiberConnection 1 }
fiberConnectionEntry OBJECT-TYPE
    SYNTAX FiberConnectionEntry
    MAX-ACCESS not-accessible
    STATUS current
    DESCRIPTION "Entry of fiberConnectionTable" 
    INDEX { fiberConnectionSrcPort,fiberConnectionDstPort }
::= { fiberConnectionTable 1 }
FiberConnectionEntry ::= 
SEQUENCE {
	fiberConnectionSrcPort RowPointer,
	fiberConnectionDstPort RowPointer,
	fiberConnectionType INTEGER,
	fiberConnectionFiberLabel OCTET STRING,
	fiberConnectionAliasName OCTET STRING
    }
fiberConnectionSrcPort OBJECT-TYPE
    SYNTAX RowPointer 
    MAX-ACCESS read-only
    STATUS current
    DESCRIPTION "
	Source port of fiber connection. 
	
		
		
		"
::= { fiberConnectionEntry 1 }
fiberConnectionDstPort OBJECT-TYPE
    SYNTAX RowPointer 
    MAX-ACCESS read-only
    STATUS current
    DESCRIPTION "
	Destination port of fiber connection.
	
		
		
		"
::= { fiberConnectionEntry 2 }
fiberConnectionType OBJECT-TYPE
    SYNTAX INTEGER  {
	 twoWay (1),
	 oneWay (2)
	}
    MAX-ACCESS read-only
    STATUS current
    DESCRIPTION "
	Indicates fiber connection type.
	
		
		
		default value :two-way"
::= { fiberConnectionEntry 3 }
fiberConnectionFiberLabel OBJECT-TYPE
    SYNTAX OCTET STRING  (SIZE (0..255))
    MAX-ACCESS read-only
    STATUS current
    DESCRIPTION "Label of fiber connection.
		
		
		"
::= { fiberConnectionEntry 4 }
fiberConnectionAliasName OBJECT-TYPE
    SYNTAX OCTET STRING  (SIZE (0..256))
    MAX-ACCESS read-only
    STATUS current
    DESCRIPTION "User defined alias for this entity. Must be an alphanumeric string with dash or underscore
		
		
		"
::= { fiberConnectionEntry 5 }
optical OBJECT IDENTIFIER ::= { services 5 }
ots OBJECT IDENTIFIER ::= { optical 2 }
otsTable OBJECT-TYPE
    SYNTAX SEQUENCE OF OtsEntry
    MAX-ACCESS not-accessible
    STATUS current
    DESCRIPTION "Represents the Optical Transmission Section (OTS) interface entity"
::= { ots 1 }
otsEntry OBJECT-TYPE
    SYNTAX OtsEntry
    MAX-ACCESS not-accessible
    STATUS current
    DESCRIPTION "Entry of otsTable" 
    INDEX { otsName }
::= { otsTable 1 }
OtsEntry ::= 
SEQUENCE {
	otsName CoriantTypesNameIdentifier,
	otsAdminStatus INTEGER,
	otsOperStatus INTEGER,
	otsAvailStatus BITS,
	otsAliasName OCTET STRING,
	otsSupportingRxPort OpticalCommonSupportingPort,
	otsSupportingTxPort OpticalCommonSupportingPort,
	otsMeasuredSpanLoss CoriantTypesOpticalDB
    }
otsName OBJECT-TYPE
    SYNTAX CoriantTypesNameIdentifier 
    MAX-ACCESS read-only
    STATUS current
    DESCRIPTION "The name is defined to uniquely identify the ots optical interface.
		
		
		"
::= { otsEntry 1 }
otsAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { otsEntry 2 }
otsOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { otsEntry 3 }
otsAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { otsEntry 4 }
otsAliasName OBJECT-TYPE
    SYNTAX OCTET STRING  (SIZE (0..256))
    MAX-ACCESS read-only
    STATUS current
    DESCRIPTION "User defined alias for this entity. Must be an alphanumeric string with dash or underscore
		
		
		"
::= { otsEntry 5 }
otsSupportingRxPort OBJECT-TYPE
    SYNTAX OpticalCommonSupportingPort 
    MAX-ACCESS read-only
    STATUS current
    DESCRIPTION "Supporting Rx port for the optical interface.
		
		
		"
::= { otsEntry 6 }
otsSupportingTxPort OBJECT-TYPE
    SYNTAX OpticalCommonSupportingPort 
    MAX-ACCESS read-only
    STATUS current
    DESCRIPTION "Supporting Tx port for the optical interface.
		
		
		"
::= { otsEntry 7 }
otsMeasuredSpanLoss OBJECT-TYPE
    SYNTAX CoriantTypesOpticalDB 
    MAX-ACCESS read-only
    STATUS current
    DESCRIPTION "The measured span loss excluding offset.
		
		
		"
::= { otsEntry 8 }
oms OBJECT IDENTIFIER ::= { optical 3 }
omsTable OBJECT-TYPE
    SYNTAX SEQUENCE OF OmsEntry
    MAX-ACCESS not-accessible
    STATUS current
    DESCRIPTION "Represents the optical multiplex section (OMS) interface MO"
::= { oms 1 }
omsEntry OBJECT-TYPE
    SYNTAX OmsEntry
    MAX-ACCESS not-accessible
    STATUS current
    DESCRIPTION "Entry of omsTable" 
    INDEX { omsName }
::= { omsTable 1 }
OmsEntry ::= 
SEQUENCE {
	omsName CoriantTypesNameIdentifier,
	omsAdminStatus INTEGER,
	omsOperStatus INTEGER,
	omsAvailStatus BITS,
	omsAliasName OCTET STRING,
	omsSupportingRxPort OpticalCommonSupportingPort,
	omsSupportingTxPort OpticalCommonSupportingPort,
	omsParentOtsInterface RowPointer,
	omsRxOpticalPower CoriantTypesOpticalPower,
	omsTxOpticalPower CoriantTypesOpticalPower
    }
omsName OBJECT-TYPE
    SYNTAX CoriantTypesNameIdentifier 
    MAX-ACCESS read-only
    STATUS current
    DESCRIPTION "The name is defined to uniquely identify the oms optical interface.
		
		
		"
::= { omsEntry 1 }
omsAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { omsEntry 2 }
omsOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { omsEntry 3 }
omsAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { omsEntry 4 }
omsAliasName OBJECT-TYPE
    SYNTAX OCTET STRING  (SIZE (0..256))
    MAX-ACCESS read-only
    STATUS current
    DESCRIPTION "User defined alias for this entity. Must be an alphanumeric string with dash or underscore
		
		
		"
::= { omsEntry 5 }
omsSupportingRxPort OBJECT-TYPE
    SYNTAX OpticalCommonSupportingPort 
    MAX-ACCESS read-only
    STATUS current
    DESCRIPTION "Supporting Rx port for the optical interface.
		
		
		"
::= { omsEntry 6 }
omsSupportingTxPort OBJECT-TYPE
    SYNTAX OpticalCommonSupportingPort 
    MAX-ACCESS read-only
    STATUS current
    DESCRIPTION "Supporting Tx port for the optical interface.
		
		
		"
::= { omsEntry 7 }
omsParentOtsInterface OBJECT-TYPE
    SYNTAX RowPointer 
    MAX-ACCESS read-only
    STATUS current
    DESCRIPTION "Supporting OTS interface.
		
		
		"
::= { omsEntry 8 }
omsRxOpticalPower OBJECT-TYPE
    SYNTAX CoriantTypesOpticalPower 
    MAX-ACCESS read-only
    STATUS current
    DESCRIPTION "Received optical power
		
		
		"
::= { omsEntry 9 }
omsTxOpticalPower OBJECT-TYPE
    SYNTAX CoriantTypesOpticalPower 
    MAX-ACCESS read-only
    STATUS current
    DESCRIPTION "Transmitted optical power
		
		
		"
::= { omsEntry 10 }
osc OBJECT IDENTIFIER ::= { optical 4 }
oscTable OBJECT-TYPE
    SYNTAX SEQUENCE OF OscEntry
    MAX-ACCESS not-accessible
    STATUS current
    DESCRIPTION "Represents the Optical Supervision Channel (OSC) MO"
::= { osc 1 }
oscEntry OBJECT-TYPE
    SYNTAX OscEntry
    MAX-ACCESS not-accessible
    STATUS current
    DESCRIPTION "Entry of oscTable" 
    INDEX { oscName }
::= { oscTable 1 }
OscEntry ::= 
SEQUENCE {
	oscName CoriantTypesNameIdentifier,
	oscAdminStatus INTEGER,
	oscOperStatus INTEGER,
	oscAvailStatus BITS,
	oscAliasName OCTET STRING,
	oscSupportingRxPort OpticalCommonSupportingPort,
	oscSupportingTxPort OpticalCommonSupportingPort,
	oscParentOtsInterface RowPointer,
	oscMode INTEGER,
	oscWavelength OCTET STRING,
	oscDataCommunication CoriantTypesEnableSwitch,
	oscRxOpticalPower CoriantTypesOpticalPower,
	oscTxOpticalPower CoriantTypesOpticalPower
    }
oscName OBJECT-TYPE
    SYNTAX CoriantTypesNameIdentifier 
    MAX-ACCESS read-only
    STATUS current
    DESCRIPTION "The name is defined to uniquely identify the osc optical interface.
		
		
		"
::= { oscEntry 1 }
oscAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { oscEntry 2 }
oscOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { oscEntry 3 }
oscAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { oscEntry 4 }
oscAliasName OBJECT-TYPE
    SYNTAX OCTET STRING  (SIZE (0..256))
    MAX-ACCESS read-only
    STATUS current
    DESCRIPTION "User defined alias for this entity. Must be an alphanumeric string with dash or underscore
		
		
		"
::= { oscEntry 5 }
oscSupportingRxPort OBJECT-TYPE
    SYNTAX OpticalCommonSupportingPort 
    MAX-ACCESS read-only
    STATUS current
    DESCRIPTION "Supporting Rx port for the optical interface.
		
		
		"
::= { oscEntry 6 }
oscSupportingTxPort OBJECT-TYPE
    SYNTAX OpticalCommonSupportingPort 
    MAX-ACCESS read-only
    STATUS current
    DESCRIPTION "Supporting Tx port for the optical interface.
		
		
		"
::= { oscEntry 7 }
oscParentOtsInterface OBJECT-TYPE
    SYNTAX RowPointer 
    MAX-ACCESS read-only
    STATUS current
    DESCRIPTION "Supporting OTS insterface.
		
		
		"
::= { oscEntry 8 }
oscMode OBJECT-TYPE
    SYNTAX INTEGER  {
	 notApplicable (0),
	 t155m52 (1)
	}
    MAX-ACCESS read-only
    STATUS current
    DESCRIPTION "
	Indicating the current OSC mode. 
	
		
		
		default value :155M52"
::= { oscEntry 9 }
oscWavelength OBJECT-TYPE
    SYNTAX OCTET STRING 
    MAX-ACCESS read-only
    STATUS current
    DESCRIPTION "
	Indicates the wavelength band of the OSC channel.
	
		
		UNITS:nm
		default value :1510"
::= { oscEntry 10 }
oscDataCommunication OBJECT-TYPE
    SYNTAX CoriantTypesEnableSwitch 
    MAX-ACCESS read-only
    STATUS current
    DESCRIPTION "Configuration for enable or disable data communication network support of the OSC.
		
		
		default value :enabled"
::= { oscEntry 11 }
oscRxOpticalPower OBJECT-TYPE
    SYNTAX CoriantTypesOpticalPower 
    MAX-ACCESS read-only
    STATUS current
    DESCRIPTION "Received optical power
		
		
		"
::= { oscEntry 12 }
oscTxOpticalPower OBJECT-TYPE
    SYNTAX CoriantTypesOpticalPower 
    MAX-ACCESS read-only
    STATUS current
    DESCRIPTION "Transmitted optical power
		
		
		"
::= { oscEntry 13 }
gopt OBJECT IDENTIFIER ::= { optical 5 }
goptTable OBJECT-TYPE
    SYNTAX SEQUENCE OF GoptEntry
    MAX-ACCESS not-accessible
    STATUS current
    DESCRIPTION "Represents the Generic Optical Section Interface (GOPT) MO"
::= { gopt 1 }
goptEntry OBJECT-TYPE
    SYNTAX GoptEntry
    MAX-ACCESS not-accessible
    STATUS current
    DESCRIPTION "Entry of goptTable" 
    INDEX { goptName }
::= { goptTable 1 }
GoptEntry ::= 
SEQUENCE {
	goptName CoriantTypesNameIdentifier,
	goptAdminStatus INTEGER,
	goptOperStatus INTEGER,
	goptAvailStatus BITS,
	goptAliasName OCTET STRING,
	goptSupportingRxPort OpticalCommonSupportingPort,
	goptSupportingTxPort OpticalCommonSupportingPort,
	goptRxOpticalPower CoriantTypesOpticalPower,
	goptTxOpticalPower CoriantTypesOpticalPower
    }
goptName OBJECT-TYPE
    SYNTAX CoriantTypesNameIdentifier 
    MAX-ACCESS read-only
    STATUS current
    DESCRIPTION "The name is defined to uniquely identify the gopt optical interface.
		
		
		"
::= { goptEntry 1 }
goptAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { goptEntry 2 }
goptOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { goptEntry 3 }
goptAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { goptEntry 4 }
goptAliasName OBJECT-TYPE
    SYNTAX OCTET STRING  (SIZE (0..256))
    MAX-ACCESS read-only
    STATUS current
    DESCRIPTION "User defined alias for this entity. Must be an alphanumeric string with dash or underscore
		
		
		"
::= { goptEntry 5 }
goptSupportingRxPort OBJECT-TYPE
    SYNTAX OpticalCommonSupportingPort 
    MAX-ACCESS read-only
    STATUS current
    DESCRIPTION "Supporting Rx port for the optical interface.
		
		
		"
::= { goptEntry 6 }
goptSupportingTxPort OBJECT-TYPE
    SYNTAX OpticalCommonSupportingPort 
    MAX-ACCESS read-only
    STATUS current
    DESCRIPTION "Supporting Tx port for the optical interface.
		
		
		"
::= { goptEntry 7 }
goptRxOpticalPower OBJECT-TYPE
    SYNTAX CoriantTypesOpticalPower 
    MAX-ACCESS read-only
    STATUS current
    DESCRIPTION "Received optical power
		
		
		"
::= { goptEntry 8 }
goptTxOpticalPower OBJECT-TYPE
    SYNTAX CoriantTypesOpticalPower 
    MAX-ACCESS read-only
    STATUS current
    DESCRIPTION "Transmitted optical power
		
		
		"
::= { goptEntry 9 }
omsStatistics OBJECT IDENTIFIER ::= { optical 9 }
omsStatisticsTable OBJECT-TYPE
    SYNTAX SEQUENCE OF OmsStatisticsEntry
    MAX-ACCESS not-accessible
    STATUS current
    DESCRIPTION "NULL"
::= { omsStatistics 1 }
omsStatisticsEntry OBJECT-TYPE
    SYNTAX OmsStatisticsEntry
    MAX-ACCESS not-accessible
    STATUS current
    DESCRIPTION "Entry of omsStatisticsTable" 
    INDEX { omsName }
::= { omsStatisticsTable 1 }
OmsStatisticsEntry ::= 
SEQUENCE {
	omsStatisticsEntryLastClear IetfYangTypesDateAndTime
    }
omsStatisticsEntryLastClear OBJECT-TYPE
    SYNTAX IetfYangTypesDateAndTime 
    MAX-ACCESS read-only
    STATUS current
    DESCRIPTION "The start time of statistics monitor
		
		
		default value :0000-00-00T00:00:00.000Z"
::= { omsStatisticsEntry 1 }
oscStatistics OBJECT IDENTIFIER ::= { optical 10 }
oscStatisticsTable OBJECT-TYPE
    SYNTAX SEQUENCE OF OscStatisticsEntry
    MAX-ACCESS not-accessible
    STATUS current
    DESCRIPTION "NULL"
::= { oscStatistics 1 }
oscStatisticsEntry OBJECT-TYPE
    SYNTAX OscStatisticsEntry
    MAX-ACCESS not-accessible
    STATUS current
    DESCRIPTION "Entry of oscStatisticsTable" 
    INDEX { oscName }
::= { oscStatisticsTable 1 }
OscStatisticsEntry ::= 
SEQUENCE {
	oscStatisticsEntryLastClear IetfYangTypesDateAndTime
    }
oscStatisticsEntryLastClear OBJECT-TYPE
    SYNTAX IetfYangTypesDateAndTime 
    MAX-ACCESS read-only
    STATUS current
    DESCRIPTION "The start time of statistics monitor
		
		
		default value :0000-00-00T00:00:00.000Z"
::= { oscStatisticsEntry 1 }
goptStatistics OBJECT IDENTIFIER ::= { optical 11 }
goptStatisticsTable OBJECT-TYPE
    SYNTAX SEQUENCE OF GoptStatisticsEntry
    MAX-ACCESS not-accessible
    STATUS current
    DESCRIPTION "NULL"
::= { goptStatistics 1 }
goptStatisticsEntry OBJECT-TYPE
    SYNTAX GoptStatisticsEntry
    MAX-ACCESS not-accessible
    STATUS current
    DESCRIPTION "Entry of goptStatisticsTable" 
    INDEX { goptName }
::= { goptStatisticsTable 1 }
GoptStatisticsEntry ::= 
SEQUENCE {
	goptStatisticsEntryProtectionSwitchDuration OCTET STRING,
	goptStatisticsEntryProtectionSwitchCount OCTET STRING,
	goptStatisticsEntryLossTx OCTET STRING,
	goptStatisticsEntryLossRx OCTET STRING,
	goptStatisticsEntryLastClear IetfYangTypesDateAndTime
    }
goptStatisticsEntryProtectionSwitchDuration OBJECT-TYPE
    SYNTAX OCTET STRING 
    MAX-ACCESS read-only
    STATUS current
    DESCRIPTION "Protection Switch Duration
		
		UNITS:seconds
		"
::= { goptStatisticsEntry 1 }
goptStatisticsEntryProtectionSwitchCount OBJECT-TYPE
    SYNTAX OCTET STRING 
    MAX-ACCESS read-only
    STATUS current
    DESCRIPTION "Protection Switch Count
		
		UNITS:times
		"
::= { goptStatisticsEntry 2 }
goptStatisticsEntryLossTx OBJECT-TYPE
    SYNTAX OCTET STRING 
    MAX-ACCESS read-only
    STATUS current
    DESCRIPTION "Loss of Signal Seconds of Transmit side
		
		UNITS:seconds
		"
::= { goptStatisticsEntry 3 }
goptStatisticsEntryLossRx OBJECT-TYPE
    SYNTAX OCTET STRING 
    MAX-ACCESS read-only
    STATUS current
    DESCRIPTION "Loss of Signal Seconds of Receive side
		
		UNITS:seconds
		"
::= { goptStatisticsEntry 4 }
goptStatisticsEntryLastClear OBJECT-TYPE
    SYNTAX IetfYangTypesDateAndTime 
    MAX-ACCESS read-only
    STATUS current
    DESCRIPTION "The start time of statistics monitor
		
		
		default value :0000-00-00T00:00:00.000Z"
::= { goptStatisticsEntry 5 }
lldp OBJECT IDENTIFIER ::= { services 6 }
lldpStatusNe OBJECT-TYPE
    SYNTAX CoriantTypesEnableSwitch 
    MAX-ACCESS read-only
    STATUS current
    DESCRIPTION "
	Global lldp control on NE level. 
	Value of 'enabled', then the LLDP agent will receive,
	but it will not transmit LLDP frames on all ports with port level lldp 
	not disabled of the NE.
	                    
	Value of 'disabled', then LLDP agent will not filter and
	receive LLDP frames on all ports of the NE.  If there is remote systems
	information which is received on ports supporting LLDP and stored in
	the system before the lldp-status becomes disabled, then the information
	will naturally age out.                 
	                    
	
		
		
		default value :disabled"
::= { lldp 1 }
performance OBJECT IDENTIFIER ::= { groove 5 }
performanceInfo OBJECT IDENTIFIER ::= { performance 1 }
performancePmdaystart OBJECT-TYPE
    SYNTAX Unsigned32  (0..23)
    MAX-ACCESS read-only
    STATUS current
    DESCRIPTION "
	Specifies the hour of starting collecting 1-DAY monitoring parameters.
	To reset the NE clock to the default value of 00:00 hours, the parameter should contain the value 0.
	
		
		UNITS:hour
		default value :0"
::= { performanceInfo 1 }
performanceStatisticsEnable OBJECT-TYPE
    SYNTAX CoriantTypesEnableSwitch 
    MAX-ACCESS read-only
    STATUS current
    DESCRIPTION "
	The global switch for all system statistics data collection. 
	
		
		
		default value :enabled"
::= { performanceInfo 2 }
pmPoint OBJECT IDENTIFIER ::= { performance 2 }
pmPointTable OBJECT-TYPE
    SYNTAX SEQUENCE OF PmPointEntry
    MAX-ACCESS not-accessible
    STATUS current
    DESCRIPTION "The list of performance monitoring points associated with the monitored management object."
::= { pmPoint 1 }
pmPointEntry OBJECT-TYPE
    SYNTAX PmPointEntry
    MAX-ACCESS not-accessible
    STATUS current
    DESCRIPTION "Entry of pmPointTable" 
    INDEX { pmPointPmEntity,pmPointPmpType,pmPointPmTimePeriod }
::= { pmPointTable 1 }
PmPointEntry ::= 
SEQUENCE {
	pmPointPmEntity RowPointer,
	pmPointPmpType CoriantPmtypesPmpType,
	pmPointPmTimePeriod CoriantTypesManagementTimePeriod,
	pmPointSupervisionSwitch CoriantTypesEnableSwitch,
	pmPointThresholdingSwitch CoriantTypesEnableSwitch,
	pmPointHistoryRecording CoriantTypesEnableSwitch
    }
pmPointPmEntity OBJECT-TYPE
    SYNTAX RowPointer 
    MAX-ACCESS read-only
    STATUS current
    DESCRIPTION "Specifies the management object instance the performance monitoring data are collected for.
		
		
		"
::= { pmPointEntry 1 }
pmPointPmpType OBJECT-TYPE
    SYNTAX CoriantPmtypesPmpType 
    MAX-ACCESS read-only
    STATUS current
    DESCRIPTION "Specifies the type of performance monitoring point.
		
		
		"
::= { pmPointEntry 2 }
pmPointPmTimePeriod OBJECT-TYPE
    SYNTAX CoriantTypesManagementTimePeriod 
    MAX-ACCESS read-only
    STATUS current
    DESCRIPTION "Specifies the time-period increments during which PM data are collected.
		
		
		"
::= { pmPointEntry 3 }
pmPointSupervisionSwitch OBJECT-TYPE
    SYNTAX CoriantTypesEnableSwitch 
    MAX-ACCESS read-only
    STATUS current
    DESCRIPTION "Enable/disable counting for all performance monitoring parameters of the given PMP.
		
		
		default value :disabled"
::= { pmPointEntry 4 }
pmPointThresholdingSwitch OBJECT-TYPE
    SYNTAX CoriantTypesEnableSwitch 
    MAX-ACCESS read-only
    STATUS current
    DESCRIPTION "Enable/disable the TCA processing and reporting for all performance monitoring parameters of the given PM point.
		
		
		default value :enabled"
::= { pmPointEntry 5 }
pmPointHistoryRecording OBJECT-TYPE
    SYNTAX CoriantTypesEnableSwitch 
    MAX-ACCESS read-only
    STATUS current
    DESCRIPTION "Enable/disable the history data storage for all performance monitoring parameters of the given PM point.
		
		
		default value :enabled"
::= { pmPointEntry 6 }
pmData OBJECT IDENTIFIER ::= { performance 3 }
pmDataCurrentTable OBJECT-TYPE
    SYNTAX SEQUENCE OF PmDataCurrentEntry
    MAX-ACCESS not-accessible
    STATUS current
    DESCRIPTION "Defines the get-pm output of record performance data for current time"
::= { pmData 2 }
pmDataCurrentEntry OBJECT-TYPE
    SYNTAX PmDataCurrentEntry
    MAX-ACCESS not-accessible
    STATUS current
    DESCRIPTION "Entry of pmDataCurrentTable" 
    INDEX { pmPointPmEntity, pmPointPmpType, pmPointPmTimePeriod, pmDataCurrentPmParameter }
::= { pmDataCurrentTable 1 }
PmDataCurrentEntry ::= 
SEQUENCE {
	pmDataCurrentMonitoringDateTime OCTET STRING,
	pmDataCurrentPmParameter CoriantPmtypesPmParameter,
	pmDataCurrentPmValue OCTET STRING,
	pmDataCurrentPmUnit CoriantCommonpmUnitOfValue,
	pmDataCurrentValidity CoriantPmtypesValidityType
    }
pmDataCurrentMonitoringDateTime OBJECT-TYPE
    SYNTAX OCTET STRING 
    MAX-ACCESS read-only
    STATUS current
    DESCRIPTION "Monitoring data and time'
		
		
		"
::= { pmDataCurrentEntry 1 }
pmDataCurrentPmParameter OBJECT-TYPE
    SYNTAX CoriantPmtypesPmParameter 
    MAX-ACCESS not-accessible
    STATUS current
    DESCRIPTION "Performance Monitoring parameter, which could be a counter or gauge parameter, the later support current, max and min values.
		
		
		"
::= { pmDataCurrentEntry 2 }
pmDataCurrentPmValue OBJECT-TYPE
    SYNTAX OCTET STRING  (SIZE (1..32))
    MAX-ACCESS read-only
    STATUS current
    DESCRIPTION "
	PM counter or gauge value of the PM parameter.
	
		
		
		"
::= { pmDataCurrentEntry 3 }
pmDataCurrentPmUnit OBJECT-TYPE
    SYNTAX CoriantCommonpmUnitOfValue 
    MAX-ACCESS read-only
    STATUS current
    DESCRIPTION "
	Unit of PM value.
	
		
		
		"
::= { pmDataCurrentEntry 4 }
pmDataCurrentValidity OBJECT-TYPE
    SYNTAX CoriantPmtypesValidityType 
    MAX-ACCESS read-only
    STATUS current
    DESCRIPTION "Indicates whether or not a performance monitoring value is valid.
		
		
		"
::= { pmDataCurrentEntry 5 }
pmDataLatestHistoryTable OBJECT-TYPE
    SYNTAX SEQUENCE OF PmDataLatestHistoryEntry
    MAX-ACCESS not-accessible
    STATUS current
    DESCRIPTION "Defines the get-pm output of record performance data for latest history time"
::= { pmData 3 }
pmDataLatestHistoryEntry OBJECT-TYPE
    SYNTAX PmDataLatestHistoryEntry
    MAX-ACCESS not-accessible
    STATUS current
    DESCRIPTION "Entry of pmDataLatestHistoryTable" 
    INDEX { pmPointPmEntity, pmPointPmpType, pmPointPmTimePeriod, pmDataLatestHistoryPmParameter }
::= { pmDataLatestHistoryTable 1 }
PmDataLatestHistoryEntry ::= 
SEQUENCE {
	pmDataLatestHistoryMonitoringDateTime OCTET STRING,
	pmDataLatestHistoryPmParameter CoriantPmtypesPmParameter,
	pmDataLatestHistoryPmValue OCTET STRING,
	pmDataLatestHistoryPmUnit CoriantCommonpmUnitOfValue,
	pmDataLatestHistoryValidity CoriantPmtypesValidityType
    }
pmDataLatestHistoryMonitoringDateTime OBJECT-TYPE
    SYNTAX OCTET STRING 
    MAX-ACCESS read-only
    STATUS current
    DESCRIPTION "Monitoring data and time'
		
		
		"
::= { pmDataLatestHistoryEntry 1 }
pmDataLatestHistoryPmParameter OBJECT-TYPE
    SYNTAX CoriantPmtypesPmParameter 
    MAX-ACCESS not-accessible
    STATUS current
    DESCRIPTION "Performance Monitoring parameter, which could be a counter or gauge parameter, the later support current, max and min values.
		
		
		"
::= { pmDataLatestHistoryEntry 2 }
pmDataLatestHistoryPmValue OBJECT-TYPE
    SYNTAX OCTET STRING  (SIZE (1..32))
    MAX-ACCESS read-only
    STATUS current
    DESCRIPTION "
	PM counter or gauge value of the PM parameter.
	
		
		
		"
::= { pmDataLatestHistoryEntry 3 }
pmDataLatestHistoryPmUnit OBJECT-TYPE
    SYNTAX CoriantCommonpmUnitOfValue 
    MAX-ACCESS read-only
    STATUS current
    DESCRIPTION "
	Unit of PM value.
	
		
		
		"
::= { pmDataLatestHistoryEntry 4 }
pmDataLatestHistoryValidity OBJECT-TYPE
    SYNTAX CoriantPmtypesValidityType 
    MAX-ACCESS read-only
    STATUS current
    DESCRIPTION "Indicates whether or not a performance monitoring value is valid.
		
		
		"
::= { pmDataLatestHistoryEntry 5 }
pmDataHistoryTable OBJECT-TYPE
    SYNTAX SEQUENCE OF PmDataHistoryEntry
    MAX-ACCESS not-accessible
    STATUS current
    DESCRIPTION "Defines the get-pm output of record performance data for history"
::= { pmData 4 }
pmDataHistoryEntry OBJECT-TYPE
    SYNTAX PmDataHistoryEntry
    MAX-ACCESS not-accessible
    STATUS current
    DESCRIPTION "Entry of pmDataHistoryTable" 
    INDEX { pmPointPmEntity, pmPointPmpType, pmPointPmTimePeriod, pmDataHistoryRecordIndex,pmDataHistoryPmParameter }
::= { pmDataHistoryTable 1 }
PmDataHistoryEntry ::= 
SEQUENCE {
	pmDataHistoryRecordIndex Unsigned32,
	pmDataHistoryMonitoringDateTime OCTET STRING,
	pmDataHistoryPmParameter CoriantPmtypesPmParameter,
	pmDataHistoryPmValue OCTET STRING,
	pmDataHistoryPmUnit CoriantCommonpmUnitOfValue,
	pmDataHistoryValidity CoriantPmtypesValidityType
    }
pmDataHistoryRecordIndex OBJECT-TYPE
    SYNTAX Unsigned32 
    MAX-ACCESS not-accessible
    STATUS current
    DESCRIPTION "Index of PM data records.
		
		
		"
::= { pmDataHistoryEntry 1 }
pmDataHistoryMonitoringDateTime OBJECT-TYPE
    SYNTAX OCTET STRING 
    MAX-ACCESS read-only
    STATUS current
    DESCRIPTION "Monitoring data and time'
		
		
		"
::= { pmDataHistoryEntry 2 }
pmDataHistoryPmParameter OBJECT-TYPE
    SYNTAX CoriantPmtypesPmParameter 
    MAX-ACCESS not-accessible
    STATUS current
    DESCRIPTION "Performance Monitoring parameter, which could be a counter or gauge parameter, the later support current, max and min values.
		
		
		"
::= { pmDataHistoryEntry 3 }
pmDataHistoryPmValue OBJECT-TYPE
    SYNTAX OCTET STRING  (SIZE (1..32))
    MAX-ACCESS read-only
    STATUS current
    DESCRIPTION "
	PM counter or gauge value of the PM parameter.
	
		
		
		"
::= { pmDataHistoryEntry 4 }
pmDataHistoryPmUnit OBJECT-TYPE
    SYNTAX CoriantCommonpmUnitOfValue 
    MAX-ACCESS read-only
    STATUS current
    DESCRIPTION "
	Unit of PM value.
	
		
		
		"
::= { pmDataHistoryEntry 5 }
pmDataHistoryValidity OBJECT-TYPE
    SYNTAX CoriantPmtypesValidityType 
    MAX-ACCESS read-only
    STATUS current
    DESCRIPTION "Indicates whether or not a performance monitoring value is valid.
		
		
		"
::= { pmDataHistoryEntry 6 }
pmThresholdsValue OBJECT IDENTIFIER ::= { performance 4 }
pmThresholdsValueTable OBJECT-TYPE
    SYNTAX SEQUENCE OF PmThresholdsValueEntry
    MAX-ACCESS not-accessible
    STATUS current
    DESCRIPTION "The list of entries of performance monitoring threshold value."
::= { pmThresholdsValue 1 }
pmThresholdsValueEntry OBJECT-TYPE
    SYNTAX PmThresholdsValueEntry
    MAX-ACCESS not-accessible
    STATUS current
    DESCRIPTION "Entry of pmThresholdsValueTable" 
    INDEX { pmPointPmEntity,pmPointPmpType,pmPointPmTimePeriod,pmThresholdsValuePmParameter }
::= { pmThresholdsValueTable 1 }
PmThresholdsValueEntry ::= 
SEQUENCE {
	pmThresholdsValuePmParameter CoriantPmtypesPmParameter,
	pmThresholdsValuePmHighThreshold CoriantCommonpmThresholdValue,
	pmThresholdsValuePmLowThreshold CoriantCommonpmThresholdValue,
	pmThresholdsValuePmUnit CoriantCommonpmUnitOfValue
    }
pmThresholdsValuePmParameter OBJECT-TYPE
    SYNTAX CoriantPmtypesPmParameter 
    MAX-ACCESS read-only
    STATUS current
    DESCRIPTION "Performance Monitoring parameter, which could be a counter or gauge parameter, the later support current, max and min values.
		
		
		"
::= { pmThresholdsValueEntry 1 }
pmThresholdsValuePmHighThreshold OBJECT-TYPE
    SYNTAX CoriantCommonpmThresholdValue 
    MAX-ACCESS read-only
    STATUS current
    DESCRIPTION "Specifies the desired high threshold value of the selected performance monitoring parameter.
		
		
		"
::= { pmThresholdsValueEntry 2 }
pmThresholdsValuePmLowThreshold OBJECT-TYPE
    SYNTAX CoriantCommonpmThresholdValue 
    MAX-ACCESS read-only
    STATUS current
    DESCRIPTION "Specifies the desired low threshold value of the selected performance monitoring parameter.
		
		
		"
::= { pmThresholdsValueEntry 3 }
pmThresholdsValuePmUnit OBJECT-TYPE
    SYNTAX CoriantCommonpmUnitOfValue 
    MAX-ACCESS read-only
    STATUS current
    DESCRIPTION "The unit of the performance monitoring value.
		
		
		"
::= { pmThresholdsValueEntry 4 }
networking OBJECT IDENTIFIER ::= { groove 6 }
networkingInfo OBJECT IDENTIFIER ::= { networking 1 }
networkingSourceAddressSelectMode OBJECT-TYPE
    SYNTAX INTEGER  {
	 loopbackPrefer (1),
	 linkPrefer (2)
	}
    MAX-ACCESS read-only
    STATUS current
    DESCRIPTION "Select the source address for route next-hop entry.
	loopback-prefer mode select the numerically lowest address configured on loopback interfaces if exist,
	link-prefer mode select the address configured on the outgoing interface
		
		
		default value :link-prefer"
::= { networkingInfo 1 }
interface OBJECT IDENTIFIER ::= { networking 2 }
interfaceTable OBJECT-TYPE
    SYNTAX SEQUENCE OF InterfaceEntry
    MAX-ACCESS not-accessible
    STATUS current
    DESCRIPTION "The list of configured interfaces on the device."
::= { interface 1 }
interfaceEntry OBJECT-TYPE
    SYNTAX InterfaceEntry
    MAX-ACCESS not-accessible
    STATUS current
    DESCRIPTION "Entry of interfaceTable" 
    INDEX { interfaceIfName }
::= { interfaceTable 1 }
InterfaceEntry ::= 
SEQUENCE {
	interfaceIfName OCTET STRING,
	interfaceIfDescription OCTET STRING,
	interfaceIfType INTEGER,
	interfaceAdminStatus INTEGER,
	interfaceOperStatus INTEGER,
	interfaceAvailStatus BITS,
	interfaceAliasName OCTET STRING
    }
interfaceIfName OBJECT-TYPE
    SYNTAX OCTET STRING  (SIZE (1..64))
    MAX-ACCESS read-only
    STATUS current
    DESCRIPTION "The name of the interface.
		
		
		"
::= { interfaceEntry 1 }
interfaceIfDescription OBJECT-TYPE
    SYNTAX OCTET STRING  (SIZE (0..255))
    MAX-ACCESS read-only
    STATUS current
    DESCRIPTION "A textual description of the interface.
		
		
		"
::= { interfaceEntry 2 }
interfaceIfType OBJECT-TYPE
    SYNTAX INTEGER  {
	 other (0),
	 ethernetcsmacd (1),
	 ppp (2),
	 softwareloopback (3),
	 lapd (4),
	 oscx (5)
	}
    MAX-ACCESS read-only
    STATUS current
    DESCRIPTION "The type of the interface. Refer to http://www.iana.org/assignments/smi-numbers
		
		
		"
::= { interfaceEntry 3 }
interfaceAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { interfaceEntry 4 }
interfaceOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { interfaceEntry 5 }
interfaceAvailStatus OBJECT-TYPE
    SYNTAX BITS  {
	 none (0),
	 failed (1),
	 mismatch (2),
	 lowerLayerDown (3),
	 notPresent (4),
	 shutdown (5),
	 degraded (6),
	 idle (7),
	 busy (8),
	 hibernation (9),
	 inTest (10),
	 loopback (11),
	 softwareUpgrade (12),
	 initializing (13),
	 unknown (14),
	 incomplete (15),
	 laserSafetyShutoff (16),
	 measuring (17),
	 firmwareLoading (18),
	 connected (19)
	}
    MAX-ACCESS read-only
    STATUS current
    DESCRIPTION "
	Provided to qualify the operational, usage and/or administrative status attributes. 
	The value shall be a bits, management interface shall show the string with space separator ' ' per yang definition.  
	            
	Following available status indication shall be supported: 
	Failed,Mismatch,LowerLayerDown,NotPresent,Shutdown,Degraded,Idle,Busy,
	Hibernation,In-Test,Loopback,SoftwareUpgrade,Initializing,Unknown,Incomplete
	            
	Example: an ODU can be failed without cross connection, the available status is 'Failed Idle'. 
	            
	Provided to qualify the operational, usage and/or administrative state attributes. The value of each 
	status attribute may denote the presence of one or more particular conditions applicable to the resource. 
	
		
		
		"
::= { interfaceEntry 6 }
interfaceAliasName OBJECT-TYPE
    SYNTAX OCTET STRING  (SIZE (0..256))
    MAX-ACCESS read-only
    STATUS current
    DESCRIPTION "User defined alias for this entity. Must be an alphanumeric string with dash or underscore
		
		
		"
::= { interfaceEntry 7 }
ethernet OBJECT IDENTIFIER ::= { networking 3 }
ethernetTable OBJECT-TYPE
    SYNTAX SEQUENCE OF EthernetEntry
    MAX-ACCESS not-accessible
    STATUS current
    DESCRIPTION "The Ethernet attributes of an Ethernet interface."
::= { ethernet 1 }
ethernetEntry OBJECT-TYPE
    SYNTAX EthernetEntry
    MAX-ACCESS not-accessible
    STATUS current
    DESCRIPTION "Entry of ethernetTable" 
    INDEX { interfaceIfName }
::= { ethernetTable 1 }
EthernetEntry ::= 
SEQUENCE {
	ethernetAutoNegotiation CoriantTypesEnableSwitch,
	ethernetDuplexMode CoriantTypesDuplexMode,
	ethernetOperationalDuplexMode CoriantTypesDuplexMode,
	ethernetRate CoriantTypesEthernetRate,
	ethernetOperationalEthernetRate CoriantTypesEthernetRate,
	ethernetFlowControl CoriantTypesFlowControl,
	ethernetOperationalFlowControl CoriantTypesFlowControl,
	ethernetMacAddress IetfYangTypesMacAddress,
	ethernetAliasName OCTET STRING
    }
ethernetAutoNegotiation OBJECT-TYPE
    SYNTAX CoriantTypesEnableSwitch 
    MAX-ACCESS read-only
    STATUS current
    DESCRIPTION "Auto negotiation mode.
		
		
		default value :disabled"
::= { ethernetEntry 1 }
ethernetDuplexMode OBJECT-TYPE
    SYNTAX CoriantTypesDuplexMode 
    MAX-ACCESS read-only
    STATUS current
    DESCRIPTION "Duplex Mode; only valid if auto negotiation is disabled.
		
		
		default value :full"
::= { ethernetEntry 2 }
ethernetOperationalDuplexMode OBJECT-TYPE
    SYNTAX CoriantTypesDuplexMode 
    MAX-ACCESS read-only
    STATUS current
    DESCRIPTION "Operational duplex mode.
		
		
		default value :NA"
::= { ethernetEntry 3 }
ethernetRate OBJECT-TYPE
    SYNTAX CoriantTypesEthernetRate 
    MAX-ACCESS read-only
    STATUS current
    DESCRIPTION "Required Ethernet Rate; only valid if auto negotiation is disabled.
		
		
		default value :max-rate"
::= { ethernetEntry 4 }
ethernetOperationalEthernetRate OBJECT-TYPE
    SYNTAX CoriantTypesEthernetRate 
    MAX-ACCESS read-only
    STATUS current
    DESCRIPTION "Operation ethernet rate.
		
		
		default value :NA"
::= { ethernetEntry 5 }
ethernetFlowControl OBJECT-TYPE
    SYNTAX CoriantTypesFlowControl 
    MAX-ACCESS read-only
    STATUS current
    DESCRIPTION "Specifies the type of flow control to be supported.
		
		
		default value :tx-rx"
::= { ethernetEntry 6 }
ethernetOperationalFlowControl OBJECT-TYPE
    SYNTAX CoriantTypesFlowControl 
    MAX-ACCESS read-only
    STATUS current
    DESCRIPTION "Operational flow control.
		
		
		default value :NA"
::= { ethernetEntry 7 }
ethernetMacAddress OBJECT-TYPE
    SYNTAX IetfYangTypesMacAddress 
    MAX-ACCESS read-only
    STATUS current
    DESCRIPTION "MAC Address of the port.
		
		
		default value :00:00:00:00:00:00"
::= { ethernetEntry 8 }
ethernetAliasName OBJECT-TYPE
    SYNTAX OCTET STRING  (SIZE (0..256))
    MAX-ACCESS read-only
    STATUS current
    DESCRIPTION "User defined alias for this entity. Must be an alphanumeric string with dash or underscore
		
		
		"
::= { ethernetEntry 9 }
ppp OBJECT IDENTIFIER ::= { networking 4 }
pppTable OBJECT-TYPE
    SYNTAX SEQUENCE OF PppEntry
    MAX-ACCESS not-accessible
    STATUS current
    DESCRIPTION "NULL"
::= { ppp 1 }
pppEntry OBJECT-TYPE
    SYNTAX PppEntry
    MAX-ACCESS not-accessible
    STATUS current
    DESCRIPTION "Entry of pppTable" 
    INDEX { interfaceIfName }
::= { pppTable 1 }
PppEntry ::= 
SEQUENCE {
	pppType INTEGER,
	pppPfRef RowPointer,
	pppResourceRef RowPointer,
	pppAliasName OCTET STRING
    }
pppType OBJECT-TYPE
    SYNTAX INTEGER  {
	 gcc0 (1)
	}
    MAX-ACCESS read-only
    STATUS current
    DESCRIPTION "Specifies the link type associated with the ppp.
		
		
		"
::= { pppEntry 1 }
pppPfRef OBJECT-TYPE
    SYNTAX RowPointer 
    MAX-ACCESS read-only
    STATUS current
    DESCRIPTION "Reference of the ppp profile.
		
		
		"
::= { pppEntry 2 }
pppResourceRef OBJECT-TYPE
    SYNTAX RowPointer 
    MAX-ACCESS read-only
    STATUS current
    DESCRIPTION "Reference of the lower layer resource associated with this interface.
		
		
		"
::= { pppEntry 3 }
pppAliasName OBJECT-TYPE
    SYNTAX OCTET STRING  (SIZE (0..256))
    MAX-ACCESS read-only
    STATUS current
    DESCRIPTION "User defined alias for this entity. Must be an alphanumeric string with dash or underscore
		
		
		"
::= { pppEntry 4 }
ipv4 OBJECT IDENTIFIER ::= { networking 5 }
ipv4Table OBJECT-TYPE
    SYNTAX SEQUENCE OF Ipv4Entry
    MAX-ACCESS not-accessible
    STATUS current
    DESCRIPTION "Parameters for the IPv4 address family."
::= { ipv4 1 }
ipv4Entry OBJECT-TYPE
    SYNTAX Ipv4Entry
    MAX-ACCESS not-accessible
    STATUS current
    DESCRIPTION "Entry of ipv4Table" 
    INDEX { interfaceIfName }
::= { ipv4Table 1 }
Ipv4Entry ::= 
SEQUENCE {
	ipv4Forwarding TruthValue,
	ipv4Mtu Unsigned32,
	ipv4AddressAssignmentMethod INTEGER
    }
ipv4Forwarding OBJECT-TYPE
    SYNTAX TruthValue 
    MAX-ACCESS read-only
    STATUS current
    DESCRIPTION "Controls IPv4 packet forwarding of datagrams received by,
	but not addressed to, this interface.  IPv4 routers
	forward datagrams.  IPv4 hosts do not (except those
	source-routed via the host).
		
		
		default value :true"
::= { ipv4Entry 1 }
ipv4Mtu OBJECT-TYPE
    SYNTAX Unsigned32  (68..65535)
    MAX-ACCESS read-only
    STATUS current
    DESCRIPTION "The size, in octets, of the largest IPv4 packet that the
	interface will send and receive. 
	                
	The server may restrict the allowed values for this leaf,
	depending on the interface's type.
	                
	If this leaf is not configured, the operationally used MTU
	depends on the interface's type.
		
		UNITS:octets
		"
::= { ipv4Entry 2 }
ipv4AddressAssignmentMethod OBJECT-TYPE
    SYNTAX INTEGER  {
	 static (1),
	 dhcp (2)
	}
    MAX-ACCESS read-only
    STATUS current
    DESCRIPTION "IPv4 address assignment method.
		
		
		default value :static"
::= { ipv4Entry 3 }
ipAddress OBJECT IDENTIFIER ::= { networking 6 }
ipAddressTable OBJECT-TYPE
    SYNTAX SEQUENCE OF IpAddressEntry
    MAX-ACCESS not-accessible
    STATUS current
    DESCRIPTION "The IPv4 address on the interface."
::= { ipAddress 1 }
ipAddressEntry OBJECT-TYPE
    SYNTAX IpAddressEntry
    MAX-ACCESS not-accessible
    STATUS current
    DESCRIPTION "Entry of ipAddressTable" 
    INDEX { interfaceIfName }
::= { ipAddressTable 1 }
IpAddressEntry ::= 
SEQUENCE {
	ipAddressIp IetfInetTypesIpv4Address,
	ipAddressOrigin INTEGER,
	ipAddressPrefixLength Unsigned32
    }
ipAddressIp OBJECT-TYPE
    SYNTAX IetfInetTypesIpv4Address 
    MAX-ACCESS read-only
    STATUS current
    DESCRIPTION "The IPv4 address on the interface.
		
		
		"
::= { ipAddressEntry 1 }
ipAddressOrigin OBJECT-TYPE
    SYNTAX INTEGER  {
	 other (1),
	 static (2),
	 dhcp (3),
	 linkLayer (4),
	 random (5)
	}
    MAX-ACCESS read-only
    STATUS current
    DESCRIPTION "The origin of this address.
		
		
		default value :static"
::= { ipAddressEntry 2 }
ipAddressPrefixLength OBJECT-TYPE
    SYNTAX Unsigned32  (0..32)
    MAX-ACCESS read-only
    STATUS current
    DESCRIPTION "The length of the subnet prefix.
		
		
		"
::= { ipAddressEntry 3 }
ipUnnumbered OBJECT IDENTIFIER ::= { networking 7 }
ipUnnumberedTable OBJECT-TYPE
    SYNTAX SEQUENCE OF IpUnnumberedEntry
    MAX-ACCESS not-accessible
    STATUS current
    DESCRIPTION "The IP unnumbered configurations."
::= { ipUnnumbered 1 }
ipUnnumberedEntry OBJECT-TYPE
    SYNTAX IpUnnumberedEntry
    MAX-ACCESS not-accessible
    STATUS current
    DESCRIPTION "Entry of ipUnnumberedTable" 
    INDEX { interfaceIfName }
::= { ipUnnumberedTable 1 }
IpUnnumberedEntry ::= 
SEQUENCE {
	ipUnnumberedUnnumEnabled TruthValue,
	ipUnnumberedParentInterface RowPointer
    }
ipUnnumberedUnnumEnabled OBJECT-TYPE
    SYNTAX TruthValue 
    MAX-ACCESS read-only
    STATUS current
    DESCRIPTION "Indicates that the interface is unnumbered. By default the interface is numbered, i.e., expected to have an IP address configuration.
		
		
		default value :false"
::= { ipUnnumberedEntry 1 }
ipUnnumberedParentInterface OBJECT-TYPE
    SYNTAX RowPointer 
    MAX-ACCESS read-only
    STATUS current
    DESCRIPTION "Reference of the parent interface of the unnumbered interface.
		
		
		"
::= { ipUnnumberedEntry 2 }
routingProtocol OBJECT IDENTIFIER ::= { networking 9 }
routingProtocolTable OBJECT-TYPE
    SYNTAX SEQUENCE OF RoutingProtocolEntry
    MAX-ACCESS not-accessible
    STATUS current
    DESCRIPTION "Routing protocol instance."
::= { routingProtocol 1 }
routingProtocolEntry OBJECT-TYPE
    SYNTAX RoutingProtocolEntry
    MAX-ACCESS not-accessible
    STATUS current
    DESCRIPTION "Entry of routingProtocolTable" 
    INDEX { routingProtocolRtpType,routingProtocolRtpName }
::= { routingProtocolTable 1 }
RoutingProtocolEntry ::= 
SEQUENCE {
	routingProtocolRtpType CoriantTypesRtpType,
	routingProtocolRtpName OCTET STRING,
	routingProtocolDescription OCTET STRING
    }
routingProtocolRtpType OBJECT-TYPE
    SYNTAX CoriantTypesRtpType 
    MAX-ACCESS read-only
    STATUS current
    DESCRIPTION "The type of the routing protocol instance.
		
		
		"
::= { routingProtocolEntry 1 }
routingProtocolRtpName OBJECT-TYPE
    SYNTAX OCTET STRING  (SIZE (1..64))
    MAX-ACCESS read-only
    STATUS current
    DESCRIPTION "The name of the routing protocol instance. 
	                    
	For system-controlled instances this name is
	persistent, i.e., it SHOULD NOT change across
	reboots.
		
		
		"
::= { routingProtocolEntry 2 }
routingProtocolDescription OBJECT-TYPE
    SYNTAX OCTET STRING 
    MAX-ACCESS read-only
    STATUS current
    DESCRIPTION "Textual description of the routing protocol instance.
		
		
		"
::= { routingProtocolEntry 3 }
staticRoute OBJECT IDENTIFIER ::= { networking 10 }
staticRouteTable OBJECT-TYPE
    SYNTAX SEQUENCE OF StaticRouteEntry
    MAX-ACCESS not-accessible
    STATUS current
    DESCRIPTION "A list of static routes."
::= { staticRoute 1 }
staticRouteEntry OBJECT-TYPE
    SYNTAX StaticRouteEntry
    MAX-ACCESS not-accessible
    STATUS current
    DESCRIPTION "Entry of staticRouteTable" 
    INDEX { routingProtocolRtpType,routingProtocolRtpName,staticRouteDestinationPrefix }
::= { staticRouteTable 1 }
StaticRouteEntry ::= 
SEQUENCE {
	staticRouteDestinationPrefix IetfInetTypesIpv4Prefix,
	staticRouteDescription OCTET STRING,
	staticRouteAdvertised TruthValue
    }
staticRouteDestinationPrefix OBJECT-TYPE
    SYNTAX IetfInetTypesIpv4Prefix  (SIZE (1..64))
    MAX-ACCESS read-only
    STATUS current
    DESCRIPTION "IPv4 destination prefix.
		
		
		"
::= { staticRouteEntry 1 }
staticRouteDescription OBJECT-TYPE
    SYNTAX OCTET STRING 
    MAX-ACCESS read-only
    STATUS current
    DESCRIPTION "Textual description of the static route.
		
		
		"
::= { staticRouteEntry 2 }
staticRouteAdvertised OBJECT-TYPE
    SYNTAX TruthValue 
    MAX-ACCESS read-only
    STATUS current
    DESCRIPTION "When set to YES, the static route is advertised in the routing
	protocol. For OSPF, the static route will be advertised as an 
	AS external route, if OSPF is configured as an ASBR.
		
		
		default value :false"
::= { staticRouteEntry 3 }
nextHop OBJECT IDENTIFIER ::= { networking 11 }
nextHopTable OBJECT-TYPE
    SYNTAX SEQUENCE OF NextHopEntry
    MAX-ACCESS not-accessible
    STATUS current
    DESCRIPTION "Configuration of static next-hop."
::= { nextHop 1 }
nextHopEntry OBJECT-TYPE
    SYNTAX NextHopEntry
    MAX-ACCESS not-accessible
    STATUS current
    DESCRIPTION "Entry of nextHopTable" 
    INDEX { routingProtocolRtpType,routingProtocolRtpName,staticRouteDestinationPrefix,nextHopIndex,ribName,routeSourceProtocol,routeDestinationPrefix }
::= { nextHopTable 1 }
NextHopEntry ::= 
SEQUENCE {
	nextHopIndex OCTET STRING,
	nextHopOutgoingInterface RowPointer,
	nextHopAddress IetfInetTypesIpv4Address,
	nextHopMetric Unsigned32
    }
nextHopIndex OBJECT-TYPE
    SYNTAX OCTET STRING  (SIZE (1..64))
    MAX-ACCESS read-only
    STATUS current
    DESCRIPTION "An user-specified identifier utilised to uniquely reference the next-hop entry in the next-hop list. The value of this index has no semantic meaning other than for referencing the entry.
		
		
		"
::= { nextHopEntry 1 }
nextHopOutgoingInterface OBJECT-TYPE
    SYNTAX RowPointer 
    MAX-ACCESS read-only
    STATUS current
    DESCRIPTION "Reference of the outgoing interface.
		
		
		"
::= { nextHopEntry 2 }
nextHopAddress OBJECT-TYPE
    SYNTAX IetfInetTypesIpv4Address 
    MAX-ACCESS read-only
    STATUS current
    DESCRIPTION "IPv4 address of the next-hop.
		
		
		"
::= { nextHopEntry 3 }
nextHopMetric OBJECT-TYPE
    SYNTAX Unsigned32 
    MAX-ACCESS read-only
    STATUS current
    DESCRIPTION "metric of the next-hop.
		
		
		default value :0"
::= { nextHopEntry 4 }
ospf OBJECT IDENTIFIER ::= { networking 12 }
ospfTable OBJECT-TYPE
    SYNTAX SEQUENCE OF OspfEntry
    MAX-ACCESS not-accessible
    STATUS current
    DESCRIPTION "OSPF protocol."
::= { ospf 1 }
ospfEntry OBJECT-TYPE
    SYNTAX OspfEntry
    MAX-ACCESS not-accessible
    STATUS current
    DESCRIPTION "Entry of ospfTable" 
    INDEX { routingProtocolRtpType,routingProtocolRtpName }
::= { ospfTable 1 }
OspfEntry ::= 
SEQUENCE {
	ospfRouterId IetfYangTypesDottedQuad,
	ospfDescription OCTET STRING,
	ospfAsbr TruthValue,
	ospfAdminStatus INTEGER,
	ospfOperStatus INTEGER,
	ospfAliasName OCTET STRING
    }
ospfRouterId OBJECT-TYPE
    SYNTAX IetfYangTypesDottedQuad 
    MAX-ACCESS read-only
    STATUS current
    DESCRIPTION "OSPF Router ID.
		
		
		"
::= { ospfEntry 1 }
ospfDescription OBJECT-TYPE
    SYNTAX OCTET STRING 
    MAX-ACCESS read-only
    STATUS current
    DESCRIPTION "Textual description of the OSPF instance.
		
		
		"
::= { ospfEntry 2 }
ospfAsbr OBJECT-TYPE
    SYNTAX TruthValue 
    MAX-ACCESS read-only
    STATUS current
    DESCRIPTION "OSPF Autonomous System Boundary Router.
		
		
		default value :true"
::= { ospfEntry 3 }
ospfAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { ospfEntry 4 }
ospfOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { ospfEntry 5 }
ospfAliasName OBJECT-TYPE
    SYNTAX OCTET STRING  (SIZE (0..256))
    MAX-ACCESS read-only
    STATUS current
    DESCRIPTION "User defined alias for this entity. Must be an alphanumeric string with dash or underscore
		
		
		"
::= { ospfEntry 6 }
ospfArea OBJECT IDENTIFIER ::= { networking 13 }
ospfAreaTable OBJECT-TYPE
    SYNTAX SEQUENCE OF OspfAreaEntry
    MAX-ACCESS not-accessible
    STATUS current
    DESCRIPTION "Configuration of ospf area."
::= { ospfArea 1 }
ospfAreaEntry OBJECT-TYPE
    SYNTAX OspfAreaEntry
    MAX-ACCESS not-accessible
    STATUS current
    DESCRIPTION "Entry of ospfAreaTable" 
    INDEX { routingProtocolRtpType,routingProtocolRtpName,ospfAreaId }
::= { ospfAreaTable 1 }
OspfAreaEntry ::= 
SEQUENCE {
	ospfAreaId IetfYangTypesDottedQuad,
	ospfAreaAdminStatus INTEGER,
	ospfAreaOperStatus INTEGER,
	ospfAreaAliasName OCTET STRING,
	ospfAreaType INTEGER
    }
ospfAreaId OBJECT-TYPE
    SYNTAX IetfYangTypesDottedQuad  (SIZE (1..64))
    MAX-ACCESS read-only
    STATUS current
    DESCRIPTION "OSPF Router Area ID.
		
		
		"
::= { ospfAreaEntry 1 }
ospfAreaAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { ospfAreaEntry 2 }
ospfAreaOperStatus OBJECT-TYPE
    SYNTAX INTEGER  {
	 up (1),
	 down (2)
	}
    MAX-ACCESS read-only
    STATUS current
    DESCRIPTION "
	The operational state specifies whether or not a resource is able to provide service. 
	The operational state shall be visible to the operator. The user cannot modify the operational state. It provides a simple mechanism for the operator to decide whether a resource is operational or not, therefore this parameter has a read-only nature. 
	The operational state is closely coupled with the alarm status of a resource, i.e. state transitions are triggered internally by the NE software. It can have one of the following values:
	Down: The resource is totally inoperable and unable to provide service to the user(s)
	Up: The resource is partially or fully operable and available for use. 
	
		
		
		default value :up"
::= { ospfAreaEntry 3 }
ospfAreaAliasName OBJECT-TYPE
    SYNTAX OCTET STRING  (SIZE (0..256))
    MAX-ACCESS read-only
    STATUS current
    DESCRIPTION "User defined alias for this entity. Must be an alphanumeric string with dash or underscore
		
		
		"
::= { ospfAreaEntry 4 }
ospfAreaType OBJECT-TYPE
    SYNTAX INTEGER  {
	 normal (1),
	 stub (2)
	}
    MAX-ACCESS read-only
    STATUS current
    DESCRIPTION "OSPF Router Area Type.
		
		
		default value :normal"
::= { ospfAreaEntry 5 }
ospfInterface OBJECT IDENTIFIER ::= { networking 14 }
ospfInterfaceTable OBJECT-TYPE
    SYNTAX SEQUENCE OF OspfInterfaceEntry
    MAX-ACCESS not-accessible
    STATUS current
    DESCRIPTION "Configuration of interface in an ospf area."
::= { ospfInterface 1 }
ospfInterfaceEntry OBJECT-TYPE
    SYNTAX OspfInterfaceEntry
    MAX-ACCESS not-accessible
    STATUS current
    DESCRIPTION "Entry of ospfInterfaceTable" 
    INDEX { routingProtocolRtpType,routingProtocolRtpName,ospfAreaId,ospfInterfaceOspfIfName }
::= { ospfInterfaceTable 1 }
OspfInterfaceEntry ::= 
SEQUENCE {
	ospfInterfaceOspfIfName OCTET STRING,
	ospfInterfaceOspfLinkpf OCTET STRING,
	ospfInterfaceOspfCost Unsigned32,
	ospfInterfaceOspfIfRouting INTEGER,
	ospfInterfaceOspfNetworkType INTEGER
    }
ospfInterfaceOspfIfName OBJECT-TYPE
    SYNTAX OCTET STRING  (SIZE (1..64))
    MAX-ACCESS read-only
    STATUS current
    DESCRIPTION "Reference of the interface in OSPF area.
		
		
		"
::= { ospfInterfaceEntry 1 }
ospfInterfaceOspfLinkpf OBJECT-TYPE
    SYNTAX OCTET STRING 
    MAX-ACCESS read-only
    STATUS current
    DESCRIPTION "Reference of the ospf link profile associated with the interface.
		
		
		"
::= { ospfInterfaceEntry 2 }
ospfInterfaceOspfCost OBJECT-TYPE
    SYNTAX Unsigned32  (0..65535)
    MAX-ACCESS read-only
    STATUS current
    DESCRIPTION "OSPF link cost.
		
		
		"
::= { ospfInterfaceEntry 3 }
ospfInterfaceOspfIfRouting OBJECT-TYPE
    SYNTAX INTEGER  {
	 active (1),
	 passive (2)
	}
    MAX-ACCESS read-only
    STATUS current
    DESCRIPTION "Specifies if Routing is enabled and if so, if Routing is passive or active.
	ACTIVE - This link is advertised and routing messages are transported over this link.
	PASSIVE - This link is advertised, routing messages are not transported over this link.
		
		
		default value :active"
::= { ospfInterfaceEntry 4 }
ospfInterfaceOspfNetworkType OBJECT-TYPE
    SYNTAX INTEGER  {
	 broadcast (1),
	 pointToPoint (2),
	 pointToMultipoint (3)
	}
    MAX-ACCESS read-only
    STATUS current
    DESCRIPTION "OSPF Interface Network Types.
		
		
		"
::= { ospfInterfaceEntry 5 }
ospfAdjacency OBJECT IDENTIFIER ::= { networking 15 }
ospfAdjacencyTable OBJECT-TYPE
    SYNTAX SEQUENCE OF OspfAdjacencyEntry
    MAX-ACCESS not-accessible
    STATUS current
    DESCRIPTION "attributes of OSPF adjacency."
::= { ospfAdjacency 1 }
ospfAdjacencyEntry OBJECT-TYPE
    SYNTAX OspfAdjacencyEntry
    MAX-ACCESS not-accessible
    STATUS current
    DESCRIPTION "Entry of ospfAdjacencyTable" 
    INDEX { routingProtocolRtpType,routingProtocolRtpName,ospfAreaId,ospfInterfaceOspfIfName,ospfAdjacencyOspfNeighborAddress }
::= { ospfAdjacencyTable 1 }
OspfAdjacencyEntry ::= 
SEQUENCE {
	ospfAdjacencyOspfNeighborAddress IetfInetTypesIpv4Address,
	ospfAdjacencyNeighborRouterId IetfYangTypesDottedQuad,
	ospfAdjacencyOspfAdjStatus INTEGER
    }
ospfAdjacencyOspfNeighborAddress OBJECT-TYPE
    SYNTAX IetfInetTypesIpv4Address  (SIZE (1..64))
    MAX-ACCESS read-only
    STATUS current
    DESCRIPTION "neighbor IP address of the OSPF adjacency.
		
		
		"
::= { ospfAdjacencyEntry 1 }
ospfAdjacencyNeighborRouterId OBJECT-TYPE
    SYNTAX IetfYangTypesDottedQuad 
    MAX-ACCESS read-only
    STATUS current
    DESCRIPTION "OSPF neighbor Router ID.
		
		
		"
::= { ospfAdjacencyEntry 2 }
ospfAdjacencyOspfAdjStatus OBJECT-TYPE
    SYNTAX INTEGER  {
	 down (1),
	 init (2),
	 attempt (3),
	 twoWay (4),
	 exstart (5),
	 exchange (6),
	 loading (7),
	 full (8)
	}
    MAX-ACCESS read-only
    STATUS current
    DESCRIPTION "OSPF adjacency status.
		
		
		"
::= { ospfAdjacencyEntry 3 }
rib OBJECT IDENTIFIER ::= { networking 16 }
ribTable OBJECT-TYPE
    SYNTAX SEQUENCE OF RibEntry
    MAX-ACCESS not-accessible
    STATUS current
    DESCRIPTION "Each entry represents a RIB identified by the 'name'
	key. All routes in a RIB MUST belong to the same address
	family. 
	            
	For each routing instance, an implementation SHOULD
	provide one system-controlled default RIB for each
	supported address family."
::= { rib 1 }
ribEntry OBJECT-TYPE
    SYNTAX RibEntry
    MAX-ACCESS not-accessible
    STATUS current
    DESCRIPTION "Entry of ribTable" 
    INDEX { ribName }
::= { ribTable 1 }
RibEntry ::= 
SEQUENCE {
	ribName OCTET STRING,
	ribAddressFamily INTEGER,
	ribDefaultRib TruthValue,
	ribDescription OCTET STRING
    }
ribName OBJECT-TYPE
    SYNTAX OCTET STRING  (SIZE (1..64))
    MAX-ACCESS read-only
    STATUS current
    DESCRIPTION "The name of the RIB.
		
		
		"
::= { ribEntry 1 }
ribAddressFamily OBJECT-TYPE
    SYNTAX INTEGER  {
	 ipv4 (1),
	 ipv4Unicast (2),
	 ipv6 (3)
	}
    MAX-ACCESS read-only
    STATUS current
    DESCRIPTION "Address family.
		
		
		"
::= { ribEntry 2 }
ribDefaultRib OBJECT-TYPE
    SYNTAX TruthValue 
    MAX-ACCESS read-only
    STATUS current
    DESCRIPTION "This flag has the value of 'true' if and only if the
	RIB is the default RIB for the given address family. 
	                
	A default RIB always receives direct routes. By
	default it also receives routes from all routing
	protocols.
		
		
		default value :true"
::= { ribEntry 3 }
ribDescription OBJECT-TYPE
    SYNTAX OCTET STRING 
    MAX-ACCESS read-only
    STATUS current
    DESCRIPTION "Textual description of the RIB.
		
		
		"
::= { ribEntry 4 }
route OBJECT IDENTIFIER ::= { networking 17 }
routeTable OBJECT-TYPE
    SYNTAX SEQUENCE OF RouteEntry
    MAX-ACCESS not-accessible
    STATUS current
    DESCRIPTION "A list of static routes."
::= { route 1 }
routeEntry OBJECT-TYPE
    SYNTAX RouteEntry
    MAX-ACCESS not-accessible
    STATUS current
    DESCRIPTION "Entry of routeTable" 
    INDEX { ribName,routeSourceProtocol,routeDestinationPrefix }
::= { routeTable 1 }
RouteEntry ::= 
SEQUENCE {
	routeSourceProtocol CoriantTypesSourceProtocol,
	routeDestinationPrefix IetfInetTypesIpv4Prefix,
	routeDescription OCTET STRING,
	routePreference Unsigned32,
	routeActive TruthValue
    }
routeSourceProtocol OBJECT-TYPE
    SYNTAX CoriantTypesSourceProtocol 
    MAX-ACCESS read-only
    STATUS current
    DESCRIPTION "Type of the routing protocol from which the route  originated.
		
		
		"
::= { routeEntry 1 }
routeDestinationPrefix OBJECT-TYPE
    SYNTAX IetfInetTypesIpv4Prefix  (SIZE (1..64))
    MAX-ACCESS read-only
    STATUS current
    DESCRIPTION "IPv4 destination prefix.
		
		
		"
::= { routeEntry 2 }
routeDescription OBJECT-TYPE
    SYNTAX OCTET STRING 
    MAX-ACCESS read-only
    STATUS current
    DESCRIPTION "Textual description of the route.
		
		
		"
::= { routeEntry 3 }
routePreference OBJECT-TYPE
    SYNTAX Unsigned32 
    MAX-ACCESS read-only
    STATUS current
    DESCRIPTION "This route attribute, also known as administrative
	distance, allows for selecting the preferred route
	among routes with the same destination prefix. A
	smaller value means a more preferred route.
		
		
		"
::= { routeEntry 4 }
routeActive OBJECT-TYPE
    SYNTAX TruthValue 
    MAX-ACCESS read-only
    STATUS current
    DESCRIPTION "Indicates that the route is preferred among all routes in the same RIB that have the same destination prefix.
		
		
		"
::= { routeEntry 5 }
profiles OBJECT IDENTIFIER ::= { networking 18 }
pppProfile OBJECT IDENTIFIER ::= { profiles 1 }
pppProfileTable OBJECT-TYPE
    SYNTAX SEQUENCE OF PppProfileEntry
    MAX-ACCESS not-accessible
    STATUS current
    DESCRIPTION "Profile for the point-to-point interface."
::= { pppProfile 1 }
pppProfileEntry OBJECT-TYPE
    SYNTAX PppProfileEntry
    MAX-ACCESS not-accessible
    STATUS current
    DESCRIPTION "Entry of pppProfileTable" 
    INDEX { pppProfilePppPfName }
::= { pppProfileTable 1 }
PppProfileEntry ::= 
SEQUENCE {
	pppProfilePppPfName OCTET STRING,
	pppProfilePppFcsLength INTEGER,
	pppProfilePppMru Unsigned32,
	pppProfilePppRestartTimer Unsigned32,
	pppProfilePppMaxFailure Unsigned32
    }
pppProfilePppPfName OBJECT-TYPE
    SYNTAX OCTET STRING  (SIZE (1..63))
    MAX-ACCESS read-only
    STATUS current
    DESCRIPTION "The name of the point-to-point protocol profile.
		
		
		"
::= { pppProfileEntry 1 }
pppProfilePppFcsLength OBJECT-TYPE
    SYNTAX INTEGER  {
	 t16 (16),
	 t32 (32)
	}
    MAX-ACCESS read-only
    STATUS current
    DESCRIPTION "Specifies whether the frame check sequence is a 16-bit or 32-bit value.
		
		
		default value :16"
::= { pppProfileEntry 2 }
pppProfilePppMru OBJECT-TYPE
    SYNTAX Unsigned32  (64..1500)
    MAX-ACCESS read-only
    STATUS current
    DESCRIPTION "Specifies the maximum number of octets in the Information and Padding fields.
		
		UNITS:octets
		default value :1500"
::= { pppProfileEntry 3 }
pppProfilePppRestartTimer OBJECT-TYPE
    SYNTAX Unsigned32  (1..10)
    MAX-ACCESS read-only
    STATUS current
    DESCRIPTION "Specifies the restart timer of the PPP protocol in seconds.
		
		UNITS:seconds
		default value :3"
::= { pppProfileEntry 4 }
pppProfilePppMaxFailure OBJECT-TYPE
    SYNTAX Unsigned32  (2..10)
    MAX-ACCESS read-only
    STATUS current
    DESCRIPTION "Specifies the maximum failure value of the PPP protocol profile.
		
		
		default value :5"
::= { pppProfileEntry 5 }
ospfLinkProfile OBJECT IDENTIFIER ::= { profiles 2 }
ospfLinkProfileTable OBJECT-TYPE
    SYNTAX SEQUENCE OF OspfLinkProfileEntry
    MAX-ACCESS not-accessible
    STATUS current
    DESCRIPTION "Profile for the OSPF protocol link."
::= { ospfLinkProfile 1 }
ospfLinkProfileEntry OBJECT-TYPE
    SYNTAX OspfLinkProfileEntry
    MAX-ACCESS not-accessible
    STATUS current
    DESCRIPTION "Entry of ospfLinkProfileTable" 
    INDEX { ospfLinkProfileOspfLinkpfName }
::= { ospfLinkProfileTable 1 }
OspfLinkProfileEntry ::= 
SEQUENCE {
	ospfLinkProfileOspfLinkpfName OCTET STRING,
	ospfLinkProfileHelloInterval Unsigned32,
	ospfLinkProfileRouterDeadInterval Unsigned32,
	ospfLinkProfileRetransmissionInterval Unsigned32
    }
ospfLinkProfileOspfLinkpfName OBJECT-TYPE
    SYNTAX OCTET STRING  (SIZE (1..64))
    MAX-ACCESS read-only
    STATUS current
    DESCRIPTION "The name of the OSPF protocol link profile.
		
		
		"
::= { ospfLinkProfileEntry 1 }
ospfLinkProfileHelloInterval OBJECT-TYPE
    SYNTAX Unsigned32  (1..255)
    MAX-ACCESS read-only
    STATUS current
    DESCRIPTION "Specifies the Hello Interval in seconds.
		
		UNITS:seconds
		default value :10"
::= { ospfLinkProfileEntry 2 }
ospfLinkProfileRouterDeadInterval OBJECT-TYPE
    SYNTAX Unsigned32  (4..1024)
    MAX-ACCESS read-only
    STATUS current
    DESCRIPTION "Specifies the Router Dead Interval in seconds.
		
		UNITS:seconds
		default value :40"
::= { ospfLinkProfileEntry 3 }
ospfLinkProfileRetransmissionInterval OBJECT-TYPE
    SYNTAX Unsigned32  (1..255)
    MAX-ACCESS read-only
    STATUS current
    DESCRIPTION "Specifies the Retransmission Interval in seconds.
		
		UNITS:seconds
		default value :5"
::= { ospfLinkProfileEntry 4 }
oscx OBJECT IDENTIFIER ::= { networking 19 }
oscxTable OBJECT-TYPE
    SYNTAX SEQUENCE OF OscxEntry
    MAX-ACCESS not-accessible
    STATUS current
    DESCRIPTION "OSCX (Optical Supervisory Channel Extended) interface"
::= { oscx 1 }
oscxEntry OBJECT-TYPE
    SYNTAX OscxEntry
    MAX-ACCESS not-accessible
    STATUS current
    DESCRIPTION "Entry of oscxTable" 
    INDEX { interfaceIfName }
::= { oscxTable 1 }
OscxEntry ::= 
SEQUENCE {
	oscxChannel INTEGER,
	oscxResourceRef RowPointer,
	oscxAliasName OCTET STRING
    }
oscxChannel OBJECT-TYPE
    SYNTAX INTEGER  {
	 t1 (1),
	 t2 (2)
	}
    MAX-ACCESS read-only
    STATUS current
    DESCRIPTION "Specifies the OSCX channel within the Optical Supervisory Channel.
		
		
		"
::= { oscxEntry 1 }
oscxResourceRef OBJECT-TYPE
    SYNTAX RowPointer 
    MAX-ACCESS read-only
    STATUS current
    DESCRIPTION "Reference of the lower layer resource associated with this interface.
		
		
		"
::= { oscxEntry 2 }
oscxAliasName OBJECT-TYPE
    SYNTAX OCTET STRING  (SIZE (0..256))
    MAX-ACCESS read-only
    STATUS current
    DESCRIPTION "User defined alias for this entity. Must be an alphanumeric string with dash or underscore
		
		
		"
::= { oscxEntry 3 }
security OBJECT IDENTIFIER ::= { groove 7 }
securityInfo OBJECT IDENTIFIER ::= { security 1 }
securitySshPublicKey OBJECT-TYPE
    SYNTAX OCTET STRING  (SIZE (0..2500))
    MAX-ACCESS read-only
    STATUS current
    DESCRIPTION "The system's public key for use with SSH or SFTP.This is a leaf list, encode by some leafs.
		
		
		"
::= { securityInfo 1 }
securitySshPublicKeyFingerprint OBJECT-TYPE
    SYNTAX OCTET STRING  (SIZE (0..256))
    MAX-ACCESS read-only
    STATUS current
    DESCRIPTION "The fingerprint of the system's public key.This is a leaf list, encode by some leafs.
		
		
		"
::= { securityInfo 2 }
securityPreLoginMessage OBJECT-TYPE
    SYNTAX OCTET STRING  (SIZE (0..1440))
    MAX-ACCESS read-only
    STATUS current
    DESCRIPTION "Welcome message displayed before user login
		
		
		default value :****************************************** Warning ******************************************

This system is restricted to authorized users for business purposes. Unauthorized access is a
violation of the law. This service may be monitored for administrative and security reasons.
By proceeding, you consent to this monitoring.

*********************************************************************************************
"
::= { securityInfo 3 }
securityWarningMessage OBJECT-TYPE
    SYNTAX OCTET STRING  (SIZE (0..1440))
    MAX-ACCESS read-only
    STATUS current
    DESCRIPTION "Welcome message displayed after user login
		
		
		default value :****************************************** Warning ******************************************

This system is restricted to authorized users for business purposes. Unauthorized access is a
violation of the law. This service may be monitored for administrative and security reasons.
By proceeding, you consent to this monitoring.

*********************************************************************************************
"
::= { securityInfo 4 }
securityAaaAuthenticationMethod OBJECT-TYPE
    SYNTAX INTEGER  {
	 localOnly (1),
	 localFirstThenRemote (3),
	 remoteFirstThenLocal (4),
	 remoteUnavailableThenLocal (5)
	}
    MAX-ACCESS read-only
    STATUS current
    DESCRIPTION "specify authentication method for the user login to the NE.
		
		
		default value :local-only"
::= { securityInfo 5 }
securitySystemFips OBJECT-TYPE
    SYNTAX INTEGER  {
	 enabled (1),
	 disabled (2)
	}
    MAX-ACCESS read-only
    STATUS current
    DESCRIPTION "specifies whether the system security is operating in compliance with FIPS.
		
		
		default value :disabled"
::= { securityInfo 6 }
securityHttpSupport OBJECT-TYPE
    SYNTAX CoriantTypesEnableSwitch 
    MAX-ACCESS read-only
    STATUS current
    DESCRIPTION "Defines whether unsecure HTTP protocol is allowed; includes file transfer, or any other application that uses HTTP
		
		
		default value :disabled"
::= { securityInfo 7 }
user OBJECT IDENTIFIER ::= { security 2 }
userTable OBJECT-TYPE
    SYNTAX SEQUENCE OF UserEntry
    MAX-ACCESS not-accessible
    STATUS current
    DESCRIPTION "NULL"
::= { user 1 }
userEntry OBJECT-TYPE
    SYNTAX UserEntry
    MAX-ACCESS not-accessible
    STATUS current
    DESCRIPTION "Entry of userTable" 
    INDEX { userName }
::= { userTable 1 }
UserEntry ::= 
SEQUENCE {
	userName CoriantTypesUserName,
	userPassword OCTET STRING,
	userClass INTEGER,
	userMaxInvalidLogin Unsigned32,
	userSuspensionTime Unsigned32,
	userTimeout Unsigned32,
	userPasswordAgingInterval Unsigned32,
	userPasswordExpirationDate IetfYangTypesDateAndTime,
	userAdminStatus INTEGER,
	userStatus INTEGER,
	userMaxSessions Unsigned32,
	userLastLoginDate IetfYangTypesDateAndTime,
	userAaaType INTEGER
    }
userName OBJECT-TYPE
    SYNTAX CoriantTypesUserName 
    MAX-ACCESS read-only
    STATUS current
    DESCRIPTION "User name.
		
		
		"
::= { userEntry 1 }
userPassword OBJECT-TYPE
    SYNTAX OCTET STRING  (SIZE (8..32))
    MAX-ACCESS read-only
    STATUS current
    DESCRIPTION "The password of the user.
		
		
		"
::= { userEntry 2 }
userClass OBJECT-TYPE
    SYNTAX INTEGER  {
	 cryptoOfficer (0),
	 administration (1),
	 configuration (2),
	 operation (3),
	 supervision (4)
	}
    MAX-ACCESS read-only
    STATUS current
    DESCRIPTION "The access class for the user.
		
		
		default value :supervision"
::= { userEntry 3 }
userMaxInvalidLogin OBJECT-TYPE
    SYNTAX Unsigned32  (0..9)
    MAX-ACCESS read-only
    STATUS current
    DESCRIPTION "This attribute is the maximum number of consecutive and invalid login attempts
	before an account is suspended (lockedout).
		
		
		default value :3"
::= { userEntry 4 }
userSuspensionTime OBJECT-TYPE
    SYNTAX Unsigned32  (0..300)
    MAX-ACCESS read-only
    STATUS current
    DESCRIPTION "This attribute is the duration of UID suspension following consecutive invalid login attempts.
	Setting the value to 0 disables this attribute.
		
		UNITS:seconds
		default value :60"
::= { userEntry 5 }
userTimeout OBJECT-TYPE
    SYNTAX Unsigned32  (0..300)
    MAX-ACCESS read-only
    STATUS current
    DESCRIPTION "This attribute is the Session Time Out Interval. If there are no messages between the user
	and the NE over the Time Out interval, the session is logged off. Setting the value to 0 disables
	this attribute (meaning the session will not time out).
		
		UNITS:minutes
		default value :30"
::= { userEntry 6 }
userPasswordAgingInterval OBJECT-TYPE
    SYNTAX Unsigned32  (0..365)
    MAX-ACCESS read-only
    STATUS current
    DESCRIPTION "This attribute is the Password Aging Interval. Setting the value to 0 disables this attribute.
		
		UNITS:days
		default value :0"
::= { userEntry 7 }
userPasswordExpirationDate OBJECT-TYPE
    SYNTAX IetfYangTypesDateAndTime 
    MAX-ACCESS read-only
    STATUS current
    DESCRIPTION "This attribute shows the password expiration date.
		
		
		"
::= { userEntry 8 }
userAdminStatus OBJECT-TYPE
    SYNTAX INTEGER  {
	 enabled (1),
	 disabled (2)
	}
    MAX-ACCESS read-only
    STATUS current
    DESCRIPTION "The attribute allows administrators to modify the user administration status.
		
		
		default value :enabled"
::= { userEntry 9 }
userStatus OBJECT-TYPE
    SYNTAX INTEGER  {
	 enabled (1),
	 disabled (2),
	 passwordAged (3),
	 lockout (4)
	}
    MAX-ACCESS read-only
    STATUS current
    DESCRIPTION "This attribute shows the user status.
	User with status 'enabled' will have access to the system.
	User with status 'disabled' not have access to the system.
	User with status 'password-aged' will have access to the system but will be forced to change his password on first-time login.
	User with status 'lockout' means the account is locked out due to unsuccessful login attempts.
		
		
		default value :disabled"
::= { userEntry 10 }
userMaxSessions OBJECT-TYPE
    SYNTAX Unsigned32  (1..20)
    MAX-ACCESS read-only
    STATUS current
    DESCRIPTION "This attribute specifies the maximum number of sessions allowed for this user.
		
		
		default value :6"
::= { userEntry 11 }
userLastLoginDate OBJECT-TYPE
    SYNTAX IetfYangTypesDateAndTime 
    MAX-ACCESS read-only
    STATUS current
    DESCRIPTION "The last login date/time of the user.
		
		
		default value :1970-01-01T00:00:00Z"
::= { userEntry 12 }
userAaaType OBJECT-TYPE
    SYNTAX INTEGER  {
	 local (1),
	 remote (2)
	}
    MAX-ACCESS read-only
    STATUS current
    DESCRIPTION "Indicates the authentication method of the user.
		
		
		default value :local"
::= { userEntry 13 }
session OBJECT IDENTIFIER ::= { security 3 }
sessionTable OBJECT-TYPE
    SYNTAX SEQUENCE OF SessionEntry
    MAX-ACCESS not-accessible
    STATUS current
    DESCRIPTION "NULL"
::= { session 1 }
sessionEntry OBJECT-TYPE
    SYNTAX SessionEntry
    MAX-ACCESS not-accessible
    STATUS current
    DESCRIPTION "Entry of sessionTable" 
    INDEX { sessionId }
::= { sessionTable 1 }
SessionEntry ::= 
SEQUENCE {
	sessionId CoriantTypesSessionId,
	sessionUser RowPointer,
	sessionType INTEGER,
	sessionProtocol INTEGER,
	sessionCreatedTime IetfYangTypesDateAndTime
    }
sessionId OBJECT-TYPE
    SYNTAX CoriantTypesSessionId 
    MAX-ACCESS read-only
    STATUS current
    DESCRIPTION "Specifies a unique identifier of the current session. It indicates the
	IP address and transport layer port number associated with this session. 
	If the session is initiated from the serial port, the value is 'NA'.
		
		
		"
::= { sessionEntry 1 }
sessionUser OBJECT-TYPE
    SYNTAX RowPointer 
    MAX-ACCESS read-only
    STATUS current
    DESCRIPTION "Points to a user instance.
		
		
		"
::= { sessionEntry 2 }
sessionType OBJECT-TYPE
    SYNTAX INTEGER  {
	 cli (1),
	 snmp (2),
	 netconf (3),
	 restconf (4),
	 webgui (5),
	 gnmi (6)
	}
    MAX-ACCESS read-only
    STATUS current
    DESCRIPTION "Session type.
		
		
		"
::= { sessionEntry 3 }
sessionProtocol OBJECT-TYPE
    SYNTAX INTEGER  {
	 telnet (1),
	 telnetRaw (2),
	 serial (3),
	 ssh (4),
	 sshRaw (5),
	 https (6),
	 http (7)
	}
    MAX-ACCESS read-only
    STATUS current
    DESCRIPTION "Indicates which protocol has been used to establish the session.
		
		
		"
::= { sessionEntry 4 }
sessionCreatedTime OBJECT-TYPE
    SYNTAX IetfYangTypesDateAndTime 
    MAX-ACCESS read-only
    STATUS current
    DESCRIPTION "The timestamp the user has created this session.
		
		
		"
::= { sessionEntry 5 }
aaaServer OBJECT IDENTIFIER ::= { security 4 }
aaaServerTable OBJECT-TYPE
    SYNTAX SEQUENCE OF AaaServerEntry
    MAX-ACCESS not-accessible
    STATUS current
    DESCRIPTION "NULL"
::= { aaaServer 1 }
aaaServerEntry OBJECT-TYPE
    SYNTAX AaaServerEntry
    MAX-ACCESS not-accessible
    STATUS current
    DESCRIPTION "Entry of aaaServerTable" 
    INDEX { aaaServerServerName }
::= { aaaServerTable 1 }
AaaServerEntry ::= 
SEQUENCE {
	aaaServerServerName OCTET STRING,
	aaaServerServerPriority Unsigned32,
	aaaServerProtocolSupported INTEGER,
	aaaServerServerIp IetfInetTypesIpv4Address,
	aaaServerServerPort IetfInetTypesPortNumber,
	aaaServerSharedSecret OCTET STRING,
	aaaServerRoleSupported BITS,
	aaaServerAdminStatus INTEGER,
	aaaServerTimeOut Unsigned32,
	aaaServerRetry Unsigned32
    }
aaaServerServerName OBJECT-TYPE
    SYNTAX OCTET STRING  (SIZE (1..32))
    MAX-ACCESS read-only
    STATUS current
    DESCRIPTION "specify the name of aaa server.
		
		
		"
::= { aaaServerEntry 1 }
aaaServerServerPriority OBJECT-TYPE
    SYNTAX Unsigned32  (1..10)
    MAX-ACCESS read-only
    STATUS current
    DESCRIPTION "This is used to sort the servers in the order of precedence.
		
		
		"
::= { aaaServerEntry 2 }
aaaServerProtocolSupported OBJECT-TYPE
    SYNTAX INTEGER  {
	 tacacsplus (1)
	}
    MAX-ACCESS read-only
    STATUS current
    DESCRIPTION "specify the protocol used for AAA.
		
		
		default value :TACACSPLUS"
::= { aaaServerEntry 3 }
aaaServerServerIp OBJECT-TYPE
    SYNTAX IetfInetTypesIpv4Address 
    MAX-ACCESS read-only
    STATUS current
    DESCRIPTION "The IPv4 address of AAA server.
		
		
		"
::= { aaaServerEntry 4 }
aaaServerServerPort OBJECT-TYPE
    SYNTAX IetfInetTypesPortNumber 
    MAX-ACCESS read-only
    STATUS current
    DESCRIPTION "AAA server port number.
		
		
		default value :49"
::= { aaaServerEntry 5 }
aaaServerSharedSecret OBJECT-TYPE
    SYNTAX OCTET STRING  (SIZE (0..100))
    MAX-ACCESS read-only
    STATUS current
    DESCRIPTION "The shared secret of the aaa server. The shared secret will be displayed as *.
		
		
		default value :sharedkey"
::= { aaaServerEntry 6 }
aaaServerRoleSupported OBJECT-TYPE
    SYNTAX BITS  {
	 authentication (0),
	 authorization (1),
	 accounting (2)
	}
    MAX-ACCESS read-only
    STATUS current
    DESCRIPTION "specify the role of the server for AAA.
		
		
		default value :authentication authorization"
::= { aaaServerEntry 7 }
aaaServerAdminStatus OBJECT-TYPE
    SYNTAX INTEGER  {
	 up (1),
	 down (2)
	}
    MAX-ACCESS read-only
    STATUS current
    DESCRIPTION "
	The administrative state specifes the permission to use or prohibition 
	against using the resource. The administrative state can be modified by the user.
	
		
		
		default value :up"
::= { aaaServerEntry 8 }
aaaServerTimeOut OBJECT-TYPE
    SYNTAX Unsigned32  (1..60)
    MAX-ACCESS read-only
    STATUS current
    DESCRIPTION "Specifies the response timeout of Access-Request messages sent to a AAA server in seconds.
		
		UNITS:seconds
		default value :5"
::= { aaaServerEntry 9 }
aaaServerRetry OBJECT-TYPE
    SYNTAX Unsigned32  (1..10)
    MAX-ACCESS read-only
    STATUS current
    DESCRIPTION "Specifies the number of attempted Access-Request messages to a single AAA server before failing authentication.
		
		
		default value :3"
::= { aaaServerEntry 10 }
keySyncSession OBJECT IDENTIFIER ::= { security 5 }
keySyncSessionTable OBJECT-TYPE
    SYNTAX SEQUENCE OF KeySyncSessionEntry
    MAX-ACCESS not-accessible
    STATUS current
    DESCRIPTION "TLS session to synchronize ODU encryption key."
::= { keySyncSession 1 }
keySyncSessionEntry OBJECT-TYPE
    SYNTAX KeySyncSessionEntry
    MAX-ACCESS not-accessible
    STATUS current
    DESCRIPTION "Entry of keySyncSessionTable" 
    INDEX { keySyncSessionId }
::= { keySyncSessionTable 1 }
KeySyncSessionEntry ::= 
SEQUENCE {
	keySyncSessionId Unsigned32,
	keySyncSessionAdminStatus INTEGER,
	keySyncSessionSessionStatus INTEGER,
	keySyncSessionRemoteIp IetfInetTypesIpv4Address,
	keySyncSessionRemotePort IetfInetTypesPortNumber,
	keySyncSessionLocalIp IetfInetTypesIpv4Address,
	keySyncSessionLocalPort IetfInetTypesPortNumber,
	keySyncSessionSourceAddressFrom OCTET STRING,
	keySyncSessionConnectedTime IetfYangTypesDateAndTime,
	keySyncSessionType INTEGER,
	keySyncSessionAuthType INTEGER,
	keySyncSessionLocalCertificate OCTET STRING
    }
keySyncSessionId OBJECT-TYPE
    SYNTAX Unsigned32  (1..65535)
    MAX-ACCESS read-only
    STATUS current
    DESCRIPTION "Specifies a unique identifier of the key synchronization session.
		
		
		"
::= { keySyncSessionEntry 1 }
keySyncSessionAdminStatus OBJECT-TYPE
    SYNTAX INTEGER  {
	 up (1),
	 down (2)
	}
    MAX-ACCESS read-only
    STATUS current
    DESCRIPTION "
	The administrative state specifies the permission to use or prohibition 
	against using the resource. The administrative state can be modified by the user, and operates independently of the operability and usage of the resource. 
	
		
		
		default value :up"
::= { keySyncSessionEntry 2 }
keySyncSessionSessionStatus OBJECT-TYPE
    SYNTAX INTEGER  {
	 unknown (0),
	 disabled (1),
	 connecting (2),
	 incomplete (3),
	 connected (4),
	 unreachable (5),
	 failedAuth (6),
	 failed (7)
	}
    MAX-ACCESS read-only
    STATUS current
    DESCRIPTION "Indicating the status of key sync session.
		
		
		"
::= { keySyncSessionEntry 4 }
keySyncSessionRemoteIp OBJECT-TYPE
    SYNTAX IetfInetTypesIpv4Address 
    MAX-ACCESS read-only
    STATUS current
    DESCRIPTION "The IP address of remote session server.
		
		
		"
::= { keySyncSessionEntry 5 }
keySyncSessionRemotePort OBJECT-TYPE
    SYNTAX IetfInetTypesPortNumber 
    MAX-ACCESS read-only
    STATUS current
    DESCRIPTION "The port number of remote session server.
		
		
		default value :8443"
::= { keySyncSessionEntry 6 }
keySyncSessionLocalIp OBJECT-TYPE
    SYNTAX IetfInetTypesIpv4Address 
    MAX-ACCESS read-only
    STATUS current
    DESCRIPTION "The source IP address of a manual session.
		
		
		"
::= { keySyncSessionEntry 7 }
keySyncSessionLocalPort OBJECT-TYPE
    SYNTAX IetfInetTypesPortNumber 
    MAX-ACCESS read-only
    STATUS current
    DESCRIPTION "The source port number of a manual session.
		
		
		"
::= { keySyncSessionEntry 8 }
keySyncSessionSourceAddressFrom OBJECT-TYPE
    SYNTAX OCTET STRING 
    MAX-ACCESS read-only
    STATUS current
    DESCRIPTION "specifies the interface of the source IP address of the outgoing packets.
		Conditions:../key-sync-session-type = 'manual'
		
		default value :auto"
::= { keySyncSessionEntry 9 }
keySyncSessionConnectedTime OBJECT-TYPE
    SYNTAX IetfYangTypesDateAndTime 
    MAX-ACCESS read-only
    STATUS current
    DESCRIPTION "The timestamp the user has created this session.
		
		
		"
::= { keySyncSessionEntry 10 }
keySyncSessionType OBJECT-TYPE
    SYNTAX INTEGER  {
	 auto (1),
	 manual (2)
	}
    MAX-ACCESS read-only
    STATUS current
    DESCRIPTION "Indicating the type of key sync session, 
	'manual' is for the session user configured, and 'auto' is for the session automatically created by system.
		
		
		default value :manual"
::= { keySyncSessionEntry 11 }
keySyncSessionAuthType OBJECT-TYPE
    SYNTAX INTEGER  {
	 tlsCertificate (1),
	 proprietaryPsk (2)
	}
    MAX-ACCESS read-only
    STATUS current
    DESCRIPTION "Indicating the authentication type of the key sync session.
		
		
		default value :proprietary-psk"
::= { keySyncSessionEntry 12 }
keySyncSessionLocalCertificate OBJECT-TYPE
    SYNTAX OCTET STRING 
    MAX-ACCESS read-only
    STATUS current
    DESCRIPTION "Previously installed certificate that authenticates the NE.
		
		
		default value :none"
::= { keySyncSessionEntry 13 }
pskMap OBJECT IDENTIFIER ::= { security 7 }
pskMapTable OBJECT-TYPE
    SYNTAX SEQUENCE OF PskMapEntry
    MAX-ACCESS not-accessible
    STATUS current
    DESCRIPTION "NULL"
::= { pskMap 1 }
pskMapEntry OBJECT-TYPE
    SYNTAX PskMapEntry
    MAX-ACCESS not-accessible
    STATUS current
    DESCRIPTION "Entry of pskMapTable" 
    INDEX { pskMapPskIdentity }
::= { pskMapTable 1 }
PskMapEntry ::= 
SEQUENCE {
	pskMapPskIdentity OCTET STRING,
	pskMapKey IetfYangTypesHexString,
	pskMapPskStatus INTEGER,
	pskMapPskInfo OCTET STRING,
	pskMapWarningTimer Unsigned32,
	pskMapCriticalTimer Unsigned32,
	pskMapTrafficOffTimer Unsigned32,
	pskMapEffectiveTimestamp IetfYangTypesDateAndTime
    }
pskMapPskIdentity OBJECT-TYPE
    SYNTAX OCTET STRING  (SIZE (1..64))
    MAX-ACCESS read-only
    STATUS current
    DESCRIPTION "The PSK identity encoded as a UTF-8 string. For
	details how certain common PSK identity formats can
	be encoded in UTF-8, see section 5.1. of RFC 4279.
		
		
		"
::= { pskMapEntry 1 }
pskMapKey OBJECT-TYPE
    SYNTAX IetfYangTypesHexString 
    MAX-ACCESS read-only
    STATUS current
    DESCRIPTION "The key associated with the PSK identity
		
		
		"
::= { pskMapEntry 2 }
pskMapPskStatus OBJECT-TYPE
    SYNTAX INTEGER  {
	 init (1),
	 sync (2),
	 fail (3),
	 authenticate (4)
	}
    MAX-ACCESS read-only
    STATUS current
    DESCRIPTION "Status of the psk-map. psk-map can be updated only if psk-status is in init or sync status; the previous psk-map updating can be cancelled only if psk-satus is updating; psk-map cannot be updated and previous psk-map updating cannot be cancelled if psk-status is candidate-key-authenticate.
		
		
		default value :init"
::= { pskMapEntry 4 }
pskMapPskInfo OBJECT-TYPE
    SYNTAX OCTET STRING  (SIZE (0..255))
    MAX-ACCESS read-only
    STATUS current
    DESCRIPTION "The label of the psk-map.
		
		
		default value :"
::= { pskMapEntry 5 }
pskMapWarningTimer OBJECT-TYPE
    SYNTAX Unsigned32  (1..240)
    MAX-ACCESS read-only
    STATUS current
    DESCRIPTION "Warning Time before psk-map updating completes.
		
		UNITS:minutes
		default value :5"
::= { pskMapEntry 6 }
pskMapCriticalTimer OBJECT-TYPE
    SYNTAX Unsigned32  (1..480)
    MAX-ACCESS read-only
    STATUS current
    DESCRIPTION "Critical time before psk-map updating completes.
		
		UNITS:minutes
		default value :30"
::= { pskMapEntry 7 }
pskMapTrafficOffTimer OBJECT-TYPE
    SYNTAX Unsigned32  (1..1440)
    MAX-ACCESS read-only
    STATUS current
    DESCRIPTION "Traffic off time before psk-map updating completes.
		
		UNITS:minutes
		default value :1440"
::= { pskMapEntry 8 }
pskMapEffectiveTimestamp OBJECT-TYPE
    SYNTAX IetfYangTypesDateAndTime 
    MAX-ACCESS read-only
    STATUS current
    DESCRIPTION "Indicates the Time of new psk starts to take effect.
		
		
		"
::= { pskMapEntry 9 }
key OBJECT IDENTIFIER ::= { security 9 }
keyTable OBJECT-TYPE
    SYNTAX SEQUENCE OF KeyEntry
    MAX-ACCESS not-accessible
    STATUS current
    DESCRIPTION "A key maintained by the keystore."
::= { key 1 }
keyEntry OBJECT-TYPE
    SYNTAX KeyEntry
    MAX-ACCESS not-accessible
    STATUS current
    DESCRIPTION "Entry of keyTable" 
    INDEX { keyName }
::= { keyTable 1 }
KeyEntry ::= 
SEQUENCE {
	keyName OCTET STRING,
	keyAlgorithmIdentifier INTEGER,
	keyPublicKey OCTET STRING
    }
keyName OBJECT-TYPE
    SYNTAX OCTET STRING  (SIZE (1..64))
    MAX-ACCESS read-only
    STATUS current
    DESCRIPTION "An arbitrary name for the key.
		
		
		"
::= { keyEntry 1 }
keyAlgorithmIdentifier OBJECT-TYPE
    SYNTAX INTEGER  {
	 rsa1024 (1),
	 rsa2048 (2),
	 rsa3072 (3),
	 rsa4096 (4),
	 rsa7680 (5),
	 rsa15360 (6),
	 secp192r1 (7),
	 secp256r1 (8),
	 secp384r1 (9),
	 secp521r1 (10)
	}
    MAX-ACCESS read-only
    STATUS current
    DESCRIPTION "Identifies which algorithm is to be used with the key.
	This value determines how the 'private-key' and 'public-key' fields are interpreted.
		
		
		"
::= { keyEntry 2 }
keyPublicKey OBJECT-TYPE
    SYNTAX OCTET STRING  (SIZE (0..2500))
    MAX-ACCESS read-only
    STATUS current
    DESCRIPTION "A binary string that contains the value of the public key. 
	The interpretation of the content is defined in the registration of the key algorithm.  
	For example, a DSA key is an INTEGER, an RSA key is represented as RSAPublicKey as defined in [RFC3447], and an Elliptic Curve Cryptography (ECC) key is represented using the 'publicKey' described in [RFC5915]
		
		
		"
::= { keyEntry 3 }
certificate OBJECT IDENTIFIER ::= { security 10 }
certificateTable OBJECT-TYPE
    SYNTAX SEQUENCE OF CertificateEntry
    MAX-ACCESS not-accessible
    STATUS current
    DESCRIPTION "A certificate for this private key."
::= { certificate 1 }
certificateEntry OBJECT-TYPE
    SYNTAX CertificateEntry
    MAX-ACCESS not-accessible
    STATUS current
    DESCRIPTION "Entry of certificateTable" 
    INDEX { keyName,certificateName }
::= { certificateTable 1 }
CertificateEntry ::= 
SEQUENCE {
	certificateName OCTET STRING,
	certificateVersion INTEGER,
	certificateSerialNumber OCTET STRING,
	certificateSignatureAlgorithm OCTET STRING,
	certificateIssuer OCTET STRING,
	certificateValidFrom OCTET STRING,
	certificateValidTo OCTET STRING,
	certificateSubject OCTET STRING,
	certificatePublicKeyAlgorithm OCTET STRING
    }
certificateName OBJECT-TYPE
    SYNTAX OCTET STRING  (SIZE (1..64))
    MAX-ACCESS read-only
    STATUS current
    DESCRIPTION "An arbitrary name for the certificate.  The name
	must be a unique across all keys, not just within
	this key.
		
		
		"
::= { certificateEntry 1 }
certificateVersion OBJECT-TYPE
    SYNTAX INTEGER  {
	 x509v1 (1),
	 x509v2 (2),
	 x509v3 (3)
	}
    MAX-ACCESS read-only
    STATUS current
    DESCRIPTION "version of the certificate.
		
		
		default value :x509v1"
::= { certificateEntry 2 }
certificateSerialNumber OBJECT-TYPE
    SYNTAX OCTET STRING 
    MAX-ACCESS read-only
    STATUS current
    DESCRIPTION "serial number of the certificate.
		
		
		"
::= { certificateEntry 3 }
certificateSignatureAlgorithm OBJECT-TYPE
    SYNTAX OCTET STRING 
    MAX-ACCESS read-only
    STATUS current
    DESCRIPTION "signature algorithm of the certificate.
		
		
		"
::= { certificateEntry 4 }
certificateIssuer OBJECT-TYPE
    SYNTAX OCTET STRING  (SIZE (0..255))
    MAX-ACCESS read-only
    STATUS current
    DESCRIPTION "issuer of the certificate.
		
		
		"
::= { certificateEntry 5 }
certificateValidFrom OBJECT-TYPE
    SYNTAX OCTET STRING 
    MAX-ACCESS read-only
    STATUS current
    DESCRIPTION "valid-from date and time of the certificate.
		
		
		"
::= { certificateEntry 6 }
certificateValidTo OBJECT-TYPE
    SYNTAX OCTET STRING 
    MAX-ACCESS read-only
    STATUS current
    DESCRIPTION "valid-to date and time of the certificate.
		
		
		"
::= { certificateEntry 7 }
certificateSubject OBJECT-TYPE
    SYNTAX OCTET STRING  (SIZE (0..255))
    MAX-ACCESS read-only
    STATUS current
    DESCRIPTION "subject of the certificate.
		
		
		"
::= { certificateEntry 8 }
certificatePublicKeyAlgorithm OBJECT-TYPE
    SYNTAX OCTET STRING 
    MAX-ACCESS read-only
    STATUS current
    DESCRIPTION "public-key-algorithm of the certificate.
		
		
		"
::= { certificateEntry 9 }
trustedCertificateGroup OBJECT IDENTIFIER ::= { security 11 }
trustedCertificateGroupTable OBJECT-TYPE
    SYNTAX SEQUENCE OF TrustedCertificateGroupEntry
    MAX-ACCESS not-accessible
    STATUS current
    DESCRIPTION "A list of trusted certificates.  
	These certificates can be used by a server to authenticate clients, or by clients to authenticate servers.  
	The certificates may be endpoint specific or for certificate authorities, to authenticate many clients at once.  
	Each list of certificates SHOULD be specific to a purpose, as the list as a whole may be referenced by other modules.
	For instance, a NETCONF server model might point to a list of certificates to use when authenticating client certificates."
::= { trustedCertificateGroup 1 }
trustedCertificateGroupEntry OBJECT-TYPE
    SYNTAX TrustedCertificateGroupEntry
    MAX-ACCESS not-accessible
    STATUS current
    DESCRIPTION "Entry of trustedCertificateGroupTable" 
    INDEX { trustedCertificateGroupName }
::= { trustedCertificateGroupTable 1 }
TrustedCertificateGroupEntry ::= 
SEQUENCE {
	trustedCertificateGroupName OCTET STRING
    }
trustedCertificateGroupName OBJECT-TYPE
    SYNTAX OCTET STRING  (SIZE (1..64))
    MAX-ACCESS read-only
    STATUS current
    DESCRIPTION "An arbitrary name for this list of trusted certificates.
		
		
		"
::= { trustedCertificateGroupEntry 1 }
trustedCertificate OBJECT IDENTIFIER ::= { security 12 }
trustedCertificateTable OBJECT-TYPE
    SYNTAX SEQUENCE OF TrustedCertificateEntry
    MAX-ACCESS not-accessible
    STATUS current
    DESCRIPTION "A trusted certificate for a specific use.  
	Note, this 'certificate' is a list in order to encode any associated intermediate certificates."
::= { trustedCertificate 1 }
trustedCertificateEntry OBJECT-TYPE
    SYNTAX TrustedCertificateEntry
    MAX-ACCESS not-accessible
    STATUS current
    DESCRIPTION "Entry of trustedCertificateTable" 
    INDEX { trustedCertificateGroupName,trustedCertificateName }
::= { trustedCertificateTable 1 }
TrustedCertificateEntry ::= 
SEQUENCE {
	trustedCertificateName OCTET STRING,
	trustedCertificateVersion INTEGER,
	trustedCertificateSerialNumber OCTET STRING,
	trustedCertificateSignatureAlgorithm OCTET STRING,
	trustedCertificateIssuer OCTET STRING,
	trustedCertificateValidFrom OCTET STRING,
	trustedCertificateValidTo OCTET STRING,
	trustedCertificateSubject OCTET STRING,
	trustedCertificatePublicKeyAlgorithm OCTET STRING
    }
trustedCertificateName OBJECT-TYPE
    SYNTAX OCTET STRING  (SIZE (1..64))
    MAX-ACCESS read-only
    STATUS current
    DESCRIPTION "An arbitrary name for this trusted certificate. 
	Must be unique across all lists of trusted certificates (not just this list) so that a leafref to it from another module can resolve to unique values.
		
		
		"
::= { trustedCertificateEntry 1 }
trustedCertificateVersion OBJECT-TYPE
    SYNTAX INTEGER  {
	 x509v1 (1),
	 x509v2 (2),
	 x509v3 (3)
	}
    MAX-ACCESS read-only
    STATUS current
    DESCRIPTION "version of the certificate.
		
		
		default value :x509v1"
::= { trustedCertificateEntry 2 }
trustedCertificateSerialNumber OBJECT-TYPE
    SYNTAX OCTET STRING 
    MAX-ACCESS read-only
    STATUS current
    DESCRIPTION "serial number of the certificate.
		
		
		"
::= { trustedCertificateEntry 3 }
trustedCertificateSignatureAlgorithm OBJECT-TYPE
    SYNTAX OCTET STRING 
    MAX-ACCESS read-only
    STATUS current
    DESCRIPTION "signature algorithm of the certificate.
		
		
		"
::= { trustedCertificateEntry 4 }
trustedCertificateIssuer OBJECT-TYPE
    SYNTAX OCTET STRING  (SIZE (0..255))
    MAX-ACCESS read-only
    STATUS current
    DESCRIPTION "issuer of the certificate.
		
		
		"
::= { trustedCertificateEntry 5 }
trustedCertificateValidFrom OBJECT-TYPE
    SYNTAX OCTET STRING 
    MAX-ACCESS read-only
    STATUS current
    DESCRIPTION "valid-from date and time of the certificate.
		
		
		"
::= { trustedCertificateEntry 6 }
trustedCertificateValidTo OBJECT-TYPE
    SYNTAX OCTET STRING 
    MAX-ACCESS read-only
    STATUS current
    DESCRIPTION "valid-to date and time of the certificate.
		
		
		"
::= { trustedCertificateEntry 7 }
trustedCertificateSubject OBJECT-TYPE
    SYNTAX OCTET STRING  (SIZE (0..255))
    MAX-ACCESS read-only
    STATUS current
    DESCRIPTION "subject of the certificate.
		
		
		"
::= { trustedCertificateEntry 8 }
trustedCertificatePublicKeyAlgorithm OBJECT-TYPE
    SYNTAX OCTET STRING 
    MAX-ACCESS read-only
    STATUS current
    DESCRIPTION "public-key-algorithm of the certificate.
		
		
		"
::= { trustedCertificateEntry 9 }
nbi OBJECT IDENTIFIER ::= { groove 8 }
snmp OBJECT IDENTIFIER ::= { nbi 1 }
snmpv3 OBJECT IDENTIFIER ::= { snmp 1 }
snmpv3Table OBJECT-TYPE
    SYNTAX SEQUENCE OF Snmpv3Entry
    MAX-ACCESS not-accessible
    STATUS current
    DESCRIPTION "SNMPv3 configuration for user"
::= { snmpv3 1 }
snmpv3Entry OBJECT-TYPE
    SYNTAX Snmpv3Entry
    MAX-ACCESS not-accessible
    STATUS current
    DESCRIPTION "Entry of snmpv3Table" 
    INDEX { userName }
::= { snmpv3Table 1 }
Snmpv3Entry ::= 
SEQUENCE {
	snmpv3UserSecLevel INTEGER,
	snmpv3AuthProtocol INTEGER,
	snmpv3AuthPassphrase OCTET STRING,
	snmpv3PrivProtocol INTEGER,
	snmpv3PrivPassphrase OCTET STRING
    }
snmpv3UserSecLevel OBJECT-TYPE
    SYNTAX INTEGER  {
	 authPriv (1),
	 authNoPriv (2),
	 noAuthNoPriv (3)
	}
    MAX-ACCESS read-only
    STATUS current
    DESCRIPTION "Specifies the SNMPv3 user security level.
		
		
		default value :no-auth-no-priv"
::= { snmpv3Entry 1 }
snmpv3AuthProtocol OBJECT-TYPE
    SYNTAX INTEGER  {
	 md5 (1),
	 sha (2)
	}
    MAX-ACCESS read-only
    STATUS current
    DESCRIPTION "Specifies the authentication protocol that the SNMPv3 user being created will use.
		Conditions:(../user-sec-level = 'auth-priv') or (../user-sec-level = 'auth-no-priv')
		
		default value :SHA"
::= { snmpv3Entry 2 }
snmpv3AuthPassphrase OBJECT-TYPE
    SYNTAX OCTET STRING  (SIZE (0|8..64))
    MAX-ACCESS read-only
    STATUS current
    DESCRIPTION "Specifies the SNMPv3 authentication pass phrase.
		Conditions:(../user-sec-level = 'auth-priv') or (../user-sec-level = 'auth-no-priv')
		
		"
::= { snmpv3Entry 3 }
snmpv3PrivProtocol OBJECT-TYPE
    SYNTAX INTEGER  {
	 des (1),
	 aes (2)
	}
    MAX-ACCESS read-only
    STATUS current
    DESCRIPTION "Specifies the privacy protocol that the SNMPv3 user being created will use.
		Conditions:../user-sec-level = 'auth-priv'
		
		default value :AES"
::= { snmpv3Entry 4 }
snmpv3PrivPassphrase OBJECT-TYPE
    SYNTAX OCTET STRING  (SIZE (0|8..64))
    MAX-ACCESS read-only
    STATUS current
    DESCRIPTION "Specifies the SNMPv3 privacy pass phrase.
		Conditions:../user-sec-level = 'auth-priv'
		
		"
::= { snmpv3Entry 5 }
snmpInfo OBJECT IDENTIFIER ::= { snmp 2 }
snmpEngineId OBJECT-TYPE
    SYNTAX OCTET STRING  (SIZE (0..256))
    MAX-ACCESS read-only
    STATUS current
    DESCRIPTION "snmp EngineID of the NE. The EngineID will follow the EngineID format 3 defined in RFC3411. The MAC address in the Engine ID will be the first MAC address of the MAC addresses Pool of the NE.
		
		
		"
::= { snmpInfo 1 }
snmpCommunity OBJECT IDENTIFIER ::= { snmp 3 }
snmpCommunityTable OBJECT-TYPE
    SYNTAX SEQUENCE OF SnmpCommunityEntry
    MAX-ACCESS not-accessible
    STATUS current
    DESCRIPTION "List of SNMP Community Strings. Please note that the trap-community-string is located in the snmp-target MO."
::= { snmpCommunity 1 }
snmpCommunityEntry OBJECT-TYPE
    SYNTAX SnmpCommunityEntry
    MAX-ACCESS not-accessible
    STATUS current
    DESCRIPTION "Entry of snmpCommunityTable" 
    INDEX { snmpCommunityCommunityString }
::= { snmpCommunityTable 1 }
SnmpCommunityEntry ::= 
SEQUENCE {
	snmpCommunityCommunityString CoriantTypesSnmpString,
	snmpCommunityCommunityStringAccess INTEGER
    }
snmpCommunityCommunityString OBJECT-TYPE
    SYNTAX CoriantTypesSnmpString 
    MAX-ACCESS read-only
    STATUS current
    DESCRIPTION "Community String.
		
		
		"
::= { snmpCommunityEntry 1 }
snmpCommunityCommunityStringAccess OBJECT-TYPE
    SYNTAX INTEGER  {
	 readOnly (1)
	}
    MAX-ACCESS read-only
    STATUS current
    DESCRIPTION "snmp access right of this community string.
		
		
		default value :read-only"
::= { snmpCommunityEntry 2 }
snmpTarget OBJECT IDENTIFIER ::= { snmp 4 }
snmpTargetTable OBJECT-TYPE
    SYNTAX SEQUENCE OF SnmpTargetEntry
    MAX-ACCESS not-accessible
    STATUS current
    DESCRIPTION "List of SNMP targets (trap listeners)"
::= { snmpTarget 1 }
snmpTargetEntry OBJECT-TYPE
    SYNTAX SnmpTargetEntry
    MAX-ACCESS not-accessible
    STATUS current
    DESCRIPTION "Entry of snmpTargetTable" 
    INDEX { snmpTargetTargetName }
::= { snmpTargetTable 1 }
SnmpTargetEntry ::= 
SEQUENCE {
	snmpTargetSnmpVersion INTEGER,
	snmpTargetSnmpv3User RowPointer,
	snmpTargetTargetName OCTET STRING,
	snmpTargetTargetIp IetfInetTypesIpv4Address,
	snmpTargetTargetPort IetfInetTypesPortNumber,
	snmpTargetTargetTransport INTEGER,
	snmpTargetTrapCommunityString CoriantTypesSnmpString
    }
snmpTargetSnmpVersion OBJECT-TYPE
    SYNTAX INTEGER  {
	 v2c (2),
	 v3 (3)
	}
    MAX-ACCESS read-only
    STATUS current
    DESCRIPTION "snmp version.
		
		
		default value :v2c"
::= { snmpTargetEntry 1 }
snmpTargetSnmpv3User OBJECT-TYPE
    SYNTAX RowPointer 
    MAX-ACCESS read-only
    STATUS current
    DESCRIPTION "Indicate the snmpv3 user.
		Conditions:../snmp-version = 'v3' 
		
		"
::= { snmpTargetEntry 2 }
snmpTargetTargetName OBJECT-TYPE
    SYNTAX OCTET STRING  (SIZE (1..32))
    MAX-ACCESS read-only
    STATUS current
    DESCRIPTION "Identifies the SNMP target
		
		
		"
::= { snmpTargetEntry 3 }
snmpTargetTargetIp OBJECT-TYPE
    SYNTAX IetfInetTypesIpv4Address 
    MAX-ACCESS read-only
    STATUS current
    DESCRIPTION "IP address of the SNMP target
		
		
		"
::= { snmpTargetEntry 4 }
snmpTargetTargetPort OBJECT-TYPE
    SYNTAX IetfInetTypesPortNumber 
    MAX-ACCESS read-only
    STATUS current
    DESCRIPTION "UDP port number.
		
		
		default value :162"
::= { snmpTargetEntry 5 }
snmpTargetTargetTransport OBJECT-TYPE
    SYNTAX INTEGER  {
	 udp (1)
	}
    MAX-ACCESS read-only
    STATUS current
    DESCRIPTION "Type of transport for the SNMP target
		
		
		default value :udp"
::= { snmpTargetEntry 6 }
snmpTargetTrapCommunityString OBJECT-TYPE
    SYNTAX CoriantTypesSnmpString 
    MAX-ACCESS read-only
    STATUS current
    DESCRIPTION "Community string used for SNMP traps
		Conditions:../snmp-version = 'v2c'
		
		default value :groove"
::= { snmpTargetEntry 7 }
cli OBJECT IDENTIFIER ::= { nbi 2 }
cliConfig OBJECT IDENTIFIER ::= { cli 1 }
cliConfigTable OBJECT-TYPE
    SYNTAX SEQUENCE OF CliConfigEntry
    MAX-ACCESS not-accessible
    STATUS current
    DESCRIPTION "NULL"
::= { cliConfig 1 }
cliConfigEntry OBJECT-TYPE
    SYNTAX CliConfigEntry
    MAX-ACCESS not-accessible
    STATUS current
    DESCRIPTION "Entry of cliConfigTable" 
    INDEX { sessionId }
::= { cliConfigTable 1 }
CliConfigEntry ::= 
SEQUENCE {
	cliConfigCliLines Unsigned32,
	cliConfigCliColumns Unsigned32,
	cliConfigMaxHistorySize Unsigned32,
	cliConfigInteractiveMode CoriantTypesEnableSwitch
    }
cliConfigCliLines OBJECT-TYPE
    SYNTAX Unsigned32  (10..1000)
    MAX-ACCESS read-only
    STATUS current
    DESCRIPTION "Number of rows to be used for display. This value is automatically 
	discovered when possible
		
		
		default value :40"
::= { cliConfigEntry 1 }
cliConfigCliColumns OBJECT-TYPE
    SYNTAX Unsigned32  (80..4000)
    MAX-ACCESS read-only
    STATUS current
    DESCRIPTION "Number of columns to be used for display. This value is automatically 
	discovered when possible
		
		
		default value :140"
::= { cliConfigEntry 2 }
cliConfigMaxHistorySize OBJECT-TYPE
    SYNTAX Unsigned32 
    MAX-ACCESS read-only
    STATUS current
    DESCRIPTION "Command history maximum size for the current session
		
		
		default value :500"
::= { cliConfigEntry 3 }
cliConfigInteractiveMode OBJECT-TYPE
    SYNTAX CoriantTypesEnableSwitch 
    MAX-ACCESS read-only
    STATUS current
    DESCRIPTION " This determines if the CLI shall issue interactive prompt (e.g. for prompting 
	additional information, or for confirmation of user initiated actions).  
	Enabled = CLI will prompt user (default)
	Disabled = CLI will suppress any prompt to the user
	This parameter is set per CLI session and is not persistent.
		
		
		default value :enabled"
::= { cliConfigEntry 4 }
restconf OBJECT IDENTIFIER ::= { nbi 3 }
restconfRestHttpSupport OBJECT-TYPE
    SYNTAX CoriantTypesEnableSwitch 
    MAX-ACCESS read-only
    STATUS current
    DESCRIPTION "Defines if the HTTP port (8080) is enabled for RESTCONF
		
		
		default value :disabled"
::= { restconf 1 }
restconfRestHttpsSupport OBJECT-TYPE
    SYNTAX CoriantTypesEnableSwitch 
    MAX-ACCESS read-only
    STATUS current
    DESCRIPTION "Defines if the HTTPS port (8181) is enabled for RESTCONF
		
		
		default value :enabled"
::= { restconf 2 }
restconfRestSessionTimeout OBJECT-TYPE
    SYNTAX Unsigned32  (1..300)
    MAX-ACCESS read-only
    STATUS current
    DESCRIPTION "Timeout of a cookie based RESTCONF session. 
	The cookie expiration date is reset every time there is activity on the session.
		
		UNITS:minutes
		default value :5"
::= { restconf 3 }
cliAlias OBJECT IDENTIFIER ::= { nbi 4 }
cliAliasTable OBJECT-TYPE
    SYNTAX SEQUENCE OF CliAliasEntry
    MAX-ACCESS not-accessible
    STATUS current
    DESCRIPTION "List of aliases used in CLI. 
	Can only be accessed via 'alias/unalias' CLI commands."
::= { cliAlias 1 }
cliAliasEntry OBJECT-TYPE
    SYNTAX CliAliasEntry
    MAX-ACCESS not-accessible
    STATUS current
    DESCRIPTION "Entry of cliAliasTable" 
    INDEX { cliAliasName }
::= { cliAliasTable 1 }
CliAliasEntry ::= 
SEQUENCE {
	cliAliasName OCTET STRING,
	cliAliasValue OCTET STRING
    }
cliAliasName OBJECT-TYPE
    SYNTAX OCTET STRING  (SIZE (1..256))
    MAX-ACCESS read-only
    STATUS current
    DESCRIPTION "Name of the alias
		
		
		"
::= { cliAliasEntry 1 }
cliAliasValue OBJECT-TYPE
    SYNTAX OCTET STRING  (SIZE (1..1024))
    MAX-ACCESS read-only
    STATUS current
    DESCRIPTION "Value of the alias
		
		
		"
::= { cliAliasEntry 2 }
cliScript OBJECT IDENTIFIER ::= { nbi 5 }
cliScriptTable OBJECT-TYPE
    SYNTAX SEQUENCE OF CliScriptEntry
    MAX-ACCESS not-accessible
    STATUS current
    DESCRIPTION "List of available CLI scripts. 
	Scripts can be executed with the 'run' command"
::= { cliScript 1 }
cliScriptEntry OBJECT-TYPE
    SYNTAX CliScriptEntry
    MAX-ACCESS not-accessible
    STATUS current
    DESCRIPTION "Entry of cliScriptTable" 
    INDEX { cliScriptScriptName }
::= { cliScriptTable 1 }
CliScriptEntry ::= 
SEQUENCE {
	cliScriptScriptName OCTET STRING,
	cliScriptDescription OCTET STRING
    }
cliScriptScriptName OBJECT-TYPE
    SYNTAX OCTET STRING  (SIZE (0..128))
    MAX-ACCESS read-only
    STATUS current
    DESCRIPTION "File name of the CLI script
		
		
		"
::= { cliScriptEntry 1 }
cliScriptDescription OBJECT-TYPE
    SYNTAX OCTET STRING  (SIZE (0..256))
    MAX-ACCESS read-only
    STATUS current
    DESCRIPTION "Description of the CLI script
		
		
		"
::= { cliScriptEntry 2 }
filesw OBJECT IDENTIFIER ::= { groove 9 }
softwareload OBJECT IDENTIFIER ::= { filesw 2 }
softwareloadTable OBJECT-TYPE
    SYNTAX SEQUENCE OF SoftwareloadEntry
    MAX-ACCESS not-accessible
    STATUS current
    DESCRIPTION "The list of the software loads in the system."
::= { softwareload 1 }
softwareloadEntry OBJECT-TYPE
    SYNTAX SoftwareloadEntry
    MAX-ACCESS not-accessible
    STATUS current
    DESCRIPTION "Entry of softwareloadTable" 
    INDEX { softwareloadSwloadId }
::= { softwareloadTable 1 }
SoftwareloadEntry ::= 
SEQUENCE {
	softwareloadSwloadId Unsigned32,
	softwareloadSwloadState INTEGER,
	softwareloadSwloadVersion CoriantFileSwTypesSwVersion,
	softwareloadSwloadVendor CoriantFileSwTypesSwloadVendor,
	softwareloadSwloadProduct CoriantFileSwTypesSwloadProduct,
	softwareloadSwloadLabel OCTET STRING
    }
softwareloadSwloadId OBJECT-TYPE
    SYNTAX Unsigned32  (1..10)
    MAX-ACCESS read-only
    STATUS current
    DESCRIPTION "
	software load identifier which is uniquely identify specific software load.
	
		
		
		"
::= { softwareloadEntry 1 }
softwareloadSwloadState OBJECT-TYPE
    SYNTAX INTEGER  {
	 active (1),
	 inactive (2)
	}
    MAX-ACCESS read-only
    STATUS current
    DESCRIPTION "
	Indicates the state of the software load. 
	
		
		
		"
::= { softwareloadEntry 2 }
softwareloadSwloadVersion OBJECT-TYPE
    SYNTAX CoriantFileSwTypesSwVersion 
    MAX-ACCESS read-only
    STATUS current
    DESCRIPTION "
	Indicates the software version of the software load. 
	
		
		
		"
::= { softwareloadEntry 3 }
softwareloadSwloadVendor OBJECT-TYPE
    SYNTAX CoriantFileSwTypesSwloadVendor 
    MAX-ACCESS read-only
    STATUS current
    DESCRIPTION "
	Vendor information of the software load. 
	
		
		
		"
::= { softwareloadEntry 4 }
softwareloadSwloadProduct OBJECT-TYPE
    SYNTAX CoriantFileSwTypesSwloadProduct 
    MAX-ACCESS read-only
    STATUS current
    DESCRIPTION "
	Indicates the network element family this software belongs to. 
	
		
		
		"
::= { softwareloadEntry 5 }
softwareloadSwloadLabel OBJECT-TYPE
    SYNTAX OCTET STRING  (SIZE (0..1024))
    MAX-ACCESS read-only
    STATUS current
    DESCRIPTION "
	The label of the software load including summary information. 
	
		
		
		"
::= { softwareloadEntry 6 }
database OBJECT IDENTIFIER ::= { filesw 3 }
databaseTable OBJECT-TYPE
    SYNTAX SEQUENCE OF DatabaseEntry
    MAX-ACCESS not-accessible
    STATUS current
    DESCRIPTION "The list of the databases in the system."
::= { database 1 }
databaseEntry OBJECT-TYPE
    SYNTAX DatabaseEntry
    MAX-ACCESS not-accessible
    STATUS current
    DESCRIPTION "Entry of databaseTable" 
    INDEX { softwareloadSwloadId,databaseId }
::= { databaseTable 1 }
DatabaseEntry ::= 
SEQUENCE {
	databaseId Unsigned32,
	databaseState INTEGER,
	databaseVersion CoriantFileSwTypesSwVersion,
	databaseVendor CoriantFileSwTypesSwloadVendor,
	databaseProduct CoriantFileSwTypesSwloadProduct,
	databaseBackupTime OCTET STRING
    }
databaseId OBJECT-TYPE
    SYNTAX Unsigned32  (1..10)
    MAX-ACCESS read-only
    STATUS current
    DESCRIPTION "
	database identifier which is uniquely identify specific database.
	
		
		
		"
::= { databaseEntry 1 }
databaseState OBJECT-TYPE
    SYNTAX INTEGER  {
	 active (1),
	 inactive (2)
	}
    MAX-ACCESS read-only
    STATUS current
    DESCRIPTION "
	Indicates the state of the database. 
	
		
		
		"
::= { databaseEntry 2 }
databaseVersion OBJECT-TYPE
    SYNTAX CoriantFileSwTypesSwVersion 
    MAX-ACCESS read-only
    STATUS current
    DESCRIPTION "
	Indicates the database version. 
	
		
		
		"
::= { databaseEntry 3 }
databaseVendor OBJECT-TYPE
    SYNTAX CoriantFileSwTypesSwloadVendor 
    MAX-ACCESS read-only
    STATUS current
    DESCRIPTION "
	Vendor information of the database. 
	
		
		
		"
::= { databaseEntry 4 }
databaseProduct OBJECT-TYPE
    SYNTAX CoriantFileSwTypesSwloadProduct 
    MAX-ACCESS read-only
    STATUS current
    DESCRIPTION "
	Indicates the network element family this database belongs to. 
	
		
		
		"
::= { databaseEntry 5 }
databaseBackupTime OBJECT-TYPE
    SYNTAX OCTET STRING 
    MAX-ACCESS read-only
    STATUS current
    DESCRIPTION "
	Indicates the database last backup time. 
	
		
		
		default value :"
::= { databaseEntry 6 }
fwVersionMap OBJECT IDENTIFIER ::= { filesw 4 }
fwVersionMapTable OBJECT-TYPE
    SYNTAX SEQUENCE OF FwVersionMapEntry
    MAX-ACCESS not-accessible
    STATUS current
    DESCRIPTION "The firmware information of the upgradable devices included in the software load."
::= { fwVersionMap 1 }
fwVersionMapEntry OBJECT-TYPE
    SYNTAX FwVersionMapEntry
    MAX-ACCESS not-accessible
    STATUS current
    DESCRIPTION "Entry of fwVersionMapTable" 
    INDEX { softwareloadSwloadId,fwVersionMapDeviceName }
::= { fwVersionMapTable 1 }
FwVersionMapEntry ::= 
SEQUENCE {
	fwVersionMapDeviceName CoriantFileSwTypesDeviceName,
	fwVersionMapDeviceFwVersion CoriantFileSwTypesDeviceFwVersion
    }
fwVersionMapDeviceName OBJECT-TYPE
    SYNTAX CoriantFileSwTypesDeviceName 
    MAX-ACCESS read-only
    STATUS current
    DESCRIPTION "
	Indicates the name of the device.
	
		
		
		"
::= { fwVersionMapEntry 1 }
fwVersionMapDeviceFwVersion OBJECT-TYPE
    SYNTAX CoriantFileSwTypesDeviceFwVersion 
    MAX-ACCESS read-only
    STATUS current
    DESCRIPTION "
	Indicates the version of the firmware.
	
		
		
		"
::= { fwVersionMapEntry 2 }
currentFwVersion OBJECT IDENTIFIER ::= { filesw 5 }
currentFwVersionTable OBJECT-TYPE
    SYNTAX SEQUENCE OF CurrentFwVersionEntry
    MAX-ACCESS not-accessible
    STATUS current
    DESCRIPTION "The firmware information of the upgradable devices included in the software load."
::= { currentFwVersion 1 }
currentFwVersionEntry OBJECT-TYPE
    SYNTAX CurrentFwVersionEntry
    MAX-ACCESS not-accessible
    STATUS current
    DESCRIPTION "Entry of currentFwVersionTable" 
    INDEX { currentFwVersionEquipmentEntity,currentFwVersionDeviceName }
::= { currentFwVersionTable 1 }
CurrentFwVersionEntry ::= 
SEQUENCE {
	currentFwVersionEquipmentEntity RowPointer,
	currentFwVersionFwEquipmentType CoriantTypesEquipmentType,
	currentFwVersionDeviceName CoriantFileSwTypesDeviceName,
	currentFwVersionDeviceFwVersion CoriantFileSwTypesDeviceFwVersion,
	currentFwVersionFwState INTEGER
    }
currentFwVersionEquipmentEntity OBJECT-TYPE
    SYNTAX RowPointer 
    MAX-ACCESS read-only
    STATUS current
    DESCRIPTION "
	Indicates the entity of the equipment carrying the device.
	
		
		
		"
::= { currentFwVersionEntry 1 }
currentFwVersionFwEquipmentType OBJECT-TYPE
    SYNTAX CoriantTypesEquipmentType 
    MAX-ACCESS read-only
    STATUS current
    DESCRIPTION "
	Indicates the type of the equipment carrying the device.
	
		
		
		"
::= { currentFwVersionEntry 2 }
currentFwVersionDeviceName OBJECT-TYPE
    SYNTAX CoriantFileSwTypesDeviceName 
    MAX-ACCESS read-only
    STATUS current
    DESCRIPTION "
	Indicates the name of the device.
	
		
		
		"
::= { currentFwVersionEntry 3 }
currentFwVersionDeviceFwVersion OBJECT-TYPE
    SYNTAX CoriantFileSwTypesDeviceFwVersion 
    MAX-ACCESS read-only
    STATUS current
    DESCRIPTION "
	Indicates the version of the firmware.
	
		
		
		"
::= { currentFwVersionEntry 4 }
currentFwVersionFwState OBJECT-TYPE
    SYNTAX INTEGER  {
	 notAvailable (0),
	 current (1),
	 notCurrent (2)
	}
    MAX-ACCESS read-only
    STATUS current
    DESCRIPTION "
	Indicates firmware state of the device.
	Current: indicates the loaded firmware is the version of current software load.
	Not-current: indicates the loaded firmware is not the version of current software load.
	
		
		
		default value :not-available"
::= { currentFwVersionEntry 5 }
rollbackPoint OBJECT IDENTIFIER ::= { filesw 6 }
rollbackPointTable OBJECT-TYPE
    SYNTAX SEQUENCE OF RollbackPointEntry
    MAX-ACCESS not-accessible
    STATUS current
    DESCRIPTION "Represents a rollback point stored in the system. 
	A rollback point represents the system configuration of a specific point in time, that the user may create with the 
	'create-rollback-point' command, visualize with the 'diff' command' and rollback to with the 'rollback' command.
	The system is able to store up to 10 rollback-points, rolling over old instances as new ones are created.
	The incremental IDs of 1..10 are automatically generated by the system whenever the rollback-point is created.
	Rollback points can be deleted as any normal object.
	A special 'backup' rollback-point can also be created with ID 0; unlike normal rollback-points, this instance will
	be kept even after activation with the 'rollback' RPC."
::= { rollbackPoint 1 }
rollbackPointEntry OBJECT-TYPE
    SYNTAX RollbackPointEntry
    MAX-ACCESS not-accessible
    STATUS current
    DESCRIPTION "Entry of rollbackPointTable" 
    INDEX { rollbackPointId }
::= { rollbackPointTable 1 }
RollbackPointEntry ::= 
SEQUENCE {
	rollbackPointId Unsigned32,
	rollbackPointCreationTime IetfYangTypesDateAndTime,
	rollbackPointCreationTrigger CoriantTypesUserName,
	rollbackPointDescription OCTET STRING,
	rollbackPointType INTEGER
    }
rollbackPointId OBJECT-TYPE
    SYNTAX Unsigned32  (0..10)
    MAX-ACCESS read-only
    STATUS current
    DESCRIPTION "Integer ID of the rollback-point. Generated dynamically whenever a rollback-point is created, with range 1 to 100
		
		
		"
::= { rollbackPointEntry 1 }
rollbackPointCreationTime OBJECT-TYPE
    SYNTAX IetfYangTypesDateAndTime 
    MAX-ACCESS read-only
    STATUS current
    DESCRIPTION "Timestamp when this rollback-point was created
		
		
		"
::= { rollbackPointEntry 2 }
rollbackPointCreationTrigger OBJECT-TYPE
    SYNTAX CoriantTypesUserName 
    MAX-ACCESS read-only
    STATUS current
    DESCRIPTION "Describes the author user-name of this rollback-point
		
		
		"
::= { rollbackPointEntry 3 }
rollbackPointDescription OBJECT-TYPE
    SYNTAX OCTET STRING  (SIZE (0..200))
    MAX-ACCESS read-only
    STATUS current
    DESCRIPTION "User defined description of this rollback-point
		
		
		"
::= { rollbackPointEntry 4 }
rollbackPointType OBJECT-TYPE
    SYNTAX INTEGER  {
	 normal (1),
	 backup (2)
	}
    MAX-ACCESS read-only
    STATUS current
    DESCRIPTION "The type of the rollback-point
		
		
		default value :normal"
::= { rollbackPointEntry 5 }
logServer OBJECT IDENTIFIER ::= { filesw 8 }
logServerTable OBJECT-TYPE
    SYNTAX SEQUENCE OF LogServerEntry
    MAX-ACCESS not-accessible
    STATUS current
    DESCRIPTION "Grouping the configuration parameters for log forwarding."
::= { logServer 1 }
logServerEntry OBJECT-TYPE
    SYNTAX LogServerEntry
    MAX-ACCESS not-accessible
    STATUS current
    DESCRIPTION "Entry of logServerTable" 
    INDEX { logServerName }
::= { logServerTable 1 }
LogServerEntry ::= 
SEQUENCE {
	logServerName OCTET STRING,
	logServerIpAddress IetfInetTypesIpv4Address,
	logServerTransport INTEGER,
	logServerPort IetfInetTypesPortNumber,
	logServerDestinationFacilityType CoriantTypesEnableSwitch,
	logServerDestinationFacility OCTET STRING
    }
logServerName OBJECT-TYPE
    SYNTAX OCTET STRING  (SIZE (1..64))
    MAX-ACCESS read-only
    STATUS current
    DESCRIPTION "The name for the endpoint to forwarding logs to.
		
		
		"
::= { logServerEntry 1 }
logServerIpAddress OBJECT-TYPE
    SYNTAX IetfInetTypesIpv4Address 
    MAX-ACCESS read-only
    STATUS current
    DESCRIPTION "The leaf uniquely specifies the ipv4 address of the remote host.
		
		
		"
::= { logServerEntry 2 }
logServerTransport OBJECT-TYPE
    SYNTAX INTEGER  {
	 tcp (1),
	 udp (2)
	}
    MAX-ACCESS read-only
    STATUS current
    DESCRIPTION "It is the transport protocol used when forwarding logs.
		
		
		default value :udp"
::= { logServerEntry 3 }
logServerPort OBJECT-TYPE
    SYNTAX IetfInetTypesPortNumber 
    MAX-ACCESS read-only
    STATUS current
    DESCRIPTION "This leaf specifies the port number used to deliver messages to the remote server.
		
		
		default value :514"
::= { logServerEntry 4 }
logServerDestinationFacilityType OBJECT-TYPE
    SYNTAX CoriantTypesEnableSwitch 
    MAX-ACCESS read-only
    STATUS current
    DESCRIPTION "Switching of the function destination-facility
		
		
		default value :disabled"
::= { logServerEntry 5 }
logServerDestinationFacility OBJECT-TYPE
    SYNTAX OCTET STRING 
    MAX-ACCESS read-only
    STATUS current
    DESCRIPTION "This leaf specifies the facility used in messages delivered to the remote server.
		
		
		default value :23"
::= { logServerEntry 6 }
logFacility OBJECT IDENTIFIER ::= { filesw 10 }
logFacilityTable OBJECT-TYPE
    SYNTAX SEQUENCE OF LogFacilityEntry
    MAX-ACCESS not-accessible
    STATUS current
    DESCRIPTION "NULL"
::= { logFacility 1 }
logFacilityEntry OBJECT-TYPE
    SYNTAX LogFacilityEntry
    MAX-ACCESS not-accessible
    STATUS current
    DESCRIPTION "Entry of logFacilityTable" 
    INDEX { logServerName,logFacilityLogSelectorFacility }
::= { logFacilityTable 1 }
LogFacilityEntry ::= 
SEQUENCE {
	logFacilityLogSelectorFacility INTEGER,
	logFacilityLogSelectorSeverity INTEGER,
	logFacilityCompareOp INTEGER
    }
logFacilityLogSelectorFacility OBJECT-TYPE
    SYNTAX INTEGER  {
	 security (1),
	 alarm (2),
	 event (3),
	 configuration (4),
	 cryptoConfiguration (5),
	 cryptoSecurity (6),
	 cryptoEvent (7),
	 cryptoAlarm (8)
	}
    MAX-ACCESS read-only
    STATUS current
    DESCRIPTION "The leaf uniquely identifies a syslog facility for forwarding. 
		
		
		"
::= { logFacilityEntry 1 }
logFacilityLogSelectorSeverity OBJECT-TYPE
    SYNTAX INTEGER  {
	 emergency (0),
	 alert (1),
	 critical (2),
	 error (3),
	 warning (4),
	 notice (5),
	 informational (6),
	 debug (7)
	}
    MAX-ACCESS read-only
    STATUS current
    DESCRIPTION "The system log selected severity level for forwarding
		
		
		default value :debug"
::= { logFacilityEntry 2 }
logFacilityCompareOp OBJECT-TYPE
    SYNTAX INTEGER  {
	 equalsOrHigher (1),
	 equals (2),
	 notEquals (3)
	}
    MAX-ACCESS read-only
    STATUS current
    DESCRIPTION "This leaf describes the option to specify how the severity comparison is performed.
		
		
		default value :equals-or-higher"
::= { logFacilityEntry 3 }
timeManager OBJECT IDENTIFIER ::= { groove 10 }
timeManagerInfo OBJECT IDENTIFIER ::= { timeManager 1 }
timeManagerTimezone OBJECT-TYPE
    SYNTAX INTEGER  {
	 internationalDateLineWestGmt1200 (1),
	 midwayIslandSamoaGmt1100 (2),
	 hawaiiGmt1000 (3),
	 alaskaGmt0900 (4),
	 pacificTimeUsAndCanadaGmt0800 (5),
	 arizonaGmt0700 (6),
	 mountainTimeUsAndCanadaGmt0700 (7),
	 centralamericaGmt0600 (8),
	 centralTimeUsAndCanadaGmt0600 (9),
	 mexicoCityTegucigalpaGmt0600 (10),
	 saskatchewanGmt0600 (11),
	 bagotaLimaQuitoGmt0500 (12),
	 easternTimeUsAndCanadaGmt0500 (13),
	 indianaEastGmt0500 (14),
	 caracasLaPazGmt0430 (15),
	 atlanticTimeCanadaGmt0400 (16),
	 santiagoGmt0400 (17),
	 newfoundlandGmt0330 (18),
	 brasiliaGmt0300 (19),
	 buenosAiresGeorgetownGmt0300 (20),
	 greenlandGmt0300 (21),
	 midAtlanticGmt0200 (22),
	 azoresGmt0100 (23),
	 capeVerdeIsGmt0100 (24),
	 casablancaMonroviaGmt (25),
	 greenwichMeanTimeDublinEdinburghLisbonLondonGmt (26),
	 amsterdamCopenhagenMadridParisvilniusGmtplus0100 (27),
	 belgradeSarajevoSkopjeSofijaZargrebGmtplus0100 (28),
	 bratislavaBudapestLjublijanaPragueWasawGmtplus0100 (29),
	 brusselsBerlinBernRomeStockholmViennaGmtplus0100 (30),
	 westCentralAfricaGmtplus0100 (31),
	 athensIstanbulMinskGmtplus0200 (32),
	 bucharestGmtplus0200 (33),
	 cairoGmtplus0200 (34),
	 hararePretoriaGmtplus0200 (35),
	 helsinkiRigaTallinnGmtplus0200 (36),
	 jerusalemGmtplus0200 (37),
	 israelGmtplus0200 (38),
	 baghdadGmtplus0300 (39),
	 kuwaitRiyadhGmtplus0300 (40),
	 moscowStPetersburgVolgogradGmtplus0300 (41),
	 nairobiGmtplus0300 (42),
	 tehranGmtplus0330 (43),
	 abuDhabiMuscatGmtplus0400 (44),
	 bakuGmtplus0400 (45),
	 tbilisiGmtplus0400 (46),
	 kabulGmtplus0430 (47),
	 ekaterinburgGmtplus0500 (48),
	 islamabadKarachiTashkentGmtplus0500 (49),
	 mumbaiCalcuttaChennaiNewDelhiGmtplus0530 (50),
	 colomboGmtplus0530 (51),
	 kathmanduGmtplus0545 (52),
	 dhakaGmtplus0600 (53),
	 almatyGmtplus0600 (54),
	 rangoonGmtplus0630 (55),
	 bangkokHanoiJakartaGmtplus0700 (56),
	 beijingChongqingHongKongUrumqiGmtplus0800 (57),
	 perthGmtplus0800 (58),
	 singaporeKualaLumpurGmtplus0800 (59),
	 taipeiGmtplus0800 (60),
	 osakaSapporoTokyoGmtplus0900 (61),
	 seoulGmtplus0900 (62),
	 yakutskGmtplus0900 (63),
	 adelaideGmtplus0930 (64),
	 darwinGmtplus0930 (65),
	 brisbaneGmtplus1000 (66),
	 canberraMelbourneSydneyGmtplus1000 (67),
	 guamPortMoresbyGmtplus1000 (68),
	 hobartGmtplus1000 (69),
	 vladivostokGmtplus1000 (70),
	 magadanSolomonIsNewCaledoniaGmtplus1100 (71),
	 aucklandWellingtonGmtplus1200 (72),
	 fijiKamchatkaMarshallIsGmtplus1200 (73),
	 eniwetokKwajaleinGmtplus1200 (74),
	 nukuAlofaGmtplus1300 (75),
	 kiritimatiGmtplus1400 (76)
	}
    MAX-ACCESS read-only
    STATUS current
    DESCRIPTION "Indicates the Name of the Time Zone of this NE.
		
		
		default value :Greenwich_Mean_Time:Dublin-Edinburgh-Lisbon-London[GMT]"
::= { timeManagerInfo 1 }
timeManagerCurrentTime OBJECT-TYPE
    SYNTAX IetfYangTypesDateAndTime 
    MAX-ACCESS read-only
    STATUS current
    DESCRIPTION "Indicates the current Date and Time of this NE.
		
		
		"
::= { timeManagerInfo 2 }
timeManagerLastStartTime OBJECT-TYPE
    SYNTAX IetfYangTypesDateAndTime 
    MAX-ACCESS read-only
    STATUS current
    DESCRIPTION "Indicate the time of last system boot.
		
		
		"
::= { timeManagerInfo 3 }
timeManagerUpTime OBJECT-TYPE
    SYNTAX OCTET STRING 
    MAX-ACCESS read-only
    STATUS current
    DESCRIPTION "Indicate how long the system has been running.
		
		
		"
::= { timeManagerInfo 4 }
timeManagerTimeSourceState OBJECT-TYPE
    SYNTAX INTEGER  {
	 external (1),
	 freerun (2)
	}
    MAX-ACCESS read-only
    STATUS current
    DESCRIPTION "Indicates the state of the time source.
		
		
		"
::= { timeManagerInfo 5 }
ntp OBJECT IDENTIFIER ::= { timeManager 2 }
ntpEnabled OBJECT-TYPE
    SYNTAX TruthValue 
    MAX-ACCESS read-only
    STATUS current
    DESCRIPTION "Indicates if NTP is enabled.
		
		
		default value :false"
::= { ntp 1 }
ntpCurrentTimeSource OBJECT-TYPE
    SYNTAX IetfInetTypesIpv4AddressNoZone 
    MAX-ACCESS read-only
    STATUS current
    DESCRIPTION "Indicates the current time source.
		
		
		default value :0.0.0.0"
::= { ntp 2 }
ntpAssociation OBJECT IDENTIFIER ::= { timeManager 3 }
ntpAssociationTable OBJECT-TYPE
    SYNTAX SEQUENCE OF NtpAssociationEntry
    MAX-ACCESS not-accessible
    STATUS current
    DESCRIPTION "NULL"
::= { ntpAssociation 1 }
ntpAssociationEntry OBJECT-TYPE
    SYNTAX NtpAssociationEntry
    MAX-ACCESS not-accessible
    STATUS current
    DESCRIPTION "Entry of ntpAssociationTable" 
    INDEX { ntpAssociationSource }
::= { ntpAssociationTable 1 }
NtpAssociationEntry ::= 
SEQUENCE {
	ntpAssociationSource IetfInetTypesIpv4AddressNoZone,
	ntpAssociationType INTEGER,
	ntpAssociationPreferredNtpAssociation TruthValue,
	ntpAssociationNtpAdminState INTEGER
    }
ntpAssociationSource OBJECT-TYPE
    SYNTAX IetfInetTypesIpv4AddressNoZone  (SIZE (1..64))
    MAX-ACCESS read-only
    STATUS current
    DESCRIPTION "Indicates the ntp-association-source.
		
		
		"
::= { ntpAssociationEntry 1 }
ntpAssociationType OBJECT-TYPE
    SYNTAX INTEGER  {
	 ntpServer (1),
	 ntpPeer (2)
	}
    MAX-ACCESS read-only
    STATUS current
    DESCRIPTION "Indicates the ntp association type.
		
		
		"
::= { ntpAssociationEntry 2 }
ntpAssociationPreferredNtpAssociation OBJECT-TYPE
    SYNTAX TruthValue 
    MAX-ACCESS read-only
    STATUS current
    DESCRIPTION "Indicates if this is preferred.
		
		
		"
::= { ntpAssociationEntry 3 }
ntpAssociationNtpAdminState OBJECT-TYPE
    SYNTAX INTEGER  {
	 up (1),
	 down (2)
	}
    MAX-ACCESS read-only
    STATUS current
    DESCRIPTION "The administrative state specifies the permission to use or prohibition against using the resource.
		
		
		default value :up"
::= { ntpAssociationEntry 4 }
ntpAssociationStatus OBJECT IDENTIFIER ::= { timeManager 4 }
ntpAssociationStatusTable OBJECT-TYPE
    SYNTAX SEQUENCE OF NtpAssociationStatusEntry
    MAX-ACCESS not-accessible
    STATUS current
    DESCRIPTION "NULL"
::= { ntpAssociationStatus 1 }
ntpAssociationStatusEntry OBJECT-TYPE
    SYNTAX NtpAssociationStatusEntry
    MAX-ACCESS not-accessible
    STATUS current
    DESCRIPTION "Entry of ntpAssociationStatusTable" 
    INDEX { ntpAssociationSource }
::= { ntpAssociationStatusTable 1 }
NtpAssociationStatusEntry ::= 
SEQUENCE {
	ntpAssociationStatusNtpAssociationRefid OCTET STRING,
	ntpAssociationStatusNtpStratum Unsigned32,
	ntpAssociationStatusNtpPollingInterval Unsigned32,
	ntpAssociationStatusNtpPrecision OCTET STRING,
	ntpAssociationStatusNtpAssociationOffset OCTET STRING,
	ntpAssociationStatusNtpAssociationReach Unsigned32,
	ntpAssociationStatusNtpAssociationDelay OCTET STRING,
	ntpAssociationStatusNtpAssociationDispersion OCTET STRING
    }
ntpAssociationStatusNtpAssociationRefid OBJECT-TYPE
    SYNTAX OCTET STRING  (SIZE (16))
    MAX-ACCESS read-only
    STATUS current
    DESCRIPTION "Reference clock type or address for the peer.
		
		
		"
::= { ntpAssociationStatusEntry 1 }
ntpAssociationStatusNtpStratum OBJECT-TYPE
    SYNTAX Unsigned32 
    MAX-ACCESS read-only
    STATUS current
    DESCRIPTION "This attribute indicates the stratum of local clock. A value of 0, indicates that Stratum in Unspecified.
		
		
		"
::= { ntpAssociationStatusEntry 2 }
ntpAssociationStatusNtpPollingInterval OBJECT-TYPE
    SYNTAX Unsigned32 
    MAX-ACCESS read-only
    STATUS current
    DESCRIPTION "NTP polling interval. This is an integer number indicating the HOST polling interval between transmitted messages, in seconds.
		
		UNITS:seconds
		"
::= { ntpAssociationStatusEntry 3 }
ntpAssociationStatusNtpPrecision OBJECT-TYPE
    SYNTAX OCTET STRING 
    MAX-ACCESS read-only
    STATUS current
    DESCRIPTION "This is an unsigned floating-point number indicating the precision of the various clocks, in milliseconds.
		
		UNITS:milliseconds
		"
::= { ntpAssociationStatusEntry 4 }
ntpAssociationStatusNtpAssociationOffset OBJECT-TYPE
    SYNTAX OCTET STRING 
    MAX-ACCESS read-only
    STATUS current
    DESCRIPTION "Indicates the offset between the local clock and the superior reference clock.
		
		UNITS:milliseconds
		"
::= { ntpAssociationStatusEntry 5 }
ntpAssociationStatusNtpAssociationReach OBJECT-TYPE
    SYNTAX Unsigned32 
    MAX-ACCESS read-only
    STATUS current
    DESCRIPTION "Indicates the reachability of the configured server or peer.
		
		
		"
::= { ntpAssociationStatusEntry 6 }
ntpAssociationStatusNtpAssociationDelay OBJECT-TYPE
    SYNTAX OCTET STRING 
    MAX-ACCESS read-only
    STATUS current
    DESCRIPTION "Indicates the delay between the local clock and the superior reference clock, in milliseconds.
		
		UNITS:milliseconds
		"
::= { ntpAssociationStatusEntry 7 }
ntpAssociationStatusNtpAssociationDispersion OBJECT-TYPE
    SYNTAX OCTET STRING 
    MAX-ACCESS read-only
    STATUS current
    DESCRIPTION "Indicates the dispersion between the local clock and the peer clock, in milliseconds.
		
		UNITS:milliseconds
		"
::= { ntpAssociationStatusEntry 8 }
ztc OBJECT IDENTIFIER ::= { groove 11 }
ztcInfo OBJECT IDENTIFIER ::= { ztc 1 }
ztcEnabled OBJECT-TYPE
    SYNTAX TruthValue 
    MAX-ACCESS read-only
    STATUS current
    DESCRIPTION "enable/disable Zero Touch commissioning.
		
		
		default value :true"
::= { ztcInfo 1 }
ztcStatus OBJECT-TYPE
    SYNTAX INTEGER  {
	 disabled (0),
	 ready (1),
	 ongoing (2),
	 failed (3),
	 done (4)
	}
    MAX-ACCESS read-only
    STATUS current
    DESCRIPTION "Shows the ZTC process status:
	disabled - ZTC will not be attempted because it was disabled via configuration
	ready - ZTC will be attempted when able to communicate with external ZTC server
	ongoing - ZTC is ongoing
	failed - some problems occurred during ZTC
	done - ZTC completed successfully.
		
		
		default value :ready"
::= { ztcInfo 2 }
common OBJECT IDENTIFIER ::= { groove 13 }
bitErrorRatePreFec OBJECT IDENTIFIER ::= { common 1 }
bitErrorRatePreFecTable OBJECT-TYPE
    SYNTAX SEQUENCE OF BitErrorRatePreFecEntry
    MAX-ACCESS not-accessible
    STATUS current
    DESCRIPTION "statistics value: average, minimum, maximum and instant value for bit error rate before fec"
::= { bitErrorRatePreFec 1 }
bitErrorRatePreFecEntry OBJECT-TYPE
    SYNTAX BitErrorRatePreFecEntry
    MAX-ACCESS not-accessible
    STATUS current
    DESCRIPTION "Entry of bitErrorRatePreFecTable" 
    INDEX { shelfId,slotId,subslotId,portId,subportId }
::= { bitErrorRatePreFecTable 1 }
BitErrorRatePreFecEntry ::= 
SEQUENCE {
	bitErrorRatePreFecInstant OCTET STRING,
	bitErrorRatePreFecAvg OCTET STRING,
	bitErrorRatePreFecMin OCTET STRING,
	bitErrorRatePreFecMax OCTET STRING
    }
bitErrorRatePreFecInstant OBJECT-TYPE
    SYNTAX OCTET STRING 
    MAX-ACCESS read-only
    STATUS current
    DESCRIPTION "the instant value of statistics counter
		
		UNITS:bit-ratio
		"
::= { bitErrorRatePreFecEntry 1 }
bitErrorRatePreFecAvg OBJECT-TYPE
    SYNTAX OCTET STRING 
    MAX-ACCESS read-only
    STATUS current
    DESCRIPTION "the average value of statistics counter
		
		UNITS:bit-ratio
		"
::= { bitErrorRatePreFecEntry 2 }
bitErrorRatePreFecMin OBJECT-TYPE
    SYNTAX OCTET STRING 
    MAX-ACCESS read-only
    STATUS current
    DESCRIPTION "the minimum value of statistics counter
		
		UNITS:bit-ratio
		"
::= { bitErrorRatePreFecEntry 3 }
bitErrorRatePreFecMax OBJECT-TYPE
    SYNTAX OCTET STRING 
    MAX-ACCESS read-only
    STATUS current
    DESCRIPTION "the maximum value of statistics counter
		
		UNITS:bit-ratio
		"
::= { bitErrorRatePreFecEntry 4 }
bitErrorRatePostFec OBJECT IDENTIFIER ::= { common 2 }
bitErrorRatePostFecTable OBJECT-TYPE
    SYNTAX SEQUENCE OF BitErrorRatePostFecEntry
    MAX-ACCESS not-accessible
    STATUS current
    DESCRIPTION "statistics value: average, minimum, maximum and instant value for bit error rate post fec"
::= { bitErrorRatePostFec 1 }
bitErrorRatePostFecEntry OBJECT-TYPE
    SYNTAX BitErrorRatePostFecEntry
    MAX-ACCESS not-accessible
    STATUS current
    DESCRIPTION "Entry of bitErrorRatePostFecTable" 
    INDEX { shelfId,slotId,subslotId,portId,subportId }
::= { bitErrorRatePostFecTable 1 }
BitErrorRatePostFecEntry ::= 
SEQUENCE {
	bitErrorRatePostFecInstant OCTET STRING,
	bitErrorRatePostFecAvg OCTET STRING,
	bitErrorRatePostFecMin OCTET STRING,
	bitErrorRatePostFecMax OCTET STRING
    }
bitErrorRatePostFecInstant OBJECT-TYPE
    SYNTAX OCTET STRING 
    MAX-ACCESS read-only
    STATUS current
    DESCRIPTION "the instant value of statistics counter
		
		UNITS:bit-ratio
		"
::= { bitErrorRatePostFecEntry 1 }
bitErrorRatePostFecAvg OBJECT-TYPE
    SYNTAX OCTET STRING 
    MAX-ACCESS read-only
    STATUS current
    DESCRIPTION "the average value of statistics counter
		
		UNITS:bit-ratio
		"
::= { bitErrorRatePostFecEntry 2 }
bitErrorRatePostFecMin OBJECT-TYPE
    SYNTAX OCTET STRING 
    MAX-ACCESS read-only
    STATUS current
    DESCRIPTION "the minimum value of statistics counter
		
		UNITS:bit-ratio
		"
::= { bitErrorRatePostFecEntry 3 }
bitErrorRatePostFecMax OBJECT-TYPE
    SYNTAX OCTET STRING 
    MAX-ACCESS read-only
    STATUS current
    DESCRIPTION "the maximum value of statistics counter
		
		UNITS:bit-ratio
		"
::= { bitErrorRatePostFecEntry 4 }
inUtilization OBJECT IDENTIFIER ::= { common 3 }
inUtilizationTable OBJECT-TYPE
    SYNTAX SEQUENCE OF InUtilizationEntry
    MAX-ACCESS not-accessible
    STATUS current
    DESCRIPTION "statistics value: average, minimum, maximum and instant value for RX utilization"
::= { inUtilization 1 }
inUtilizationEntry OBJECT-TYPE
    SYNTAX InUtilizationEntry
    MAX-ACCESS not-accessible
    STATUS current
    DESCRIPTION "Entry of inUtilizationTable" 
    INDEX { shelfId,slotId,subslotId,portId,subportId }
::= { inUtilizationTable 1 }
InUtilizationEntry ::= 
SEQUENCE {
	inUtilizationInstant CoriantTypesPercentage,
	inUtilizationAvg CoriantTypesPercentage,
	inUtilizationMin CoriantTypesPercentage,
	inUtilizationMax CoriantTypesPercentage
    }
inUtilizationInstant OBJECT-TYPE
    SYNTAX CoriantTypesPercentage 
    MAX-ACCESS read-only
    STATUS current
    DESCRIPTION "the instant value of statistics counter
		
		
		"
::= { inUtilizationEntry 1 }
inUtilizationAvg OBJECT-TYPE
    SYNTAX CoriantTypesPercentage 
    MAX-ACCESS read-only
    STATUS current
    DESCRIPTION "the average value of statistics counter
		
		
		"
::= { inUtilizationEntry 2 }
inUtilizationMin OBJECT-TYPE
    SYNTAX CoriantTypesPercentage 
    MAX-ACCESS read-only
    STATUS current
    DESCRIPTION "the minimum value of statistics counter
		
		
		"
::= { inUtilizationEntry 3 }
inUtilizationMax OBJECT-TYPE
    SYNTAX CoriantTypesPercentage 
    MAX-ACCESS read-only
    STATUS current
    DESCRIPTION "the maximum value of statistics counter
		
		
		"
::= { inUtilizationEntry 4 }
outUtilization OBJECT IDENTIFIER ::= { common 4 }
outUtilizationTable OBJECT-TYPE
    SYNTAX SEQUENCE OF OutUtilizationEntry
    MAX-ACCESS not-accessible
    STATUS current
    DESCRIPTION "statistics value: average, minimum, maximum and instant value for TX utilization"
::= { outUtilization 1 }
outUtilizationEntry OBJECT-TYPE
    SYNTAX OutUtilizationEntry
    MAX-ACCESS not-accessible
    STATUS current
    DESCRIPTION "Entry of outUtilizationTable" 
    INDEX { shelfId,slotId,subslotId,portId,subportId }
::= { outUtilizationTable 1 }
OutUtilizationEntry ::= 
SEQUENCE {
	outUtilizationInstant CoriantTypesPercentage,
	outUtilizationAvg CoriantTypesPercentage,
	outUtilizationMin CoriantTypesPercentage,
	outUtilizationMax CoriantTypesPercentage
    }
outUtilizationInstant OBJECT-TYPE
    SYNTAX CoriantTypesPercentage 
    MAX-ACCESS read-only
    STATUS current
    DESCRIPTION "the instant value of statistics counter
		
		
		"
::= { outUtilizationEntry 1 }
outUtilizationAvg OBJECT-TYPE
    SYNTAX CoriantTypesPercentage 
    MAX-ACCESS read-only
    STATUS current
    DESCRIPTION "the average value of statistics counter
		
		
		"
::= { outUtilizationEntry 2 }
outUtilizationMin OBJECT-TYPE
    SYNTAX CoriantTypesPercentage 
    MAX-ACCESS read-only
    STATUS current
    DESCRIPTION "the minimum value of statistics counter
		
		
		"
::= { outUtilizationEntry 3 }
outUtilizationMax OBJECT-TYPE
    SYNTAX CoriantTypesPercentage 
    MAX-ACCESS read-only
    STATUS current
    DESCRIPTION "the maximum value of statistics counter
		
		
		"
::= { outUtilizationEntry 4 }
oduDelay OBJECT IDENTIFIER ::= { common 23 }
oduDelayTable OBJECT-TYPE
    SYNTAX SEQUENCE OF OduDelayEntry
    MAX-ACCESS not-accessible
    STATUS current
    DESCRIPTION "statistics value: average, minimum, maximum and instant value for measured odu signal delay"
::= { oduDelay 1 }
oduDelayEntry OBJECT-TYPE
    SYNTAX OduDelayEntry
    MAX-ACCESS not-accessible
    STATUS current
    DESCRIPTION "Entry of oduDelayTable" 
    INDEX { shelfId,slotId,subslotId,portId,subportId,odutypeL1,oduidL1,odutypeL2,oduidL2,odutypeL3,oduidL3,odutypeL4,oduidL4 }
::= { oduDelayTable 1 }
OduDelayEntry ::= 
SEQUENCE {
	oduDelayInstant OCTET STRING,
	oduDelayAvg OCTET STRING,
	oduDelayMin OCTET STRING,
	oduDelayMax OCTET STRING
    }
oduDelayInstant OBJECT-TYPE
    SYNTAX OCTET STRING 
    MAX-ACCESS read-only
    STATUS current
    DESCRIPTION "the instant value of statistics counter
		
		UNITS:microseconds
		"
::= { oduDelayEntry 1 }
oduDelayAvg OBJECT-TYPE
    SYNTAX OCTET STRING 
    MAX-ACCESS read-only
    STATUS current
    DESCRIPTION "the average value of statistics counter
		
		UNITS:microseconds
		"
::= { oduDelayEntry 2 }
oduDelayMin OBJECT-TYPE
    SYNTAX OCTET STRING 
    MAX-ACCESS read-only
    STATUS current
    DESCRIPTION "the minimum value of statistics counter
		
		UNITS:microseconds
		"
::= { oduDelayEntry 3 }
oduDelayMax OBJECT-TYPE
    SYNTAX OCTET STRING 
    MAX-ACCESS read-only
    STATUS current
    DESCRIPTION "the maximum value of statistics counter
		
		UNITS:microseconds
		"
::= { oduDelayEntry 4 }
inOpticalPower OBJECT IDENTIFIER ::= { common 24 }
inOpticalPowerTable OBJECT-TYPE
    SYNTAX SEQUENCE OF InOpticalPowerEntry
    MAX-ACCESS not-accessible
    STATUS current
    DESCRIPTION "statistics value: average, minimum, maximum and instant value for RX optical power"
::= { inOpticalPower 1 }
inOpticalPowerEntry OBJECT-TYPE
    SYNTAX InOpticalPowerEntry
    MAX-ACCESS not-accessible
    STATUS current
    DESCRIPTION "Entry of inOpticalPowerTable" 
    INDEX { shelfId,slotId,subslotId,portId,subportId,omsName,oscName,goptName }
::= { inOpticalPowerTable 1 }
InOpticalPowerEntry ::= 
SEQUENCE {
	inOpticalPowerInstant CoriantTypesOpticalPower,
	inOpticalPowerAvg CoriantTypesOpticalPower,
	inOpticalPowerMin CoriantTypesOpticalPower,
	inOpticalPowerMax CoriantTypesOpticalPower
    }
inOpticalPowerInstant OBJECT-TYPE
    SYNTAX CoriantTypesOpticalPower 
    MAX-ACCESS read-only
    STATUS current
    DESCRIPTION "the instant value of statistics counter
		
		
		"
::= { inOpticalPowerEntry 1 }
inOpticalPowerAvg OBJECT-TYPE
    SYNTAX CoriantTypesOpticalPower 
    MAX-ACCESS read-only
    STATUS current
    DESCRIPTION "the average value of statistics counter
		
		
		"
::= { inOpticalPowerEntry 2 }
inOpticalPowerMin OBJECT-TYPE
    SYNTAX CoriantTypesOpticalPower 
    MAX-ACCESS read-only
    STATUS current
    DESCRIPTION "the minimum value of statistics counter
		
		
		"
::= { inOpticalPowerEntry 3 }
inOpticalPowerMax OBJECT-TYPE
    SYNTAX CoriantTypesOpticalPower 
    MAX-ACCESS read-only
    STATUS current
    DESCRIPTION "the maximum value of statistics counter
		
		
		"
::= { inOpticalPowerEntry 4 }
outOpticalPower OBJECT IDENTIFIER ::= { common 25 }
outOpticalPowerTable OBJECT-TYPE
    SYNTAX SEQUENCE OF OutOpticalPowerEntry
    MAX-ACCESS not-accessible
    STATUS current
    DESCRIPTION "statistics value: average, minimum, maximum and instant value for TX optical power"
::= { outOpticalPower 1 }
outOpticalPowerEntry OBJECT-TYPE
    SYNTAX OutOpticalPowerEntry
    MAX-ACCESS not-accessible
    STATUS current
    DESCRIPTION "Entry of outOpticalPowerTable" 
    INDEX { shelfId,slotId,subslotId,portId,subportId,omsName,oscName,goptName }
::= { outOpticalPowerTable 1 }
OutOpticalPowerEntry ::= 
SEQUENCE {
	outOpticalPowerInstant CoriantTypesOpticalPower,
	outOpticalPowerAvg CoriantTypesOpticalPower,
	outOpticalPowerMin CoriantTypesOpticalPower,
	outOpticalPowerMax CoriantTypesOpticalPower
    }
outOpticalPowerInstant OBJECT-TYPE
    SYNTAX CoriantTypesOpticalPower 
    MAX-ACCESS read-only
    STATUS current
    DESCRIPTION "the instant value of statistics counter
		
		
		"
::= { outOpticalPowerEntry 1 }
outOpticalPowerAvg OBJECT-TYPE
    SYNTAX CoriantTypesOpticalPower 
    MAX-ACCESS read-only
    STATUS current
    DESCRIPTION "the average value of statistics counter
		
		
		"
::= { outOpticalPowerEntry 2 }
outOpticalPowerMin OBJECT-TYPE
    SYNTAX CoriantTypesOpticalPower 
    MAX-ACCESS read-only
    STATUS current
    DESCRIPTION "the minimum value of statistics counter
		
		
		"
::= { outOpticalPowerEntry 3 }
outOpticalPowerMax OBJECT-TYPE
    SYNTAX CoriantTypesOpticalPower 
    MAX-ACCESS read-only
    STATUS current
    DESCRIPTION "the maximum value of statistics counter
		
		
		"
::= { outOpticalPowerEntry 4 }
differentialGroupDelay OBJECT IDENTIFIER ::= { common 26 }
differentialGroupDelayTable OBJECT-TYPE
    SYNTAX SEQUENCE OF DifferentialGroupDelayEntry
    MAX-ACCESS not-accessible
    STATUS current
    DESCRIPTION "statistics value: average, minimum, maximum and instant value for differential group delay"
::= { differentialGroupDelay 1 }
differentialGroupDelayEntry OBJECT-TYPE
    SYNTAX DifferentialGroupDelayEntry
    MAX-ACCESS not-accessible
    STATUS current
    DESCRIPTION "Entry of differentialGroupDelayTable" 
    INDEX { shelfId,slotId,subslotId,portId }
::= { differentialGroupDelayTable 1 }
DifferentialGroupDelayEntry ::= 
SEQUENCE {
	differentialGroupDelayInstant Unsigned32,
	differentialGroupDelayAvg Unsigned32,
	differentialGroupDelayMin Unsigned32,
	differentialGroupDelayMax Unsigned32
    }
differentialGroupDelayInstant OBJECT-TYPE
    SYNTAX Unsigned32 
    MAX-ACCESS read-only
    STATUS current
    DESCRIPTION "the instant value of statistics counter
		
		UNITS:ps
		"
::= { differentialGroupDelayEntry 1 }
differentialGroupDelayAvg OBJECT-TYPE
    SYNTAX Unsigned32 
    MAX-ACCESS read-only
    STATUS current
    DESCRIPTION "the average value of statistics counter
		
		UNITS:ps
		"
::= { differentialGroupDelayEntry 2 }
differentialGroupDelayMin OBJECT-TYPE
    SYNTAX Unsigned32 
    MAX-ACCESS read-only
    STATUS current
    DESCRIPTION "the minimum value of statistics counter
		
		UNITS:ps
		"
::= { differentialGroupDelayEntry 3 }
differentialGroupDelayMax OBJECT-TYPE
    SYNTAX Unsigned32 
    MAX-ACCESS read-only
    STATUS current
    DESCRIPTION "the maximum value of statistics counter
		
		UNITS:ps
		"
::= { differentialGroupDelayEntry 4 }
chromaticDispersion OBJECT IDENTIFIER ::= { common 27 }
chromaticDispersionTable OBJECT-TYPE
    SYNTAX SEQUENCE OF ChromaticDispersionEntry
    MAX-ACCESS not-accessible
    STATUS current
    DESCRIPTION "statistics value: average, minimum, maximum and instant value for chromatic dispersion"
::= { chromaticDispersion 1 }
chromaticDispersionEntry OBJECT-TYPE
    SYNTAX ChromaticDispersionEntry
    MAX-ACCESS not-accessible
    STATUS current
    DESCRIPTION "Entry of chromaticDispersionTable" 
    INDEX { shelfId,slotId,subslotId,portId }
::= { chromaticDispersionTable 1 }
ChromaticDispersionEntry ::= 
SEQUENCE {
	chromaticDispersionInstant INTEGER,
	chromaticDispersionAvg INTEGER,
	chromaticDispersionMin INTEGER,
	chromaticDispersionMax INTEGER
    }
chromaticDispersionInstant OBJECT-TYPE
    SYNTAX INTEGER 
    MAX-ACCESS read-only
    STATUS current
    DESCRIPTION "the instant value of statistics counter
		
		UNITS:ps/nm
		"
::= { chromaticDispersionEntry 1 }
chromaticDispersionAvg OBJECT-TYPE
    SYNTAX INTEGER 
    MAX-ACCESS read-only
    STATUS current
    DESCRIPTION "the average value of statistics counter
		
		UNITS:ps/pm
		"
::= { chromaticDispersionEntry 2 }
chromaticDispersionMin OBJECT-TYPE
    SYNTAX INTEGER 
    MAX-ACCESS read-only
    STATUS current
    DESCRIPTION "the minimum value of statistics counter
		
		UNITS:ps/pm
		"
::= { chromaticDispersionEntry 3 }
chromaticDispersionMax OBJECT-TYPE
    SYNTAX INTEGER 
    MAX-ACCESS read-only
    STATUS current
    DESCRIPTION "the maximum value of statistics counter
		
		UNITS:ps/pm
		"
::= { chromaticDispersionEntry 4 }
osnr OBJECT IDENTIFIER ::= { common 28 }
osnrTable OBJECT-TYPE
    SYNTAX SEQUENCE OF OsnrEntry
    MAX-ACCESS not-accessible
    STATUS current
    DESCRIPTION "statistics value: average, minimum, maximum and instant value for osnr"
::= { osnr 1 }
osnrEntry OBJECT-TYPE
    SYNTAX OsnrEntry
    MAX-ACCESS not-accessible
    STATUS current
    DESCRIPTION "Entry of osnrTable" 
    INDEX { shelfId,slotId,subslotId,portId }
::= { osnrTable 1 }
OsnrEntry ::= 
SEQUENCE {
	osnrInstant CoriantTypesDBPrecision1,
	osnrAvg CoriantTypesDBPrecision1,
	osnrMin CoriantTypesDBPrecision1,
	osnrMax CoriantTypesDBPrecision1
    }
osnrInstant OBJECT-TYPE
    SYNTAX CoriantTypesDBPrecision1 
    MAX-ACCESS read-only
    STATUS current
    DESCRIPTION "the instant value of statistics counter
		
		
		"
::= { osnrEntry 1 }
osnrAvg OBJECT-TYPE
    SYNTAX CoriantTypesDBPrecision1 
    MAX-ACCESS read-only
    STATUS current
    DESCRIPTION "the average value of statistics counter
		
		
		"
::= { osnrEntry 2 }
osnrMin OBJECT-TYPE
    SYNTAX CoriantTypesDBPrecision1 
    MAX-ACCESS read-only
    STATUS current
    DESCRIPTION "the minimum value of statistics counter
		
		
		"
::= { osnrEntry 3 }
osnrMax OBJECT-TYPE
    SYNTAX CoriantTypesDBPrecision1 
    MAX-ACCESS read-only
    STATUS current
    DESCRIPTION "the maximum value of statistics counter
		
		
		"
::= { osnrEntry 4 }
qFactor OBJECT IDENTIFIER ::= { common 29 }
qFactorTable OBJECT-TYPE
    SYNTAX SEQUENCE OF QFactorEntry
    MAX-ACCESS not-accessible
    STATUS current
    DESCRIPTION "statistics value: average, minimum, maximum and instant value for q-factor"
::= { qFactor 1 }
qFactorEntry OBJECT-TYPE
    SYNTAX QFactorEntry
    MAX-ACCESS not-accessible
    STATUS current
    DESCRIPTION "Entry of qFactorTable" 
    INDEX { shelfId,slotId,subslotId,portId }
::= { qFactorTable 1 }
QFactorEntry ::= 
SEQUENCE {
	qFactorInstant CoriantTypesDBPrecision1,
	qFactorAvg CoriantTypesDBPrecision1,
	qFactorMin CoriantTypesDBPrecision1,
	qFactorMax CoriantTypesDBPrecision1
    }
qFactorInstant OBJECT-TYPE
    SYNTAX CoriantTypesDBPrecision1 
    MAX-ACCESS read-only
    STATUS current
    DESCRIPTION "the instant value of statistics counter
		
		
		"
::= { qFactorEntry 1 }
qFactorAvg OBJECT-TYPE
    SYNTAX CoriantTypesDBPrecision1 
    MAX-ACCESS read-only
    STATUS current
    DESCRIPTION "the average value of statistics counter
		
		
		"
::= { qFactorEntry 2 }
qFactorMin OBJECT-TYPE
    SYNTAX CoriantTypesDBPrecision1 
    MAX-ACCESS read-only
    STATUS current
    DESCRIPTION "the minimum value of statistics counter
		
		
		"
::= { qFactorEntry 3 }
qFactorMax OBJECT-TYPE
    SYNTAX CoriantTypesDBPrecision1 
    MAX-ACCESS read-only
    STATUS current
    DESCRIPTION "the maximum value of statistics counter
		
		
		"
::= { qFactorEntry 4 }
polarizationDependentLoss OBJECT IDENTIFIER ::= { common 30 }
polarizationDependentLossTable OBJECT-TYPE
    SYNTAX SEQUENCE OF PolarizationDependentLossEntry
    MAX-ACCESS not-accessible
    STATUS current
    DESCRIPTION "statistics value: average, minimum, maximum and instant value for polarization dependent loss"
::= { polarizationDependentLoss 1 }
polarizationDependentLossEntry OBJECT-TYPE
    SYNTAX PolarizationDependentLossEntry
    MAX-ACCESS not-accessible
    STATUS current
    DESCRIPTION "Entry of polarizationDependentLossTable" 
    INDEX { shelfId,slotId,subslotId,portId }
::= { polarizationDependentLossTable 1 }
PolarizationDependentLossEntry ::= 
SEQUENCE {
	polarizationDependentLossInstant CoriantTypesDBPrecision1,
	polarizationDependentLossAvg CoriantTypesDBPrecision1,
	polarizationDependentLossMin CoriantTypesDBPrecision1,
	polarizationDependentLossMax CoriantTypesDBPrecision1
    }
polarizationDependentLossInstant OBJECT-TYPE
    SYNTAX CoriantTypesDBPrecision1 
    MAX-ACCESS read-only
    STATUS current
    DESCRIPTION "the instant value of statistics counter
		
		
		"
::= { polarizationDependentLossEntry 1 }
polarizationDependentLossAvg OBJECT-TYPE
    SYNTAX CoriantTypesDBPrecision1 
    MAX-ACCESS read-only
    STATUS current
    DESCRIPTION "the average value of statistics counter
		
		
		"
::= { polarizationDependentLossEntry 2 }
polarizationDependentLossMin OBJECT-TYPE
    SYNTAX CoriantTypesDBPrecision1 
    MAX-ACCESS read-only
    STATUS current
    DESCRIPTION "the minimum value of statistics counter
		
		
		"
::= { polarizationDependentLossEntry 3 }
polarizationDependentLossMax OBJECT-TYPE
    SYNTAX CoriantTypesDBPrecision1 
    MAX-ACCESS read-only
    STATUS current
    DESCRIPTION "the maximum value of statistics counter
		
		
		"
::= { polarizationDependentLossEntry 4 }
inOpticalFrequency OBJECT IDENTIFIER ::= { common 31 }
inOpticalFrequencyTable OBJECT-TYPE
    SYNTAX SEQUENCE OF InOpticalFrequencyEntry
    MAX-ACCESS not-accessible
    STATUS current
    DESCRIPTION "statistics value: average, minimum, maximum and instant value for RX optical frequency"
::= { inOpticalFrequency 1 }
inOpticalFrequencyEntry OBJECT-TYPE
    SYNTAX InOpticalFrequencyEntry
    MAX-ACCESS not-accessible
    STATUS current
    DESCRIPTION "Entry of inOpticalFrequencyTable" 
    INDEX { shelfId,slotId,subslotId,portId }
::= { inOpticalFrequencyTable 1 }
InOpticalFrequencyEntry ::= 
SEQUENCE {
	inOpticalFrequencyInstant Unsigned32,
	inOpticalFrequencyAvg Unsigned32,
	inOpticalFrequencyMin Unsigned32,
	inOpticalFrequencyMax Unsigned32
    }
inOpticalFrequencyInstant OBJECT-TYPE
    SYNTAX Unsigned32 
    MAX-ACCESS read-only
    STATUS current
    DESCRIPTION "the instant value of statistics counter
		
		UNITS:MHz
		"
::= { inOpticalFrequencyEntry 1 }
inOpticalFrequencyAvg OBJECT-TYPE
    SYNTAX Unsigned32 
    MAX-ACCESS read-only
    STATUS current
    DESCRIPTION "the average value of statistics counter
		
		UNITS:MHz
		"
::= { inOpticalFrequencyEntry 2 }
inOpticalFrequencyMin OBJECT-TYPE
    SYNTAX Unsigned32 
    MAX-ACCESS read-only
    STATUS current
    DESCRIPTION "the minimum value of statistics counter
		
		UNITS:MHz
		"
::= { inOpticalFrequencyEntry 3 }
inOpticalFrequencyMax OBJECT-TYPE
    SYNTAX Unsigned32 
    MAX-ACCESS read-only
    STATUS current
    DESCRIPTION "the maximum value of statistics counter
		
		UNITS:MHz
		"
::= { inOpticalFrequencyEntry 4 }
outOpticalFrequency OBJECT IDENTIFIER ::= { common 32 }
outOpticalFrequencyTable OBJECT-TYPE
    SYNTAX SEQUENCE OF OutOpticalFrequencyEntry
    MAX-ACCESS not-accessible
    STATUS current
    DESCRIPTION "statistics value: average, minimum, maximum and instant value for TX optical frequency"
::= { outOpticalFrequency 1 }
outOpticalFrequencyEntry OBJECT-TYPE
    SYNTAX OutOpticalFrequencyEntry
    MAX-ACCESS not-accessible
    STATUS current
    DESCRIPTION "Entry of outOpticalFrequencyTable" 
    INDEX { shelfId,slotId,subslotId,portId }
::= { outOpticalFrequencyTable 1 }
OutOpticalFrequencyEntry ::= 
SEQUENCE {
	outOpticalFrequencyInstant Unsigned32,
	outOpticalFrequencyAvg Unsigned32,
	outOpticalFrequencyMin Unsigned32,
	outOpticalFrequencyMax Unsigned32
    }
outOpticalFrequencyInstant OBJECT-TYPE
    SYNTAX Unsigned32 
    MAX-ACCESS read-only
    STATUS current
    DESCRIPTION "the instant value of statistics counter
		
		UNITS:MHz
		"
::= { outOpticalFrequencyEntry 1 }
outOpticalFrequencyAvg OBJECT-TYPE
    SYNTAX Unsigned32 
    MAX-ACCESS read-only
    STATUS current
    DESCRIPTION "the average value of statistics counter
		
		UNITS:MHz
		"
::= { outOpticalFrequencyEntry 2 }
outOpticalFrequencyMin OBJECT-TYPE
    SYNTAX Unsigned32 
    MAX-ACCESS read-only
    STATUS current
    DESCRIPTION "the minimum value of statistics counter
		
		UNITS:MHz
		"
::= { outOpticalFrequencyEntry 3 }
outOpticalFrequencyMax OBJECT-TYPE
    SYNTAX Unsigned32 
    MAX-ACCESS read-only
    STATUS current
    DESCRIPTION "the maximum value of statistics counter
		
		UNITS:MHz
		"
::= { outOpticalFrequencyEntry 4 }
inOpticalPowerLaneHigh OBJECT IDENTIFIER ::= { common 33 }
inOpticalPowerLaneHighTable OBJECT-TYPE
    SYNTAX SEQUENCE OF InOpticalPowerLaneHighEntry
    MAX-ACCESS not-accessible
    STATUS current
    DESCRIPTION "statistics value: average, minimum, maximum and instant value for highest value of RX lane optical power"
::= { inOpticalPowerLaneHigh 1 }
inOpticalPowerLaneHighEntry OBJECT-TYPE
    SYNTAX InOpticalPowerLaneHighEntry
    MAX-ACCESS not-accessible
    STATUS current
    DESCRIPTION "Entry of inOpticalPowerLaneHighTable" 
    INDEX { shelfId,slotId,subslotId,portId }
::= { inOpticalPowerLaneHighTable 1 }
InOpticalPowerLaneHighEntry ::= 
SEQUENCE {
	inOpticalPowerLaneHighInstant CoriantTypesOpticalPower,
	inOpticalPowerLaneHighAvg CoriantTypesOpticalPower,
	inOpticalPowerLaneHighMin CoriantTypesOpticalPower,
	inOpticalPowerLaneHighMax CoriantTypesOpticalPower
    }
inOpticalPowerLaneHighInstant OBJECT-TYPE
    SYNTAX CoriantTypesOpticalPower 
    MAX-ACCESS read-only
    STATUS current
    DESCRIPTION "the instant value of statistics counter
		
		
		"
::= { inOpticalPowerLaneHighEntry 1 }
inOpticalPowerLaneHighAvg OBJECT-TYPE
    SYNTAX CoriantTypesOpticalPower 
    MAX-ACCESS read-only
    STATUS current
    DESCRIPTION "the average value of statistics counter
		
		
		"
::= { inOpticalPowerLaneHighEntry 2 }
inOpticalPowerLaneHighMin OBJECT-TYPE
    SYNTAX CoriantTypesOpticalPower 
    MAX-ACCESS read-only
    STATUS current
    DESCRIPTION "the minimum value of statistics counter
		
		
		"
::= { inOpticalPowerLaneHighEntry 3 }
inOpticalPowerLaneHighMax OBJECT-TYPE
    SYNTAX CoriantTypesOpticalPower 
    MAX-ACCESS read-only
    STATUS current
    DESCRIPTION "the maximum value of statistics counter
		
		
		"
::= { inOpticalPowerLaneHighEntry 4 }
inOpticalPowerLaneLow OBJECT IDENTIFIER ::= { common 34 }
inOpticalPowerLaneLowTable OBJECT-TYPE
    SYNTAX SEQUENCE OF InOpticalPowerLaneLowEntry
    MAX-ACCESS not-accessible
    STATUS current
    DESCRIPTION "statistics value: average, minimum, maximum and instant value for lowest value of RX lane optical power"
::= { inOpticalPowerLaneLow 1 }
inOpticalPowerLaneLowEntry OBJECT-TYPE
    SYNTAX InOpticalPowerLaneLowEntry
    MAX-ACCESS not-accessible
    STATUS current
    DESCRIPTION "Entry of inOpticalPowerLaneLowTable" 
    INDEX { shelfId,slotId,subslotId,portId }
::= { inOpticalPowerLaneLowTable 1 }
InOpticalPowerLaneLowEntry ::= 
SEQUENCE {
	inOpticalPowerLaneLowInstant CoriantTypesOpticalPower,
	inOpticalPowerLaneLowAvg CoriantTypesOpticalPower,
	inOpticalPowerLaneLowMin CoriantTypesOpticalPower,
	inOpticalPowerLaneLowMax CoriantTypesOpticalPower
    }
inOpticalPowerLaneLowInstant OBJECT-TYPE
    SYNTAX CoriantTypesOpticalPower 
    MAX-ACCESS read-only
    STATUS current
    DESCRIPTION "the instant value of statistics counter
		
		
		"
::= { inOpticalPowerLaneLowEntry 1 }
inOpticalPowerLaneLowAvg OBJECT-TYPE
    SYNTAX CoriantTypesOpticalPower 
    MAX-ACCESS read-only
    STATUS current
    DESCRIPTION "the average value of statistics counter
		
		
		"
::= { inOpticalPowerLaneLowEntry 2 }
inOpticalPowerLaneLowMin OBJECT-TYPE
    SYNTAX CoriantTypesOpticalPower 
    MAX-ACCESS read-only
    STATUS current
    DESCRIPTION "the minimum value of statistics counter
		
		
		"
::= { inOpticalPowerLaneLowEntry 3 }
inOpticalPowerLaneLowMax OBJECT-TYPE
    SYNTAX CoriantTypesOpticalPower 
    MAX-ACCESS read-only
    STATUS current
    DESCRIPTION "the maximum value of statistics counter
		
		
		"
::= { inOpticalPowerLaneLowEntry 4 }
inOpticalPowerLaneTotal OBJECT IDENTIFIER ::= { common 35 }
inOpticalPowerLaneTotalTable OBJECT-TYPE
    SYNTAX SEQUENCE OF InOpticalPowerLaneTotalEntry
    MAX-ACCESS not-accessible
    STATUS current
    DESCRIPTION "statistics value: average, minimum, maximum and instant value for total value of RX lane optical power"
::= { inOpticalPowerLaneTotal 1 }
inOpticalPowerLaneTotalEntry OBJECT-TYPE
    SYNTAX InOpticalPowerLaneTotalEntry
    MAX-ACCESS not-accessible
    STATUS current
    DESCRIPTION "Entry of inOpticalPowerLaneTotalTable" 
    INDEX { shelfId,slotId,subslotId,portId }
::= { inOpticalPowerLaneTotalTable 1 }
InOpticalPowerLaneTotalEntry ::= 
SEQUENCE {
	inOpticalPowerLaneTotalInstant CoriantTypesOpticalPower,
	inOpticalPowerLaneTotalAvg CoriantTypesOpticalPower,
	inOpticalPowerLaneTotalMin CoriantTypesOpticalPower,
	inOpticalPowerLaneTotalMax CoriantTypesOpticalPower
    }
inOpticalPowerLaneTotalInstant OBJECT-TYPE
    SYNTAX CoriantTypesOpticalPower 
    MAX-ACCESS read-only
    STATUS current
    DESCRIPTION "the instant value of statistics counter
		
		
		"
::= { inOpticalPowerLaneTotalEntry 1 }
inOpticalPowerLaneTotalAvg OBJECT-TYPE
    SYNTAX CoriantTypesOpticalPower 
    MAX-ACCESS read-only
    STATUS current
    DESCRIPTION "the average value of statistics counter
		
		
		"
::= { inOpticalPowerLaneTotalEntry 2 }
inOpticalPowerLaneTotalMin OBJECT-TYPE
    SYNTAX CoriantTypesOpticalPower 
    MAX-ACCESS read-only
    STATUS current
    DESCRIPTION "the minimum value of statistics counter
		
		
		"
::= { inOpticalPowerLaneTotalEntry 3 }
inOpticalPowerLaneTotalMax OBJECT-TYPE
    SYNTAX CoriantTypesOpticalPower 
    MAX-ACCESS read-only
    STATUS current
    DESCRIPTION "the maximum value of statistics counter
		
		
		"
::= { inOpticalPowerLaneTotalEntry 4 }
outOpticalPowerLaneHigh OBJECT IDENTIFIER ::= { common 36 }
outOpticalPowerLaneHighTable OBJECT-TYPE
    SYNTAX SEQUENCE OF OutOpticalPowerLaneHighEntry
    MAX-ACCESS not-accessible
    STATUS current
    DESCRIPTION "statistics value: average, minimum, maximum and instant value for highest value of TX lane optical power"
::= { outOpticalPowerLaneHigh 1 }
outOpticalPowerLaneHighEntry OBJECT-TYPE
    SYNTAX OutOpticalPowerLaneHighEntry
    MAX-ACCESS not-accessible
    STATUS current
    DESCRIPTION "Entry of outOpticalPowerLaneHighTable" 
    INDEX { shelfId,slotId,subslotId,portId }
::= { outOpticalPowerLaneHighTable 1 }
OutOpticalPowerLaneHighEntry ::= 
SEQUENCE {
	outOpticalPowerLaneHighInstant CoriantTypesOpticalPower,
	outOpticalPowerLaneHighAvg CoriantTypesOpticalPower,
	outOpticalPowerLaneHighMin CoriantTypesOpticalPower,
	outOpticalPowerLaneHighMax CoriantTypesOpticalPower
    }
outOpticalPowerLaneHighInstant OBJECT-TYPE
    SYNTAX CoriantTypesOpticalPower 
    MAX-ACCESS read-only
    STATUS current
    DESCRIPTION "the instant value of statistics counter
		
		
		"
::= { outOpticalPowerLaneHighEntry 1 }
outOpticalPowerLaneHighAvg OBJECT-TYPE
    SYNTAX CoriantTypesOpticalPower 
    MAX-ACCESS read-only
    STATUS current
    DESCRIPTION "the average value of statistics counter
		
		
		"
::= { outOpticalPowerLaneHighEntry 2 }
outOpticalPowerLaneHighMin OBJECT-TYPE
    SYNTAX CoriantTypesOpticalPower 
    MAX-ACCESS read-only
    STATUS current
    DESCRIPTION "the minimum value of statistics counter
		
		
		"
::= { outOpticalPowerLaneHighEntry 3 }
outOpticalPowerLaneHighMax OBJECT-TYPE
    SYNTAX CoriantTypesOpticalPower 
    MAX-ACCESS read-only
    STATUS current
    DESCRIPTION "the maximum value of statistics counter
		
		
		"
::= { outOpticalPowerLaneHighEntry 4 }
outOpticalPowerLaneLow OBJECT IDENTIFIER ::= { common 37 }
outOpticalPowerLaneLowTable OBJECT-TYPE
    SYNTAX SEQUENCE OF OutOpticalPowerLaneLowEntry
    MAX-ACCESS not-accessible
    STATUS current
    DESCRIPTION "statistics value: average, minimum, maximum and instant value for lowest value of TX lane optical power"
::= { outOpticalPowerLaneLow 1 }
outOpticalPowerLaneLowEntry OBJECT-TYPE
    SYNTAX OutOpticalPowerLaneLowEntry
    MAX-ACCESS not-accessible
    STATUS current
    DESCRIPTION "Entry of outOpticalPowerLaneLowTable" 
    INDEX { shelfId,slotId,subslotId,portId }
::= { outOpticalPowerLaneLowTable 1 }
OutOpticalPowerLaneLowEntry ::= 
SEQUENCE {
	outOpticalPowerLaneLowInstant CoriantTypesOpticalPower,
	outOpticalPowerLaneLowAvg CoriantTypesOpticalPower,
	outOpticalPowerLaneLowMin CoriantTypesOpticalPower,
	outOpticalPowerLaneLowMax CoriantTypesOpticalPower
    }
outOpticalPowerLaneLowInstant OBJECT-TYPE
    SYNTAX CoriantTypesOpticalPower 
    MAX-ACCESS read-only
    STATUS current
    DESCRIPTION "the instant value of statistics counter
		
		
		"
::= { outOpticalPowerLaneLowEntry 1 }
outOpticalPowerLaneLowAvg OBJECT-TYPE
    SYNTAX CoriantTypesOpticalPower 
    MAX-ACCESS read-only
    STATUS current
    DESCRIPTION "the average value of statistics counter
		
		
		"
::= { outOpticalPowerLaneLowEntry 2 }
outOpticalPowerLaneLowMin OBJECT-TYPE
    SYNTAX CoriantTypesOpticalPower 
    MAX-ACCESS read-only
    STATUS current
    DESCRIPTION "the minimum value of statistics counter
		
		
		"
::= { outOpticalPowerLaneLowEntry 3 }
outOpticalPowerLaneLowMax OBJECT-TYPE
    SYNTAX CoriantTypesOpticalPower 
    MAX-ACCESS read-only
    STATUS current
    DESCRIPTION "the maximum value of statistics counter
		
		
		"
::= { outOpticalPowerLaneLowEntry 4 }
outOpticalPowerLaneTotal OBJECT IDENTIFIER ::= { common 38 }
outOpticalPowerLaneTotalTable OBJECT-TYPE
    SYNTAX SEQUENCE OF OutOpticalPowerLaneTotalEntry
    MAX-ACCESS not-accessible
    STATUS current
    DESCRIPTION "statistics value: average, minimum, maximum and instant value for total value of TX lane optical power"
::= { outOpticalPowerLaneTotal 1 }
outOpticalPowerLaneTotalEntry OBJECT-TYPE
    SYNTAX OutOpticalPowerLaneTotalEntry
    MAX-ACCESS not-accessible
    STATUS current
    DESCRIPTION "Entry of outOpticalPowerLaneTotalTable" 
    INDEX { shelfId,slotId,subslotId,portId }
::= { outOpticalPowerLaneTotalTable 1 }
OutOpticalPowerLaneTotalEntry ::= 
SEQUENCE {
	outOpticalPowerLaneTotalInstant CoriantTypesOpticalPower,
	outOpticalPowerLaneTotalAvg CoriantTypesOpticalPower,
	outOpticalPowerLaneTotalMin CoriantTypesOpticalPower,
	outOpticalPowerLaneTotalMax CoriantTypesOpticalPower
    }
outOpticalPowerLaneTotalInstant OBJECT-TYPE
    SYNTAX CoriantTypesOpticalPower 
    MAX-ACCESS read-only
    STATUS current
    DESCRIPTION "the instant value of statistics counter
		
		
		"
::= { outOpticalPowerLaneTotalEntry 1 }
outOpticalPowerLaneTotalAvg OBJECT-TYPE
    SYNTAX CoriantTypesOpticalPower 
    MAX-ACCESS read-only
    STATUS current
    DESCRIPTION "the average value of statistics counter
		
		
		"
::= { outOpticalPowerLaneTotalEntry 2 }
outOpticalPowerLaneTotalMin OBJECT-TYPE
    SYNTAX CoriantTypesOpticalPower 
    MAX-ACCESS read-only
    STATUS current
    DESCRIPTION "the minimum value of statistics counter
		
		
		"
::= { outOpticalPowerLaneTotalEntry 3 }
outOpticalPowerLaneTotalMax OBJECT-TYPE
    SYNTAX CoriantTypesOpticalPower 
    MAX-ACCESS read-only
    STATUS current
    DESCRIPTION "the maximum value of statistics counter
		
		
		"
::= { outOpticalPowerLaneTotalEntry 4 }
moduleTemperature OBJECT IDENTIFIER ::= { common 39 }
moduleTemperatureTable OBJECT-TYPE
    SYNTAX SEQUENCE OF ModuleTemperatureEntry
    MAX-ACCESS not-accessible
    STATUS current
    DESCRIPTION "statistics value: average, minimum, maximum and instant value for module temperature"
::= { moduleTemperature 1 }
moduleTemperatureEntry OBJECT-TYPE
    SYNTAX ModuleTemperatureEntry
    MAX-ACCESS not-accessible
    STATUS current
    DESCRIPTION "Entry of moduleTemperatureTable" 
    INDEX { shelfId,slotId,subslotId }
::= { moduleTemperatureTable 1 }
ModuleTemperatureEntry ::= 
SEQUENCE {
	moduleTemperatureInstant CoriantTypesTemperaturePrecision3,
	moduleTemperatureAvg CoriantTypesTemperaturePrecision3,
	moduleTemperatureMin CoriantTypesTemperaturePrecision3,
	moduleTemperatureMax CoriantTypesTemperaturePrecision3
    }
moduleTemperatureInstant OBJECT-TYPE
    SYNTAX CoriantTypesTemperaturePrecision3 
    MAX-ACCESS read-only
    STATUS current
    DESCRIPTION "the instant value of statistics counter
		
		
		"
::= { moduleTemperatureEntry 1 }
moduleTemperatureAvg OBJECT-TYPE
    SYNTAX CoriantTypesTemperaturePrecision3 
    MAX-ACCESS read-only
    STATUS current
    DESCRIPTION "the average value of statistics counter
		
		
		"
::= { moduleTemperatureEntry 2 }
moduleTemperatureMin OBJECT-TYPE
    SYNTAX CoriantTypesTemperaturePrecision3 
    MAX-ACCESS read-only
    STATUS current
    DESCRIPTION "the minimum value of statistics counter
		
		
		"
::= { moduleTemperatureEntry 3 }
moduleTemperatureMax OBJECT-TYPE
    SYNTAX CoriantTypesTemperaturePrecision3 
    MAX-ACCESS read-only
    STATUS current
    DESCRIPTION "the maximum value of statistics counter
		
		
		"
::= { moduleTemperatureEntry 4 }
inletTemperature OBJECT IDENTIFIER ::= { common 40 }
inletTemperatureTable OBJECT-TYPE
    SYNTAX SEQUENCE OF InletTemperatureEntry
    MAX-ACCESS not-accessible
    STATUS current
    DESCRIPTION "statistics value: average, minimum, maximum and instant value for inlet temperature"
::= { inletTemperature 1 }
inletTemperatureEntry OBJECT-TYPE
    SYNTAX InletTemperatureEntry
    MAX-ACCESS not-accessible
    STATUS current
    DESCRIPTION "Entry of inletTemperatureTable" 
    INDEX { shelfId }
::= { inletTemperatureTable 1 }
InletTemperatureEntry ::= 
SEQUENCE {
	inletTemperatureInstant CoriantTypesTemperaturePrecision3,
	inletTemperatureAvg CoriantTypesTemperaturePrecision3,
	inletTemperatureMin CoriantTypesTemperaturePrecision3,
	inletTemperatureMax CoriantTypesTemperaturePrecision3
    }
inletTemperatureInstant OBJECT-TYPE
    SYNTAX CoriantTypesTemperaturePrecision3 
    MAX-ACCESS read-only
    STATUS current
    DESCRIPTION "the instant value of statistics counter
		
		
		"
::= { inletTemperatureEntry 1 }
inletTemperatureAvg OBJECT-TYPE
    SYNTAX CoriantTypesTemperaturePrecision3 
    MAX-ACCESS read-only
    STATUS current
    DESCRIPTION "the average value of statistics counter
		
		
		"
::= { inletTemperatureEntry 2 }
inletTemperatureMin OBJECT-TYPE
    SYNTAX CoriantTypesTemperaturePrecision3 
    MAX-ACCESS read-only
    STATUS current
    DESCRIPTION "the minimum value of statistics counter
		
		
		"
::= { inletTemperatureEntry 3 }
inletTemperatureMax OBJECT-TYPE
    SYNTAX CoriantTypesTemperaturePrecision3 
    MAX-ACCESS read-only
    STATUS current
    DESCRIPTION "the maximum value of statistics counter
		
		
		"
::= { inletTemperatureEntry 4 }
outletTemperature OBJECT IDENTIFIER ::= { common 41 }
outletTemperatureTable OBJECT-TYPE
    SYNTAX SEQUENCE OF OutletTemperatureEntry
    MAX-ACCESS not-accessible
    STATUS current
    DESCRIPTION "statistics value: average, minimum, maximum and instant value for outlet temperature"
::= { outletTemperature 1 }
outletTemperatureEntry OBJECT-TYPE
    SYNTAX OutletTemperatureEntry
    MAX-ACCESS not-accessible
    STATUS current
    DESCRIPTION "Entry of outletTemperatureTable" 
    INDEX { shelfId }
::= { outletTemperatureTable 1 }
OutletTemperatureEntry ::= 
SEQUENCE {
	outletTemperatureInstant CoriantTypesTemperaturePrecision3,
	outletTemperatureAvg CoriantTypesTemperaturePrecision3,
	outletTemperatureMin CoriantTypesTemperaturePrecision3,
	outletTemperatureMax CoriantTypesTemperaturePrecision3
    }
outletTemperatureInstant OBJECT-TYPE
    SYNTAX CoriantTypesTemperaturePrecision3 
    MAX-ACCESS read-only
    STATUS current
    DESCRIPTION "the instant value of statistics counter
		
		
		"
::= { outletTemperatureEntry 1 }
outletTemperatureAvg OBJECT-TYPE
    SYNTAX CoriantTypesTemperaturePrecision3 
    MAX-ACCESS read-only
    STATUS current
    DESCRIPTION "the average value of statistics counter
		
		
		"
::= { outletTemperatureEntry 2 }
outletTemperatureMin OBJECT-TYPE
    SYNTAX CoriantTypesTemperaturePrecision3 
    MAX-ACCESS read-only
    STATUS current
    DESCRIPTION "the minimum value of statistics counter
		
		
		"
::= { outletTemperatureEntry 3 }
outletTemperatureMax OBJECT-TYPE
    SYNTAX CoriantTypesTemperaturePrecision3 
    MAX-ACCESS read-only
    STATUS current
    DESCRIPTION "the maximum value of statistics counter
		
		
		"
::= { outletTemperatureEntry 4 }

END
