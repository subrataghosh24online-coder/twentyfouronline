DOCS-IF-MIB DEFINITIONS ::= BEGIN

  IMPORTS
     MODULE-IDENTITY,
     OBJECT-TYPE,
     Unsigned32,
     Integer32,
     Counter32,
     Counter64,
     TimeTicks,
     IpAddress,
     transmission
             FROM SNMPv2-SMI        -- [RFC2578]
     TEXTUAL-CONVENTION,
     MacAddress,
     RowStatus,
     TruthValue,
     TimeInterval,
     TimeStamp,
     StorageType
             FROM SNMPv2-TC         -- [RFC2579]
     OBJECT-GROUP,
     MODULE-COMPLIANCE
             FROM SNMPv2-CONF       -- [RFC2580]
     ifIndex, InterfaceIndexOrZero
             FROM IF-MIB            -- [RFC2863]
     InetAddressType,
     InetAddress
             FROM INET-ADDRESS-MIB  -- [RFC4001]
     IANAifType
             FROM IANAifType-MIB;   -- [IANA]

docsIfMib MODULE-IDENTITY
     LAST-UPDATED    "200605240000Z" -- May 24, 2006
     ORGANIZATION    "IETF IPCDN Working Group"
     CONTACT-INFO
         "        David Raftus
          Postal: ATI Technologies Inc.
                  340 Terry Fox Drive, Suite 202
                  Ottawa Ontario
                  Canada
          Phone:  +1 613 592 1052 ext.222
          E-mail: david.raftus@ati.com

                  Eduardo Cardona
          Postal: Cable Television Laboratories, Inc.
                  858 Coal Creek Circle
                  Louisville, CO 80027-9750
                  U.S.A.
          Phone:  Tel:    +1 303 661 9100
                  Fax:    +1 303 661 9199
          E-mail: e.cardona@cablelabs.com;mibs@cablelabs.com

          IETF IPCDN Working Group
          General Discussion: ipcdn@ietf.org
          Subscribe: http://www.ietf.org/mailman/listinfo/ipcdn
          Archive: ftp://ftp.ietf.org/ietf-mail-archive/ipcdn
          Co-chairs: Richard Woundy, Richard_Woundy@cable.comcast.com
                     Jean-Francois Mule, jf.mule@cablelabs.com"
     DESCRIPTION
         "This is the MIB Module for DOCSIS 2.0-compliant Radio
          Frequency (RF) interfaces in Cable Modems and
          Cable Modem Termination Systems.

          Copyright (C) The Internet Society (2006).  This
          version of this MIB module is part of RFC 4546; see
          the RFC itself for full legal notices."

     REVISION        "200605240000Z"
     DESCRIPTION
         "Revision of the IETF RF MIB module for DOCSIS 2.0.
          This version published as RFC 4546.
          This MIB module revision includes the following
          among others:
          Usage of ifType (205) for upstream logical channels.
          Addition of downstream and upstream utilization
          counters.
          Additional statistics per upstream interface.
          Upstream channel offline configuration mechanism.
          Added MIB support for new DOCSIS 2.0 modulation
          attributes.
          Euro-DOCSIS downstream interleave values.
          Adjustments to RFC 2670 definitions based on
          the MIB review guidelines from the IETF

          Operations and Management Area (OPS)."

     REVISION "199908190000Z"
     DESCRIPTION
         "Initial version, published as RFC 2670.
          Modified by Mike St. Johns to fix problems identified by
          the first pass of the MIB doctor.  Of special note,
          docsIfRangingResp and docsIfCmtsInsertionInterval were
          obsoleted and replaced by other objects with the same
          functionality, but with more appropriate syntax."
     ::= { transmission 127 }

-- Textual Conventions

TenthdBmV ::= TEXTUAL-CONVENTION
     DISPLAY-HINT "d-1"
     STATUS       current
     DESCRIPTION
         "This data type represents power levels that are normally
          expressed in dBmV.  Units are in tenths of a dBmV;
          for example, 5.1 dBmV will be represented as 51."
     SYNTAX       Integer32

TenthdB ::= TEXTUAL-CONVENTION
     DISPLAY-HINT "d-1"
     STATUS       current
     DESCRIPTION
         "This data type represents power levels that are normally
          expressed in dB.  Units are in tenths of a dB;
          for example, 5.1 dB will be represented as 51."
     SYNTAX       Integer32

DocsisVersion ::= TEXTUAL-CONVENTION
    STATUS          current
    DESCRIPTION
        "Indicates the DOCSIS Radio Frequency specification being
         referenced.
         'docsis10' indicates DOCSIS 1.0.
         'docsis11' indicates DOCSIS 1.1.
         'docsis20' indicates DOCSIS 2.0."
    SYNTAX        INTEGER {
         docsis10 (1),
         docsis11 (2),
         docsis20 (3)
    }

DocsisQosVersion ::= TEXTUAL-CONVENTION
    STATUS          current
    DESCRIPTION
        "Indicates the referenced quality-of-service
         level.
         'docsis10 refers to DOCSIS 1.0 Class of
         Service queuing services, and 'docsis11' refers
         to DOCSIS 1.1 Quality of Service."
    SYNTAX        INTEGER {
        docsis10 (1),
        docsis11 (2)
    }

DocsisUpstreamType ::= TEXTUAL-CONVENTION
    STATUS          current
    DESCRIPTION
         "Indicates the DOCSIS Upstream Channel Type.
          'unknown' means information not available.
          'tdma' is related to TDMA, Time Division
          Multiple Access; 'atdma' is related to A-TDMA,
          Advanced Time Division Multiple Access,
          'scdma' is related to S-CDMA, Synchronous
          Code Division Multiple Access.
          'tdmaAndAtdma is related to simultaneous support of
          TDMA and A-TDMA modes."
    SYNTAX          INTEGER {
        unknown(0),
        tdma(1),
        atdma(2),
        scdma(3),
        tdmaAndAtdma(4)
    }

 DocsEqualizerData ::= TEXTUAL-CONVENTION
      STATUS       current
      DESCRIPTION
          "This data type represents the equalizer data
           as measured at the receiver interface.
           The format of the equalizer follows the structure of the
           Transmit Equalization Adjust RNG-RSP TLV of DOCSIS RFI
           v2.0 :
           1 byte Main tap location 1..(n + m)
           1 byte Number of forward taps per symbol
           1 byte Number of forward taps: n
           1 byte Number of reverse taps: m

           Following are the equalizer coefficients:
           First, forward taps coefficients:
           2 bytes F1 (real),  2 bytes  F1 (imag)

           ...
           2 bytes Fn (real),  2 bytes  Fn (imag)

           Then, reverse taps coefficients:
           2 bytes D1 (real),  2 bytes  D1 (imag)
           ...

           2 bytes Dm (real),  2 bytes  Dm (imag)

           The equalizer coefficients are considered signed 16-bit
           integers in the range from -32768 (0x8000) to 32767
           (0x7FFF).

           DOCSIS specifications require up to a maximum of
           64 equalizer taps (n + m); therefore, this object size
            can get up 260 bytes (4 + 4x64).
           The minimum object size (other than zero) for a t-spaced
           tap with a minimum of 8 symbols will be 36 (4 + 4x8)."
      REFERENCE
         "Data-Over-Cable Service Interface Specifications: Radio
          Frequency Interface Specification SP-RFIv2.0-I10-051209,
          Figure 8-23."
      SYNTAX       OCTET STRING(SIZE (0 | 36..260))

docsIfMibObjects  OBJECT IDENTIFIER ::= { docsIfMib 1 }
docsIfBaseObjects OBJECT IDENTIFIER ::= { docsIfMibObjects 1 }
docsIfCmObjects   OBJECT IDENTIFIER ::= { docsIfMibObjects 2 }
docsIfCmtsObjects OBJECT IDENTIFIER ::= { docsIfMibObjects 3 }

--
-- BASE GROUP
--

--
-- The following table is implemented on both the Cable Modem
-- and the Cable Modem Termination System.  This table is
-- read only for the CM.
--

docsIfDownstreamChannelTable OBJECT-TYPE
     SYNTAX      SEQUENCE OF DocsIfDownstreamChannelEntry
     MAX-ACCESS  not-accessible
     STATUS      current
     DESCRIPTION
         "This table describes the attributes of downstream
          channels (frequency bands)."
     REFERENCE
         "Data-Over-Cable Service Interface Specifications: Radio
          Frequency Interface Specification SP-RFIv2.0-I10-051209,
          Tables 6-16, and 6-17."
     ::= { docsIfBaseObjects 1 }

docsIfDownstreamChannelEntry OBJECT-TYPE
     SYNTAX      DocsIfDownstreamChannelEntry
     MAX-ACCESS  not-accessible
     STATUS      current
     DESCRIPTION
         "An entry provides a list of attributes for a single
          downstream channel.
          An entry in this table exists for each ifEntry with an
          ifType of docsCableDownstream(128)."
     INDEX { ifIndex }
     ::= { docsIfDownstreamChannelTable 1 }

DocsIfDownstreamChannelEntry ::= SEQUENCE {
         docsIfDownChannelId               Integer32,
         docsIfDownChannelFrequency        Integer32,
         docsIfDownChannelWidth            Integer32,
         docsIfDownChannelModulation       INTEGER,
         docsIfDownChannelInterleave       INTEGER,
         docsIfDownChannelPower            TenthdBmV,
         docsIfDownChannelAnnex            INTEGER,
         docsIfDownChannelStorageType      StorageType
     }

docsIfDownChannelId OBJECT-TYPE
     SYNTAX      Integer32 (0..255)
     MAX-ACCESS  read-only
     STATUS      current
     DESCRIPTION
         "The Cable Modem Termination System identification of the
          downstream channel within this particular MAC interface.
          if the interface is down, the object returns the most
          current value.  If the downstream channel ID is unknown,
          this object returns a value of 0."
     ::= { docsIfDownstreamChannelEntry 1 }

docsIfDownChannelFrequency OBJECT-TYPE
     SYNTAX      Integer32 (0..1000000000)
     UNITS       "hertz"
     MAX-ACCESS  read-write
     STATUS      current
     DESCRIPTION
         "The center of the downstream frequency associated with
          this channel.  This object will return the current tuner

          frequency.  If a CMTS provides IF output, this object
          will return 0, unless this CMTS is in control of the
          final downstream frequency.  See the associated
          compliance object for a description of valid frequencies
          that may be written to this object."
     REFERENCE
         "Data-Over-Cable Service Interface Specifications: Radio
          Frequency Interface Specification SP-RFIv2.0-I10-051209,
          Section 6.3.3."
     ::= { docsIfDownstreamChannelEntry 2 }

docsIfDownChannelWidth OBJECT-TYPE
     SYNTAX      Integer32 (0..16000000)
     UNITS       "hertz"
     MAX-ACCESS  read-write
     STATUS      current
     DESCRIPTION
         "The bandwidth of this downstream channel.  Most
          implementations are expected to support a channel width
          of 6 MHz (North America) and/or 8 MHz (Europe).  See the
          associated compliance object for a description of the
          valid channel widths for this object."
     REFERENCE
         "Data-Over-Cable Service Interface Specifications: Radio
          Frequency Interface Specification SP-RFIv2.0-I10-051209,
          Table 6-17."
     ::= { docsIfDownstreamChannelEntry 3 }

docsIfDownChannelModulation OBJECT-TYPE
     SYNTAX      INTEGER {
         unknown(1),
         other(2),
         qam64(3),
         qam256(4)
     }
     MAX-ACCESS  read-write
     STATUS      current
     DESCRIPTION
         "The modulation type associated with this downstream
          channel.  If the interface is down, this object either
          returns the configured value (CMTS), the most current
          value (CM), or the value of unknown(1).  See the
          associated conformance object for write conditions and
          limitations.  See the reference for specifics on the
          modulation profiles implied by qam64 and qam256."
     REFERENCE
         "Data-Over-Cable Service Interface Specifications: Radio

          Frequency Interface Specification SP-RFIv2.0-I10-051209,
          Table 6-17."
     ::= { docsIfDownstreamChannelEntry 4 }

docsIfDownChannelInterleave OBJECT-TYPE
     SYNTAX      INTEGER {
         unknown(1),
         other(2),
         taps8Increment16(3),
         taps16Increment8(4),
         taps32Increment4(5),
         taps64Increment2(6),
         taps128Increment1(7),
         taps12increment17(8)
     }
     MAX-ACCESS  read-write
     STATUS      current
     DESCRIPTION
         "The Forward Error Correction (FEC) interleaving used
          for this downstream channel.
          Values are defined as follows:
          taps8Increment16(3):   protection 5.9/4.1 usec,
                                 latency .22/.15 msec
          taps16Increment8(4):   protection 12/8.2 usec,
                                 latency .48/.33 msec
          taps32Increment4(5):   protection 24/16 usec,
                                 latency .98/.68 msec
          taps64Increment2(6):   protection 47/33 usec,
                                 latency 2/1.4 msec
          taps128Increment1(7):  protection 95/66 usec,
                                 latency 4/2.8 msec
          taps12increment17(8):  protection 18/14 usec,
                                 latency 0.43/0.32 msec

         The value 'taps12increment17' is supported by EuroDOCSIS
         cable systems only, and the others by DOCSIS cable systems.

          If the interface is down, this object either returns
          the configured value (CMTS), the most current value (CM),
          or the value of unknown(1).
          The value of other(2) is returned if the interleave
          is known but not defined in the above list.
          See the associated conformance object for write
          conditions and limitations.  See the reference for the FEC
          configuration described by the setting of this object."
     REFERENCE
         "Data-Over-Cable Service Interface Specifications: Radio
          Frequency Interface Specification SP-RFIv2.0-I10-051209,
          Table 6-15."
     ::= { docsIfDownstreamChannelEntry 5 }

docsIfDownChannelPower OBJECT-TYPE
     SYNTAX      TenthdBmV
     UNITS       "dBmV"
     MAX-ACCESS  read-write
     STATUS      current
     DESCRIPTION
         "At the CMTS, the operational transmit power.  At the CM,
          the received power level.
          If the interface is down, this object either returns
          the configured value (CMTS), the most current value (CM)
          or the value of 0.  See the associated conformance object
          for write conditions and limitations.  See the reference
          for recommended and required power levels."
     REFERENCE
         "Data-Over-Cable Service Interface Specifications: Radio
          Frequency Interface Specification SP-RFIv2.0-I10-051209,
          Tables 6-16, 6-17."
     ::= { docsIfDownstreamChannelEntry 6 }

docsIfDownChannelAnnex OBJECT-TYPE
     SYNTAX      INTEGER {
         unknown(1),
         other(2),
         annexA(3),
         annexB(4),
         annexC(5)
     }
     MAX-ACCESS  read-only
     STATUS      current
     DESCRIPTION
         "The value of this object indicates the conformance of
          the implementation to important regional cable standards.
          annexA : Annex A from ITU-T J.83 is used.
                   (equivalent to EN 300 429)
          annexB : Annex B from ITU-T J.83 is used.
          annexC : Annex C from ITU-T J.83 is used."
     REFERENCE
         "Data-Over-Cable Service Interface Specifications: Radio
          Frequency Interface Specification SP-RFIv2.0-I10-051209,
          Sections 6.3.1, and H.3.1."
     ::= { docsIfDownstreamChannelEntry 7 }

docsIfDownChannelStorageType OBJECT-TYPE
     SYNTAX       StorageType
     MAX-ACCESS   read-only
     STATUS       current
     DESCRIPTION
         "The storage type for this conceptual row.
          Entries with this object set to permanent(4)
          do not require write operations for read-write
          objects."
     ::= { docsIfDownstreamChannelEntry 8 }

--
-- The following table is implemented on both the CM and the CMTS.
-- For the CM, only attached channels appear in the table.  For the
-- CM, this table is read-only as well.
--

docsIfUpstreamChannelTable OBJECT-TYPE
     SYNTAX      SEQUENCE OF DocsIfUpstreamChannelEntry
     MAX-ACCESS  not-accessible
     STATUS      current
     DESCRIPTION
         "This table describes the attributes of attached upstream
          channels."
     ::= { docsIfBaseObjects 2 }

docsIfUpstreamChannelEntry OBJECT-TYPE
     SYNTAX      DocsIfUpstreamChannelEntry
     MAX-ACCESS  not-accessible
     STATUS      current
     DESCRIPTION
         "List of attributes for a single upstream channel.  For
          DOCSIS 2.0 CMTSs, an entry in this table exists for
          each ifEntry with an ifType of docsCableUpstreamChannel
          (205).
          For DOCSIS 1.x CM/CMTSs and DOCSIS 2.0 CMs, an entry in
          this table exists for each ifEntry with an ifType of
          docsCableUpstream (129).

          For DOCSIS 2.0 CMTSs, two classes of interfaces can be
          defined for this table:
           o Upstream Physical Interfaces: The traditional DOCSIS
             1.x CMTS upstream interface ifType 129 and the DOCSIS
             2.0 ifType 205 that are functional.  In other words,
             interfaces that represent upstream receivers within
             an RF MAC interface.
             Entries of physical interfaces are exposed to the
             management interface with their corresponding
             ifStack hierarchy and are not administratively
             created by this table.

           o Upstream Temporary Interfaces: A fictitious
             interface created for the purpose of manipulating
             physical interface parameters offline, then
             validating prior to updating the target physical
             interface.

          In case of a reinitialization of the managed system,
          physical interfaces values persist while the temporary
          interfaces are not recreated.

          This mechanism helps to minimize service disruptions
          originating in situations where a group of interface
          parameter values need to be consistent with each other
          in SET operations.  A temporary buffer
          (temporary interface) is provided to allow the CMTS
          to validate the parameters offline."
     INDEX { ifIndex }
     ::= { docsIfUpstreamChannelTable 1 }

DocsIfUpstreamChannelEntry ::= SEQUENCE {
         docsIfUpChannelId                     Integer32,
         docsIfUpChannelFrequency              Integer32,
         docsIfUpChannelWidth                  Integer32,
         docsIfUpChannelModulationProfile      Unsigned32,
         docsIfUpChannelSlotSize               Unsigned32,
         docsIfUpChannelTxTimingOffset         Unsigned32,
         docsIfUpChannelRangingBackoffStart    Integer32,
         docsIfUpChannelRangingBackoffEnd      Integer32,
         docsIfUpChannelTxBackoffStart         Integer32,
         docsIfUpChannelTxBackoffEnd           Integer32,
         docsIfUpChannelScdmaActiveCodes       Unsigned32,
         docsIfUpChannelScdmaCodesPerSlot      Integer32,
         docsIfUpChannelScdmaFrameSize         Unsigned32,
         docsIfUpChannelScdmaHoppingSeed       Unsigned32,
         docsIfUpChannelType                   DocsisUpstreamType,
         docsIfUpChannelCloneFrom              InterfaceIndexOrZero,
         docsIfUpChannelUpdate                 TruthValue,
         docsIfUpChannelStatus                 RowStatus,
         docsIfUpChannelPreEqEnable            TruthValue
     }

docsIfUpChannelId OBJECT-TYPE
     SYNTAX      Integer32 (0..255)
     MAX-ACCESS  read-only
     STATUS      current
     DESCRIPTION
         "The CMTS identification of the upstream channel."
     ::= { docsIfUpstreamChannelEntry 1 }

docsIfUpChannelFrequency OBJECT-TYPE
     SYNTAX      Integer32 (0..1000000000)
     UNITS       "hertz"
     MAX-ACCESS  read-create
     STATUS      current
     DESCRIPTION
         "The center of the frequency band associated with this
          upstream interface.  This object returns 0 if the frequency
          is undefined or unknown.  Minimum permitted upstream
          frequency is 5,000,000 Hz for current technology.  See
          the associated conformance object for write conditions
          and limitations."
     REFERENCE
         "Data-Over-Cable Service Interface Specifications: Radio
          Frequency Interface Specification SP-RFIv2.0-I10-051209,
          Table 4-2."
     ::= { docsIfUpstreamChannelEntry 2 }

docsIfUpChannelWidth OBJECT-TYPE
     SYNTAX      Integer32 (0..64000000)
     UNITS       "hertz"
     MAX-ACCESS  read-create
     STATUS      current
     DESCRIPTION
         "The bandwidth of this upstream interface.  This object
          returns 0 if the interface width is undefined or unknown.
          Minimum permitted interface width is currently 200,000 Hz.
          See the associated conformance object for write conditions
          and limitations."
     REFERENCE
         "Data-Over-Cable Service Interface Specifications: Radio
          Frequency Interface Specification SP-RFIv2.0-I10-051209,
          Table 6-5."
     ::= { docsIfUpstreamChannelEntry 3 }

docsIfUpChannelModulationProfile OBJECT-TYPE
     SYNTAX      Unsigned32
     MAX-ACCESS  read-create
     STATUS      current
     DESCRIPTION
         "An entry identical to the docsIfModIndex in the
          docsIfCmtsModulationTable that describes this channel.
          This channel is further instantiated there by a grouping
          of interval usage codes (IUCs) that, together, fully
          describe the channel modulation.  This object returns 0 if
          the docsIfCmtsModulationTable entry does not exist or is
          empty.  See the associated conformance object for write
          conditions and limitations.

          Setting this object returns an 'inconsistentValue'
          error if the following conditions are not satisfied:
          1. All the IUC entries in the selected modulation profile
          MUST have the same value of docsIfCmtsModChannelType.
          2. All of the Modulation parameters in the selected
          modulation profile MUST be consistent with the other
          parameters in this docsIfUpstreamChannelEntry."
     REFERENCE
         "Data-Over-Cable Service Interface Specifications: Radio
          Frequency Interface Specification SP-RFIv2.0-I10-051209,
          Table 8-19."
     ::= { docsIfUpstreamChannelEntry 4 }

docsIfUpChannelSlotSize OBJECT-TYPE
     SYNTAX      Unsigned32
     UNITS       "ticks"
     MAX-ACCESS  read-create
     STATUS      current
     DESCRIPTION
         "Applicable to TDMA and ATDMA channel types only.
          The number of 6.25 microsecond ticks in each upstream
          mini-slot.  Returns zero if the value is undefined or
          unknown or in case of an SCDMA channel.
          See the associated conformance object for write
          conditions and limitations."
     REFERENCE
         "Data-Over-Cable Service Interface Specifications: Radio
          Frequency Interface Specification SP-RFIv2.0-I10-051209,
          Section 8.1.2.4."
     ::= { docsIfUpstreamChannelEntry 5 }

docsIfUpChannelTxTimingOffset OBJECT-TYPE
     SYNTAX      Unsigned32
     MAX-ACCESS  read-only
     STATUS      current
     DESCRIPTION
         "At the CM, a measure of the current round trip time
          obtained from the ranging offset (initial ranging offset +
          ranging offset adjustments).
          At the CMTS, the maximum of timing offset, among all the
          CMs that are/were present on the channel, taking into
          account all ( initial + periodic ) timing offset
          corrections that were sent for each of the CMs.  Generally,
          these measurements are positive, but if the measurements
          are negative, the value of this object is zero.  Used for
          timing of CM upstream transmissions to ensure synchronized
          arrivals at the CMTS.
          Units are one 64th fraction of 6.25 microseconds."
     REFERENCE
         "Data-Over-Cable Service Interface Specifications: Radio
          Frequency Interface Specification SP-RFIv2.0-I10-051209,
          Section 6.2.19."
     ::= { docsIfUpstreamChannelEntry 6 }

docsIfUpChannelRangingBackoffStart OBJECT-TYPE
     SYNTAX      Integer32 (0..16)
     MAX-ACCESS  read-create
     STATUS      current
     DESCRIPTION
         "The initial random backoff window to use when retrying
          Ranging Requests.  Expressed as a power of 2.  A value of
          16 at the CMTS indicates that a proprietary adaptive retry
          mechanism is to be used.  See the associated conformance
          object for write conditions and limitations."
     REFERENCE
         "Data-Over-Cable Service Interface Specifications: Radio
          Frequency Interface Specification SP-RFIv2.0-I10-051209,
          Sections 8.3.4, and 9.4."
     ::= { docsIfUpstreamChannelEntry 7 }

docsIfUpChannelRangingBackoffEnd OBJECT-TYPE
     SYNTAX      Integer32 (0..16)
     MAX-ACCESS  read-create
     STATUS      current
     DESCRIPTION
         "The final random backoff window to use when retrying
          Ranging Requests.  Expressed as a power of 2.  A value of
          16 at the CMTS indicates that a proprietary adaptive retry
          mechanism is to be used.  See the associated conformance
          object for write conditions and limitations."
     REFERENCE
         "Data-Over-Cable Service Interface Specifications: Radio
          Frequency Interface Specification SP-RFIv2.0-I10-051209,
          Section 8.3.4, and 9.4."
     ::= { docsIfUpstreamChannelEntry 8 }

docsIfUpChannelTxBackoffStart OBJECT-TYPE
     SYNTAX      Integer32 (0..16)
     MAX-ACCESS  read-create
     STATUS      current
     DESCRIPTION
         "The initial random backoff window to use when retrying
          transmissions.  Expressed as a power of 2.  A value of 16
          at the CMTS indicates that a proprietary adaptive retry
          mechanism is to be used.  See the associated conformance
          object for write conditions and limitations."
     REFERENCE
         "Data-Over-Cable Service Interface Specifications: Radio
          Frequency Interface Specification SP-RFIv2.0-I10-051209,
          Section 8.3.4, and 9.4."
     ::= { docsIfUpstreamChannelEntry 9 }

docsIfUpChannelTxBackoffEnd OBJECT-TYPE
     SYNTAX      Integer32 (0..16)
     MAX-ACCESS  read-create
     STATUS      current
     DESCRIPTION
         "The final random backoff window to use when retrying
          transmissions.  Expressed as a power of 2.  A value of 16
          at the CMTS indicates that a proprietary adaptive retry
          mechanism is to be used.  See the associated conformance
          object for write conditions and limitations."
     REFERENCE
         "Data-Over-Cable Service Interface Specifications: Radio
          Frequency Interface Specification SP-RFIv2.0-I10-051209,
          Section 8.3.4, and 9.4."
     ::= { docsIfUpstreamChannelEntry 10 }

docsIfUpChannelScdmaActiveCodes OBJECT-TYPE
     SYNTAX     Unsigned32 (0|64..66|68..70|72|74..78|80..82|84..88
                             |90..96|98..100|102|104..106|108
                             |110..112|114..126|128)
     MAX-ACCESS read-create
     STATUS     current
     DESCRIPTION
         "Applicable for SCDMA channel types only.
          Number of active codes.  Returns zero for
          Non-SCDMA channel types.  Note that legal
          values from 64..128 MUST be non-prime."
     REFERENCE
         "Data-Over-Cable Service Interface Specifications: Radio
          Frequency Interface Specification SP-RFIv2.0-I10-051209,
          Section 6.2.11.2.1."
     ::= { docsIfUpstreamChannelEntry 11 }

docsIfUpChannelScdmaCodesPerSlot OBJECT-TYPE
     SYNTAX      Integer32(0 | 2..32)
     UNITS       "codesperMinislots"
     MAX-ACCESS  read-create
     STATUS      current
     DESCRIPTION
         "Applicable for SCDMA channel types only.
          The number of SCDMA codes per mini-slot.
          Returns zero if the value is undefined or unknown or in

          case of a TDMA or ATDMA channel."
     REFERENCE
         "Data-Over-Cable Service Interface Specifications: Radio
          Frequency Interface Specification SP-RFIv2.0-I10-051209,
          Section 6.2.11.2.1."
     ::= { docsIfUpstreamChannelEntry 12 }

docsIfUpChannelScdmaFrameSize OBJECT-TYPE
     SYNTAX      Unsigned32 (0..32)
     UNITS       "spreadIntervals"
     MAX-ACCESS  read-create
     STATUS      current
     DESCRIPTION
         "Applicable for SCDMA channel types only.
          SCDMA Frame size in units of spreading intervals.
          This value returns zero for non-SCDMA Profiles."
     REFERENCE
         "Data-Over-Cable Service Interface Specifications: Radio
          Frequency Interface Specification SP-RFIv2.0-I10-051209,
          Section 6.2.12."
     ::= { docsIfUpstreamChannelEntry 13 }

docsIfUpChannelScdmaHoppingSeed OBJECT-TYPE
     SYNTAX     Unsigned32 (0..32767)
     MAX-ACCESS read-create
     STATUS     current
     DESCRIPTION
         "Applicable for SCDMA channel types only.
          15-bit seed used for code hopping sequence initialization.
          Returns zero for non-SCDMA channel types.
          Setting this value to a value different than zero for
          non-SCDMA channel types returns the error 'wrongValue'."
     REFERENCE
         "Data-Over-Cable Service Interface Specifications: Radio
          Frequency Interface Specification SP-RFIv2.0-I10-051209,
          Section 6.2.14.1."
     ::= { docsIfUpstreamChannelEntry 14 }

docsIfUpChannelType OBJECT-TYPE
     SYNTAX      DocsisUpstreamType
     MAX-ACCESS  read-only
     STATUS      current
     DESCRIPTION
         "Reflects the Upstream channel type.
          This object returns the value of docsIfCmtsModChannelType
          for the modulation profile selected in
          docsIfUpChannelModulationProfile for this row."
     REFERENCE
         "Data-Over-Cable Service Interface Specifications: Radio
          Frequency Interface Specification SP-RFIv2.0-I10-051209,
          Section 6.2.1."
     ::= { docsIfUpstreamChannelEntry 15 }

docsIfUpChannelCloneFrom OBJECT-TYPE
     SYNTAX      InterfaceIndexOrZero
     MAX-ACCESS  read-create
     STATUS      current
     DESCRIPTION
         "This object contains the ifIndex value of the physical
          interface row entry whose parameters are to be adjusted.

          Upon setting this object to the ifIndex value of a
          physical interface, the following interface objects values
          are copied to this entry:
          docsIfUpChannelFrequency,
          docsIfUpChannelWidth,
          docsIfUpChannelModulationProfile,
          docsIfUpChannelSlotSize,
          docsIfUpChannelRangingBackoffStart,
          docsIfUpChannelRangingBackoffEnd,
          docsIfUpChannelTxBackoffStart,
          docsIfUpChannelTxBackoffEnd,
          docsIfUpChannelScdmaActiveCodes,
          docsIfUpChannelScdmaCodesPerSlot,
          docsIfUpChannelScdmaFrameSize,
          docsIfUpChannelScdmaHoppingSeed,
          docsIfUpChannelType, and
          docsIfUpChannelPreEqEnable
          Setting this object to the value of a non-existent or
          a temporary upstream interface returns the error
          'wrongValue'.
          This object MUST contain a value of zero for physical
          interfaces entries.
          Setting this object in row entries that correspond to
          physical interfaces returns the error 'wrongValue'."
     ::= { docsIfUpstreamChannelEntry 16 }

docsIfUpChannelUpdate OBJECT-TYPE
     SYNTAX      TruthValue
     MAX-ACCESS  read-create
     STATUS      current
     DESCRIPTION
         "Used to perform the copy of adjusted parameters from the
          temporary interface entry to the physical interface
          indicated by the docsIfUpChannelCloneFrom object.  The
          transfer is initiated through an SNMP SET to 'true' of

          this object.
          A SET to 'true' fails and returns error 'commitFailed'
          if docsIfUpChannelStatus value is 'notInService', which
          means that the interface parameters values are not
          compatible with each other or have not been validated yet.
          Reading this object always returns 'false'."
     ::= { docsIfUpstreamChannelEntry 17 }

docsIfUpChannelStatus OBJECT-TYPE
     SYNTAX      RowStatus
     MAX-ACCESS  read-create
     STATUS      current
     DESCRIPTION
         "This object is only used for the creation of a temporary
          upstream row with the purpose of updating the parameters
          of a physical upstream channel entry.

          The following restrictions apply to this object:
          1. This object is not writable for physical interfaces.
          2. Temporary interface entries are only created by a SET
             of this object to createandWait(5).
          3. ifAdminStatus from the Interface MIB RFC 2863 is used
             to take a physical upstream channel offline, to be
             consistent with DOCSIS 1.x operation, as indicated in
             RFC 2670.
             In addition,
              o ifAdminStatus 'down' is reflected in this object
                as 'notInService'.
              o ifOperStatus 'down' while ifAdminStatus 'up' is
                reflected in this object as 'notInservice'.
          4. Temporary created rows MUST be set to 'active' with
             the purpose of validating upstream parameter
             consistency prior to transferring the parameters to the
             physical interface.

          Below is a mandatory procedure for adjusting the values
          of a physical interface:
          1. Create a temporary interface entry through an SNMP SET
             using 'createAndWait'.  At this point, the RowStatus
             reports 'notReady'.
             The Manager entity uses an ifIndex value outside the
             operational range of the physical interfaces for the
             creation of a temporary interface.
          2. Set the docsIfUpChannelCloneFrom object to the ifIndex
             value of the physical row to update.  Now
             docsIfUpChannelStatus reports 'notInService'.
          3. Change the upstream parameters to the desired values
             in the temporary row.

          4. Validate that all parameters are consistent by setting
             docsIfUpChannelStatus to 'active'.  A failure to set the
             RowStatus to 'active' returns the error 'commitFailed',
             which means the parameters are not compatible with the
             target physical interface.
          5. With docsIfUpChannelStatus 'active', transfer the
             parameters to the target physical interface by setting
             the object docsIfUpChannelUpdate to 'true'.
          6. Delete the temporary row by setting
             docsIfUpChannelStatus to 'destroy'."
     ::= { docsIfUpstreamChannelEntry 18 }

docsIfUpChannelPreEqEnable OBJECT-TYPE
     SYNTAX      TruthValue
     MAX-ACCESS  read-create
     STATUS      current
     DESCRIPTION
         "At the CMTS, this object is used to enable or disable
          pre-equalization on the upstream channel represented by
          this table instance.  At the CM, this object is read-only
          and reflects the status of pre-equalization as represented
          in the RNG-RSP.  Pre-equalization is considered enabled at
          the CM if a RNG-RSP with pre-equalization data has been
          received at least once since the last mac
          reinitialization."
     DEFVAL {false}
     ::= { docsIfUpstreamChannelEntry 19 }

-- The following table describes the attributes of each class of
-- service.  The entries in this table are referenced from the
-- docsIfServiceEntries.  They exist as a separate table in order to
-- reduce redundant information in docsIfServiceTable.
--
-- This table is implemented at both the CM and the CMTS.
-- The CM need only maintain entries for the classes of service
-- referenced by its docsIfCmServiceTable.
--

docsIfQosProfileTable OBJECT-TYPE
     SYNTAX      SEQUENCE OF DocsIfQosProfileEntry
     MAX-ACCESS  not-accessible
     STATUS      current
     DESCRIPTION
         "Describes the attributes for each class of service."
     ::= { docsIfBaseObjects 3 }

docsIfQosProfileEntry OBJECT-TYPE
     SYNTAX      DocsIfQosProfileEntry
     MAX-ACCESS  not-accessible
     STATUS      current
     DESCRIPTION
         "Describes the attributes for a single class of service.
          If implemented as read-create in the Cable Modem
          Termination System, creation of entries in this table is
          controlled by the value of
          docsIfCmtsQosProfilePermissions.

          If implemented as read-only, entries are created based
          on information in REG-REQ MAC messages received from
          cable modems (for Cable Modem Termination System), or
          based on information extracted from the TFTP option file
          (for Cable Modem).
          In the Cable Modem Termination System, read-only entries
          are removed if no longer referenced by
          docsIfCmtsServiceTable.

          An entry in this table MUST not be removed while it is
          referenced by an entry in docsIfCmServiceTable (Cable
          Modem) or docsIfCmtsServiceTable (Cable Modem Termination
          System).

          An entry in this table SHOULD NOT be changeable while
          it is referenced by an entry in docsIfCmtsServiceTable.

          If this table is created automatically, there SHOULD only
          be a single entry for each Class of Service.  Multiple
          entries with the same Class of Service parameters are NOT
          RECOMMENDED."
     INDEX { docsIfQosProfIndex }
     ::= { docsIfQosProfileTable 1 }

DocsIfQosProfileEntry ::= SEQUENCE {
         docsIfQosProfIndex                Integer32,
         docsIfQosProfPriority             Integer32,
         docsIfQosProfMaxUpBandwidth       Integer32,
         docsIfQosProfGuarUpBandwidth      Integer32,
         docsIfQosProfMaxDownBandwidth     Integer32,
         docsIfQosProfMaxTxBurst           Integer32,  -- deprecated
         docsIfQosProfBaselinePrivacy      TruthValue,
         docsIfQosProfStatus               RowStatus,
         docsIfQosProfMaxTransmitBurst     Integer32,
         docsIfQosProfStorageType          StorageType
     }

docsIfQosProfIndex OBJECT-TYPE
     SYNTAX      Integer32 (1..16383)
     MAX-ACCESS  not-accessible
     STATUS      current
     DESCRIPTION
         "The index value that uniquely identifies an entry
          in the docsIfQosProfileTable."
     ::= { docsIfQosProfileEntry 1 }

docsIfQosProfPriority OBJECT-TYPE
     SYNTAX      Integer32 (0..7)
     MAX-ACCESS  read-create
     STATUS      current
     DESCRIPTION
         "A relative priority assigned to this service when
          allocating bandwidth.  Zero indicates lowest priority
          and seven indicates highest priority.
          Interpretation of priority is device-specific.
          MUST NOT be changed while this row is active."
     REFERENCE
         "Data-Over-Cable Service Interface Specifications: Radio
          Frequency Interface Specification SP-RFIv2.0-I10-051209,
          Annex C.1.1.4."
     DEFVAL { 0 }
     ::= { docsIfQosProfileEntry 2 }

docsIfQosProfMaxUpBandwidth OBJECT-TYPE
     SYNTAX      Integer32 (0..100000000)
     UNITS "bits per second"
     MAX-ACCESS  read-create
     STATUS      current
     DESCRIPTION
         "The maximum upstream bandwidth, in bits per second,
          allowed for a service with this service class.
          Zero if there is no restriction of upstream bandwidth.
          MUST NOT be changed while this row is active."
     REFERENCE
         "Data-Over-Cable Service Interface Specifications: Radio
          Frequency Interface Specification SP-RFIv2.0-I10-051209,
          Annex C.1.1.4."
     DEFVAL { 0 }
     ::= { docsIfQosProfileEntry 3 }

docsIfQosProfGuarUpBandwidth OBJECT-TYPE
     SYNTAX      Integer32 (0..100000000)
     UNITS "bits per second"
     MAX-ACCESS  read-create
     STATUS      current
     DESCRIPTION
         "Minimum guaranteed upstream bandwidth, in bits per second,
          allowed for a service with this service class.
          MUST NOT be changed while this row is active."
     REFERENCE
         "Data-Over-Cable Service Interface Specifications: Radio
          Frequency Interface Specification SP-RFIv2.0-I10-051209,
          Annex C.1.1.4."
     DEFVAL { 0 }
     ::= { docsIfQosProfileEntry 4 }

docsIfQosProfMaxDownBandwidth OBJECT-TYPE
     SYNTAX      Integer32 (0..100000000)
     UNITS "bits per second"
     MAX-ACCESS  read-create
     STATUS      current
     DESCRIPTION
         "The maximum downstream bandwidth, in bits per second,
          allowed for a service with this service class.
          Zero if there is no restriction of downstream bandwidth.
          MUST NOT be changed while this row is active."
     REFERENCE
         "Data-Over-Cable Service Interface Specifications: Radio
          Frequency Interface Specification SP-RFIv2.0-I10-051209,
          Annex C.1.1.4."
     DEFVAL { 0 }
     ::= { docsIfQosProfileEntry 5 }

docsIfQosProfMaxTxBurst OBJECT-TYPE
     SYNTAX      Integer32 (0..255)
     UNITS "mini-slots"
     MAX-ACCESS  read-create
     STATUS      deprecated
     DESCRIPTION
         "The maximum number of mini-slots that may be requested
          for a single upstream transmission.
          A value of zero means there is no limit.
          MUST NOT be changed while this row is active.
          This object has been deprecated and replaced by
          docsIfQosProfMaxTransmitBurst, to fix a mismatch
          of the units and value range with respect to the DOCSIS
          Maximum Upstream Channel Transmit Burst Configuration
          Setting."
     REFERENCE
         "Data-Over-Cable Service Interface Specifications: Radio
          Frequency Interface Specification SP-RFIv2.0-I10-051209,
          C.1.1.4."
     DEFVAL { 0 }
     ::= { docsIfQosProfileEntry 6 }

docsIfQosProfBaselinePrivacy OBJECT-TYPE
     SYNTAX      TruthValue
     MAX-ACCESS  read-create
     STATUS      current
     DESCRIPTION
         "Indicates whether Baseline Privacy is enabled for this
          service class.
          MUST NOT be changed while this row is active."
     DEFVAL { false }
     ::= { docsIfQosProfileEntry 7 }

docsIfQosProfStatus OBJECT-TYPE
     SYNTAX      RowStatus
     MAX-ACCESS  read-create
     STATUS      current
     DESCRIPTION
         "This is object is used to create or delete rows in
          this table.  This object MUST NOT be changed from active
          while the row is referenced by any entry in either
          docsIfCmServiceTable (on the CM) or
          docsIfCmtsServiceTable (on the CMTS)."
     ::= { docsIfQosProfileEntry 8 }

docsIfQosProfMaxTransmitBurst OBJECT-TYPE
     SYNTAX      Integer32 (0..65535)
     UNITS       "bytes"
     MAX-ACCESS  read-create
     STATUS      current
     DESCRIPTION
         "The maximum number of bytes that may be requested for a
          single upstream transmission.  A value of zero means there
          is no limit.  Note: This value does not include any
          physical layer overhead.
          MUST NOT be changed while this row is active."
     REFERENCE
         "Data-Over-Cable Service Interface Specifications: Radio
          Frequency Interface Specification SP-RFIv2.0-I10-051209,
          Annex C.1.1.4."
     DEFVAL { 0 }
     ::= { docsIfQosProfileEntry 9 }

docsIfQosProfStorageType OBJECT-TYPE
     SYNTAX       StorageType
     MAX-ACCESS   read-only
     STATUS       current
     DESCRIPTION
         "The storage type for this conceptual row.
          Entries with this object set to permanent(4)

          do not require write operations for writable
          objects."
     ::= { docsIfQosProfileEntry 10 }

docsIfSignalQualityTable OBJECT-TYPE
     SYNTAX      SEQUENCE OF DocsIfSignalQualityEntry
     MAX-ACCESS  not-accessible
     STATUS      current
     DESCRIPTION
         "At the CM, describes the PHY signal quality of downstream
          channels.  At the CMTS, this object describes the PHY
          signal quality of upstream channels.  At the CMTS, this
          table MAY exclude contention intervals."
     ::= { docsIfBaseObjects 4 }

docsIfSignalQualityEntry OBJECT-TYPE
     SYNTAX      DocsIfSignalQualityEntry
     MAX-ACCESS  not-accessible
     STATUS      current
     DESCRIPTION
         "At the CM, this object describes the PHY characteristics of
          a downstream channel.  At the CMTS, it describes the PHY
          signal quality of an upstream channel.
          An entry in this table exists for each ifEntry with an
          ifType of docsCableDownstream(128) for Cable Modems.
          For DOCSIS 1.1 Cable Modem Termination Systems, an entry
          exists for each ifEntry with an ifType of
          docsCableUpstream (129).
          For DOCSIS 2.0 Cable Modem Termination Systems, an entry
          exists for each ifEntry with an ifType of
          docsCableUpstreamChannel (205)."
     INDEX { ifIndex }
     ::= { docsIfSignalQualityTable 1 }

DocsIfSignalQualityEntry ::= SEQUENCE {
         docsIfSigQIncludesContention  TruthValue,
         docsIfSigQUnerroreds          Counter32,
         docsIfSigQCorrecteds          Counter32,
         docsIfSigQUncorrectables      Counter32,
         docsIfSigQSignalNoise         TenthdB,
         docsIfSigQMicroreflections    Integer32,
         docsIfSigQEqualizationData    DocsEqualizerData,
         docsIfSigQExtUnerroreds       Counter64,
         docsIfSigQExtCorrecteds       Counter64,
         docsIfSigQExtUncorrectables   Counter64
     }

docsIfSigQIncludesContention OBJECT-TYPE
     SYNTAX      TruthValue
     MAX-ACCESS  read-only
     STATUS      current
     DESCRIPTION
         "true(1) if this CMTS includes contention intervals in
          the counters in this table.  Always false(2) for CMs."
     REFERENCE
         "Data-Over-Cable Service Interface Specifications: Radio
          Frequency Interface Specification SP-RFIv2.0-I10-051209,
          Section 9.4.1"
     ::= { docsIfSignalQualityEntry 1 }

docsIfSigQUnerroreds OBJECT-TYPE
     SYNTAX      Counter32
     UNITS       "codewords"
     MAX-ACCESS  read-only
     STATUS      current
     DESCRIPTION
         "Codewords received on this channel without error.
          This includes all codewords, whether or not they
          were part of frames destined for this device.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Sections 6.2.4, and 6.3.6."
     ::= { docsIfSignalQualityEntry 2 }

docsIfSigQCorrecteds OBJECT-TYPE
     SYNTAX      Counter32
     UNITS       "codewords"
     MAX-ACCESS  read-only
     STATUS      current
     DESCRIPTION
         "Codewords received on this channel with correctable
          errors.  This includes all codewords, whether or not
          they were part of frames destined for this device.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Sections 6.2.4, and 6.3.6."
     ::= { docsIfSignalQualityEntry 3 }

docsIfSigQUncorrectables OBJECT-TYPE
     SYNTAX      Counter32
     UNITS       "codewords"
     MAX-ACCESS  read-only
     STATUS      current
     DESCRIPTION
         "Codewords received on this channel with uncorrectable
          errors.  This includes all codewords, whether or not
          they were part of frames destined for this device.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Sections 6.2.4, and 6.3.6."
     ::= { docsIfSignalQualityEntry 4 }

docsIfSigQSignalNoise OBJECT-TYPE
     SYNTAX      TenthdB
     UNITS       "TenthdB"
     MAX-ACCESS  read-only
     STATUS      current
     DESCRIPTION
         "Signal/Noise ratio as perceived for this channel.
          At the CM, this object  describes the Signal/Noise of the
          downstream channel.  At the CMTS, it describes the
          average Signal/Noise of the upstream channel."
     REFERENCE
         "Data-Over-Cable Service Interface Specifications: Radio
          Frequency Interface Specification SP-RFIv2.0-I10-051209,
          Tables 4-1 and 4-2"
     ::= { docsIfSignalQualityEntry 5 }

docsIfSigQMicroreflections OBJECT-TYPE
     SYNTAX      Integer32 (0..255)
     UNITS       "-dBc"
     MAX-ACCESS  read-only
     STATUS      current
     DESCRIPTION
         "Microreflections, including in-channel response
          as perceived on this interface, measured in dBc below
          the signal level.
          This object is not assumed to return an absolutely
          accurate value, but it gives a rough indication

          of microreflections received on this interface.
          It is up to the implementer to provide information
          as accurately as possible."
     REFERENCE
         "Data-Over-Cable Service Interface Specifications: Radio
          Frequency Interface Specification SP-RFIv2.0-I10-051209,
          Tables 4-1 and 4-2"
     ::= { docsIfSignalQualityEntry 6 }

docsIfSigQEqualizationData OBJECT-TYPE
        SYNTAX      DocsEqualizerData
        MAX-ACCESS  read-only
        STATUS      current
        DESCRIPTION
            "At the CM, this object returns the equalization data for
             the downstream channel.

             At the CMTS, this object is not applicable and is not
             instantiated.  Note that previous CMTS implementations
             may instantiate this object in two ways:
             - An equalization value indicating an equalization
               average for the upstream channel.  Those values have
               vendor-dependent interpretations.
             - Return a zero-length OCTET STRING to indicate that
               the value is unknown or if there is no equalization
               data available or defined."
        REFERENCE
            "DOCSIS Radio Frequency Interface Specification,
             Figure 6-23."
        ::= { docsIfSignalQualityEntry 7 }

docsIfSigQExtUnerroreds OBJECT-TYPE
     SYNTAX      Counter64
     UNITS       "codewords"
     MAX-ACCESS  read-only
     STATUS      current
     DESCRIPTION
         "Codewords received on this channel without error.
          This includes all codewords, whether or not they
          were part of frames destined for this device.
          This is the 64-bit version of docsIfSigQUnerroreds.
          Discontinuities in the value of this counter can occur
          at reinitialization of the managed system, and at other
          times as indicated by the value of
          ifCounterDiscontinuityTime for the associated ifIndex."
     REFERENCE
         "Data-Over-Cable Service Interface Specifications: Radio

          Frequency Interface Specification SP-RFIv2.0-I10-051209,
          Sections 6.2.4, and 6.3.6."
     ::= { docsIfSignalQualityEntry 8 }

docsIfSigQExtCorrecteds OBJECT-TYPE
     SYNTAX      Counter64
     UNITS       "codewords"
     MAX-ACCESS  read-only
     STATUS      current
     DESCRIPTION
         "Codewords received on this channel with correctable
          errors.  This includes all codewords, whether or not
          they were part of frames destined for this device.
          This is the 64-bit version of docsIfSigQCorrecteds.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Sections 6.2.4, and 6.3.6."
     ::= { docsIfSignalQualityEntry 9 }

docsIfSigQExtUncorrectables OBJECT-TYPE
     SYNTAX      Counter64
     UNITS       "codewords"
     MAX-ACCESS  read-only
     STATUS      current
     DESCRIPTION
         "Codewords received on this channel with uncorrectable
          errors.  This includes all codewords, whether or not
          they were part of frames destined for this device.
          This is the 64-bit version of docsIfSigQUncorrectables.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Sections 6.2.4, 6.3.6."
     ::= { docsIfSignalQualityEntry 10 }

--
-- DOCSIS Version of the device
--

docsIfDocsisBaseCapability OBJECT-TYPE
        SYNTAX      DocsisVersion
        MAX-ACCESS  read-only
        STATUS      current
        DESCRIPTION
            "Indication of the DOCSIS capability of the device."
        REFERENCE
            "Data-Over-Cable Service Interface Specifications: Radio
             Frequency Interface Specification SP-RFIv2.0-I10-051209,
             Annex G."
        ::= { docsIfBaseObjects 5 }

--
-- CABLE MODEM GROUP
--

--
-- The CM MAC Table
--

docsIfCmMacTable OBJECT-TYPE
     SYNTAX      SEQUENCE OF DocsIfCmMacEntry
     MAX-ACCESS  not-accessible
     STATUS      current
     DESCRIPTION
         "Describes the attributes of each CM MAC interface,
          extending the information available from ifEntry."
     ::= { docsIfCmObjects 1 }

docsIfCmMacEntry OBJECT-TYPE
     SYNTAX      DocsIfCmMacEntry
     MAX-ACCESS  not-accessible
     STATUS      current
     DESCRIPTION
         "An entry containing objects describing attributes of
          each MAC entry, extending the information in ifEntry.
          An entry in this table exists for each ifEntry with an
          ifType of docsCableMaclayer(127)."
     INDEX { ifIndex }
     ::= { docsIfCmMacTable 1 }

DocsIfCmMacEntry ::= SEQUENCE {
         docsIfCmCmtsAddress           MacAddress,
         docsIfCmCapabilities          BITS,
         docsIfCmRangingRespTimeout    TimeTicks,
         docsIfCmRangingTimeout        TimeInterval
      }

docsIfCmCmtsAddress OBJECT-TYPE
     SYNTAX      MacAddress
     MAX-ACCESS  read-only
     STATUS      current
     DESCRIPTION
         "Identifies the CMTS that is believed to control this MAC
          domain.  At the CM, this will be the source address from
          SYNC, MAP, and other MAC-layer messages.  If the CMTS is
          unknown, returns 00-00-00-00-00-00."
     REFERENCE
         "Data-Over-Cable Service Interface Specifications: Radio
          Frequency Interface Specification SP-RFIv2.0-I10-051209,
          Section 8.2.2."
     ::= { docsIfCmMacEntry 1 }

docsIfCmCapabilities OBJECT-TYPE
     SYNTAX      BITS {
         atmCells(0),
         concatenation(1)
     }
     MAX-ACCESS  read-only
     STATUS      current
     DESCRIPTION
         "Identifies the capabilities of the MAC implementation
          at this interface.  Note that packet transmission is
          always supported.  Therefore, there is no specific bit
          required to explicitly indicate this capability.
          Note that BITS objects are encoded most significant bit
          first.  For example, if bit 1 is set, the value of this
          object is the octet string '40'H."
     ::= { docsIfCmMacEntry 2 }

docsIfCmRangingRespTimeout OBJECT-TYPE
     SYNTAX      TimeTicks
     MAX-ACCESS  read-write
     STATUS      obsolete
     DESCRIPTION
         "Waiting time for a Ranging Response packet.
          This object has been obsoleted and replaced by
          docsIfCmRangingTimeout to correct the typing to
          TimeInterval."
     REFERENCE
         "Data-Over-Cable Service Interface Specifications: Radio
          Frequency Interface Specification SP-RFIv2.0-I10-051209,
          Section 9.1.6."
     DEFVAL { 20 }
     ::= { docsIfCmMacEntry 3 }

docsIfCmRangingTimeout OBJECT-TYPE
     SYNTAX      TimeInterval
     UNITS       "HundredOfSeconds"
     MAX-ACCESS  read-write
     STATUS      current
     DESCRIPTION
         "Waiting time for a Ranging Response packet.
          This object MUST NOT persist at reinitialization
          of the managed system."
     REFERENCE
         "Data-Over-Cable Service Interface Specifications: Radio
          Frequency Interface Specification SP-RFIv2.0-I10-051209,
          Section 9.1.6, timer T3."
     DEFVAL { 20 }
     ::= { docsIfCmMacEntry 4 }

--
-- CM status table.
-- This table is implemented only at the CM.
--

docsIfCmStatusTable OBJECT-TYPE
     SYNTAX      SEQUENCE OF DocsIfCmStatusEntry
     MAX-ACCESS  not-accessible
     STATUS      current
     DESCRIPTION
         "This table maintains a number of status objects
          and counters for Cable Modems."
     ::= { docsIfCmObjects 2 }

docsIfCmStatusEntry OBJECT-TYPE
     SYNTAX      DocsIfCmStatusEntry
     MAX-ACCESS  not-accessible
     STATUS      current
     DESCRIPTION
         "A set of status objects and counters for a single MAC
          layer instance in Cable Modem.
          An entry in this table exists for each ifEntry with an
          ifType of docsCableMaclayer(127)."
     INDEX { ifIndex }
     ::= { docsIfCmStatusTable 1 }

DocsIfCmStatusEntry ::= SEQUENCE {
         docsIfCmStatusValue               INTEGER,
         docsIfCmStatusCode                OCTET STRING,
         docsIfCmStatusTxPower             TenthdBmV,
         docsIfCmStatusResets              Counter32,
         docsIfCmStatusLostSyncs           Counter32,
         docsIfCmStatusInvalidMaps         Counter32,
         docsIfCmStatusInvalidUcds         Counter32,
         docsIfCmStatusInvalidRangingResponses   Counter32,
         docsIfCmStatusInvalidRegistrationResponses Counter32,
         docsIfCmStatusT1Timeouts          Counter32,
         docsIfCmStatusT2Timeouts          Counter32,
         docsIfCmStatusT3Timeouts          Counter32,
         docsIfCmStatusT4Timeouts          Counter32,
         docsIfCmStatusRangingAborteds     Counter32,
         docsIfCmStatusDocsisOperMode      DocsisQosVersion,
         docsIfCmStatusModulationType      DocsisUpstreamType,
         docsIfCmStatusEqualizationData    DocsEqualizerData,
         docsIfCmStatusUCCs                Counter32,
         docsIfCmStatusUCCFails            Counter32
     }

docsIfCmStatusValue OBJECT-TYPE
     SYNTAX      INTEGER {
         other(1),
         notReady(2),
         notSynchronized(3),
         phySynchronized(4),
         usParametersAcquired(5),
         rangingComplete(6),
         ipComplete(7),
         todEstablished(8),
         securityEstablished(9),
         paramTransferComplete(10),
         registrationComplete(11),
         operational(12),
         accessDenied(13)
     }
     MAX-ACCESS  read-only
     STATUS      current
     DESCRIPTION
         "Current Cable Modem connectivity state, as specified
          in the RF Interface Specification.  Interpretations for
          state values 1-12 are clearly outlined in the SP-RFI
          reference given below.
          The state value accessDenied(13) indicates the CMTS has
          sent a Registration Aborted message to the CM.  The same
          state is reported as accessDenied(7) by the CMTS object
          docsIfCmtsCmStatusValue."
     REFERENCE
         "Data-Over-Cable Service Interface Specifications: Radio
          Frequency Interface Specification SP-RFIv2.0-I10-051209,
          Section 11.2.
          Data-Over-Cable Service Interface Specifications:

          Operations Support System Interface Specification
          SP-OSSIv2.0-I09-050812, Section 6.3.4.2."
     ::= { docsIfCmStatusEntry 1 }

docsIfCmStatusCode OBJECT-TYPE
     SYNTAX      OCTET STRING (SIZE( 0 | 5 | 6 ))
     MAX-ACCESS  read-only
     STATUS      current
     DESCRIPTION
         "Status code for a Cable Modem as defined in the
          OSSI Specification.  The status code consists
          of a single character indicating error groups, followed
          by a two- or three-digit number indicating the status
          condition, followed by a decimal.
          An example of a returned value could be 'T101.0'.
          The zero-length OCTET STRING indicates no status code yet
          registered."
     REFERENCE
         "Data-Over-Cable Service Interface Specifications:
          Operations Support System Interface Specification
          SP-OSSIv2.0-I09-050812, Annex D."
     ::= { docsIfCmStatusEntry 2 }

docsIfCmStatusTxPower OBJECT-TYPE
     SYNTAX      TenthdBmV
     UNITS       "TenthdBmV"
     MAX-ACCESS  read-only
     STATUS      current
     DESCRIPTION
         "The operational transmit power for the attached upstream
          channel."
     REFERENCE
         "Data-Over-Cable Service Interface Specifications: Radio
          Frequency Interface Specification SP-RFIv2.0-I10-051209,
          Section 6.2.18."
     ::= { docsIfCmStatusEntry 3 }

docsIfCmStatusResets OBJECT-TYPE
     SYNTAX      Counter32
     UNITS       "resets"
     MAX-ACCESS  read-only
     STATUS      current
     DESCRIPTION
         "Number of times the CM reset or initialized this
          interface.
          Discontinuities in the value of this counter can occur
          at reinitialization of the managed system, and at other

          times as indicated by the value of
          ifCounterDiscontinuityTime for the associated ifIndex."
     ::= { docsIfCmStatusEntry 4 }

docsIfCmStatusLostSyncs OBJECT-TYPE
     SYNTAX      Counter32
     MAX-ACCESS  read-only
     STATUS      current
     DESCRIPTION
         "Number of times the CM lost synchronization with
          the downstream channel.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Section 8.3.2."
     ::= { docsIfCmStatusEntry 5 }

docsIfCmStatusInvalidMaps OBJECT-TYPE
     SYNTAX      Counter32
     UNITS       "maps"
     MAX-ACCESS  read-only
     STATUS      current
     DESCRIPTION
         "Number of times the CM received invalid MAP messages.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Section 8.3.4."
     ::= { docsIfCmStatusEntry 6 }

docsIfCmStatusInvalidUcds OBJECT-TYPE
     SYNTAX      Counter32
     UNITS       "messages"
     MAX-ACCESS  read-only
     STATUS      current
     DESCRIPTION
         "Number of times the CM received invalid UCD messages.
          Discontinuities in the value of this counter can occur
          at reinitialization of the managed system, and at other
          times as indicated by the value of

          ifCounterDiscontinuityTime for the associated ifIndex."
     REFERENCE
         "Data-Over-Cable Service Interface Specifications: Radio
          Frequency Interface Specification SP-RFIv2.0-I10-051209,
          Section 8.3.3."
     ::= { docsIfCmStatusEntry 7 }

docsIfCmStatusInvalidRangingResponses OBJECT-TYPE
     SYNTAX      Counter32
     UNITS       "messages"
     MAX-ACCESS  read-only
     STATUS      current
     DESCRIPTION
         "Number of times the CM received invalid ranging response
          messages.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Section 8.3.6."
     ::= { docsIfCmStatusEntry 8 }

docsIfCmStatusInvalidRegistrationResponses OBJECT-TYPE
     SYNTAX      Counter32
     UNITS       "messages"
     MAX-ACCESS  read-only
     STATUS      current
     DESCRIPTION
         "Number of times the CM received invalid registration
          response messages.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Section 8.3.8."
     ::= { docsIfCmStatusEntry 9 }

docsIfCmStatusT1Timeouts OBJECT-TYPE
     SYNTAX      Counter32
     UNITS       "timeouts"
     MAX-ACCESS  read-only
     STATUS      current
     DESCRIPTION
         "Number of times counter T1 expired in the CM.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Figure 9-2."
     ::= { docsIfCmStatusEntry 10 }

docsIfCmStatusT2Timeouts OBJECT-TYPE
     SYNTAX      Counter32
     UNITS       "timeouts"
     MAX-ACCESS  read-only
     STATUS      current
     DESCRIPTION
         "Number of times counter T2 expired in the CM.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Figure 9-2."
     ::= { docsIfCmStatusEntry 11 }

docsIfCmStatusT3Timeouts OBJECT-TYPE
     SYNTAX      Counter32
     UNITS       "timeouts"
     MAX-ACCESS  read-only
     STATUS      current
     DESCRIPTION
         "Number of times counter T3 expired in the CM.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Figure 9-2."
     ::= { docsIfCmStatusEntry 12 }

docsIfCmStatusT4Timeouts OBJECT-TYPE
     SYNTAX      Counter32
     UNITS       "timeouts"
     MAX-ACCESS  read-only
     STATUS      current
     DESCRIPTION
         "Number of times counter T4 expired in the CM.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Figure 9-2."
     ::= { docsIfCmStatusEntry 13 }

docsIfCmStatusRangingAborteds OBJECT-TYPE
     SYNTAX      Counter32
     UNITS       "attempts"
     MAX-ACCESS  read-only
     STATUS      current
     DESCRIPTION
         "Number of times the ranging process was aborted
          by the CMTS.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Section 9.3.3."
     ::= { docsIfCmStatusEntry 14 }

docsIfCmStatusDocsisOperMode OBJECT-TYPE
     SYNTAX      DocsisQosVersion
     MAX-ACCESS  read-only
     STATUS      current
     DESCRIPTION
          "Indication of whether the device has registered using 1.0
           Class of Service or 1.1 Quality of Service.
           An unregistered CM SHOULD indicate 'docsis11' for a
           docsIfDocsisBaseCapability value of DOCSIS 1.1/2.0.  An
           unregistered CM SHOULD indicate 'docsis10'  for a
           docsIfDocsisBaseCapability value of DOCSIS 1.0."
     REFERENCE
         "Data-Over-Cable Service Interface Specifications: Radio
          Frequency Interface Specification SP-RFIv2.0-I10-051209,
          Annex G."
     ::= { docsIfCmStatusEntry 15 }

docsIfCmStatusModulationType OBJECT-TYPE
      SYNTAX      DocsisUpstreamType
      MAX-ACCESS  read-only
      STATUS      current
      DESCRIPTION
          "Indicates modulation type status currently used by the
           CM.  Since this object specifically identifies PHY mode,
           the shared upstream channel type is not permitted."
     REFERENCE
         "Data-Over-Cable Service Interface Specifications: Radio
          Frequency Interface Specification SP-RFIv2.0-I10-051209,
          Section 6.2.1."
      ::= { docsIfCmStatusEntry 16 }

docsIfCmStatusEqualizationData OBJECT-TYPE
     SYNTAX      DocsEqualizerData
     MAX-ACCESS  read-only
     STATUS      current
     DESCRIPTION
         "Pre-equalization data for this CM after convolution with
          data indicated in the RNG-RSP.  This data is valid when
          docsIfUpChannelPreEqEnable is set to true."
     REFERENCE
         "Data-Over-Cable Service Interface Specifications: Radio
          Frequency Interface Specification SP-RFIv2.0-I10-051209,
          Figure 8-23."
     ::= { docsIfCmStatusEntry 17 }

docsIfCmStatusUCCs OBJECT-TYPE
     SYNTAX          Counter32
     UNITS           "attempts"
     MAX-ACCESS      read-only
     STATUS          current
     DESCRIPTION
         "The number of successful Upstream Channel Change
          transactions.
          Discontinuities in the value of this counter can occur
          at reinitialization of the managed system, and at other
          times as indicated by the value of
          ifCounterDiscontinuityTime for the associated ifIndex."
     ::= { docsIfCmStatusEntry 18 }

docsIfCmStatusUCCFails OBJECT-TYPE
     SYNTAX          Counter32
     UNITS           "attempts"
     MAX-ACCESS      read-only
     STATUS          current
     DESCRIPTION
         "The number of failed Upstream Channel Change
          transactions.
          Discontinuities in the value of this counter can occur
          at reinitialization of the managed system, and at other
          times as indicated by the value of
          ifCounterDiscontinuityTime for the associated ifIndex."
     ::= { docsIfCmStatusEntry 19 }

--
-- The Cable Modem Service Table
--

docsIfCmServiceTable OBJECT-TYPE
     SYNTAX      SEQUENCE OF DocsIfCmServiceEntry
     MAX-ACCESS  not-accessible
     STATUS      current
     DESCRIPTION
         "Describes the attributes of each upstream service queue
          on a CM."
     ::= { docsIfCmObjects 3 }

docsIfCmServiceEntry OBJECT-TYPE
     SYNTAX      DocsIfCmServiceEntry
     MAX-ACCESS  not-accessible
     STATUS      current
     DESCRIPTION
         "Describes the attributes of an upstream bandwidth service
          queue.
          An entry in this table exists for each Service ID.
          The primary index is an ifIndex with an ifType of
          docsCableMaclayer(127)."
     INDEX { ifIndex, docsIfCmServiceId }
     ::= { docsIfCmServiceTable 1 }

DocsIfCmServiceEntry ::= SEQUENCE {
         docsIfCmServiceId               Integer32,
         docsIfCmServiceQosProfile       Integer32,
         docsIfCmServiceTxSlotsImmed     Counter32,
         docsIfCmServiceTxSlotsDed       Counter32,
         docsIfCmServiceTxRetries        Counter32,
         docsIfCmServiceTxExceededs      Counter32,
         docsIfCmServiceRqRetries        Counter32,
         docsIfCmServiceRqExceededs      Counter32,
         docsIfCmServiceExtTxSlotsImmed  Counter64,
         docsIfCmServiceExtTxSlotsDed    Counter64

      }

docsIfCmServiceId OBJECT-TYPE
     SYNTAX      Integer32 (1..16383)
     MAX-ACCESS  not-accessible
     STATUS      current
     DESCRIPTION
         "Identifies a service queue for upstream bandwidth.  The
          attributes of this service queue are shared between the
          CM and the CMTS.  The CMTS allocates upstream bandwidth
          to this service queue based on requests from the CM and
          on the class of service associated with this queue."
     ::= { docsIfCmServiceEntry 1 }

docsIfCmServiceQosProfile OBJECT-TYPE
     SYNTAX      Integer32 (0..16383)
     MAX-ACCESS  read-only
     STATUS      current
     DESCRIPTION
         "The index in docsIfQosProfileTable describing the quality
          of service attributes associated with this particular
          service.  If no associated entry in docsIfQosProfileTable
          exists, this object returns a value of zero."
     ::= { docsIfCmServiceEntry 2 }

docsIfCmServiceTxSlotsImmed OBJECT-TYPE
     SYNTAX      Counter32
     UNITS       "mini-slots"
     MAX-ACCESS  read-only
     STATUS      current
     DESCRIPTION
         "The number of upstream mini-slots that have been used to
          transmit data PDUs in immediate (contention) mode.  This
          includes only those PDUs that are presumed to have
          arrived at the head-end (i.e., those that were explicitly
          acknowledged).  It does not include retransmission attempts
          or mini-slots used by requests.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Section 9.4."
     ::= { docsIfCmServiceEntry 3 }

docsIfCmServiceTxSlotsDed OBJECT-TYPE
     SYNTAX      Counter32
     UNITS       "mini-slots"
     MAX-ACCESS  read-only
     STATUS      current
     DESCRIPTION
         "The number of upstream mini-slots that have been used to
          transmit data PDUs in dedicated mode (i.e., as a result
          of a unicast Data Grant).
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Section 9.4."
     ::= { docsIfCmServiceEntry 4 }

docsIfCmServiceTxRetries OBJECT-TYPE
     SYNTAX      Counter32
     UNITS       "attempts"
     MAX-ACCESS  read-only
     STATUS      current
     DESCRIPTION
         "The number of attempts to transmit data PDUs containing
          requests for acknowledgment that did not result in
          acknowledgment.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Section 9.4."
     ::= { docsIfCmServiceEntry 5 }

docsIfCmServiceTxExceededs OBJECT-TYPE
     SYNTAX      Counter32
     UNITS       "attempts"
     MAX-ACCESS  read-only
     STATUS      current
     DESCRIPTION
         "The number of data PDU transmission failures due to
          excessive retries without acknowledgment.
          Discontinuities in the value of this counter can occur
          at reinitialization of the managed system, and at other
          times as indicated by the value of

          ifCounterDiscontinuityTime for the associated ifIndex."
     REFERENCE
         "Data-Over-Cable Service Interface Specifications: Radio
          Frequency Interface Specification SP-RFIv2.0-I10-051209,
          Section 9.4."
     ::= { docsIfCmServiceEntry 6 }

docsIfCmServiceRqRetries OBJECT-TYPE
     SYNTAX      Counter32
     UNITS       "attempts"
     MAX-ACCESS  read-only
     STATUS      current
     DESCRIPTION
         "The number of attempts to transmit bandwidth requests
          that did not result in acknowledgment.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Section 9.4."
     ::= { docsIfCmServiceEntry 7 }

docsIfCmServiceRqExceededs OBJECT-TYPE
     SYNTAX      Counter32
     UNITS       "attempts"
     MAX-ACCESS  read-only
     STATUS      current
     DESCRIPTION
         "The number of requests for bandwidth that failed due to
          excessive retries without acknowledgment.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Section 9.4."
     ::= { docsIfCmServiceEntry 8 }

docsIfCmServiceExtTxSlotsImmed OBJECT-TYPE
     SYNTAX      Counter64
     UNITS       "mini-slots"
     MAX-ACCESS  read-only
     STATUS      current
     DESCRIPTION
         "The number of upstream mini-slots that have been used to
          transmit data PDUs in immediate (contention) mode.  This
          includes only those PDUs that are presumed to have
          arrived at the head-end (i.e., those that were explicitly
          acknowledged).  It does not include retransmission attempts
          or mini-slots used by requests.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Section 9.4."
     ::= { docsIfCmServiceEntry 9 }

docsIfCmServiceExtTxSlotsDed OBJECT-TYPE
     SYNTAX      Counter64
     UNITS       "mini-slots"
     MAX-ACCESS  read-only
     STATUS      current
     DESCRIPTION
         "The number of upstream mini-slots that have been used to
          transmit data PDUs in dedicated mode (i.e., as a result
          of a unicast Data Grant).
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Section 9.4."
     ::= { docsIfCmServiceEntry 10 }

--
-- CMTS GROUP
--

--
-- The CMTS MAC Table
--

docsIfCmtsMacTable OBJECT-TYPE
     SYNTAX      SEQUENCE OF DocsIfCmtsMacEntry
     MAX-ACCESS  not-accessible
     STATUS      current
     DESCRIPTION
         "Describes the attributes of each CMTS MAC interface,
          extending the information available from ifEntry.
          Mandatory for all CMTS devices."
     ::= { docsIfCmtsObjects 1 }

docsIfCmtsMacEntry OBJECT-TYPE
     SYNTAX      DocsIfCmtsMacEntry
     MAX-ACCESS  not-accessible
     STATUS      current
     DESCRIPTION
         "An entry containing objects describing attributes of each
          MAC entry, extending the information in ifEntry.
          An entry in this table exists for each ifEntry with an
          ifType of docsCableMaclayer(127)."
     INDEX { ifIndex }
     ::= { docsIfCmtsMacTable 1 }

DocsIfCmtsMacEntry ::= SEQUENCE {
         docsIfCmtsCapabilities            BITS,
         docsIfCmtsSyncInterval            Integer32,
         docsIfCmtsUcdInterval             Integer32,
         docsIfCmtsMaxServiceIds           Integer32,
         docsIfCmtsInsertionInterval       TimeTicks,   -- Obsolete
         docsIfCmtsInvitedRangingAttempts  Integer32,
         docsIfCmtsInsertInterval          TimeInterval,
         docsIfCmtsMacStorageType          StorageType
     }

docsIfCmtsCapabilities OBJECT-TYPE
     SYNTAX      BITS {
         atmCells(0),
         concatenation(1)
     }
     MAX-ACCESS  read-only
     STATUS      current
     DESCRIPTION
         "Identifies the capabilities of the CMTS MAC
          implementation at this interface.  Note that packet
          transmission is always supported.  Therefore, there
          is no specific bit required to explicitly indicate
          this capability.
          Note that BITS objects are encoded most significant bit
          first.  For example, if bit 1 is set, the value of this
          object is the octet string '40'H."
     ::= { docsIfCmtsMacEntry 1 }

docsIfCmtsSyncInterval OBJECT-TYPE
     SYNTAX      Integer32 (1..200)
     UNITS       "Milliseconds"
     MAX-ACCESS  read-write
     STATUS      current
     DESCRIPTION
         "The interval between CMTS transmission of successive SYNC
          messages at this interface."
     REFERENCE
         "Data-Over-Cable Service Interface Specifications: Radio
          Frequency Interface Specification SP-RFIv2.0-I10-051209,
          Section 9.3."
     ::= { docsIfCmtsMacEntry 2 }

docsIfCmtsUcdInterval OBJECT-TYPE
     SYNTAX      Integer32 (1..2000)
     UNITS       "Milliseconds"
     MAX-ACCESS  read-write
     STATUS      current
     DESCRIPTION
         "The interval between CMTS transmission of successive
          Upstream Channel Descriptor messages for each upstream
          channel at this interface."
     REFERENCE
         "Data-Over-Cable Service Interface Specifications: Radio
          Frequency Interface Specification SP-RFIv2.0-I10-051209,
          Section 9.3"
     ::= { docsIfCmtsMacEntry 3 }

docsIfCmtsMaxServiceIds OBJECT-TYPE
     SYNTAX     Integer32 (1..16383)
     UNITS      "SIDs"
     MAX-ACCESS read-only
     STATUS     current
     DESCRIPTION
         "The maximum number of service IDs that may be
          simultaneously active."
     ::= { docsIfCmtsMacEntry 4 }

docsIfCmtsInsertionInterval OBJECT-TYPE
     SYNTAX      TimeTicks
     MAX-ACCESS  read-write
     STATUS      obsolete
     DESCRIPTION
         "The amount of time to elapse between each broadcast
          initial maintenance grant.  Broadcast initial maintenance
          grants are used to allow new cable modems to join the
          network.  Zero indicates that a vendor-specific algorithm
          is used instead of a fixed time.  The maximum amount of

          time permitted by the specification is 2 seconds.
          This object has been obsoleted and replaced by
          docsIfCmtsInsertInterval to fix a SYNTAX typing problem."
     REFERENCE
         "Data-Over-Cable Service Interface Specifications: Radio
          Frequency Interface Specification SP-RFIv2.0-I10-051209,
          Annex B."
     ::= { docsIfCmtsMacEntry 5 }

docsIfCmtsInvitedRangingAttempts OBJECT-TYPE
     SYNTAX      Integer32 (0..1024)
     UNITS      "attempts"
     MAX-ACCESS  read-write
     STATUS      current
     DESCRIPTION
         "The maximum number of attempts to make on invitations
          for ranging requests.  A value of zero means the system
          SHOULD attempt to range forever."
     REFERENCE
         "Data-Over-Cable Service Interface Specifications: Radio
          Frequency Interface Specification SP-RFIv2.0-I10-051209,
          Section 9.3.3 and Annex B."
     ::= { docsIfCmtsMacEntry 6 }

docsIfCmtsInsertInterval OBJECT-TYPE
     SYNTAX      TimeInterval
     UNITS       "HundredOfSeconds"
     MAX-ACCESS  read-write
     STATUS      current
     DESCRIPTION
         "The amount of time to elapse between each broadcast
          initial maintenance grant.  Broadcast initial maintenance
          grants are used to allow new cable modems to join the
          network.  Zero indicates that a vendor-specific algorithm
          is used instead of a fixed time.  The maximum amount of
          time permitted by the specification is 2 seconds."
     REFERENCE
         "Data-Over-Cable Service Interface Specifications: Radio
          Frequency Interface Specification SP-RFIv2.0-I10-051209,
          Annex B."
     ::= { docsIfCmtsMacEntry 7 }

docsIfCmtsMacStorageType OBJECT-TYPE
     SYNTAX       StorageType
     MAX-ACCESS   read-only
     STATUS       current
     DESCRIPTION
         "The storage type for this conceptual row.

          Entries with this object set to permanent(4)
          do not require write operations for read-write
          objects."
     ::= { docsIfCmtsMacEntry 8 }

--
--
-- CMTS status table.
--

docsIfCmtsStatusTable OBJECT-TYPE
     SYNTAX      SEQUENCE OF DocsIfCmtsStatusEntry
     MAX-ACCESS  not-accessible
     STATUS      current
     DESCRIPTION
         "For the MAC layer, this group maintains a number of
          status objects and counters."
     ::= { docsIfCmtsObjects 2 }

docsIfCmtsStatusEntry OBJECT-TYPE
     SYNTAX      DocsIfCmtsStatusEntry
     MAX-ACCESS  not-accessible
     STATUS      current
     DESCRIPTION
        "Status entry for a single MAC layer.
          An entry in this table exists for each ifEntry with an
          ifType of docsCableMaclayer(127)."
     INDEX { ifIndex }
     ::= { docsIfCmtsStatusTable 1 }

DocsIfCmtsStatusEntry ::= SEQUENCE {
         docsIfCmtsStatusInvalidRangeReqs        Counter32,
         docsIfCmtsStatusRangingAborteds         Counter32,
         docsIfCmtsStatusInvalidRegReqs          Counter32,
         docsIfCmtsStatusFailedRegReqs           Counter32,
         docsIfCmtsStatusInvalidDataReqs         Counter32,
         docsIfCmtsStatusT5Timeouts              Counter32
     }

docsIfCmtsStatusInvalidRangeReqs OBJECT-TYPE
     SYNTAX      Counter32
     UNITS       "messages"
     MAX-ACCESS  read-only
     STATUS      current
     DESCRIPTION
         "This object counts invalid RNG-REQ messages received on
          this interface.
          Discontinuities in the value of this counter can occur

          at reinitialization of the managed system, and at other
          times as indicated by the value of
          ifCounterDiscontinuityTime for the associated ifIndex."
     REFERENCE
         "Data-Over-Cable Service Interface Specifications: Radio
          Frequency Interface Specification SP-RFIv2.0-I10-051209,
          Section 8.3.5."
     ::= { docsIfCmtsStatusEntry 1 }

docsIfCmtsStatusRangingAborteds OBJECT-TYPE
     SYNTAX      Counter32
     UNITS       "attempts"
     MAX-ACCESS  read-only
     STATUS      current
     DESCRIPTION
         "This object counts ranging attempts that were explicitly
          aborted by the CMTS.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Section 8.3.6."
     ::= { docsIfCmtsStatusEntry 2 }

docsIfCmtsStatusInvalidRegReqs OBJECT-TYPE
     SYNTAX      Counter32
     UNITS       "messages"
     MAX-ACCESS  read-only
     STATUS      current
     DESCRIPTION
         "This object counts invalid REG-REQ messages received on
          this interface; that is, syntax, out of range parameters,
          or erroneous requests.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Section 8.3.7."
     ::= { docsIfCmtsStatusEntry 3 }

docsIfCmtsStatusFailedRegReqs OBJECT-TYPE
     SYNTAX      Counter32
     UNITS       "attempts"
     MAX-ACCESS  read-only
     STATUS      current
     DESCRIPTION
         "This object counts failed registration attempts.  Included
          are docsIfCmtsStatusInvalidRegReqs, authentication, and
          class of service failures.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Section 8.3.7."
     ::= { docsIfCmtsStatusEntry 4 }

docsIfCmtsStatusInvalidDataReqs OBJECT-TYPE
     SYNTAX      Counter32
     UNITS       "messages"
     MAX-ACCESS  read-only
     STATUS      current
     DESCRIPTION
         "This object counts invalid data request messages
          received on this interface.
          Discontinuities in the value of this counter can occur
          at reinitialization of the managed system, and at other
          times as indicated by the value of
          ifCounterDiscontinuityTime for the associated ifIndex."
     ::= { docsIfCmtsStatusEntry 5 }

docsIfCmtsStatusT5Timeouts OBJECT-TYPE
     SYNTAX      Counter32
     UNITS       "timeouts"
     MAX-ACCESS  read-only
     STATUS      current
     DESCRIPTION
         "This object counts the number of times counter T5
          expired on this interface.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Figure 9-2."
     ::= { docsIfCmtsStatusEntry 6 }

--
-- CM status table (within CMTS).
-- This table is implemented only at the CMTS.
-- It contains per-CM status information available in the CMTS.
--

docsIfCmtsCmStatusTable OBJECT-TYPE
     SYNTAX      SEQUENCE OF DocsIfCmtsCmStatusEntry
     MAX-ACCESS  not-accessible
     STATUS      current
     DESCRIPTION
         "A set of objects in the CMTS, maintained for each
          cable modem connected to this CMTS."
     ::= { docsIfCmtsObjects 3 }

docsIfCmtsCmStatusEntry OBJECT-TYPE
     SYNTAX      DocsIfCmtsCmStatusEntry
     MAX-ACCESS  not-accessible
     STATUS      current
     DESCRIPTION
         "Status information for a single cable modem.
          An entry in this table exists for each cable modem
          that is connected to the CMTS implementing this table."
     INDEX { docsIfCmtsCmStatusIndex }
     ::= { docsIfCmtsCmStatusTable 1 }

DocsIfCmtsCmStatusEntry ::= SEQUENCE {
         docsIfCmtsCmStatusIndex               Integer32,
         docsIfCmtsCmStatusMacAddress          MacAddress,
         docsIfCmtsCmStatusIpAddress        IpAddress, -- deprecated
         docsIfCmtsCmStatusDownChannelIfIndex  InterfaceIndexOrZero,
         docsIfCmtsCmStatusUpChannelIfIndex    InterfaceIndexOrZero,
         docsIfCmtsCmStatusRxPower             TenthdBmV,
         docsIfCmtsCmStatusTimingOffset        Unsigned32,
         docsIfCmtsCmStatusEqualizationData    DocsEqualizerData,
         docsIfCmtsCmStatusValue               INTEGER,
         docsIfCmtsCmStatusUnerroreds          Counter32,
         docsIfCmtsCmStatusCorrecteds          Counter32,
         docsIfCmtsCmStatusUncorrectables      Counter32,
         docsIfCmtsCmStatusSignalNoise         TenthdB,
         docsIfCmtsCmStatusMicroreflections    Integer32,
         docsIfCmtsCmStatusExtUnerroreds       Counter64,
         docsIfCmtsCmStatusExtCorrecteds       Counter64,
         docsIfCmtsCmStatusExtUncorrectables   Counter64,
         docsIfCmtsCmStatusDocsisRegMode       DocsisQosVersion,
         docsIfCmtsCmStatusModulationType      DocsisUpstreamType,
         docsIfCmtsCmStatusInetAddressType     InetAddressType,
         docsIfCmtsCmStatusInetAddress         InetAddress,
         docsIfCmtsCmStatusValueLastUpdate     TimeStamp,
         docsIfCmtsCmStatusHighResolutionTimingOffset Unsigned32
     }

docsIfCmtsCmStatusIndex OBJECT-TYPE
     SYNTAX      Integer32 (1..2147483647)
     MAX-ACCESS  not-accessible
     STATUS      current
     DESCRIPTION
         "Index value to uniquely identify an entry in this table.
          For an individual cable modem, this index value SHOULD
          NOT change during CMTS uptime."
     ::= { docsIfCmtsCmStatusEntry 1 }

docsIfCmtsCmStatusMacAddress OBJECT-TYPE
     SYNTAX      MacAddress
     MAX-ACCESS  read-only
     STATUS      current
     DESCRIPTION
         "MAC address of the cable modem.  If the cable modem has
          multiple MAC addresses, this is the MAC address associated
          with the Cable interface."
     REFERENCE
         "Data-Over-Cable Service Interface Specifications: Radio
          Frequency Interface Specification SP-RFIv2.0-I10-051209,
          Section 8.2.2."
     ::= { docsIfCmtsCmStatusEntry 2 }

docsIfCmtsCmStatusIpAddress OBJECT-TYPE
     SYNTAX      IpAddress
     MAX-ACCESS  read-only
     STATUS      deprecated
     DESCRIPTION
         "IP address of this cable modem.  If the cable modem has no
          IP address assigned, or the IP address is unknown, this
          object returns a value of 0.0.0.0.  If the cable modem has
          multiple IP addresses, this object returns the IP address
          associated with the Cable interface.
          This object has been deprecated and replaced by
          docsIfCmtsCmStatusInetAddressType and
          docsIfCmtsCmStatusInetAddress, to enable IPv6 addressing
          in the future."
     ::= { docsIfCmtsCmStatusEntry 3 }

docsIfCmtsCmStatusDownChannelIfIndex OBJECT-TYPE
     SYNTAX      InterfaceIndexOrZero
     MAX-ACCESS  read-only
     STATUS      current
     DESCRIPTION
         "IfIndex of the downstream channel that this CM is
          connected to.  If the downstream channel is unknown, this
          object returns a value of zero."
     ::= { docsIfCmtsCmStatusEntry 4 }

docsIfCmtsCmStatusUpChannelIfIndex OBJECT-TYPE
     SYNTAX      InterfaceIndexOrZero
     MAX-ACCESS  read-only
     STATUS      current
     DESCRIPTION
        "For DOCSIS 2.0, indicates the ifIndex of the logical
         upstream channel (ifType 205) this CM is connected to.
         For DOCSIS 1.x, indicates the ifIndex of the upstream
          channel (ifType 129) this CM is connected to.
          If the upstream channel is unknown, this object
          returns a value of zero."
     ::= { docsIfCmtsCmStatusEntry 5 }

docsIfCmtsCmStatusRxPower OBJECT-TYPE
     SYNTAX      TenthdBmV
     UNITS       "ThenthdBmV"
     MAX-ACCESS  read-only
     STATUS      current
     DESCRIPTION
         "The receive power as perceived for upstream data from
          this cable modem.
          If the receive power is unknown, this object returns
          a value of zero."
     REFERENCE
         "Data-Over-Cable Service Interface Specifications: Radio
          Frequency Interface Specification SP-RFIv2.0-I10-051209,
          Section 6.2.18."
     ::= { docsIfCmtsCmStatusEntry 6 }

docsIfCmtsCmStatusTimingOffset OBJECT-TYPE
     SYNTAX      Unsigned32 (0..4294967295)
     MAX-ACCESS  read-only
     STATUS      current
     DESCRIPTION
         "A measure of the current round trip time for this CM.
          Used for timing of CM upstream transmissions to ensure
          synchronized arrivals at the CMTS.  Units are in terms
          of (6.25 microseconds/64).  Returns zero if the value
          is unknown.
          For channels requiring finer resolution, please refer to
          object docsIfCmtsCmStatusHighResolutionTimingOffset."
     REFERENCE
         "Data-Over-Cable Service Interface Specifications: Radio
          Frequency Interface Specification SP-RFIv2.0-I10-051209,
          Section 6.2.17."
     ::= { docsIfCmtsCmStatusEntry 7 }

docsIfCmtsCmStatusEqualizationData OBJECT-TYPE
     SYNTAX      DocsEqualizerData
     MAX-ACCESS  read-only
     STATUS      current
     DESCRIPTION
         "Equalization data for this CM, as measured by the CMTS.
          Returns the zero-length OCTET STRING if the value is
          unknown or if there is no equalization data available
          or defined."
     REFERENCE
         "Data-Over-Cable Service Interface Specifications: Radio
          Frequency Interface Specification SP-RFIv2.0-I10-051209,
          Figure 8-23."
     ::= { docsIfCmtsCmStatusEntry 8 }

docsIfCmtsCmStatusValue OBJECT-TYPE
     SYNTAX      INTEGER {
         other(1),
         ranging(2),
         rangingAborted(3),
         rangingComplete(4),
         ipComplete(5),
         registrationComplete(6),
         accessDenied(7),
         operational(8),
         -- value 8 should not be used
         registeredBPIInitializing(9)
     }
     MAX-ACCESS  read-only
     STATUS      current
     DESCRIPTION
         "Current cable modem connectivity state, as specified
          in the RF Interface Specification.  Returned status
          information is the CM status, as assumed by the CMTS,
          and indicates the following events:
          other(1)
             Any state other than below.
          ranging(2)
             The CMTS has received an Initial Ranging Request
             message from the CM, and the ranging process is not
             yet complete.
          rangingAborted(3)
             The CMTS has sent a Ranging Abort message to the CM.

          rangingComplete(4)
             The CMTS has sent a Ranging Complete message to the CM.
          ipComplete(5)
             The CMTS has received a DHCP reply message and
             forwarded it to the CM.
          registrationComplete(6)
             The CMTS has sent a Registration Response message to
             the CM.
          accessDenied(7)
             The CMTS has sent a Registration Aborted message
             to the CM.
          operational(8)
             Value 8 is considered reserved and should not be defined
             in future revisions of this MIB module to avoid conflict
             with documented implementations that support value 8 to
             indicate operational state after completing the BPI
             initialization process.
          registeredBPIInitializing(9)
             Baseline Privacy (BPI) is enabled and the CMTS is in the
             process of completing BPI initialization.  This state
             MAY last for a significant length of time if failures
             occur during the initialization process.  After
             completion of BPI initialization, the CMTS will report
             registrationComplete(6).
          The CMTS only needs to report states it is able to
          detect."
     REFERENCE
         "Data-Over-Cable Service Interface Specifications: Radio
          Frequency Interface Specification SP-RFIv2.0-I10-051209,
          Section 11.2."
     ::= { docsIfCmtsCmStatusEntry 9 }

docsIfCmtsCmStatusUnerroreds OBJECT-TYPE
     SYNTAX      Counter32
     UNITS       "codewords"
     MAX-ACCESS  read-only
     STATUS      current
     DESCRIPTION
         "Codewords received without error from this cable modem.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Section 6.2.4."
     ::= { docsIfCmtsCmStatusEntry 10 }

docsIfCmtsCmStatusCorrecteds OBJECT-TYPE
     SYNTAX      Counter32
     UNITS       "codewords"
     MAX-ACCESS  read-only
     STATUS      current
     DESCRIPTION
         "Codewords received with correctable errors from this
          cable modem.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Section 6.2.4."
     ::= { docsIfCmtsCmStatusEntry 11 }

docsIfCmtsCmStatusUncorrectables OBJECT-TYPE
     SYNTAX      Counter32
     UNITS       "codewords"
     MAX-ACCESS  read-only
     STATUS      current
     DESCRIPTION
         "Codewords received with uncorrectable errors from this
          cable modem.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Section 6.2.4."
     ::= { docsIfCmtsCmStatusEntry 12 }

docsIfCmtsCmStatusSignalNoise OBJECT-TYPE
     SYNTAX      TenthdB
     UNITS       "TenthdB"
     MAX-ACCESS  read-only
     STATUS      current
     DESCRIPTION
         "Signal/Noise ratio as perceived for upstream data from
          this cable modem.
          If the Signal/Noise is unknown, this object returns
          a value of zero."
     REFERENCE
         "Data-Over-Cable Service Interface Specifications: Radio

          Frequency Interface Specification SP-RFIv2.0-I10-051209,
          Tables 4-1 and 4-2."
     ::= { docsIfCmtsCmStatusEntry 13 }

docsIfCmtsCmStatusMicroreflections OBJECT-TYPE
     SYNTAX      Integer32 (0..255)
     UNITS       "-dBc"
     MAX-ACCESS  read-only
     STATUS      current
     DESCRIPTION
         "Total microreflections, including in-channel response
          as perceived on this interface, measured in dBc below
          the signal level.
          This object is not assumed to return an absolutely
          accurate value, but it gives a rough indication
          of microreflections received on this interface.
          It is up to the implementer to provide information
          as accurately as possible.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Tables 4-1 and 4-2"
     ::= { docsIfCmtsCmStatusEntry 14 }

docsIfCmtsCmStatusExtUnerroreds OBJECT-TYPE
     SYNTAX      Counter64
     UNITS       "codewords"
     MAX-ACCESS  read-only
     STATUS      current
     DESCRIPTION
         "Codewords received without error from this cable modem.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Section 6.2.5."
     ::= { docsIfCmtsCmStatusEntry 15 }

docsIfCmtsCmStatusExtCorrecteds OBJECT-TYPE
     SYNTAX      Counter64
     UNITS       "codewords"
     MAX-ACCESS  read-only
     STATUS      current
     DESCRIPTION
         "Codewords received with correctable errors from this
          cable modem.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Section 6.2.5."
     ::= { docsIfCmtsCmStatusEntry 16 }

docsIfCmtsCmStatusExtUncorrectables OBJECT-TYPE
     SYNTAX      Counter64
     UNITS       "codewords"
     MAX-ACCESS  read-only
     STATUS      current
     DESCRIPTION
         "Codewords received with uncorrectable errors from this
          cable modem.
          Discontinuities in the value of this counter can occur
          at reinitialization of the managed system, and at other
          times as indicated by the value of
          ifCounterDiscontinuityTime for the associated ifIndex."
     REFERENCE
         "Data-Over-Cable Service Interface Specifications: Radio
          Frequency Interface Specification SP-RFIv2.0-I10-051209,
          Section 6.2.5."
     ::= { docsIfCmtsCmStatusEntry 17 }

docsIfCmtsCmStatusDocsisRegMode OBJECT-TYPE
        SYNTAX      DocsisQosVersion
        MAX-ACCESS  read-only
        STATUS      current
        DESCRIPTION
            "Indication of whether the CM has registered using 1.0
             Class of Service or 1.1 Quality of Service."
     REFERENCE
         "Data-Over-Cable Service Interface Specifications: Radio
          Frequency Interface Specification SP-RFIv2.0-I10-051209,
          Annex G."
     ::= { docsIfCmtsCmStatusEntry 18 }

docsIfCmtsCmStatusModulationType OBJECT-TYPE
      SYNTAX      DocsisUpstreamType
      MAX-ACCESS  read-only
      STATUS      current
      DESCRIPTION
          "Indicates modulation type currently used by the CM.  Since
           this object specifically identifies PHY mode, the shared
           type is not permitted.  If the upstream channel is
           unknown, this object returns a value of zero."
     REFERENCE
         "Data-Over-Cable Service Interface Specifications: Radio
          Frequency Interface Specification SP-RFIv2.0-I10-051209,
          Table 8-19."
      ::= { docsIfCmtsCmStatusEntry 19 }

docsIfCmtsCmStatusInetAddressType OBJECT-TYPE
        SYNTAX      InetAddressType
        MAX-ACCESS  read-only
        STATUS      current
        DESCRIPTION
            "The type of internet address of
             docsIfCmtsCmStatusInetAddress.  If the cable modem
             internet address is unassigned or unknown, then the
             value of this object is unknown(0)."
        ::= { docsIfCmtsCmStatusEntry 20 }

docsIfCmtsCmStatusInetAddress OBJECT-TYPE
        SYNTAX      InetAddress
        MAX-ACCESS  read-only
        STATUS      current
        DESCRIPTION
            "Internet address of this cable modem.  If the Cable
             Modem has no Internet address assigned, or the Internet
             address is unknown, the value of this object is the
             zero-length OCTET STRING.  If the cable modem has
             multiple Internet addresses, this object returns the
             Internet address associated with the Cable
             (i.e., RF MAC) interface."
        ::= { docsIfCmtsCmStatusEntry 21 }

docsIfCmtsCmStatusValueLastUpdate OBJECT-TYPE
        SYNTAX      TimeStamp
        MAX-ACCESS  read-only
        STATUS      current
        DESCRIPTION
            "The value of sysUpTime when docsIfCmtsCmStatusValue
             was last updated."
        ::= { docsIfCmtsCmStatusEntry 22 }

docsIfCmtsCmStatusHighResolutionTimingOffset OBJECT-TYPE
     SYNTAX      Unsigned32 (0..4294967295)
     MAX-ACCESS  read-only
     STATUS      current
     DESCRIPTION
         "A measure of the current round trip time for this CM.
          Used for timing of CM upstream transmissions to ensure
          synchronized arrivals at the CMTS.  Units are in terms
          of (6.25 microseconds/(64*256)).  Returns zero if the value
          is unknown.
          This is the high resolution version of object
          docsIfCmtsCmStatusTimingOffset, for channels requiring
          finer resolution."
     REFERENCE
         "Data-Over-Cable Service Interface Specifications: Radio
          Frequency Interface Specification SP-RFIv2.0-I10-051209,
          Section 6.2.17."
     ::= { docsIfCmtsCmStatusEntry 23 }

--
-- The CMTS Service Table.
--

docsIfCmtsServiceTable OBJECT-TYPE
     SYNTAX      SEQUENCE OF DocsIfCmtsServiceEntry
     MAX-ACCESS  not-accessible
     STATUS      current
     DESCRIPTION
         "Describes the attributes of upstream service queues
          in a Cable Modem Termination System."
     ::= { docsIfCmtsObjects 4 }

docsIfCmtsServiceEntry OBJECT-TYPE
     SYNTAX      DocsIfCmtsServiceEntry
     MAX-ACCESS  not-accessible
     STATUS      current
     DESCRIPTION
         "Describes the attributes of a single upstream bandwidth
          service queue.
          Entries in this table exist for each ifEntry with an
          ifType of docsCableMaclayer(127), and for each service
          queue (Service ID) within this MAC layer.
          Entries in this table are created with the creation of
          individual Service IDs by the MAC layer and removed
          when a Service ID is removed."
     INDEX { ifIndex, docsIfCmtsServiceId }
     ::= { docsIfCmtsServiceTable 1 }

DocsIfCmtsServiceEntry ::= SEQUENCE {

         docsIfCmtsServiceId               Integer32,
         docsIfCmtsServiceCmStatusIndex    Integer32,  -- deprecated
         docsIfCmtsServiceAdminStatus      INTEGER,
         docsIfCmtsServiceQosProfile       Integer32,
         docsIfCmtsServiceCreateTime       TimeStamp,
         docsIfCmtsServiceInOctets         Counter32,
         docsIfCmtsServiceInPackets        Counter32,
         docsIfCmtsServiceNewCmStatusIndex Integer32
     }

docsIfCmtsServiceId OBJECT-TYPE
     SYNTAX      Integer32 (1..16383)
     MAX-ACCESS  not-accessible
     STATUS      current
     DESCRIPTION
         "Identifies a service queue for upstream bandwidth.  The
          attributes of this service queue are shared between the
          Cable Modem and the Cable Modem Termination System.
          The CMTS allocates upstream bandwidth to this service
          queue based on requests from the CM and on the class of
          service associated with this queue."
     ::= { docsIfCmtsServiceEntry 1 }

docsIfCmtsServiceCmStatusIndex OBJECT-TYPE
     SYNTAX      Integer32 (0..65535)
     MAX-ACCESS  read-only
     STATUS      deprecated
     DESCRIPTION
         "Pointer to an entry in docsIfCmtsCmStatusTable identifying
          the cable modem using this Service Queue.  If multiple
          cable modems are using this Service Queue, the value of
          this object is zero.
          This object has been deprecated and replaced by
          docsIfCmtsServiceNewCmStatusIndex, to fix a mismatch
          of the value range with respect to docsIfCmtsCmStatusIndex
          (1..2147483647)."
     ::= { docsIfCmtsServiceEntry 2 }

docsIfCmtsServiceAdminStatus OBJECT-TYPE
     SYNTAX      INTEGER {
         enabled(1),
         disabled(2),
         destroyed(3) }
     MAX-ACCESS  read-write
     STATUS      current
     DESCRIPTION
         "Allows a service class for a particular modem to be
          suppressed, (re-)enabled, or deleted altogether."
     ::= { docsIfCmtsServiceEntry 3 }

docsIfCmtsServiceQosProfile OBJECT-TYPE
     SYNTAX      Integer32 (0..16383)
     MAX-ACCESS  read-only
     STATUS      current
     DESCRIPTION
         "The index in docsIfQosProfileTable describing the quality
          of service attributes associated with this particular
          service.  If no associated docsIfQosProfileTable entry
          exists, this object returns a value of zero."
     ::= { docsIfCmtsServiceEntry 4 }

docsIfCmtsServiceCreateTime OBJECT-TYPE
     SYNTAX      TimeStamp
     MAX-ACCESS  read-only
     STATUS      current
     DESCRIPTION
         "The value of sysUpTime when this entry was created."
     ::= { docsIfCmtsServiceEntry 5 }

docsIfCmtsServiceInOctets OBJECT-TYPE
     SYNTAX      Counter32
     UNITS       "Bytes"
     MAX-ACCESS  read-only
     STATUS      current
     DESCRIPTION
         "The cumulative number of Packet Data octets received
          on this Service ID.  The count does not include the
          size of the Cable MAC header.
          Discontinuities in the value of this counter can occur
          at reinitialization of the managed system, and at other
          times as indicated by the value of
          ifCounterDiscontinuityTime for the associated ifIndex."
     ::= { docsIfCmtsServiceEntry 6 }

docsIfCmtsServiceInPackets OBJECT-TYPE
     SYNTAX      Counter32
     UNITS       "packets"
     MAX-ACCESS  read-only
     STATUS      current
     DESCRIPTION
         "The cumulative number of Packet Data packets received
          on this Service ID.
          Discontinuities in the value of this counter can occur
          at reinitialization of the managed system, and at other
          times as indicated by the value of
          ifCounterDiscontinuityTime for the associated ifIndex."
     ::= { docsIfCmtsServiceEntry 7 }

docsIfCmtsServiceNewCmStatusIndex OBJECT-TYPE
     SYNTAX      Integer32 (0..2147483647)
     MAX-ACCESS  read-only
     STATUS      current
     DESCRIPTION
         "Pointer (via docsIfCmtsCmStatusIndex) to an entry in
          docsIfCmtsCmStatusTable identifying the cable modem
          using this Service Queue.  If multiple cable modems are
          using this Service Queue, the value of this object is
          zero."
     ::= { docsIfCmtsServiceEntry 8 }

--
-- The following table provides upstream channel modulation profiles.
-- Entries in this table can be
-- re-used by one or more upstream channels.  An upstream channel
-- will have a modulation profile for each value of
-- docsIfModIntervalUsageCode.
--

docsIfCmtsModulationTable OBJECT-TYPE
     SYNTAX      SEQUENCE OF DocsIfCmtsModulationEntry
     MAX-ACCESS  not-accessible
     STATUS      current
     DESCRIPTION
         "Describes a modulation profile associated with one or more
          upstream channels."
     ::= { docsIfCmtsObjects 5 }

docsIfCmtsModulationEntry OBJECT-TYPE
     SYNTAX      DocsIfCmtsModulationEntry
     MAX-ACCESS  not-accessible
     STATUS      current
     DESCRIPTION
         "Describes a modulation profile for an Interval Usage Code
          for one or more upstream channels.
          Entries in this table are created by the operator.

          Initial default entries MAY be created at system
          initialization time, which could report a value of
          'permanent' or 'readOnly' for docsIfCmtsModStorageType.
          A CMTS MAY reject the creation of additional Interval
          Usage Codes for a modulation profile being defined at
          Initialization time.
          No individual objects have to be specified in order
          to create an entry in this table.

          Note that some objects do not have DEFVAL clauses
          but do have calculated defaults and need not be specified
          during row creation."
      INDEX { docsIfCmtsModIndex, docsIfCmtsModIntervalUsageCode}
     ::= { docsIfCmtsModulationTable 1 }

DocsIfCmtsModulationEntry ::= SEQUENCE {
         docsIfCmtsModIndex                    Integer32,
         docsIfCmtsModIntervalUsageCode        INTEGER,
         docsIfCmtsModControl                  RowStatus,
         docsIfCmtsModType                     INTEGER,
         docsIfCmtsModPreambleLen              Integer32,
         docsIfCmtsModDifferentialEncoding     TruthValue,
         docsIfCmtsModFECErrorCorrection       Integer32,
         docsIfCmtsModFECCodewordLength        Integer32,
         docsIfCmtsModScramblerSeed            Integer32,
         docsIfCmtsModMaxBurstSize             Integer32,
         docsIfCmtsModGuardTimeSize            Unsigned32,
         docsIfCmtsModLastCodewordShortened    TruthValue,
         docsIfCmtsModScrambler                TruthValue,
         docsIfCmtsModByteInterleaverDepth     Unsigned32,
         docsIfCmtsModByteInterleaverBlockSize Unsigned32,
         docsIfCmtsModPreambleType             INTEGER,
         docsIfCmtsModTcmErrorCorrectionOn     TruthValue,
         docsIfCmtsModScdmaInterleaverStepSize Unsigned32,
         docsIfCmtsModScdmaSpreaderEnable      TruthValue,
         docsIfCmtsModScdmaSubframeCodes       Unsigned32,
         docsIfCmtsModChannelType              DocsisUpstreamType,
         docsIfCmtsModStorageType              StorageType
     }

docsIfCmtsModIndex OBJECT-TYPE
     SYNTAX       Integer32 (1..2147483647)
     MAX-ACCESS   not-accessible
     STATUS      current
     DESCRIPTION
          "An index into the Channel Modulation table representing
           a group of Interval Usage Codes, all associated with the
           same channel."
     ::= { docsIfCmtsModulationEntry 1 }

docsIfCmtsModIntervalUsageCode OBJECT-TYPE
     SYNTAX       INTEGER {
         request(1),
         requestData(2),
         initialRanging(3),
         periodicRanging(4),
         shortData(5),
         longData(6),
         advPhyShortData(9),
         advPhyLongData(10),
         ugs(11)
     }
     MAX-ACCESS  not-accessible
     STATUS      current
     DESCRIPTION
         "An index into the Channel Modulation table that, when
          grouped with other Interval Usage Codes, fully
          instantiates all modulation sets for a given upstream
          channel."
     REFERENCE
         "Data-Over-Cable Service Interface Specifications: Radio
          Frequency Interface Specification SP-RFIv2.0-I10-051209,
          Table 8-20."
     ::= { docsIfCmtsModulationEntry 2 }

docsIfCmtsModControl OBJECT-TYPE
     SYNTAX      RowStatus
     MAX-ACCESS  read-create
     STATUS      current
     DESCRIPTION
         "Controls and reflects the status of rows in this table.
          There is no restriction on the changing of values in this
          table while their associated rows are active, with the
          exception of:

          1. If a modulation profile is being referenced by one
             or more upstream channels, an attempt to set the value
             of docsIfCmtsModChannelType returns an
             'inconsistentValue' error.

          2. If a modulation profile is being referenced by one
             or more upstream channels, an attempt to set
             docsIfCmtsModControl to destroy(6) or notInService(2)
             returns an 'inconsistentValue' error."
     ::= { docsIfCmtsModulationEntry 3 }

docsIfCmtsModType OBJECT-TYPE
     SYNTAX      INTEGER {
         other(1),
         qpsk(2),
         qam16(3),
         qam8(4),
         qam32(5),
         qam64(6),
         qam128(7)

     }
     MAX-ACCESS  read-create
     STATUS      current
     DESCRIPTION
         "The modulation type used on this channel.  Returns
          other(1) if the modulation type is not
          qpsk, qam16, qam8, qam32, qam64, or qam128.
          Type qam128 is used for SCDMA channels only.
          See the reference for the modulation profiles
          implied by different modulation types."
     REFERENCE
         "Data-Over-Cable Service Interface Specifications: Radio
          Frequency Interface Specification SP-RFIv2.0-I10-051209,
          Tables 6-7, and 8-19."
     DEFVAL { qpsk }
     ::= { docsIfCmtsModulationEntry 4 }

docsIfCmtsModPreambleLen OBJECT-TYPE
     SYNTAX      Integer32 (0..1536)
     UNITS       "bits"
     MAX-ACCESS  read-create
     STATUS      current
     DESCRIPTION
         "The preamble length for this modulation profile in bits.
          Default value is the minimum needed by the implementation
          at the CMTS for the given modulation profile."
     REFERENCE
         "Data-Over-Cable Service Interface Specifications: Radio
          Frequency Interface Specification SP-RFIv2.0-I10-051209,
          Tables 6-7, and 8-19."
     ::= { docsIfCmtsModulationEntry 5 }

docsIfCmtsModDifferentialEncoding OBJECT-TYPE
     SYNTAX      TruthValue
     MAX-ACCESS  read-create
     STATUS      current
     DESCRIPTION
         "Specifies whether or not differential encoding is used
          on this channel."
     REFERENCE
         "Data-Over-Cable Service Interface Specifications: Radio
          Frequency Interface Specification SP-RFIv2.0-I10-051209,
          Tables 6-7, and 8-19."
     DEFVAL { false }
     ::= { docsIfCmtsModulationEntry 6 }

docsIfCmtsModFECErrorCorrection OBJECT-TYPE
     SYNTAX      Integer32 (0..16)
     UNITS       "Bytes"
     MAX-ACCESS  read-create
     STATUS      current
     DESCRIPTION
         "The number of correctable errored bytes (t) used in
          forward error correction code.  The value of 0 indicates
          that no correction is employed.  The number of check bytes
          appended will be twice this value."
     REFERENCE
         "Data-Over-Cable Service Interface Specifications: Radio
          Frequency Interface Specification SP-RFIv2.0-I10-051209,
          Tables 6-7, and 8-19."
     DEFVAL { 0 }
     ::= { docsIfCmtsModulationEntry 7 }

docsIfCmtsModFECCodewordLength OBJECT-TYPE
     SYNTAX      Integer32 (1..255)
     UNITS       "Bytes"
     MAX-ACCESS  read-create
     STATUS      current
     DESCRIPTION
         "The number of data bytes (k) in the forward error
          correction codeword.
          This object is not used if docsIfCmtsModFECErrorCorrection
          is zero."
     REFERENCE
         "Data-Over-Cable Service Interface Specifications: Radio
          Frequency Interface Specification SP-RFIv2.0-I10-051209,
          Tables 6-7, and 8-19."
     DEFVAL { 32 }
     ::= { docsIfCmtsModulationEntry 8 }

docsIfCmtsModScramblerSeed OBJECT-TYPE
     SYNTAX      Integer32 (0..32767)
     MAX-ACCESS  read-create
     STATUS      current
     DESCRIPTION
         "The 15-bit seed value for the scrambler polynomial."
     REFERENCE
         "Data-Over-Cable Service Interface Specifications: Radio
          Frequency Interface Specification SP-RFIv2.0-I10-051209,
          Table 8-19."
     DEFVAL { 0 }
     ::= { docsIfCmtsModulationEntry 9 }

docsIfCmtsModMaxBurstSize OBJECT-TYPE
     SYNTAX      Integer32 (0..255)
     UNITS       "mini-slots"
     MAX-ACCESS  read-create
     STATUS      current
     DESCRIPTION
         "The maximum number of mini-slots that can be transmitted
          during this channel's burst time.  Returns zero if the
          burst length is bounded by the allocation MAP rather than
          by this profile.
          Default value is 0, except for shortData, where it is 8."
     REFERENCE
         "Data-Over-Cable Service Interface Specifications: Radio
          Frequency Interface Specification SP-RFIv2.0-I10-051209,
          Table 8-19."
     ::= { docsIfCmtsModulationEntry 10 }

docsIfCmtsModGuardTimeSize OBJECT-TYPE
     SYNTAX      Unsigned32
     UNITS       "Symbol-times"
     MAX-ACCESS  read-only
     STATUS      current
     DESCRIPTION
         "The number of symbol-times that MUST follow the end of
          this channel's burst.  Default value is the minimum time
          needed by the implementation for this modulation profile."
     REFERENCE
         "Data-Over-Cable Service Interface Specifications: Radio
          Frequency Interface Specification SP-RFIv2.0-I10-051209,
          Tables 6-7, and 8-19."
     ::= { docsIfCmtsModulationEntry 11 }

docsIfCmtsModLastCodewordShortened OBJECT-TYPE
     SYNTAX      TruthValue
     MAX-ACCESS  read-create
     STATUS      current
     DESCRIPTION
         "Indicates whether the last FEC codeword is truncated."
     REFERENCE
         "Data-Over-Cable Service Interface Specifications: Radio
          Frequency Interface Specification SP-RFIv2.0-I10-051209,
          Tables 6-7, and 8-19."
     DEFVAL { true }
     ::= { docsIfCmtsModulationEntry 12 }

docsIfCmtsModScrambler OBJECT-TYPE
     SYNTAX      TruthValue
     MAX-ACCESS  read-create
     STATUS      current
     DESCRIPTION
         "Indicates whether the scrambler is employed."
     REFERENCE
         "Data-Over-Cable Service Interface Specifications: Radio
          Frequency Interface Specification SP-RFIv2.0-I10-051209,
          Tables 6-7, and 8-19."
     DEFVAL { false }
     ::= { docsIfCmtsModulationEntry 13 }

docsIfCmtsModByteInterleaverDepth OBJECT-TYPE
     SYNTAX      Unsigned32
     MAX-ACCESS  read-create
     STATUS      current
     DESCRIPTION
         "ATDMA Byte Interleaver Depth (Ir).  This object returns 1
          for non-ATDMA profiles."
     REFERENCE
         "Data-Over-Cable Service Interface Specifications: Radio
          Frequency Interface Specification SP-RFIv2.0-I10-051209,
          Tables 6-7, and 8-19."
     DEFVAL { 1 }
     ::= { docsIfCmtsModulationEntry 14 }

docsIfCmtsModByteInterleaverBlockSize OBJECT-TYPE
     SYNTAX      Unsigned32
     MAX-ACCESS  read-create
     STATUS      current
     DESCRIPTION
         "ATDMA Byte Interleaver Block size (Br).  This object
          returns zero for non-ATDMA profiles "
     REFERENCE
         "Data-Over-Cable Service Interface Specifications: Radio
          Frequency Interface Specification SP-RFIv2.0-I10-051209,
          Tables 6-7, and 8-19."
     DEFVAL { 18 }
     ::= { docsIfCmtsModulationEntry 15 }

docsIfCmtsModPreambleType OBJECT-TYPE
     SYNTAX       INTEGER {
         unknown(0),
         qpsk0(1),
         qpsk1(2)
     }
     MAX-ACCESS  read-create
     STATUS      current
     DESCRIPTION
         "Preamble type for DOCSIS 2.0 bursts.  The value
          'unknown(0)' represents a row entry consisting only of
          DOCSIS 1.x bursts"
     REFERENCE
         "Data-Over-Cable Service Interface Specifications: Radio
          Frequency Interface Specification SP-RFIv2.0-I10-051209,
          Tables 6-7, and 8-19."
     DEFVAL { qpsk0 }
     ::= { docsIfCmtsModulationEntry 16 }

docsIfCmtsModTcmErrorCorrectionOn OBJECT-TYPE
     SYNTAX      TruthValue
     MAX-ACCESS  read-create
     STATUS      current
     DESCRIPTION
         "Trellis Code Modulation (TCM) On/Off.  This value returns
          false for non-S-CDMA profiles."
     REFERENCE
         "Data-Over-Cable Service Interface Specifications: Radio
          Frequency Interface Specification SP-RFIv2.0-I10-051209,
          Tables 6-7, and 8-19."
     DEFVAL { false }
     ::= { docsIfCmtsModulationEntry 17 }

docsIfCmtsModScdmaInterleaverStepSize OBJECT-TYPE
     SYNTAX      Unsigned32 (0 | 1..32)
     MAX-ACCESS  read-create
     STATUS      current
     DESCRIPTION
         " S-CDMA Interleaver step size.  This value returns zero
           for non-S-CDMA profiles."
     REFERENCE
         "Data-Over-Cable Service Interface Specifications: Radio
          Frequency Interface Specification SP-RFIv2.0-I10-051209,
          Tables 6-7, and 8-19."
     DEFVAL { 1 }
     ::= { docsIfCmtsModulationEntry 18 }

docsIfCmtsModScdmaSpreaderEnable OBJECT-TYPE
     SYNTAX      TruthValue
     MAX-ACCESS  read-create
     STATUS      current
     DESCRIPTION
         " S-CDMA spreader.  This value returns false for non-S-CDMA
           profiles.  Default value for IUC 3 and 4 is OFF; for
           all other IUCs it is ON."
     REFERENCE
         "Data-Over-Cable Service Interface Specifications: Radio
          Frequency Interface Specification SP-RFIv2.0-I10-051209,
          Tables 6-7, and 8-19."
     ::= { docsIfCmtsModulationEntry 19 }

docsIfCmtsModScdmaSubframeCodes OBJECT-TYPE
     SYNTAX      Unsigned32 (0 | 1..128)
     MAX-ACCESS  read-create
     STATUS      current
     DESCRIPTION
         " S-CDMA sub-frame size.  This value returns zero
           for non-S-CDMA profiles."
     REFERENCE
         "Data-Over-Cable Service Interface Specifications: Radio
          Frequency Interface Specification SP-RFIv2.0-I10-051209,
          Table 6-7, and 8-19."
     DEFVAL { 1 }
     ::= { docsIfCmtsModulationEntry 20 }

docsIfCmtsModChannelType OBJECT-TYPE
     SYNTAX      DocsisUpstreamType
     MAX-ACCESS  read-create
     STATUS      current
     DESCRIPTION
         "Describes the modulation channel type for this modulation
          entry.
          All the active entries in a modulation profile (that is all
          active entries that share a common docsIfCmtsModIndex)
          MUST have the same value of docsIfCmtsModChannelType."
     REFERENCE
         "Data-Over-Cable Service Interface Specifications: Radio
          Frequency Interface Specification SP-RFIv2.0-I10-051209,
          Table 8-19."
     DEFVAL { tdma }
     ::= { docsIfCmtsModulationEntry 21 }

docsIfCmtsModStorageType OBJECT-TYPE
     SYNTAX       StorageType
     MAX-ACCESS   read-only
     STATUS       current
     DESCRIPTION
         "The storage type for this conceptual row.
          Entries with this object set to permanent(4)
          do not require write operations for read-write
          objects."
     DEFVAL      { nonVolatile }
 ::= { docsIfCmtsModulationEntry 22 }

docsIfCmtsQosProfilePermissions OBJECT-TYPE
     SYNTAX      BITS {
         createByManagement(0),
         updateByManagement(1),
         createByModems(2)

     }
     MAX-ACCESS  read-write
     STATUS      current
     DESCRIPTION
         "This object specifies permitted methods of creating
          entries in docsIfQosProfileTable.
          createByManagement(0) is set if entries can be created
          using SNMP.  updateByManagement(1) is set if updating
          entries using SNMP is permitted.  createByModems(2)
          is set if entries can be created based on information
          in REG-REQ MAC messages received from cable modems.
          Information in this object is only applicable if
          docsIfQosProfileTable is implemented as read-create.
          Otherwise, this object is implemented as read-only
          and returns createByModems(2).
          Either createByManagement(0) or updateByManagement(1)
          MUST be set when writing to this object.
          Note that BITS objects are encoded most significant bit
          first.  For example, if bit 2 is set, the value of this
          object is the octet string '20'H."
     ::= { docsIfCmtsObjects 6 }

docsIfCmtsMacToCmTable OBJECT-TYPE
     SYNTAX      SEQUENCE OF DocsIfCmtsMacToCmEntry
     MAX-ACCESS  not-accessible
     STATUS      current
     DESCRIPTION
         "This is a table to provide a quick access index into the
          docsIfCmtsCmStatusTable.  There is exactly one row in this
          table for each row in the docsIfCmtsCmStatusTable.  In
          general, the management station SHOULD use this table only
          to get a pointer into the docsIfCmtsCmStatusTable (which
          corresponds to the CM's RF interface MAC address) and
          SHOULD not iterate (e.g., GetNext through) this table."
     ::= { docsIfCmtsObjects 7 }

docsIfCmtsMacToCmEntry OBJECT-TYPE
     SYNTAX      DocsIfCmtsMacToCmEntry
     MAX-ACCESS  not-accessible
     STATUS      current
     DESCRIPTION
         "A row in the docsIfCmtsMacToCmTable.
          An entry in this table exists for each cable modem
          that is connected to the CMTS implementing this table."
     INDEX   { docsIfCmtsCmMac }
     ::= {docsIfCmtsMacToCmTable 1 }

DocsIfCmtsMacToCmEntry ::= SEQUENCE {

             docsIfCmtsCmMac     MacAddress,
             docsIfCmtsCmPtr     Integer32
     }

docsIfCmtsCmMac OBJECT-TYPE
     SYNTAX      MacAddress
     MAX-ACCESS  not-accessible
     STATUS      current
     DESCRIPTION
         "The RF side MAC address for the referenced CM (e.g., the
          interface on the CM that has docsCableMacLayer(127) as
          its ifType)."
     ::= { docsIfCmtsMacToCmEntry 1 }

docsIfCmtsCmPtr OBJECT-TYPE
     SYNTAX      Integer32 (1..2147483647)
     MAX-ACCESS  read-only
     STATUS      current
     DESCRIPTION
         "An row index into docsIfCmtsCmStatusTable.  When queried
          with the correct instance value (e.g., a CM's MAC address),
          returns the index in docsIfCmtsCmStatusTable that
          represents that CM."
     ::= { docsIfCmtsMacToCmEntry 2 }

-- The following independent object and associated table provide
-- operators with a mechanism to evaluate the load/utilization of
-- both upstream and downstream physical channels.  This information
-- may be used for capacity planning and incident analysis and may
-- be particularly helpful in provisioning of high value QOS.
--
-- Utilization is expressed as an index representing the calculated
-- percentage utilization of the upstream or downstream channel in
-- the most recent sampling interval (i.e., utilization interval).
-- Refer to the DESCRIPTION field of the
-- docsIfCmtsChannelUtUtilization object for definitions and
-- calculation details.

docsIfCmtsChannelUtilizationInterval OBJECT-TYPE
     SYNTAX      Integer32 (0..86400)
     UNITS       "seconds"
     MAX-ACCESS  read-write
     STATUS      current
     DESCRIPTION
         "The time interval in seconds over which the channel
          utilization index is calculated.  All upstream/downstream
          channels use the same
          docsIfCmtsChannelUtilizationInterval.

          Setting a value of zero disables utilization reporting.
          A channel utilization index is calculated over a fixed
          window applying to the most recent
          docsIfCmtsChannelUtilizationInterval.  It would therefore
          be prudent to use a relatively short
          docsIfCmtsChannelUtilizationInterval.
          It is a vendor decision whether to reset the timer when
          docsIfCmtsChannelUtilizationInterval is changed during a
          utilization sampling period."
     ::= { docsIfCmtsObjects 8 }

docsIfCmtsChannelUtilizationTable OBJECT-TYPE
     SYNTAX      SEQUENCE OF DocsIfCmtsChannelUtilizationEntry
     MAX-ACCESS  not-accessible
     STATUS      current
     DESCRIPTION
         "Reports utilization statistics for attached upstream and
          downstream physical channels."
     ::= { docsIfCmtsObjects 9 }

docsIfCmtsChannelUtilizationEntry OBJECT-TYPE
     SYNTAX      DocsIfCmtsChannelUtilizationEntry
     MAX-ACCESS  not-accessible
     STATUS      current
     DESCRIPTION
         "Utilization statistics for a single upstream or downstream
          physical channel.  An entry exists in this table for each
          ifEntry with an ifType equal to
          docsCableDownstream (128)
          or docsCableUpstream (129)."
     INDEX  { ifIndex, docsIfCmtsChannelUtIfType,
          docsIfCmtsChannelUtId }
     ::= { docsIfCmtsChannelUtilizationTable 1 }

DocsIfCmtsChannelUtilizationEntry ::= SEQUENCE {
         docsIfCmtsChannelUtIfType         IANAifType,
         docsIfCmtsChannelUtId             Integer32,
         docsIfCmtsChannelUtUtilization    Integer32
     }

docsIfCmtsChannelUtIfType OBJECT-TYPE
     SYNTAX       IANAifType
     MAX-ACCESS   not-accessible
     STATUS       current
     DESCRIPTION
         "The secondary index into this table.  Indicates the IANA
          interface type associated with this physical channel.
          Only docsCableDownstream (128) and

          docsCableUpstream (129) are valid."
     ::= { docsIfCmtsChannelUtilizationEntry 1 }

docsIfCmtsChannelUtId OBJECT-TYPE
     SYNTAX       Integer32 (0..255)
     MAX-ACCESS   not-accessible
     STATUS       current
     DESCRIPTION
          "The tertiary index into this table.  Indicates the CMTS
           identifier for this physical channel."
     ::= { docsIfCmtsChannelUtilizationEntry 2 }

docsIfCmtsChannelUtUtilization OBJECT-TYPE
     SYNTAX       Integer32 (0..100)
     UNITS        "percent"
     MAX-ACCESS   read-only
     STATUS       current
     DESCRIPTION
         "The calculated and truncated utilization index for this
          physical upstream or downstream channel, accurate as of
          the most recent docsIfCmtsChannelUtilizationInterval.

          Upstream Channel Utilization Index:

          The upstream channel utilization index is expressed as a
          percentage of mini-slots utilized on the physical channel,
          regardless of burst type.  For an Initial Maintenance
          region, the mini-slots for the complete region are
          considered utilized if the CMTS received an upstream
          burst within the region from any CM on the physical
          channel.  For contention REQ and REQ/DATA regions, the
          mini-slots for a transmission opportunity within the
          region are considered utilized if the CMTS received an
          upstream burst within the opportunity from any CM on the
          physical channel.  For all other regions, utilized
          mini-slots are those in which the CMTS granted
          bandwidth to any unicast SID on the physical channel.

          For an upstream interface that has multiple logical
          upstream channels enabled, the utilization index is a
          weighted sum of utilization indices for the logical
          channels.  The weight for each utilization index is the
          percentage of upstream mini-slots allocated for the
          corresponding logical channel.
          Example:
          If 75% of bandwidth is allocated to the first logical
          channel and 25% to the second, and the utilization
          indices for each are 60 and 40, respectively, the

          utilization index for the upstream physical channel is
          (60 * 0.75) + (40 * 0.25) = 55.  This figure
          applies to the most recent utilization interval.

          Downstream Channel Utilization Index:

          The downstream channel utilization index is a percentage
          expressing the ratio between bytes used to transmit data
          versus the total number of bytes transmitted in the raw
          bandwidth of the MPEG channel.  As with the upstream
          utilization index, the calculated value represents
          the most recent utilization interval.
          Formula:
          Downstream utilization index =
          (100 * (data bytes / raw bytes))

          Definitions:
          Data bytes:    Number of bytes transmitted as data in the
                         docsIfCmtsChannelUtilizationInterval.
                         Identical to docsIfCmtsDownChannelCtrUsed
                         Bytes measured over the utilization
                         interval.
          Raw bandwidth: Total number of bytes available for
                         transmitting data, not including bytes
                         used for headers and other overhead.
          Raw bytes:     (raw bandwidth *
                         docsIfCmtsChannelUtilizationInterval).
                         Identical to docsIfCmtsDownChannelCtrTotal
                         Bytes measured over the utilization
                         interval."
     ::= { docsIfCmtsChannelUtilizationEntry 3 }

-- The following table provides operators with input data
-- appropriate for calculating downstream channel utilization.
-- Operators may use the docsIfCmtsChannelUtilizationTable or
-- perform their own polling of the
-- docsIfCmtsDownChannelCounterTable objects to characterize
-- their downstream channel usage.  The 32-bit counter objects are
-- included to provide backward compatibility with SNMPv1 managers,
-- which cannot access 64-bit counter objects.

docsIfCmtsDownChannelCounterTable OBJECT-TYPE
     SYNTAX      SEQUENCE OF DocsIfCmtsDownChannelCounterEntry
     MAX-ACCESS  not-accessible
     STATUS      current
     DESCRIPTION
         "This table is implemented at the CMTS to collect
          downstream channel statistics for utilization

          calculations."
     ::= { docsIfCmtsObjects 10 }

docsIfCmtsDownChannelCounterEntry OBJECT-TYPE
     SYNTAX      DocsIfCmtsDownChannelCounterEntry
     MAX-ACCESS  not-accessible
     STATUS      current
     DESCRIPTION
         "An entry provides a list of traffic counters for a single
          downstream channel.
          An entry in this table exists for each ifEntry with an
          ifType of docsCableDownstream(128)."
     INDEX { ifIndex }
     ::= { docsIfCmtsDownChannelCounterTable 1 }

DocsIfCmtsDownChannelCounterEntry ::= SEQUENCE {
         docsIfCmtsDownChnlCtrId              Integer32,
         docsIfCmtsDownChnlCtrTotalBytes      Counter32,
         docsIfCmtsDownChnlCtrUsedBytes       Counter32,
         docsIfCmtsDownChnlCtrExtTotalBytes   Counter64,
         docsIfCmtsDownChnlCtrExtUsedBytes    Counter64
     }

docsIfCmtsDownChnlCtrId OBJECT-TYPE
     SYNTAX      Integer32 (0..255)
     MAX-ACCESS  read-only
     STATUS      current
     DESCRIPTION
         "The Cable Modem Termination System identification
          of the downstream channel within this particular MAC
          interface.  If the interface is down, the object returns
          the most current value.  If the downstream channel ID is
          unknown, this object returns a value of 0."
     ::= { docsIfCmtsDownChannelCounterEntry 1 }

docsIfCmtsDownChnlCtrTotalBytes OBJECT-TYPE
     SYNTAX      Counter32
     UNITS       "Bytes"
     MAX-ACCESS  read-only
     STATUS      current
     DESCRIPTION
         "At the CMTS, the total number of bytes in the Payload
          portion of MPEG Packets (i.e., not including MPEG header
          or pointer_field) transported by this downstream channel.
          This is the 32-bit version of
          docsIfCmtsDownChnlCtrExtTotalBytes, included to provide
          back compatibility with SNMPv1 managers.
          Discontinuities in the value of this counter can occur

          at reinitialization of the managed system, and at other
          times as indicated by the value of
          ifCounterDiscontinuityTime for the associated ifIndex."
     ::= { docsIfCmtsDownChannelCounterEntry 2 }

docsIfCmtsDownChnlCtrUsedBytes OBJECT-TYPE
     SYNTAX      Counter32
     UNITS       "Bytes"
     MAX-ACCESS  read-only
     STATUS      current
     DESCRIPTION
         "At the CMTS, the total number of DOCSIS data bytes
          transported by this downstream channel.
          The number of data bytes is defined as the total number
          of bytes transported in DOCSIS payloads minus the number
          of stuff bytes transported in DOCSIS payloads.
          This is the 32-bit version of
          docsIfCmtsDownChnlCtrExtUsedBytes, included to provide
          back compatibility with SNMPv1 managers.
          Discontinuities in the value of this counter can occur
          at reinitialization of the managed system, and at other
          times as indicated by the value of
          ifCounterDiscontinuityTime for the associated ifIndex."
     ::= { docsIfCmtsDownChannelCounterEntry 3 }

docsIfCmtsDownChnlCtrExtTotalBytes OBJECT-TYPE
     SYNTAX      Counter64
     UNITS       "Bytes"
     MAX-ACCESS  read-only
     STATUS      current
     DESCRIPTION
         "At the CMTS, the total number of bytes in the Payload
          portion of MPEG Packets (i.e., not including MPEG header
          or pointer_field) transported by this downstream
          channel.
          This is the 64-bit version of
          docsIfCmtsDownChnlCtrTotalBytes and will not be
          accessible to SNMPv1 managers.
          Discontinuities in the value of this counter can occur
          at reinitialization of the managed system, and at other
          times as indicated by the value of
          ifCounterDiscontinuityTime for the associated ifIndex."
     ::= { docsIfCmtsDownChannelCounterEntry 4 }

docsIfCmtsDownChnlCtrExtUsedBytes OBJECT-TYPE
     SYNTAX      Counter64
     UNITS       "Bytes"
     MAX-ACCESS  read-only
     STATUS      current
     DESCRIPTION
         "At the CMTS, the total number of DOCSIS data bytes
          transported by this downstream channel.  The number
          of data bytes is defined as the total number of bytes
          transported in DOCSIS payloads minus the number of
          stuff bytes transported in DOCSIS payloads.
          This is the 64-bit version of
          docsIfCmtsDownChnlCtrUsedBytes and will not be accessible
          to SNMPv1 managers.
          Discontinuities in the value of this counter can occur
          at reinitialization of the managed system, and at other
          times as indicated by the value of
          ifCounterDiscontinuityTime for the associated ifIndex."
     ::= { docsIfCmtsDownChannelCounterEntry 5 }

-- The following table provides operators with input data appropriate
-- for calculating upstream channel utilization, and for determining
-- the traffic characteristics of upstream channels.  Operators may
-- use the docsIfCmtsChannelUtilizationTable or perform their own
-- polling of the docsIfCmtsUpChannelCounterTable objects for
-- utilization determination.
-- The first four 32 and 64 objects in this table are mandatory.
-- Vendors may choose to implement the remaining optional objects to
-- provide operators with finer characterization of upstream channel
-- traffic patterns.  The 32-bit counter objects are included to
-- provide backward compatibility with SNMPv1 managers, which cannot
-- access 64-bit counter objects.

docsIfCmtsUpChannelCounterTable OBJECT-TYPE
     SYNTAX      SEQUENCE OF DocsIfCmtsUpChannelCounterEntry
     MAX-ACCESS  not-accessible
     STATUS      current
     DESCRIPTION
         "This table is implemented at the CMTS to provide upstream
          channel statistics appropriate for channel utilization
          calculations."
     ::= { docsIfCmtsObjects 11 }

docsIfCmtsUpChannelCounterEntry OBJECT-TYPE
     SYNTAX      DocsIfCmtsUpChannelCounterEntry
     MAX-ACCESS  not-accessible
     STATUS      current
     DESCRIPTION
         "List of traffic statistics for a single upstream channel.
          For DOCSIS 2.0 CMTSs, an entry in this table
          exists for each ifEntry with an ifType of
          docsCableUpstreamChannel (205).

          For DOCSIS 1.x CMTSs, an entry in this table
          exists for each ifEntry with an ifType of
          docsCableUpstream (129)."
     INDEX { ifIndex }
     ::= { docsIfCmtsUpChannelCounterTable 1 }

DocsIfCmtsUpChannelCounterEntry ::= SEQUENCE {
         docsIfCmtsUpChnlCtrId                          Integer32,
         docsIfCmtsUpChnlCtrTotalMslots                 Counter32,
         docsIfCmtsUpChnlCtrUcastGrantedMslots          Counter32,
         docsIfCmtsUpChnlCtrTotalCntnMslots             Counter32,
         docsIfCmtsUpChnlCtrUsedCntnMslots              Counter32,
         docsIfCmtsUpChnlCtrExtTotalMslots              Counter64,
         docsIfCmtsUpChnlCtrExtUcastGrantedMslots       Counter64,
         docsIfCmtsUpChnlCtrExtTotalCntnMslots          Counter64,
         docsIfCmtsUpChnlCtrExtUsedCntnMslots           Counter64,
         docsIfCmtsUpChnlCtrCollCntnMslots              Counter32,
         docsIfCmtsUpChnlCtrTotalCntnReqMslots          Counter32,
         docsIfCmtsUpChnlCtrUsedCntnReqMslots           Counter32,
         docsIfCmtsUpChnlCtrCollCntnReqMslots           Counter32,
         docsIfCmtsUpChnlCtrTotalCntnReqDataMslots      Counter32,
         docsIfCmtsUpChnlCtrUsedCntnReqDataMslots       Counter32,
         docsIfCmtsUpChnlCtrCollCntnReqDataMslots       Counter32,
         docsIfCmtsUpChnlCtrTotalCntnInitMaintMslots    Counter32,
         docsIfCmtsUpChnlCtrUsedCntnInitMaintMslots     Counter32,
         docsIfCmtsUpChnlCtrCollCntnInitMaintMslots     Counter32,
         docsIfCmtsUpChnlCtrExtCollCntnMslots           Counter64,
         docsIfCmtsUpChnlCtrExtTotalCntnReqMslots       Counter64,
         docsIfCmtsUpChnlCtrExtUsedCntnReqMslots        Counter64,
         docsIfCmtsUpChnlCtrExtCollCntnReqMslots        Counter64,
         docsIfCmtsUpChnlCtrExtTotalCntnReqDataMslots   Counter64,
         docsIfCmtsUpChnlCtrExtUsedCntnReqDataMslots    Counter64,
         docsIfCmtsUpChnlCtrExtCollCntnReqDataMslots    Counter64,
         docsIfCmtsUpChnlCtrExtTotalCntnInitMaintMslots Counter64,
         docsIfCmtsUpChnlCtrExtUsedCntnInitMaintMslots  Counter64,
         docsIfCmtsUpChnlCtrExtCollCntnInitMaintMslots  Counter64
     }

docsIfCmtsUpChnlCtrId OBJECT-TYPE
     SYNTAX      Integer32 (0..255)
     MAX-ACCESS  read-only
     STATUS      current
     DESCRIPTION
         "The CMTS identification of the upstream channel."
     ::= { docsIfCmtsUpChannelCounterEntry 1 }

docsIfCmtsUpChnlCtrTotalMslots OBJECT-TYPE
     SYNTAX      Counter32
     UNITS       "mini-slots"
     MAX-ACCESS  read-only
     STATUS      current
     DESCRIPTION
         "Current count, from CMTS initialization, of all mini-slots
          defined for this upstream logical channel.  This count
          includes all IUCs and SIDs, even those allocated to the
          NULL SID for a 2.0 logical channel that is inactive.  This
          is the 32-bit version of docsIfCmtsUpChnlCtrExtTotalMslots
          and is included for back compatibility with SNMPv1
          managers.  Support for this object is mandatory.
          Discontinuities in the value of this counter can occur
          at reinitialization of the managed system, and at other
          times as indicated by the value of
          ifCounterDiscontinuityTime for the associated ifIndex."
     ::= { docsIfCmtsUpChannelCounterEntry 2 }

docsIfCmtsUpChnlCtrUcastGrantedMslots OBJECT-TYPE
     SYNTAX      Counter32
     UNITS       "mini-slots"
     MAX-ACCESS  read-only
     STATUS      current
     DESCRIPTION
         "Current count, from CMTS initialization, of unicast
          granted mini-slots on the upstream logical channel,
          regardless of burst type.  Unicast granted mini-slots are
          those in which the CMTS assigned bandwidth to any unicast
          SID on the logical channel.  However, this object does not
          include minis-lots for reserved IUCs, or grants to SIDs
          designated as meaning 'no CM'.  This is the 32-bit version
          of docsIfCmtsUpChnlCtrExtUcastGrantedMslots, and is
          included for back compatibility with SNMPv1 managers.
          Support for this object is mandatory.
          Discontinuities in the value of this counter can occur
          at reinitialization of the managed system, and at other
          times as indicated by the value of
          ifCounterDiscontinuityTime for the associated ifIndex."
     ::= { docsIfCmtsUpChannelCounterEntry 3 }

docsIfCmtsUpChnlCtrTotalCntnMslots OBJECT-TYPE
     SYNTAX      Counter32
     UNITS       "mini-slots"
     MAX-ACCESS  read-only
     STATUS      current
     DESCRIPTION
         "Current count, from CMTS initialization, of contention
          mini-slots defined for this upstream logical channel.  This
          count includes all mini-slots assigned to a broadcast or

          multicast SID on the logical channel.  This is the 32-bit
          version of docsIfCmtsUpChnlCtrExtTotalCntnMslots, and is
          included for back compatibility with SNMPv1 managers.
          Support for this object is mandatory.
          Discontinuities in the value of this counter can occur
          at reinitialization of the managed system, and at other
          times as indicated by the value of
          ifCounterDiscontinuityTime for the associated ifIndex."
     ::= { docsIfCmtsUpChannelCounterEntry 4 }

docsIfCmtsUpChnlCtrUsedCntnMslots OBJECT-TYPE
     SYNTAX      Counter32
     UNITS       "mini-slots"
     MAX-ACCESS  read-only
     STATUS      current
     DESCRIPTION
         "Current count, from CMTS initialization, of contention
          mini-slots utilized on the upstream logical channel.  For
          contention regions, utilized mini-slots are those in which
          the CMTS correctly received an upstream burst from any CM
          on the upstream logical channel.  This is the 32-bit
          version of docsIfCmtsUpChnlCtrExtUsedCntnMslots and is
          included for back compatibility with SNMPv1 managers.
          Support for this object is mandatory.
          Discontinuities in the value of this counter can occur
          at reinitialization of the managed system, and at other
          times as indicated by the value of
          ifCounterDiscontinuityTime for the associated ifIndex."
     ::= { docsIfCmtsUpChannelCounterEntry 5 }

docsIfCmtsUpChnlCtrExtTotalMslots OBJECT-TYPE
     SYNTAX      Counter64
     UNITS       "mini-slots"
     MAX-ACCESS  read-only
     STATUS      current
     DESCRIPTION
         "Current count, from CMTS initialization, of all mini-slots
          defined for this upstream logical channel.  This count
          includes all IUCs and SIDs, even those allocated to the
          NULL SID for a 2.0 logical channel that is inactive.  This
          is the 64-bit version of docsIfCmtsUpChnlCtrTotalMslots
          and will not be accessible to SNMPv1 managers.
          Support for this object is mandatory.
          Discontinuities in the value of this counter can occur
          at reinitialization of the managed system, and at other
          times as indicated by the value of
          ifCounterDiscontinuityTime for the associated ifIndex."
     ::= { docsIfCmtsUpChannelCounterEntry 6 }

docsIfCmtsUpChnlCtrExtUcastGrantedMslots OBJECT-TYPE
     SYNTAX      Counter64
     UNITS       "mini-slots"
     MAX-ACCESS  read-only
     STATUS      current
     DESCRIPTION
         "Current count, from CMTS initialization, of unicast
          granted mini-slots on the upstream logical channel,
          regardless of burst type.  Unicast granted mini-slots are
          those in which the CMTS assigned bandwidth to any unicast
          SID on the logical channel.  However, this object does not
          include mini-slots for reserved IUCs, or grants to SIDs
          designated as meaning 'no CM'.  This is the 64-bit version
          of docsIfCmtsUpChnlCtrUcastGrantedMslots and will not be
          accessible to SNMPv1 managers.
          Support for this object is mandatory.
          Discontinuities in the value of this counter can occur
          at reinitialization of the managed system, and at other
          times as indicated by the value of
          ifCounterDiscontinuityTime for the associated ifIndex."
     ::= { docsIfCmtsUpChannelCounterEntry 7 }

docsIfCmtsUpChnlCtrExtTotalCntnMslots OBJECT-TYPE
     SYNTAX      Counter64
     UNITS       "mini-slots"
     MAX-ACCESS  read-only
     STATUS      current
     DESCRIPTION
         "Current count, from CMTS initialization, of contention
          mini-slots defined for this upstream logical channel.  This
          count includes all mini-slots assigned to a broadcast or
          multicast SID on the logical channel.  This is the 64-bit
          version of docsIfCmtsUpChnlCtrTotalCntnMslots and will
          not be accessible to SNMPv1 managers.
          Support for this object is mandatory.
          Discontinuities in the value of this counter can occur
          at reinitialization of the managed system, and at other
          times as indicated by the value of
          ifCounterDiscontinuityTime for the associated ifIndex."
     ::= { docsIfCmtsUpChannelCounterEntry 8 }

docsIfCmtsUpChnlCtrExtUsedCntnMslots OBJECT-TYPE
     SYNTAX      Counter64
     UNITS       "mini-slots"
     MAX-ACCESS  read-only
     STATUS      current
     DESCRIPTION
         "Current count, from CMTS initialization, of contention

          mini-slots utilized on the upstream logical channel.  For
          contention regions, utilized mini-slots are those in which
          the CMTS correctly received an upstream burst from any CM
          on the upstream logical channel.  This is the 64-bit
          version of docsIfCmtsUpChnlCtrUsedCntnMslots and will not
          be accessible to SNMPv1 managers.
          Support for this object is mandatory.
          Discontinuities in the value of this counter can occur
          at reinitialization of the managed system, and at other
          times as indicated by the value of
          ifCounterDiscontinuityTime for the associated ifIndex."
     ::= { docsIfCmtsUpChannelCounterEntry 9 }

docsIfCmtsUpChnlCtrCollCntnMslots OBJECT-TYPE
     SYNTAX      Counter32
     UNITS       "mini-slots"
     MAX-ACCESS  read-only
     STATUS      current
     DESCRIPTION
         "Current count, from CMTS initialization, of contention
          mini-slots subjected to collisions on the upstream logical
          channel.  For contention regions, these are the mini-slots
          applicable to bursts that the CMTS detected but could not
          correctly receive.  This is the 32-bit version of
          docsIfCmtsUpChnlCtrExtCollCntnMslots and is included for
          back compatibility with SNMPv1 managers.
          Discontinuities in the value of this counter can occur
          at reinitialization of the managed system, and at other
          times as indicated by the value of
          ifCounterDiscontinuityTime for the associated ifIndex."
     ::= { docsIfCmtsUpChannelCounterEntry 10 }

docsIfCmtsUpChnlCtrTotalCntnReqMslots OBJECT-TYPE
     SYNTAX      Counter32
     UNITS       "mini-slots"
     MAX-ACCESS  read-only
     STATUS      current
     DESCRIPTION
         "Current count, from CMTS initialization, of contention
          request mini-slots defined for this upstream logical
          channel.  This count includes all mini-slots for IUC1
          assigned to a broadcast or multicast SID on the logical
          channel.  This is the 32-bit version of
          docsIfCmtsUpChnlCtrExtTotalCntnReqMslots and is included
          for back compatibility with SNMPv1 managers.
          Discontinuities in the value of this counter can occur
          at reinitialization of the managed system, and at other
          times as indicated by the value of

          ifCounterDiscontinuityTime for the associated ifIndex."
     ::= { docsIfCmtsUpChannelCounterEntry 11 }

docsIfCmtsUpChnlCtrUsedCntnReqMslots OBJECT-TYPE
     SYNTAX      Counter32
     UNITS       "mini-slots"
     MAX-ACCESS  read-only
     STATUS      current
     DESCRIPTION
         "Current count, from CMTS initialization, of contention
          request mini-slots utilized on this upstream logical
          channel.  This count includes all contention mini-slots for
          IUC1 applicable to bursts that the CMTS correctly
          received.  This is the 32-bit version of
          docsIfCmtsUpChnlCtrExtUsedCntnReqMslots and is included
          for back compatibility with SNMPv1 managers.
          Discontinuities in the value of this counter can occur
          at reinitialization of the managed system, and at other
          times as indicated by the value of
          ifCounterDiscontinuityTime for the associated ifIndex."
     ::= { docsIfCmtsUpChannelCounterEntry 12 }

docsIfCmtsUpChnlCtrCollCntnReqMslots OBJECT-TYPE
     SYNTAX      Counter32
     UNITS       "mini-slots"
     MAX-ACCESS  read-only
     STATUS      current
     DESCRIPTION
         "Current count, from CMTS initialization, of contention
          request mini-slots subjected to collisions on this upstream
          logical channel.  This includes all contention mini-slots
          for IUC1 applicable to bursts that the CMTS detected but
          could not correctly receive.  This is the 32-bit version of
          docsIfCmtsUpChnlCtrExtCollCntnReqMslots and is included
          for back compatibility with SNMPv1 managers.
          Discontinuities in the value of this counter can occur
          at reinitialization of the managed system, and at other
          times as indicated by the value of
          ifCounterDiscontinuityTime for the associated ifIndex."
     ::= { docsIfCmtsUpChannelCounterEntry 13 }

docsIfCmtsUpChnlCtrTotalCntnReqDataMslots OBJECT-TYPE
     SYNTAX      Counter32
     UNITS       "mini-slots"
     MAX-ACCESS  read-only
     STATUS      current
     DESCRIPTION
         "Current count, from CMTS initialization, of contention

          request data mini-slots defined for this upstream logical
          channel.  This count includes all mini-slots for IUC2
          assigned to a broadcast or multicast SID on the logical
          channel.  This is the 32-bit version of
          docsIfCmtsUpChnlCtrExtTotalCntnReqDataMslots and is
          included for back compatibility with SNMPv1 managers.
          Discontinuities in the value of this counter can occur
          at reinitialization of the managed system, and at other
          times as indicated by the value of
          ifCounterDiscontinuityTime for the associated ifIndex."
     ::= { docsIfCmtsUpChannelCounterEntry 14 }

docsIfCmtsUpChnlCtrUsedCntnReqDataMslots OBJECT-TYPE
     SYNTAX      Counter32
     UNITS       "mini-slots"
MAX-ACCESS  read-only
     STATUS      current
     DESCRIPTION
         "Current count, from CMTS initialization, of contention
          request data mini-slots utilized on this upstream logical
          channel.  This includes all contention mini-slots for IUC2
          applicable to bursts that the CMTS correctly received.
          This is the 32-bit version of
          docsIfCmtsUpChnlCtrExtUsedCntnReqDataMslots and is
          included for back compatibility with SNMPv1 managers.
          Discontinuities in the value of this counter can occur
          at reinitialization of the managed system, and at other
          times as indicated by the value of
          ifCounterDiscontinuityTime for the associated ifIndex."
     ::= { docsIfCmtsUpChannelCounterEntry 15 }

docsIfCmtsUpChnlCtrCollCntnReqDataMslots OBJECT-TYPE
     SYNTAX      Counter32
     UNITS       "mini-slots"
     MAX-ACCESS  read-only
     STATUS      current
     DESCRIPTION
         "Current count, from CMTS initialization, of contention
          request data mini-slots subjected to collisions on this
          upstream logical channel.  This includes all contention
          mini-slots for IUC2 applicable to bursts that the CMTS
          detected, but could not correctly receive.  This is the
          32-bit version of
          docsIfCmtsUpChnlCtrExtCollCntnReqDataMslots and is
          included for back compatibility with SNMPv1 managers.
          Discontinuities in the value of this counter can occur
          at reinitialization of the managed system, and at other
          times as indicated by the value of

          ifCounterDiscontinuityTime for the associated ifIndex."
     ::= { docsIfCmtsUpChannelCounterEntry 16 }

docsIfCmtsUpChnlCtrTotalCntnInitMaintMslots OBJECT-TYPE
     SYNTAX      Counter32
     UNITS       "mini-slots"
     MAX-ACCESS  read-only
     STATUS      current
     DESCRIPTION
         "Current count, from CMTS initialization, of contention
          initial maintenance mini-slots defined for this upstream
          logical channel.  This includes all mini-slots for IUC3
          assigned to a broadcast or multicast SID on the logical
          channel.  This is the 32-bit version of
          docsIfCmtsUpChnlCtrExtTotalCntnInitMaintMslots
          and is included for back compatibility with SNMPv1
          managers.
          Discontinuities in the value of this counter can occur
          at reinitialization of the managed system, and at other
          times as indicated by the value of
          ifCounterDiscontinuityTime for the associated ifIndex."
     ::= { docsIfCmtsUpChannelCounterEntry 17 }

docsIfCmtsUpChnlCtrUsedCntnInitMaintMslots OBJECT-TYPE
     SYNTAX      Counter32
     MAX-ACCESS  read-only
     STATUS      current
     DESCRIPTION
         "Current count, from CMTS initialization, of contention
          initial maintenance mini-slots utilized on this upstream
          logical channel.  This includes all contention mini-slots
          for IUC3 applicable to bursts that the CMTS correctly
          received.  This is the 32-bit version of
          docsIfCmtsUpChnlCtrExtUsedCntnInitMaintMslots
          and is included for back compatibility with SNMPv1
          managers.
          Discontinuities in the value of this counter can occur
          at reinitialization of the managed system, and at other
          times as indicated by the value of
          ifCounterDiscontinuityTime for the associated ifIndex."
     ::= { docsIfCmtsUpChannelCounterEntry 18 }

docsIfCmtsUpChnlCtrCollCntnInitMaintMslots OBJECT-TYPE
     SYNTAX      Counter32
     UNITS       "mini-slots"
     MAX-ACCESS  read-only
     STATUS      current
     DESCRIPTION
         "Current count, from CMTS initialization, of contention
          initial maintenance mini-slots subjected to collisions on
          this upstream logical channel.  This includes all
          contention mini-slots for IUC3 applicable to bursts that
          the CMTS detected, but could not correctly receive.
          This is the 32-bit version of
          docsIfCmtsUpChnlCtrExtCollCntnInitMaintMslots
          and is included for back compatibility with SNMPv1
          managers.
          Discontinuities in the value of this counter can occur
          at reinitialization of the managed system, and at other
          times as indicated by the value of
          ifCounterDiscontinuityTime for the associated ifIndex."
     ::= { docsIfCmtsUpChannelCounterEntry 19 }

docsIfCmtsUpChnlCtrExtCollCntnMslots OBJECT-TYPE
     SYNTAX      Counter64
     UNITS       "mini-slots"
     MAX-ACCESS  read-only
     STATUS      current
     DESCRIPTION
         "Current count, from CMTS initialization, of collision
          contention mini-slots on the upstream logical channel.
          For contention regions, these are the mini-slots applicable
          to bursts that the CMTS detected, but could not correctly
          receive.  This is the 64-bit version of
          docsIfCmtsUpChnlCtrCollCntnMslots and will not be
          accessible to SNMPv1 managers.
          Discontinuities in the value of this counter can occur
          at reinitialization of the managed system, and at other
          times as indicated by the value of
          ifCounterDiscontinuityTime for the associated ifIndex."
     ::= { docsIfCmtsUpChannelCounterEntry 20 }

docsIfCmtsUpChnlCtrExtTotalCntnReqMslots OBJECT-TYPE
     SYNTAX      Counter64
     UNITS       "mini-slots"
     MAX-ACCESS  read-only
     STATUS      current
     DESCRIPTION
         "Current count, from CMTS initialization, of contention
          request mini-slots defined for this upstream logical
          channel.  This count includes all mini-slots for IUC1
          assigned to a broadcast or multicast SID on the logical
          channel.  This is the 64-bit version of
          docsIfCmtsUpChnlCtrTotalCntnReqMslots and will not be
          accessible to SNMPv1 managers.
          Discontinuities in the value of this counter can occur

          at reinitialization of the managed system, and at other
          times as indicated by the value of
          ifCounterDiscontinuityTime for the associated ifIndex."
     ::= { docsIfCmtsUpChannelCounterEntry 21 }

docsIfCmtsUpChnlCtrExtUsedCntnReqMslots OBJECT-TYPE
     SYNTAX      Counter64
     UNITS       "mini-slots"
     MAX-ACCESS  read-only
     STATUS      current
     DESCRIPTION
         "Current count, from CMTS initialization, of contention
          request mini-slots utilized on this upstream logical
          channel.  This count includes all contention mini-slots for
          IUC1 applicable to bursts that the CMTS correctly
          received.  This is the 64-bit version of
          docsIfCmtsUpChnlCtrUsedCntnReqMslots and will not be
          accessible to SNMPv1 managers.
          Discontinuities in the value of this counter can occur
          at reinitialization of the managed system, and at other
          times as indicated by the value of
          ifCounterDiscontinuityTime for the associated ifIndex."
     ::= { docsIfCmtsUpChannelCounterEntry 22 }

docsIfCmtsUpChnlCtrExtCollCntnReqMslots OBJECT-TYPE
     SYNTAX      Counter64
     UNITS       "mini-slots"
     MAX-ACCESS  read-only
     STATUS      current
     DESCRIPTION
         "Current count, from CMTS initialization, of contention
          request mini-slots subjected to collisions on this upstream
          logical channel.  This includes all contention mini-slots
          for IUC1 applicable to bursts that the CMTS detected,
          but could not correctly receive.  This is the 64-bit
          version of docsIfCmtsUpChnlCtrCollCntnReqMslots and will
          not be accessible to SNMPv1 managers.
          Discontinuities in the value of this counter can occur
          at reinitialization of the managed system, and at other
          times as indicated by the value of
          ifCounterDiscontinuityTime for the associated ifIndex."
     ::= { docsIfCmtsUpChannelCounterEntry 23 }

docsIfCmtsUpChnlCtrExtTotalCntnReqDataMslots OBJECT-TYPE
     SYNTAX      Counter64
     UNITS       "mini-slots"
     MAX-ACCESS  read-only
     STATUS      current
     DESCRIPTION
         "Current count, from CMTS initialization, of contention
          request data mini-slots defined for this upstream logical
          channel.  This count includes all mini-slots for IUC2
          assigned to a broadcast or multicast SID on the logical
          channel.  This is the 64-bit version of
          docsIfCmtsUpChnlCtrTotalCntnReqDataMslots and will not be
          accessible to SNMPv1 managers.
          Discontinuities in the value of this counter can occur
          at reinitialization of the managed system, and at other
          times as indicated by the value of
          ifCounterDiscontinuityTime for the associated ifIndex."
     ::= { docsIfCmtsUpChannelCounterEntry 24 }

docsIfCmtsUpChnlCtrExtUsedCntnReqDataMslots OBJECT-TYPE
     SYNTAX      Counter64
     UNITS       "mini-slots"
     MAX-ACCESS  read-only
     STATUS      current
     DESCRIPTION
         "Current count, from CMTS initialization, of contention
          request data mini-slots utilized on this upstream logical
          channel.  This includes all contention mini-slots for IUC2
          applicable to bursts that the CMTS correctly received.
          This is the 64-bit version of
          docsIfCmtsUpChnlCtrUsedCntnReqDataMslots and will not be
          accessible to SNMPv1 managers.
          Discontinuities in the value of this counter can occur
          at reinitialization of the managed system, and at other
          times as indicated by the value of
          ifCounterDiscontinuityTime for the associated ifIndex."
     ::= { docsIfCmtsUpChannelCounterEntry 25 }

docsIfCmtsUpChnlCtrExtCollCntnReqDataMslots OBJECT-TYPE
     SYNTAX      Counter64
     UNITS       "mini-slots"
     MAX-ACCESS  read-only
     STATUS      current
     DESCRIPTION
         "Current count, from CMTS initialization, of contention
          request data mini-slots subjected to collisions on this
          upstream logical channel.  This includes all contention
          mini-slots for IUC2 applicable to bursts that the CMTS
          detected, but could not correctly receive.  This is the
          64-bit version of
          docsIfCmtsUpChnlCtrCollCntnReqDataMslots
          and will not be accessible to SNMPv1 managers.
          Discontinuities in the value of this counter can occur

          at reinitialization of the managed system, and at other
          times as indicated by the value of
          ifCounterDiscontinuityTime for the associated ifIndex."
     ::= { docsIfCmtsUpChannelCounterEntry 26 }

docsIfCmtsUpChnlCtrExtTotalCntnInitMaintMslots OBJECT-TYPE
     SYNTAX      Counter64
     UNITS       "mini-slots"
     MAX-ACCESS  read-only
     STATUS      current
     DESCRIPTION
         "Current count, from CMTS initialization, of initial
          maintenance mini-slots defined for this upstream logical
          channel.  This count includes all mini-slots for IUC3
          assigned to a broadcast or multicast SID on the logical
          channel.  This is the 64-bit version of
          docsIfCmtsUpChnlCtrTotalCntnInitMaintMslots
          and will not be accessible to SNMPv1 managers.
          Discontinuities in the value of this counter can occur
          at reinitialization of the managed system, and at other
          times as indicated by the value of
          ifCounterDiscontinuityTime for the associated ifIndex."
     ::= { docsIfCmtsUpChannelCounterEntry 27 }

docsIfCmtsUpChnlCtrExtUsedCntnInitMaintMslots OBJECT-TYPE
     SYNTAX      Counter64
     UNITS       "mini-slots"
     MAX-ACCESS  read-only
     STATUS      current
     DESCRIPTION
         "Current count, from CMTS initialization, of initial
          maintenance mini-slots utilized on this upstream logical
          channel.  This includes all contention mini-slots for IUC3
          applicable to bursts that the CMTS correctly received.
          This is the 64-bit version of
          docsIfCmtsUpChnlCtrUsedCntnInitMaintMslots
          and will not be accessible to SNMPv1 managers.
          Discontinuities in the value of this counter can occur
          at reinitialization of the managed system, and at other
          times as indicated by the value of
          ifCounterDiscontinuityTime for the associated ifIndex."
     ::= { docsIfCmtsUpChannelCounterEntry 28 }

docsIfCmtsUpChnlCtrExtCollCntnInitMaintMslots OBJECT-TYPE
     SYNTAX      Counter64
     UNITS       "mini-slots"
     MAX-ACCESS  read-only
     STATUS      current
     DESCRIPTION
         "Current count, from CMTS initialization, of contention
          initial maintenance mini-slots subjected to collisions on
          this upstream logical channel.  This includes all
          contention mini-slots for IUC3 applicable to bursts that
          the CMTS detected, but could not correctly receive.
          This is the 64-bit version of
          docsIfCmtsUpChnlCtrCollCntnInitMaintMslots and will not
          be accessible to SNMPv1 managers.
          Discontinuities in the value of this counter can occur
          at reinitialization of the managed system, and at other
          times as indicated by the value of
          ifCounterDiscontinuityTime for the associated ifIndex."
     ::= { docsIfCmtsUpChannelCounterEntry 29 }

--
-- notification group is for future extension.
--

docsIfNotification OBJECT IDENTIFIER     ::= { docsIfMib 2 }

--
-- MIB Compliance statements.
--

--
-- Conformance definitions
--

docsIfConformance  OBJECT IDENTIFIER     ::= { docsIfMib 3 }
docsIfCompliances  OBJECT IDENTIFIER     ::= { docsIfConformance 1 }
docsIfGroups       OBJECT IDENTIFIER     ::= { docsIfConformance 2 }

docsIfBasicCompliance MODULE-COMPLIANCE
     STATUS      deprecated
     DESCRIPTION
         "The compliance statement for devices that implement
          DOCSIS 1.x compliant Radio Frequency Interfaces."

MODULE  -- docsIfMib

-- unconditionally mandatory groups
MANDATORY-GROUPS {
     docsIfBasicGroup
     }

-- conditionally mandatory group
GROUP docsIfCmGroup
     DESCRIPTION
         "This group is implemented only in cable modems, not in
          cable modem termination systems."

-- conditionally mandatory group
GROUP docsIfCmtsGroup
     DESCRIPTION
         "This group is implemented only in cable modem termination
          systems, not in cable modems."

OBJECT  docsIfDownChannelFrequency
     WRITE-SYNTAX Integer32 (54000000..860000000)
     MIN-ACCESS  read-only
     DESCRIPTION
         "Read-write in cable modem termination systems;
          read-only in cable modems.  The values above are
          appropriate for a cable plant using a Sub-Split channel
          plan.  If DOCSIS is extended to cover other types of
          channel plans (and frequency allocations), this object
          will be modified accordingly."

OBJECT  docsIfDownChannelWidth
     WRITE-SYNTAX Integer32 (6000000)
     MIN-ACCESS  read-only
     DESCRIPTION
         "It is important to implement this object as read-only.
          In cable modems, this object is always implemented as
          read-only.  The above value is appropriate for cable
          plants running under NTSC (National Television
          Standards Committee) standards.  If DOCSIS is extended to
          work with other standards (e.g., European standards), this
          object will be modified accordingly."

OBJECT  docsIfDownChannelModulation
     WRITE-SYNTAX INTEGER {
                            qam64 (3),
                            qam256 (4)
                          }
     MIN-ACCESS  read-only
     DESCRIPTION
         "Read-write in cable modem termination systems;
          read-only in cable modems."

OBJECT  docsIfDownChannelInterleave
     WRITE-SYNTAX INTEGER {
                 taps8Increment16(3),
                 taps16Increment8(4),
                 taps32Increment4(5),
                 taps64Increment2(6),
                 taps128Increment1(7)
                  }
     MIN-ACCESS  read-only
     DESCRIPTION
         "Read-write in cable modem termination systems;
          read-only in cable modems."

OBJECT  docsIfDownChannelPower
     MIN-ACCESS  read-only
     DESCRIPTION
         "Read-write in cable modem termination systems;
          read-only in cable modems."

OBJECT  docsIfUpChannelFrequency
     WRITE-SYNTAX Integer32 (5000000..42000000)
     MIN-ACCESS  read-only
     DESCRIPTION
         "Read-write in cable modem termination systems;
          read-only in cable modems.  The values above are
          appropriate for a cable plant using a Sub-Split channel
          plan.  If DOCSIS is extended to cover other types of
          channel plans (and frequency allocations), this object
          will be modified accordingly."

OBJECT  docsIfUpChannelWidth
     WRITE-SYNTAX Integer32 (200000..3200000)
     MIN-ACCESS  read-only
     DESCRIPTION
         "Read-write in cable modem termination systems;
          read-only in cable modems.  The above value is appropriate
          for cable plants running under NTSC (National Television
          Standards Committee) standards.  If DOCSIS is extended to
          work with other standards (e.g., European standards), this
          object will be modified accordingly."

OBJECT  docsIfUpChannelModulationProfile
     MIN-ACCESS  read-only
     DESCRIPTION
         "Read-write in cable modem termination systems;
          read-only in cable modems."

OBJECT  docsIfUpChannelSlotSize
     MIN-ACCESS  read-only
     DESCRIPTION
         "This object is always read-only in cable modems.
          It is compliant to implement this object as read-only
          in cable modem termination systems."

OBJECT  docsIfUpChannelRangingBackoffStart
     MIN-ACCESS  read-only
     DESCRIPTION
         "Read-write in cable modem termination systems;
          read-only in cable modems."

OBJECT  docsIfUpChannelRangingBackoffEnd
     MIN-ACCESS  read-only
     DESCRIPTION
         "Read-write in cable modem termination systems;
          read-only in cable modems."

OBJECT  docsIfUpChannelTxBackoffStart
     MIN-ACCESS  read-only
     DESCRIPTION
         "Read-write in cable modem termination systems;
          read-only in cable modems."

OBJECT  docsIfUpChannelTxBackoffEnd
     MIN-ACCESS  read-only
     DESCRIPTION
         "Read-write in cable modem termination systems;
          read-only in cable modems."

OBJECT  docsIfQosProfPriority
     MIN-ACCESS  read-only
     DESCRIPTION
         "This object is always read-only in cable modems.
          It is compliant to implement this object as read-only
          in cable modem termination systems."

OBJECT  docsIfQosProfMaxUpBandwidth
     MIN-ACCESS  read-only
     DESCRIPTION
         "This object is always read-only in cable modems.
          It is compliant to implement this object as read-only
          in cable modem termination systems."

OBJECT  docsIfQosProfGuarUpBandwidth
     MIN-ACCESS  read-only
     DESCRIPTION
         "This object is always read-only in cable modems.
          It is compliant to implement this object as read-only
          in cable modem termination systems."

OBJECT  docsIfQosProfMaxDownBandwidth
     MIN-ACCESS  read-only
     DESCRIPTION
         "This object is always read-only in cable modems.
          It is compliant to implement this object as read-only
          in cable modem termination systems."

OBJECT  docsIfQosProfMaxTxBurst
     MIN-ACCESS  read-only
     DESCRIPTION
         "This object is always read-only in cable modems.
          It is compliant to implement this object as read-only
          in cable modem termination systems."

OBJECT  docsIfQosProfBaselinePrivacy
     MIN-ACCESS  read-only
     DESCRIPTION
         "This object is always read-only in cable modems.
          It is compliant to implement this object as read-only
          in cable modem termination systems."

OBJECT  docsIfQosProfStatus
     MIN-ACCESS  read-only
     DESCRIPTION
         "This object is always read-only in cable modems.
          It is compliant to implement this object as read-only
          in cable modem termination systems."

OBJECT  docsIfCmtsServiceAdminStatus
     MIN-ACCESS  read-only
     DESCRIPTION
         "It is compliant to implement this object as read-only."

OBJECT  docsIfCmtsSyncInterval
     MIN-ACCESS  read-only
     DESCRIPTION
         "It is compliant to implement this object as read-only."

OBJECT  docsIfCmtsUcdInterval
     MIN-ACCESS  read-only
     DESCRIPTION
         "It is compliant to implement this object as read-only."

OBJECT  docsIfCmtsInsertInterval
     MIN-ACCESS  read-only
     DESCRIPTION
         "It is compliant to implement this object as read-only."

OBJECT  docsIfCmtsInvitedRangingAttempts
     MIN-ACCESS  read-only
     DESCRIPTION
         "It is compliant to implement this object as read-only."

OBJECT  docsIfCmtsQosProfilePermissions
     WRITE-SYNTAX     BITS {
         createByManagement(0),
         updateByManagement(1)
        }
     MIN-ACCESS  read-only
     DESCRIPTION
         "It is compliant to implement this object as read-only."

OBJECT docsIfCmtsModType
     WRITE-SYNTAX INTEGER {
                     qpsk (2),
                     qam16 (3)
                      }
     DESCRIPTION
         "A management station MAY only set 16QAM or QPSK modulation,
          but others might be possible, based on device
          configuration."

OBJECT  docsIfCmtsModPreambleLen
     SYNTAX Integer32 (0..1024)
     DESCRIPTION
         "The range of the values for this MODULE-COMPLIANCE
          is 0..1024."

OBJECT  docsIfCmtsModFECErrorCorrection
        SYNTAX Integer32 (0..10)
        DESCRIPTION
            "The range of the values for this MODULE-COMPLIANCE
             is 0..10."
     ::= { docsIfCompliances 1 }

docsIfBasicComplianceV2 MODULE-COMPLIANCE
     STATUS      current
     DESCRIPTION
         "The compliance statement for devices that implement
          DOCSIS 2.0 Radio Frequency Interfaces."

MODULE  -- docsIfMib

-- unconditionally mandatory groups
MANDATORY-GROUPS {
     docsIfBasicGroupV2
     }

-- conditionally mandatory group
GROUP docsIfCmGroupV2
     DESCRIPTION
         "This group is implemented only in cable modems, not in
          cable modem termination systems."

-- conditionally mandatory group
GROUP docsIfCmtsGroupV2
     DESCRIPTION
         "This group is implemented only in cable modem termination
          systems, not in cable modems."

OBJECT  docsIfDownChannelFrequency
     WRITE-SYNTAX Integer32 (47000000..862000000)
     MIN-ACCESS  read-only
     DESCRIPTION
         "Read-write in cable modem termination systems;
          read-only in cable modems.
          A range of 54MHz to 860MHz is appropriate for a cable
          plant using a North American Sub-Split channel plan.
          The spectrum range has been expanded to accommodate
          a lower edge of 47MHz and an upper edge of 862MHz
          for some European channel plans.
          If DOCSIS is extended to cover other types of channel
          plans (and frequency allocations), this object will be
          modified accordingly."

OBJECT  docsIfDownChannelWidth
     WRITE-SYNTAX Integer32 (6000000 | 8000000)
     MIN-ACCESS  read-only
     DESCRIPTION
         "It is important to implement this object as read-only.
          In cable modems, this object is always implemented as
          read-only.  The value of 6 MHz is appropriate for cable
          plants running under NTSC (National Television
          Standards Committee) standards.  The value of 8 MHz is
          appropriate for cable plants running under ETSI
          standards.  For other regional standards, this
          object will be modified accordingly."

OBJECT  docsIfDownChannelModulation
     WRITE-SYNTAX INTEGER {
                            qam64 (3),
                            qam256 (4)
                          }
     MIN-ACCESS  read-only
     DESCRIPTION
         "Read-write in cable modem termination systems;
          read-only in cable modems."

OBJECT  docsIfDownChannelInterleave
     WRITE-SYNTAX INTEGER {
                 taps8Increment16(3),
                 taps16Increment8(4),
                 taps32Increment4(5),
                 taps64Increment2(6),
                 taps128Increment1(7),
                 taps12increment17(8)
                  }
     MIN-ACCESS  read-only
     DESCRIPTION
         "Read-write in cable modem termination systems;
          read-only in cable modems."

OBJECT  docsIfDownChannelPower
     MIN-ACCESS  read-only
     DESCRIPTION
         "Read-write in cable modem termination systems;
          read-only in cable modems."

OBJECT  docsIfUpChannelFrequency
     WRITE-SYNTAX Integer32 (5000000..65000000)
     MIN-ACCESS  read-only
     DESCRIPTION
         "Read-create in cable modem termination systems;
          read-only in cable modems.
          A range of 5MHz to 42MHz is appropriate for a cable
          plant using a North American Sub-Split channel plan.
          The spectrum range has been expanded to accommodate
          an upper edge of 65MHz for some European channel plans.
          If DOCSIS is extended to cover other types of channel
          plans (and frequency allocations), this object will
          be modified accordingly."

OBJECT  docsIfUpChannelWidth
     WRITE-SYNTAX Integer32 (200000..6400000)
     MIN-ACCESS  read-only
     DESCRIPTION
         "Read-create in cable modem termination systems,
          read-only in cable modems.  The above value is appropriate
          for cable plants running under NTSC (National Television
          Standards Committee) standards.  If DOCSIS is extended to
          work with other standards (e.g., European standards), this
          object will be modified accordingly."

OBJECT  docsIfUpChannelModulationProfile
     MIN-ACCESS  read-only
     DESCRIPTION
         "Read-create in cable modem termination systems;
          read-only in cable modems."

OBJECT  docsIfUpChannelSlotSize
     MIN-ACCESS  read-only
     DESCRIPTION
         "This object is always read-only in cable modems.
          It is compliant to implement this object as read-only
          in cable modem termination systems."

OBJECT  docsIfUpChannelRangingBackoffStart
     MIN-ACCESS  read-only
     DESCRIPTION
         "Read-create in cable modem termination systems;
          read-only in cable modems."

OBJECT  docsIfUpChannelRangingBackoffEnd
     MIN-ACCESS  read-only
     DESCRIPTION
         "Read-create in cable modem termination systems;
          read-only in cable modems."

OBJECT  docsIfUpChannelTxBackoffStart
     MIN-ACCESS  read-only
     DESCRIPTION
         "Read-create in cable modem termination systems;
          read-only in cable modems."

OBJECT  docsIfUpChannelTxBackoffEnd
     MIN-ACCESS  read-only
     DESCRIPTION
         "Read-create in cable modem termination systems;
          read-only in cable modems."

OBJECT  docsIfUpChannelScdmaActiveCodes
     MIN-ACCESS  read-only
     DESCRIPTION
         "Read-create in cable modem termination systems;
          read-only in cable modems.
          The number of active codes when SCDMA is in use MUST range
          from 64 to 128 and MUST be a non-Prime value.
          Providing this range allows for the following features
          and capabilities:
             1) Power management in S-CDMA spreader-on frames
                (with a 3 dB spread).

             2) Avoidance of code 0.
             3) Flexible mini-slot sizes with and without the use of
                code 0."

OBJECT  docsIfUpChannelScdmaCodesPerSlot
     MIN-ACCESS  read-only
     DESCRIPTION
         "Read-create in cable modem termination systems;
          read-only in cable modems."

OBJECT  docsIfUpChannelScdmaFrameSize
     MIN-ACCESS  read-only
     DESCRIPTION
         "Read-create in cable modem termination systems;
          read-only in cable modems."

OBJECT  docsIfUpChannelScdmaHoppingSeed
     MIN-ACCESS  read-only
     DESCRIPTION
         "Read-create in cable modem termination systems;
          read-only in cable modems."

OBJECT  docsIfUpChannelCloneFrom
     MIN-ACCESS  read-only
     DESCRIPTION
         "Read-create in cable modem termination systems;
          read-only in cable modems."

OBJECT  docsIfUpChannelUpdate
     MIN-ACCESS  read-only
     DESCRIPTION
         "Read-create in cable modem termination systems;
          read-only in cable modems."

OBJECT  docsIfUpChannelStatus
        MIN-ACCESS  read-only
        DESCRIPTION
            "Read-create in Cable Modem Termination Systems;
             read-only in Cable Modems.
             Entries associated to physical interfaces only support
             the read-only value 'active'."

OBJECT  docsIfUpChannelPreEqEnable
     MIN-ACCESS  read-only
     DESCRIPTION
         "Read-create in cable modem termination systems;
          read-only in cable modems."

OBJECT  docsIfQosProfPriority
     MIN-ACCESS  read-only
     DESCRIPTION
         "This object is always read-only in cable modems.
          It is compliant to implement this object as read-only
          in cable modem termination systems."

OBJECT  docsIfQosProfMaxUpBandwidth
     MIN-ACCESS  read-only
     DESCRIPTION
         "This object is always read-only in cable modems.
          It is compliant to implement this object as read-only
          in cable modem termination systems."

OBJECT  docsIfQosProfGuarUpBandwidth
     MIN-ACCESS  read-only
     DESCRIPTION
         "This object is always read-only in cable modems.
          It is compliant to implement this object as read-only
          in cable modem termination systems."

OBJECT  docsIfQosProfMaxDownBandwidth
     MIN-ACCESS  read-only
     DESCRIPTION
         "This object is always read-only in cable modems.
          It is compliant to implement this object as read-only
          in cable modem termination systems."

OBJECT  docsIfQosProfBaselinePrivacy
     MIN-ACCESS  read-only
     DESCRIPTION
         "This object is always read-only in cable modems.
          It is compliant to implement this object as read-only
          in cable modem termination systems."

OBJECT  docsIfQosProfStatus
     MIN-ACCESS  read-only
     DESCRIPTION
         "This object is always read-only in cable modems.
          It is compliant to implement this object as read-only
          in cable modem termination systems."

OBJECT  docsIfQosProfMaxTransmitBurst
     MIN-ACCESS  read-only
     DESCRIPTION
         "This object is always read-only in cable modems.
          It is compliant to implement this object as read-only
          in cable modem termination systems."

OBJECT  docsIfCmRangingTimeout
     MIN-ACCESS  read-only
     DESCRIPTION
         "It is compliant to implement this object as read-only."

OBJECT docsIfCmStatusModulationType
    SYNTAX          INTEGER {
        unknown(0),
        tdma(1),
        atdma(2),
        scdma(3)
    }
     DESCRIPTION
         "CM does not use both modulation burst profiles of a
          'tdmAndAtdma' ChannelType; therefore, 'tdmAndAtdma'is
          not supported."

OBJECT  docsIfCmtsServiceAdminStatus
     MIN-ACCESS  read-only
     DESCRIPTION
         "It is compliant to implement this object as read-only."

OBJECT  docsIfCmtsSyncInterval
     MIN-ACCESS  read-only
     DESCRIPTION
         "It is compliant to implement this object as read-only."

OBJECT  docsIfCmtsUcdInterval
     MIN-ACCESS  read-only
     DESCRIPTION
         "It is compliant to implement this object as read-only."

OBJECT  docsIfCmtsInsertInterval
     MIN-ACCESS  read-only
     DESCRIPTION
         "It is compliant to implement this object as read-only."

OBJECT  docsIfCmtsInvitedRangingAttempts
     MIN-ACCESS  read-only
     DESCRIPTION
         "It is compliant to implement this object as read-only."

OBJECT  docsIfCmtsQosProfilePermissions
     WRITE-SYNTAX     BITS {
         createByManagement(0),
         updateByManagement(1)
        }
     MIN-ACCESS  read-only
     DESCRIPTION
         "It is compliant to implement this object as read-only."

OBJECT docsIfCmtsModType
     WRITE-SYNTAX      INTEGER {
         qpsk(2),
         qam16(3),
         qam64(6)
     }
     DESCRIPTION
         "A management station MAY only set 64QAM, 16QAM, or QPSK
          modulation for Time or Code division Multiple Access,
          but others might be possible based on device
          configuration."

OBJECT docsIfCmtsCmStatusModulationType
    SYNTAX          INTEGER {
        unknown(0),
        tdma(1),
        atdma(2),
        scdma(3)
    }
     DESCRIPTION
         "CM does not use both modulation burst profiles of a
          'tdmAndAtdma' ChannelType; therefore, 'tdmAndAtdma'is
          not supported."
     ::= { docsIfCompliances 2 }

docsIfBasicGroup OBJECT-GROUP
     OBJECTS {
         docsIfDownChannelId,
         docsIfDownChannelFrequency,
         docsIfDownChannelWidth,
         docsIfDownChannelModulation,
         docsIfDownChannelInterleave,
         docsIfDownChannelPower,
         docsIfUpChannelId,
         docsIfUpChannelFrequency,
         docsIfUpChannelWidth,
         docsIfUpChannelModulationProfile,
         docsIfUpChannelSlotSize,
         docsIfUpChannelTxTimingOffset,
         docsIfUpChannelRangingBackoffStart,
         docsIfUpChannelRangingBackoffEnd,
         docsIfUpChannelTxBackoffStart,
         docsIfUpChannelTxBackoffEnd,
         docsIfQosProfPriority,
         docsIfQosProfMaxUpBandwidth,
         docsIfQosProfGuarUpBandwidth,
         docsIfQosProfMaxDownBandwidth,
         docsIfQosProfMaxTxBurst,
         docsIfQosProfBaselinePrivacy,
         docsIfQosProfStatus,
         docsIfSigQIncludesContention,
         docsIfSigQUnerroreds,
         docsIfSigQCorrecteds,
         docsIfSigQUncorrectables,
         docsIfSigQSignalNoise,
         docsIfSigQMicroreflections,
         docsIfSigQEqualizationData
     }
     STATUS      deprecated
     DESCRIPTION
         "Group of objects implemented in both cable modems and
          cable modem termination systems."
     ::= { docsIfGroups 1 }

docsIfCmGroup OBJECT-GROUP
     OBJECTS {
         docsIfCmCmtsAddress,
         docsIfCmCapabilities,
         docsIfCmRangingTimeout,
         docsIfCmStatusValue,
         docsIfCmStatusCode,
         docsIfCmStatusTxPower,
         docsIfCmStatusResets,
         docsIfCmStatusLostSyncs,
         docsIfCmStatusInvalidMaps,
         docsIfCmStatusInvalidUcds,
         docsIfCmStatusInvalidRangingResponses,
         docsIfCmStatusInvalidRegistrationResponses,
         docsIfCmStatusT1Timeouts,
         docsIfCmStatusT2Timeouts,
         docsIfCmStatusT3Timeouts,
         docsIfCmStatusT4Timeouts,
         docsIfCmStatusRangingAborteds,
         docsIfCmServiceQosProfile,
         docsIfCmServiceTxSlotsImmed,
         docsIfCmServiceTxSlotsDed,
         docsIfCmServiceTxRetries,
         docsIfCmServiceTxExceededs,
         docsIfCmServiceRqRetries,
         docsIfCmServiceRqExceededs
     }
     STATUS      deprecated
     DESCRIPTION
         "Group of objects implemented in cable modems."
     ::= { docsIfGroups 2 }

docsIfCmtsGroup OBJECT-GROUP
     OBJECTS {
         docsIfCmtsCapabilities,
         docsIfCmtsSyncInterval,
         docsIfCmtsUcdInterval,
         docsIfCmtsMaxServiceIds,
         docsIfCmtsInvitedRangingAttempts,
         docsIfCmtsInsertInterval,
         docsIfCmtsStatusInvalidRangeReqs,
         docsIfCmtsStatusRangingAborteds,
         docsIfCmtsStatusInvalidRegReqs,
         docsIfCmtsStatusFailedRegReqs,
         docsIfCmtsStatusInvalidDataReqs,
         docsIfCmtsStatusT5Timeouts,
         docsIfCmtsCmStatusMacAddress,
         docsIfCmtsCmStatusIpAddress,
         docsIfCmtsCmStatusDownChannelIfIndex,
         docsIfCmtsCmStatusUpChannelIfIndex,
         docsIfCmtsCmStatusRxPower,
         docsIfCmtsCmStatusTimingOffset,
         docsIfCmtsCmStatusEqualizationData,
         docsIfCmtsCmStatusValue,
         docsIfCmtsCmStatusUnerroreds,
         docsIfCmtsCmStatusCorrecteds,
         docsIfCmtsCmStatusUncorrectables,
         docsIfCmtsCmStatusSignalNoise,
         docsIfCmtsCmStatusMicroreflections,
         docsIfCmtsServiceCmStatusIndex,
         docsIfCmtsServiceAdminStatus,
         docsIfCmtsServiceQosProfile,
         docsIfCmtsServiceCreateTime,
         docsIfCmtsServiceInOctets,
         docsIfCmtsServiceInPackets,
         docsIfCmtsModType,
         docsIfCmtsModControl,
         docsIfCmtsModPreambleLen,
         docsIfCmtsModDifferentialEncoding,
         docsIfCmtsModFECErrorCorrection,
         docsIfCmtsModFECCodewordLength,
         docsIfCmtsModScramblerSeed,
         docsIfCmtsModMaxBurstSize,
         docsIfCmtsModGuardTimeSize,
         docsIfCmtsModLastCodewordShortened,
         docsIfCmtsModScrambler,
         docsIfCmtsQosProfilePermissions,
         docsIfCmtsCmPtr
     }
     STATUS      deprecated
     DESCRIPTION
         "Group of objects implemented in Cable Modem Termination
          Systems."
     ::= { docsIfGroups 3 }

-- obsolete group
-- RFC 2670 already had a obsolete group, even though RFC2670
-- was the first version of this MIB Module.

docsIfObsoleteGroup OBJECT-GROUP
     OBJECTS {
         docsIfCmRangingRespTimeout,
         docsIfCmtsInsertionInterval
     }
     STATUS      obsolete
     DESCRIPTION
         "Group of objects obsoleted."
     ::= { docsIfGroups 4 }

docsIfBasicGroupV2 OBJECT-GROUP
     OBJECTS {
         docsIfDownChannelId,
         docsIfDownChannelFrequency,
         docsIfDownChannelWidth,
         docsIfDownChannelModulation,
         docsIfDownChannelInterleave,
         docsIfDownChannelPower,
         docsIfDownChannelAnnex,
         docsIfUpChannelId,
         docsIfUpChannelFrequency,
         docsIfUpChannelWidth,
         docsIfUpChannelModulationProfile,
         docsIfUpChannelSlotSize,
         docsIfUpChannelTxTimingOffset,
         docsIfUpChannelRangingBackoffStart,
         docsIfUpChannelRangingBackoffEnd,
         docsIfUpChannelTxBackoffStart,
         docsIfUpChannelTxBackoffEnd,
         docsIfUpChannelScdmaActiveCodes,
         docsIfUpChannelScdmaCodesPerSlot,
         docsIfUpChannelScdmaFrameSize,
         docsIfUpChannelScdmaHoppingSeed,
         docsIfUpChannelType,
         docsIfUpChannelCloneFrom,
         docsIfUpChannelUpdate,
         docsIfUpChannelStatus,
         docsIfUpChannelPreEqEnable,
         docsIfQosProfPriority,
         docsIfQosProfMaxUpBandwidth,
         docsIfQosProfGuarUpBandwidth,
         docsIfQosProfMaxDownBandwidth,
         docsIfQosProfBaselinePrivacy,
         docsIfQosProfStatus,
         docsIfQosProfMaxTransmitBurst,
         docsIfSigQIncludesContention,
         docsIfSigQUnerroreds,
         docsIfSigQCorrecteds,
         docsIfSigQUncorrectables,
         docsIfSigQSignalNoise,
         docsIfSigQMicroreflections,
         docsIfSigQExtUnerroreds,
         docsIfSigQExtCorrecteds,
         docsIfSigQExtUncorrectables,
         docsIfDocsisBaseCapability
     }
     STATUS      current
     DESCRIPTION
         "Group of objects implemented in both cable modems and
          cable modem termination systems."
     ::= { docsIfGroups 5 }

docsIfCmGroupV2 OBJECT-GROUP
     OBJECTS {
         docsIfCmCmtsAddress,
         docsIfCmCapabilities,
         docsIfCmRangingTimeout,
         docsIfCmStatusValue,
         docsIfCmStatusCode,
         docsIfCmStatusTxPower,
         docsIfCmStatusResets,
         docsIfCmStatusLostSyncs,
         docsIfCmStatusInvalidMaps,
         docsIfCmStatusInvalidUcds,
         docsIfCmStatusInvalidRangingResponses,
         docsIfCmStatusInvalidRegistrationResponses,
         docsIfCmStatusT1Timeouts,
         docsIfCmStatusT2Timeouts,
         docsIfCmStatusT3Timeouts,
         docsIfCmStatusT4Timeouts,
         docsIfCmStatusRangingAborteds,
         docsIfCmStatusDocsisOperMode,
         docsIfCmStatusModulationType,
         docsIfCmStatusEqualizationData,
         docsIfCmStatusUCCs,
         docsIfCmStatusUCCFails,
         docsIfCmServiceQosProfile,
         docsIfCmServiceTxSlotsImmed,
         docsIfCmServiceTxSlotsDed,
         docsIfCmServiceTxRetries,
         docsIfCmServiceTxExceededs,
         docsIfCmServiceRqRetries,
         docsIfCmServiceRqExceededs,
         docsIfCmServiceExtTxSlotsImmed,
         docsIfCmServiceExtTxSlotsDed,
         docsIfSigQEqualizationData
     }
     STATUS      current
     DESCRIPTION
         "Group of objects implemented in cable modems."
     ::= { docsIfGroups 6 }

docsIfCmtsGroupV2 OBJECT-GROUP
     OBJECTS {
         docsIfCmtsCapabilities,
         docsIfCmtsSyncInterval,
         docsIfCmtsUcdInterval,
         docsIfCmtsMaxServiceIds,
         docsIfCmtsInvitedRangingAttempts,
         docsIfCmtsInsertInterval,
         docsIfCmtsMacStorageType,
         docsIfCmtsStatusInvalidRangeReqs,
         docsIfCmtsStatusRangingAborteds,
         docsIfCmtsStatusInvalidRegReqs,
         docsIfCmtsStatusFailedRegReqs,
         docsIfCmtsStatusInvalidDataReqs,
         docsIfCmtsStatusT5Timeouts,
         docsIfCmtsCmStatusMacAddress,
         docsIfCmtsCmStatusDownChannelIfIndex,
         docsIfCmtsCmStatusUpChannelIfIndex,
         docsIfCmtsCmStatusRxPower,
         docsIfCmtsCmStatusTimingOffset,
         docsIfCmtsCmStatusEqualizationData,
         docsIfCmtsCmStatusValue,
         docsIfCmtsCmStatusUnerroreds,
         docsIfCmtsCmStatusCorrecteds,
         docsIfCmtsCmStatusUncorrectables,
         docsIfCmtsCmStatusSignalNoise,
         docsIfCmtsCmStatusMicroreflections,
         docsIfCmtsCmStatusExtUnerroreds,
         docsIfCmtsCmStatusExtCorrecteds,
         docsIfCmtsCmStatusExtUncorrectables,
         docsIfCmtsCmStatusDocsisRegMode,
         docsIfCmtsCmStatusModulationType,
         docsIfCmtsCmStatusInetAddressType,
         docsIfCmtsCmStatusInetAddress,
         docsIfCmtsCmStatusValueLastUpdate,
         docsIfCmtsCmStatusHighResolutionTimingOffset,
         docsIfCmtsServiceAdminStatus,
         docsIfCmtsServiceQosProfile,
         docsIfCmtsServiceCreateTime,
         docsIfCmtsServiceInOctets,
         docsIfCmtsServiceInPackets,
         docsIfCmtsServiceNewCmStatusIndex,
         docsIfCmtsModType,
         docsIfCmtsModControl,
         docsIfCmtsModPreambleLen,
         docsIfCmtsModDifferentialEncoding,
         docsIfCmtsModFECErrorCorrection,
         docsIfCmtsModFECCodewordLength,
         docsIfCmtsModScramblerSeed,
         docsIfCmtsModMaxBurstSize,
         docsIfCmtsModGuardTimeSize,
         docsIfCmtsModLastCodewordShortened,
         docsIfCmtsModScrambler,
         docsIfCmtsModByteInterleaverDepth,
         docsIfCmtsModByteInterleaverBlockSize,
         docsIfCmtsModPreambleType,
         docsIfCmtsModTcmErrorCorrectionOn,
         docsIfCmtsModScdmaInterleaverStepSize,
         docsIfCmtsModScdmaSpreaderEnable,
         docsIfCmtsModScdmaSubframeCodes,
         docsIfCmtsModChannelType,
         docsIfCmtsModStorageType,
         docsIfCmtsQosProfilePermissions,
         docsIfCmtsCmPtr,
         docsIfCmtsChannelUtilizationInterval,
         docsIfCmtsChannelUtUtilization,
         docsIfCmtsDownChnlCtrId,
         docsIfCmtsDownChnlCtrTotalBytes,
         docsIfCmtsDownChnlCtrUsedBytes,
         docsIfCmtsDownChnlCtrExtTotalBytes,
         docsIfCmtsDownChnlCtrExtUsedBytes,
         docsIfCmtsUpChnlCtrId,
         docsIfCmtsUpChnlCtrTotalMslots,
         docsIfCmtsUpChnlCtrUcastGrantedMslots,
         docsIfCmtsUpChnlCtrTotalCntnMslots,
         docsIfCmtsUpChnlCtrUsedCntnMslots,
         docsIfCmtsUpChnlCtrExtTotalMslots,
         docsIfCmtsUpChnlCtrExtUcastGrantedMslots,
         docsIfCmtsUpChnlCtrExtTotalCntnMslots,
         docsIfCmtsUpChnlCtrExtUsedCntnMslots,
         docsIfCmtsUpChnlCtrCollCntnMslots,
         docsIfCmtsUpChnlCtrTotalCntnReqMslots,
         docsIfCmtsUpChnlCtrUsedCntnReqMslots,
         docsIfCmtsUpChnlCtrCollCntnReqMslots,
         docsIfCmtsUpChnlCtrTotalCntnReqDataMslots,
         docsIfCmtsUpChnlCtrUsedCntnReqDataMslots,
         docsIfCmtsUpChnlCtrCollCntnReqDataMslots,
         docsIfCmtsUpChnlCtrTotalCntnInitMaintMslots,
         docsIfCmtsUpChnlCtrUsedCntnInitMaintMslots,
         docsIfCmtsUpChnlCtrCollCntnInitMaintMslots,
         docsIfCmtsUpChnlCtrExtCollCntnMslots,
         docsIfCmtsUpChnlCtrExtTotalCntnReqMslots,
         docsIfCmtsUpChnlCtrExtUsedCntnReqMslots,
         docsIfCmtsUpChnlCtrExtCollCntnReqMslots,
         docsIfCmtsUpChnlCtrExtTotalCntnReqDataMslots,
         docsIfCmtsUpChnlCtrExtUsedCntnReqDataMslots,
         docsIfCmtsUpChnlCtrExtCollCntnReqDataMslots,
         docsIfCmtsUpChnlCtrExtTotalCntnInitMaintMslots,
         docsIfCmtsUpChnlCtrExtUsedCntnInitMaintMslots,
         docsIfCmtsUpChnlCtrExtCollCntnInitMaintMslots,
         docsIfDownChannelStorageType,
         docsIfQosProfStorageType

     }
     STATUS      current
     DESCRIPTION
         "Group of objects implemented in Cable Modem Termination
          Systems."
     ::= { docsIfGroups 7 }

END
