CM-FACILITY-MIB DEFINITIONS ::= BEGIN

IMPORTS
    MODULE-COMPLIANCE, OBJECT-GROUP 
             FROM SNMPv2-CONF
    MODULE-IDENTITY, OBJECT-TYPE, Integer32, Unsigned32, IpAddress, Counter64
             FROM SNMPv2-SMI
    DateAndTime, DisplayString, TruthValue, RowStatus, StorageType, 
    MacAddress, VariablePointer, TEXTUAL-CONVENTION
             FROM SNMPv2-TC
    Ipv6Address
             FROM IPV6-TC
    InterfaceIndex
             FROM IF-MIB
    PhysicalIndex
             FROM ENTITY-MIB
    neIndex, shelfIndex, slotIndex, f3UsbHostIndex, networkElementEntry
             FROM CM-ENTITY-MIB
    fsp150cm
             FROM  ADVA-MIB 
    AdminState, OperationalState, SecondaryState, EthernetMediaType, 
    EthernetPortSpeed, TrafficDirection, SfpConnectorValue, SfpMediaType,
    VlanId, VlanPriority, VlanTagType, PriorityMapMode, SignalDirectionType,
    AfpTagControl, VlanEthertype,
    CmTrafficAclFilterActionType,IpVersion,CmTrafficACLPriorityType,
    CmTrafficAclFilterType, CmTrafficAclProtocolType, TDMFrequencySourceType,
    F3DisplayString, FlowSecState, UsbOperationalMode, SfpIdentifierValue
             FROM  CM-COMMON-MIB
    f3LagIndex
             FROM F3-LAG-MIB
    SSMQualityLevel, SquelchControl, TimeSource, ClkSignalType
             FROM F3-SYNC-MIB;


cmFacilityMIB MODULE-IDENTITY
    LAST-UPDATED        "202101270000Z"
    ORGANIZATION    "ADVA Optical Networking SE"
    CONTACT-INFO
        "Web URL: http://adva.com/
        E-mail:  support@adva.com
        Postal:  ADVA Optical Networking SE
             Campus Martinsried
             Fraunhoferstrasse 9a
             82152 Martinsried/Munich
             Germany
        Phone: +49 089 89 06 65 0
        Fax:  +49 089 89 06 65 199 "
    DESCRIPTION
            "This module defines the Facility MIB definitions used by 
             the F3 (FSP150CM/CC) product lines.  
             Copyright (C) ADVA."
    REVISION        "202101270000Z"
    DESCRIPTION
        "
        Notes from release 202009220000Z,
         (1) Added new entries to SfpChannelIdentifier TEXTUAL-CONVENTION:
             frequency-19605, autoTuning.

         Notes from release 202005120000Z,
         (1) Added TEXTUAL-CONVENTIONs:
             PlugType, PlugMode, RelativeChannelIdentifier, ChannelType, OutOfBandChannelStatus,
             GMetroAutoTuningMode, FrequencyIdentifier, ITUCBandChannelIdentifier.

         (2) Added cmEthernetAccPortSfpIdentifierValue column to cmEthernetAccPortTable.

         (3) Added cmEthernetNetPortSfpIdentifierValue column to cmEthernetNetPortTable.

         (4) Added cmEthernetTrafficPortSfpIdentifierValue, cmEthernetTrafficPortPlugType,
             cmEthernetTrafficPortPlugMode, cmEthernetTrafficPortPlugGMetroAutoTuningMode,
             cmEthernetTrafficPortPlugChannelType, cmEthernetTrafficPortPlugITUCbandChannel,
             cmEthernetTrafficPortPlugRelativeChannel, cmEthernetTrafficPortPlugFrequency,
             cmEthernetTrafficPortPlugOutOfBandChannelStatus, cmEthernetTrafficPortRemotePlugITUCbandChannel,
             cmEthernetTrafficPortRemotePlugRelativeChannel, cmEthernetTrafficPortRemotePlugFrequency,
             cmEthernetTrafficPortRemoteSfpVendorName, cmEthernetTrafficPortRemoteSfpName,
             cmEthernetTrafficPortRemoteSfpPartNumber, cmEthernetTrafficPortRemoteSfpHardwareRevision,
             cmEthernetTrafficPortRemoteSfpSerialNumber, cmEthernetTrafficPortRemoteSfpDateOfManufacture,
             cmEthernetTrafficPortRemoteSfpLinkLength, cmEthernetTrafficPortRemoteSfpLaserWaveLength,
             cmEthernetTrafficPortRemoteSfpLaserFrequency, cmEthernetTrafficPortRemoteSfpMediaType,
             cmEthernetTrafficPortRemoteSfpConnectorValue and cmEthernetTrafficPortRemoteSfpIdentifierValue
             columns to cmEthernetTrafficPortTable.

         Notes from release 202006040000Z,
           (1) Added cmEthernetAccPortLoopbackTestReflectorIPv4AddressControl,
               cmEthernetAccPortLoopbackTestReflectorIPv4Address,
               cmEthernetAccPortLoopbackTestReflectorIPv6AddressControl,
               cmEthernetAccPortLoopbackTestReflectorIPv6Address
               columns to cmEthernetAccPortTable.

           (2) Added cmEthernetNetPortLoopbackTestReflectorIPv4AddressControl,
               cmEthernetNetPortLoopbackTestReflectorIPv4Address,
               cmEthernetNetPortLoopbackTestReflectorIPv6AddressControl,
               cmEthernetNetPortLoopbackTestReflectorIPv6Address
               columns to cmEthernetNetPortTable.

           (3) Added cmEthernetTrafficPortLoopbackTestReflectorIPv4AddressControl,
               cmEthernetTrafficPortLoopbackTestReflectorIPv4Address,
               cmEthernetTrafficPortLoopbackTestReflectorIPv6AddressControl,
               cmEthernetTrafficPortLoopbackTestReflectorIPv6Address
               columns to cmEthernetTrafficPortTable.

         Notes from release 202005110000Z,
           (1) new f3IrigOutputGroupIfIndex
           (2) new f3IrigOutputGroupEntityIndex

         Notes from release 202001300000Z,
           (1) Added f3GPSReceiverPortSpoofingPpsThreshold , f3GPSReceiverPortSpoofingPpsDifference  , f3GPSReceiverPortSpoofingLocationThreshold,
               f3GPSReceiverPortSpoofingLocationDifference , f3GPSReceiverPortGnssDynamicModel 
           (2) New TEXTUAL-CONVENTION:: DynamicModelType
               - portable, stationary, pedestrian, automotive, sea, airborne_1g, airborne_2g, airborne_4g

         Notes from release 201912090000Z
           (1) Added new column to f3PulsePerSecondPortTable:
               f3PulsePerSecondPortAssumedClockClass
           (2) Added new column to f3TimeOfDayPortTable:
               f3TimeOfDayPortAssumedClockClass

         Notes from release 201912080000Z
           (1) f3PulsePerSecondPortDelayCompensation SYNTAX
               Integer32 is redefined to (-5000000..5000000)
           (2) f3TimeOfDayPortDelayCompensation
               Integer32 is redefined to (-5000000..5000000)

         Notes from release 201911240000Z
            (1) Added new column to f3GPSReceiverPortTable:
                  f3GPSReceiverPortFailureSuspendTime

         Notes from release 201911210000Z
            (1) Added TEXTUAL-CONVENTION:
                  CcActivePortState

         Notes from release 201911190000Z
            (1) Added TEXTUAL-CONVENTION:
                  CcPortDutyCycle
            (2) New ccInputPortTable, with columns:
                  ccInputPortIndex, ccInputPortIfIndex, ccInputPortEntityIndex, ccInputPortAlias,
                  ccInputPortAdminState, ccInputPortOperationalState, ccInputPortSecondaryState
            (3) New ccGroupPortEntry, with columns:
                  ccGroupIndex, ccGroupIfIndex, ccGroupEntityIndex, ccGroupAlias,
                  ccGroupActivePorts, ccGroupPhaseAdjust, ccGroupDutyCycle

         Notes from release 201910180000Z
             Added new SNMP table: cmEncapFlowPointTable 

         Notes from release 201909130000Z
            (1) Added TEXTUAL-CONVENTION:
                  IrigTimeCode, IrigControlField, IrigRelayOperation,
                  IrigOutputType, IrigDigitalSignalVoltage, IrigGroupExtensionType
            (2) New f3IrigRs422OutputPortTable, with columns:
                  f3IrigRs422OutputPortIndex, f3IrigRs422OutputPortIfIndex, f3IrigRs422OutputPortEntityIndex,
                  f3IrigRs422OutputPortAlias, f3IrigRs422OutputPortAdminState, f3IrigRs422OutputPortOperationalState,
                  f3IrigRs422OutputPortSecondaryState, f3IrigRs422OutputPortTimeCode, f3IrigRs422OutputPortControlField
            (3) New f3IrigOpticalOutputPortTable, with columns:
                  f3IrigOpticalOutputPortIndex, f3IrigOpticalOutputPortIfIndex, f3IrigOpticalOutputPortEntityIndex,
                  f3IrigOpticalOutputPortAlias, f3IrigOpticalOutputPortAdminState, f3IrigOpticalOutputPortOperationalState,
                  f3IrigOpticalOutputPortSecondaryState, f3IrigOpticalOutputPortTimeCode, f3IrigOpticalOutputPortControlField
            (4) New f3IrigRelayOutputPortTable, with columns:
                  f3IrigRelayOutputPortIndex, f3IrigRelayOutputPortIfIndex, f3IrigRelayOutputPortEntityIndex,
                  f3IrigRelayOutputPortAlias, f3IrigRelayOutputPortAdminState, f3IrigRelayOutputPortOperationalState,
                  f3IrigRelayOutputPortSecondaryState, f3IrigRelayOutputPortRelayOperation
            (5) New f3IrigOutputGroupTable, with columns:
                  f3IrigOutputGroupIndex, f3IrigOutputGroupAlias, f3IrigOutputGroupExtensionType,
                  f3IrigOutputGroupExtensionDetection
            (6) New f3IrigOutputUnitPortTable, with columns:
                  f3IrigOutputUnitPortIndex, f3IrigOutputUnitPortIfIndex, f3IrigOutputUnitPortEntityIndex,
                  f3IrigOutputUnitPortAlias, f3IrigOutputUnitPortAdminState, f3IrigOutputUnitPortOperationalState,
                  f3IrigOutputUnitPortSecondaryState, f3IrigOutputUnitPortTimeCode, f3IrigOutputUnitPortControlField,
                  f3IrigOutputUnitPortType, f3IrigOutputUnitPortDigitalVoltage
            (7) New Conformance Group: f3IrigPortGroup 

         Notes from release 201909110000Z,
          (1) New GPS10MHzPortEntry column: 
                - gps10MHzPortInputSignalType

         Notes from release 201909050000Z
            (1) New bits8PortGroupTable column:
                - bits8PortGroupClkIfEnabledPorts
        
         Notes from release 201907080000Z,
            (1) Added f3GPSReceiverPortSelfSurveyPositionAccuracy, f3GPSReceiverPortHorizontalAccuracy, f3GPSReceiverPortVerticalAccuracy,
                      f3GPSReceiverPortTDOP, f3GPSReceiverPortHDOP, f3GPSReceiverPortVDOP

         Notes from release 201905210000Z
            (1) Add missing f3PulsePerSecondPortTable column:
                - f3PulsePerSecondPortAlias
            (2) Add missing f3TimeOfDayPort column:
                - f3TimeOfDayPortAlias

         Notes from release 201903210000Z
            (1) Added the following to cmEthernetTrafficPortTable
                - cmEthernetTrafficPortSfpTxPowerLevel
                - cmEthernetTrafficPortSfpRxPowerLevel

         Notes from release 201902220000Z
            (1) New f3Usb3GDCNPortTable columns:
                - f3Usb3GDCNPortIpAddress
                - f3Usb3GDCNPortNetMask

          Notes from release 201901240000Z,
            (1) Modified f3GPSReceiverPortTable colums:
               - f3GPSReceiverPortCoordinateAltitude:  
                      MAX-ACCESS is reverted to read-only,
                      SYNTAX is reverted to Unsigned32
            (2) New f3GPSReceiverPortTable columns:
                - f3GPSReceiverPortCoordinateStringAltitude with:
                      MAX-ACCESS read-write,
                      SYNTAX DisplayString
                
            (3) Modified f3GPSReceiverPortTable colums:
               - f3GPSReceiverPortCoordinateLatitude:  MAX-ACCESS read-write instead read-only
               - f3GPSReceiverPortCoordinateLongitude: MAX-ACCESS read-write instead read-only
               - f3GPSReceiverPortCoordinateAltitude:  MAX-ACCESS read-write instead read-only,
                                                       SYNTAX DisplayString instead Unsigned32
            (4) New f3GPSReceiverPortTable columns:
                - f3GPSReceiverPortSelfSurveyControl
            
         Notes from release 201901180000Z
            (1) Added f3GPSReceiverPortAGC

         Notes from release 201901070000Z
            (1) Added TEXTUAL-CONVENTION:: SciSignalMode, SciSignalDirection, and SciRxSsmQL
            (2) Added sciPortTable and sciPortGroup
            (3) Added TEXTUAL-CONVENTION:: SynceRxSsmQl and SynceMode
            (3) Added cmEthernetTrafficPortTxSsm, cmEthernetTrafficPortRxSsmQL,
                      cmEthernetTrafficPortSyncEMode, cmEthernetTrafficPortSyncEServiceAvailableTime,
                      cmEthernetTrafficPortSyncEServiceUnavailableTime, and 
                      cmEthernetTrafficPortSyncEServiceAvailablePercentage
            (4) Added qzss(5) to ConstellationTypesBitMap
            (5) Added TEXTUAL-CONVENTION:: LocationMode and TimeAdvanceMode
            (6) Added f3GPSReceiverPortLocationMode, f3GPSReceiverPortTimeAdvanceMode,
                      f3GPSReceiverPortTimeAdvanceValue, f3GPSReceiverPortForcedAntennaConnected,
                      f3GPSReceiverPortServiceAvailableTime, f3GPSReceiverPortServiceUnavailableTime, and
                      f3GPSReceiverPortServiceAvailablePercentage
            (7) Modified f3GPSReceiverPortTable colums:
               - f3GPSReceiverPortCoordinateLatitude:  MAX-ACCESS read-write instead of read-only
               - f3GPSReceiverPortCoordinateLongitude: MAX-ACCESS read-write instead of read-only
            (8) New f3GPSReceiverPortTable columns:
                - f3GPSReceiverPortSelfSurveyControl
                - f3GPSReceiverPortCoordinateStringAltitude with:
                      MAX-ACCESS read-write,
                      SYNTAX DisplayString

         Notes from release 201810260000Z
            (1) New cmFlowPointTable columns
                - cmFlowPointWfqSegmentationCOS
                - cmFlowPointWfqGroupCOS
                - cmFlowPointWfqGroupEirLo
                - cmFlowPointWfqGroupEirHi
            (2) New f3FpQosShaperTable column
                - f3FpQosShaperWfqWeight
            (3) New cmEthernetTrafficPortTable columns
                - cmEthernetTrafficPortWfqSegmentationCOS
                - cmEthernetTrafficPortWfqGroupCOS
                - cmEthernetTrafficPortWfqGroupEirLo
                - cmEthernetTrafficPortWfqGroupEirHi     
            (4) New cmTrafficPortQosShaperTable column
                - cmTrafficPortQosShaperWfqWeight

          Notes from release 201804300000Z
            (1) New cmFlowPointTable column added for Elephant Flow management:
                - cmFlowPointEfIdentificationFields,
            (2) New textual convention: EfIdentificationFieldType

          Notes from release 201802210000Z,
            (1) New bitsPortTable columns:
                - bitsPortCrc4
                - bitsPortIdleCode
                - bitsPortAis
                - bitsPortSaBitsAdminState
                - bitsPortSquelchControl
                - bitsPortSignalShape
                - bitsPortSignalFrequency
            (2) New f3PulsePerSecondPortTable columns:
                - f3PulsePerSecondPortOutputDelay
                - f3PulsePerSecondPortWidth
                - f3PulsePerSecondPortPolarity
                - f3PulsePerSecondPortImpedance
            (3) Added BitsPortImpedanceMode literals:
                - bits-50Ohm(4)
            (4) Added BitsPortLineType literals:
                - other(4)
            (5) New textual conventions:
                  SaBitsState, SignalShape, SignalFrequency,
                  PpsPolarity and PpsPortImpedanceMode    
                     
          Notes from release 201802020000Z
           (1) Added cmQosFlowPolicerPolicingEnabled to cmQosFlowPolicerTable
          
          Notes from release 201706210000Z,
           (1) New f3GPSReceiverPortTable columns:
               - f3GPSReceiverPortPDOP
           (2) Modified f3GPSReceiverPortTable columns:
               - New value range for f3GPSReceiverPortPDOPMask
          Notes from release 201703300000Z,
           (1) New f3GPSReceiverPortTable columns:
               - f3TimeOfDayPortSignalDirection
               - f3TimeOfDayPortInputRate
               - f3TimeOfDayPortDelayCompensation
           (2) f3PulsePerSecondPortDelayCompensation SYNTAX
               Integer32 is redefined to (-100000..100000)
          Notes from release 201703100000Z,
           (1) New f3GPSReceiverPortTable columns:
               - f3GPSReceiverPortPDOPMask
               - f3GPSReceiverPortSelfSurveyPeriod
               - f3GPSReceiverPortSatMin1Threshold
               - f3GPSReceiverPortSatMin2Threshold
           (2) f3GPSReceiverPortGnssSystem STATUS is deprecated 
         
         Notes from release 201711300000Z
            (1) New cmFlowPointTable column added:
                - cmFlowPointAclNoMatchDisposition,
            (2) New textual convention AclNoMatchDispositionType
         Notes from release 201706120000Z
            (1) New cmFlowPointTable columns added for elephant flow management:
                - cmFlowPointEfEnabled,
                - cmFlowPointEfIdentificationType,
                - cmFlowPointEfRateThresholdLo,
                - cmFlowPointEfRateThresholdHi
            (2) New textual convention: EfIdentificationType
         Notes from release 201704100000Z
            (1) update CmRemoteLinkIds
                - add bit fields 17 to 26
         Notes from release 201703220000Z
            (1) New f3AclRuleTable column:
                - f3AclRuleActive
         Notes from release 201702140000Z
            (1) New cmEthernetTrafficPortTable columns:
                - cmEthernetTrafficPortExpDEEncType,
                - cmEthernetTrafficPortExpDEPairsAction
            (2) New tables:
                - f3EthernetTrafficPortExpDEEncTable,
                - f3EthernetTrafficPortExpDEDecTable,
                - f3EthernetTrafficPortExpDEPairTable
         Notes from release 201612140000Z
            (1) New cmFlowPointTable columns:
                - cmFlowPointRefElpObject
          Notes from release 201611280000Z,
           (1) New textual conventions: SatelliteHealth, DelayOption
           (2) Added f3SatelliteTable
           (3) New f3GPSReceiverPortTable columns:
               - f3GPSReceiverPortAntennaDelayValue
               - f3GPSReceiverPortAntennaDelayType
               - f3GPSReceiverPortCNOMask
               - f3GPSReceiverPortElevationMask
               - f3GPSReceiverPortCoordinateLatitude
               - f3GPSReceiverPortCoordinateLongitude
               - f3GPSReceiverPortCoordinateAltitude
         Notes from release 201610190000Z
            (1) New cmFlowPointTable columns:
                - cmFlowPointElmiEvcIdentifier
         Notes from release 201610050000Z
            (1) Added f3AclRuleTable.
         Notes from release 201609130000Z
            (1) New cmFlowPointTable columns:
                - cmFlowPointRefEoMplsPwObject
         Notes from release 201607110000Z
            (1) New cmEthernetTrafficPortTable columns:
                - cmEthernetTrafficPortIngressSwapPriorityVIDEnabled,
                - cmEthernetTrafficPortEgressSwapPriorityVIDEnabled,
                - cmEthernetTrafficPortSwapPriorityVID
         Notes from release 201607110000Z
            (1) renamed the type FlowSecureState to FlowSecState
         Notes from release 201606070000Z,
            (1) New cmEthernetTrafficPortTable columns:
                - cmEthernetTrafficPortMode,
                - cmEthernetTrafficPortServiceType,
                - cmEthernetTrafficPortLoopbackSourceMacControlEnabled,
                - cmEthernetTrafficPortLoopbackDestMacControlEnabled,
                - cmEthernetTrafficPortLoopbackSourceMacAddress,
                - cmEthernetTrafficPortLoopbackDestMacAddress,
                - cmEthernetTrafficPortLoopbackBlockingEnabled,
                - cmEthernetTrafficPortMediaTypeAutoSelected,
                - cmEthernetTrafficPortLowLatencyQueuingEnabled,
                - cmEthernetTrafficPortDiagnosticMacAddress
            (2) New cmFlowPointTable columns:
                - cmFlowPointEgressShapingType,
                - cmFlowPointEgressInnerTagPrioMapEnabled,
                - cmFlowPointAutoBandwidthConfigEnabled,
                - cmFlowPointAutoCIRPercentage,
                - cmFlowPointFrameFwdEnabled,
                - cmFlowPointUsePortPrioMapProfile
            (3) Added cmEthernetTrafficPortExtTable.
            (4) Added cmEthernetTrafficPortJdsuExtTable.
            (5) Added f3FpQosShaperTable.
            (6) Added f3FpQosPolicerTable.
          Notes from release 201607110000Z
             (1) renamed the type FlowSecureState to FlowSecState
          Notes from release 201601200000Z 
            (1) add f3GPSReceiverPortAlias to f3GPSReceiverPortTable
            (2) add f3GPSReceiverPortGnssSystemsBitMap to f3GPSReceiverPortTable
          Notes frome release 201505010000Z,
           (1) Added cmEthernetAccPortDiagnosticMacAddress
           (2) Added cmEthernetNetPortDiagnosticMacAddress

          Notes frome release 201410150000Z,
           (1) Removed CmLinkLossFwdTriggerTypes literals:
                 - trig-opu-ais,
                 - trig-eth-epc.
           (2) Removed CmLinkLossFwdTxActionType literal:
                 - llf-eth-epc.
           Notes from release 201408270000Z,
           (1) Added TxDeiAction TEXTUAL-CONVENTION.
           (2) Added RxDeiAction TEXTUAL-CONVENTION.
           (3) Added DeiOuterTagType TEXTUAL-CONVENTION.
           (4) New cmEthernetAccPortTable columns:
               - cmEthernetAccPortRxDeiAction
               - cmEthernetAccPortTxDeiAction
               - cmEthernetAccPortRxDeiOuterTagType
               - cmEthernetAccPortTxDeiOuterTagType
           (5) New cmEthernetNetPortTable columns:
               - cmEthernetNetPortRxDeiAction
               - cmEthernetNetPortTxDeiAction
               - cmEthernetNetPortRxDeiOuterTagType
               - cmEthernetNetPortTxDeiOuterTagType
         Notes from release 201407180000Z,
           (1) Added new CmLoopbackType literals:
                 - facility-och,
                 - facility-och-timed,
                 - terminal-och,
                 - terminal-och-timed.

           (2) Added new CmLinkLossFwdSignalType literals:
                 - llf-odu-ais,
                 - llf-odu-lck,
                 - llf-odu-tim,
                 - llf-odu-bdi,
                 - llf-opu-plm,
                 - llf-opu-csf,
                 - llf-eth-epc.

           (3) Added new CmLinkLossFwdTriggerTypes literals:
                 - trig-odu-ais,
                 - trig-odu-lck,
                 - trig-odu-tim,
                 - trig-odu-bdi,
                 - trig-opu-ais,
                 - trig-opu-plm,
                 - trig-opu-csf,
                 - trig-eth-epc.

           (4) Added new CmLinkLossFwdTxActionType literals:
                 - llf-eth-epc,
                 - llf-odu-ais,
                 - llf-opu-csf,
                 - llf-otu-ais.

           (5) Added new XgePhyType literal:
                 - otn.

         Notes from release 201406250000Z,
           (1) New cmEthernetAccPortTable columns:
               - cmEthernetAccPortLowLatencyQueuingEnabled,
               - cmEthernetAccPortA2nSwapPriorityVIDEnabled,
               - cmEthernetAccPortN2aSwapPriorityVIDEnabled,
               - cmEthernetAccPortSwapPriorityVID.
           (2) New cmEthernetNetPortTable column:
               - cmEthernetNetPortLowLatencyQueuingEnabled.
           (3) Added new literal for FlowTrafficType:
               - policed-only.
           (4) Added new literal for ShapingType:
               - llq.
         Notes from release 201405210000Z,
           (1) New cmEthernetAccPortTable column:
               - cmEthernetAccPortMediaTypeAutoSelected.
           (2) New cmEthernetNetPortTable column:
               - cmEthernetNetPortMediaTypeAutoSelected.
         Notes from release 201405050000Z,
           (1) New SfpChannelIdentifier literals:
               - frequency-19195,
               - frequency-19190,
               - frequency-19185,
               - frequency-19180,
               - frequency-19175,
               - frequency-19170,
               - frequency-19165,
               - frequency-19160,
               - frequency-19155,
               - frequency-19150,
               - frequency-19145,
               - frequency-19140,
               - frequency-19135,
               - frequency-19130,
               - frequency-19125.
         Notes from release 201404240000Z,
           (1) New cmQosShaperTable objects:
               - cmQosShaperSoamCIRLo,
               - cmQosShaperSoamCIRHi,
               - cmQosShaperSoamEIRLo,
               - cmQosShaperSoamEIRHi.
           (2) New cmAccPortQosShaperTable objects:
               - cmAccPortQosShaperSoamCIRLo,
               - cmAccPortQosShaperSoamCIRHi,
               - cmAccPortQosShaperSoamEIRLo,
               - cmAccPortQosShaperSoamEIRHi.
         Notes from release 201404170000Z,
           (1) New cmEthernetAccPortTable objects:
               - cmEthernetAccPortLaserWDMChannel,
               - cmEthernetAccPortLaserIsTunable,
               - cmEthernetAccPortLaserFrequency.
           (2) New cmEthernetNetPortTable objects:
               - cmEthernetNetPortLaserWDMChannel,
               - cmEthernetNetPortLaserIsTunable,
               - cmEthernetNetPortLaserFrequency.
         Notes from release 201310210000Z,
           (1) Deleted cmEthernetAccPortTable object:
               - cmEthernetAccPortMonitorPortEnabled,
               - cmEthernetAccPortBufferSize,
               - cmEthernetAccPortJDSUControlFramesSnoopingEnabled,
               - cmEthernetAccPortJDSULoopbackVlan.
           (2) Deleted cmEthernetNetPortTable object:
               - cmEthernetNetPortJDSUControlFramesSnoopingEnabled,
               - cmEthernetNetPortJDSULoopbackVlan.
           (3) Added tables:
               - cmEthernetAccPortJdsuExtTable, 
               - cmEthernetNetPortJdsuExtTable.
         Notes from release 201310140000Z,
           (1) New cmEthernetAccPortTable objects:
               - cmEthernetAccPortMonitorPortEnabled,
               - cmEthernetAccPortBufferSize.
         Notes from release 201310070000Z,
           (1) Deleted cmEthernetAccPortTable object:
               - cmEthernetAccPortJDSUUnitTextId.
           (2) Deleted cmEthernetNetPortTable object:
               - cmEthernetNetPortJDSUUnitTextId.
         Notes from release 201310030000Z,
           (1) New gps10MHzPortTable object:
               gps10MHzPortAssumedQL
         Notes from release 201309160000Z,
           (1) Added new literals for CmLoopbackType:
               - jdsu-terminal-port-tailend,
               - jdsu-terminal-vlan-tailend,
               - jdsu-facility-port-tailend,
               - jdsu-facility-vlan-tailend.
           (2) New cmEthernetAccPortTable objects:
               - cmEthernetAccPortJDSUControlFramesSnoopingEnabled,
               - cmEthernetAccPortJDSULoopbackVlan,
               - cmEthernetAccPortJDSUUnitTextId.
           (3) New cmEthernetNetPortTable objects:
               - cmEthernetNetPortJDSUControlFramesSnoopingEnabled,
               - cmEthernetNetPortJDSULoopbackVlan,
               - cmEthernetNetPortJDSUUnitTextId.
         Notes from release 201306100000Z,
           (1) Added table: networkElementTMParamsTable
           (2) Added TEXTUAL-CONVENTION: BandwidthProfileMode
           (3) Added group: networkElementTMParamsGroup
         Notes frome release 201305230000Z,
           (1) New cmEthernetAccPortTable objects:
               - cmEthernetAccPortLoopbackSourceMacControlEnabled,
               - cmEthernetAccPortLoopbackDestMacControlEnabled,
               - cmEthernetAccPortLoopbackSourceMacAddress,
               - cmEthernetAccPortLoopbackDestMacAddress,
               - cmEthernetAccPortLoopbackBlockingEnabled
           (2) New cmEthernetNetPortTable objects:
               - cmEthernetNetPortLoopbackSourceMacControlEnabled,
               - cmEthernetNetPortLoopbackDestMacControlEnabled,
               - cmEthernetNetPortLoopbackSourceMacAddress,
               - cmEthernetNetPortLoopbackDestMacAddress,
               - cmEthernetNetPortLoopbackBlockingEnabled

         Notes from release 201303140000Z,
           (1) New cmFlowTable object:
               cmFlowN2NForwardingEnabled

         Notes from release 201210150000Z,
           (1) New cmFlowTable objects:
               cmFlowPort1, cmFlowPort2, cmFlowPolicingControl, cmFlowAutoCIRPercentage,
               cmFlowLoopAvoidanceObject

         Notes from release 201207190000Z,
           (1) New textual conventions: OCNSTMPortType, E1T1LineType, E1T1LineCode,
               E1T1FrameFormat, E1T1RcvSensitivity  
           (2) New ocnStmTable object: ocnStmPortType
           (3) New e1T1Table objects: e1t1LineType, e1t1LineCode, e1t1FrameFormat,
                 e1t1LineBuildOut, e1T1TimingDomain, e1T1RcvSensitivity,
                 e1T1IdlePatternProfile, e1T1LoopbackProfile

         Notes from release 201106110000Z,
           -Added f3PulsePerSecondPortTable, f3TimeOfDayPortTable 

         Notes from release 201205020000Z,
           -CPD support for LLDP and ELMI for Access/Network Port, Flow CPD 

         Notes from release 201105270000Z,
           -Formalized the OBJECT-GROUP definitions

         Notes from release 201102100000Z
            (i)Added variable bitsPortLineBuildOut 

         Notes from release 201101250000Z
            (i)Added enc-custom to PcpDEEncType

         Notes from release 201010130000Z
            PCP based Drop Eligibility function is added,
            (i)New textual conventions PcpDEEncType, PcpDEPairsAction
            (ii)New Access Port objects cmEthernetAccPortDeiEnable, 
                            cmEthernetAccPortPcpDEEncType, 
                            cmEthernetAccPortPcpDEPairsAction
            (iii)New Network Port objects cmEthernetNetPortDeiEnable, 
                            cmEthernetNetPortPcpDEEncType, 
                            cmEthernetNetPortPcpDEPairsAction
            (iv)New Access Port tables cmAccPortPcpDEEncTable, cmAccPortPcpDEDecTable,
                          cmAccPortPcpDEPairTable
            (v)New Network tables cmNetPortPcpDEEncTable, cmNetPortPcpDEDecTable,
                          cmNetPortPcpDEPairTable

         Notes from release 201010130000Z
           (i)Added cmFlowN2AOuterTagPrioEnabled, cmEthernetNetPortPrioMapMode and 
              cmNetPortPrioMapTable to support the Network Port Priority Mapping function
           (ii)Added FlowTagControl of pop 

         Notes from release 201006100000Z
         Updated range of cmEthernetAccPortOuterVlanLoopbackMask,
            cmEthernetAccPortInnerVlanLoopbackMask, cmEthernetNetPortOuterVlanLoopbackMask,
            cmEthernetNetPortInnerVlanLoopbackMask,
            to INTEGER(0..16) to indicate mask not SET

         Notes from release 201003310000Z
        (1)cmFlowTable has two new objects 
               cmFlowPreserveSTagProperties, cmFlowInnerTagPrioEnabled,
               cmPrioMapInnerTagPriority

         Notes from release 201002120000Z
        (1)cmFlowTable has new object cmFlowPolicingEnabled
        (2)New table ieee1588EthernetPortTable represents the IEEE 1588 Ethernet Port
        (3)New table gps10MHzPortTable represents the 10MHz Port


         Notes from release 200903160000Z
         This release is applicable to the FSP150CC Release 4.1 
         devices GE206.
         Following new objects are added to cmEthernetAccPortEntry,
          cmEthernetAccPortMDIXStatus, cmEthernetAccPortSfpReach,
          cmEthernetAccPortSfpLaserWaveLength,
          cmEthernetAccPortSfpMediaType, cmEthernetAccPortOamEnabled,
          cmEthernetAccPortShapingEnabled,
          cmEthernetAccPortShapedSpeedLo, cmEthernetAccPortShapedSpeedHi,
          cmEthernetAccPortQinQEtherType, cmEthernetAccPortRxPauseEnabled,
          cmEthernetAccPortAutoDiagEnabled,
          cmEthernetAccPortLinkLossFwdTxActionType,
          cmEthernetAccPortN2AVlanTrunkingEnabled, 
          cmEthernetAccPortA2NPushPVIDEnabled,
          cmEthernetAccPortN2APopPVIDEnabled, cmEthernetAccPortPortVlanId,
          cmEthernetAccPortPortVlanPriority, 
          cmEthernetAccPortPrioMapMode, cmEthernetAccPortSyncEEnabled,
          cmEthernetAccPortQLModeEnabled, cmEthernetAccPortExpectedQL,
          cmEthernetAccPortAssumedQL, cmEthernetAccPortReceivedQL, 
          cmEthernetAccPortTransmitQL,
          cmEthernetAccPortDeiEnable,
          cmEthernetAccPortPcpDEEncType, cmEthernetAccPortPcpDEPairsAction,

         Following new objects are added to cmFlowEntry,
          cmFlowTrafficType, cmFlowCOS, cmFlowVlanMemberList,
          cmFlowAction, cmFlowActionVlan, cmFlowUntaggedMemberEnabled,
          cmFlowA2NCIRHi, cmFlowA2NEIRHi,
          cmFlowN2ACIRHi, cmFlowN2AEIRHi, cmFlowHCOSMgmtEnabled,
          cmFlowGuaranteedA2NBandwidthLo,
          cmFlowGuaranteedA2NBandwidthHi, cmFlowMaximumA2NBandwidthLo,
          cmFlowMaximumA2NBandwidthHi, cmFlowCTagControl,
          cmFlowCTagVlanId, cmFlowCTagVlanPriority, cmFlowCTagMatchRxPrio,
          cmFlowSTagControl, cmFlowSTagVlanId, cmFlowSTagVlanPriority,
          cmFlowOuterTagPrioEnabled, cmFlowESFramesLossThreshold,
          cmFlowSESFramesLossThresholdRatio, 

         Following new objects are added to cmQosShaperEntry,
          cmQosShaperCOS, cmQosShaperCIRHi, cmQosShaperEIRHi

         Following new objects are added to cmEthernetNetPortEntry,
          cmEthernetNetPortMDIXStatus, cmEthernetNetPortSfpReach,
          cmEthernetNetPortSfpLaserWaveLength,
          cmEthernetNetPortSfpMediaType, cmEthernetNetPortOamEnabled,
          cmEthernetNetPortShapingEnabled,
          cmEthernetNetPortShapedSpeedLo, cmEthernetNetPortShapedSpeedHi,
          cmEthernetNetPortQinQEtherType, cmEthernetNetPortAutoDiagEnabled,
          cmEthernetNetPortLinkLossFwdTxActionType,
          cmEthernetNetPortSyncEEnabled, cmEthernetNetPortQLModeEnabled,
          cmEthernetNetPortExpectedQL, cmEthernetNetPortAssumedQL,
          cmEthernetNetPortReceivedQL, cmEthernetNetPortTransmitQL,
          cmEthernetNetPortPrioMapMode, cmEthernetNetPortDeiEnable,
          cmEthernetNetPortPcpDEEncType, cmEthernetNetPortPcpDEPairsAction,


         Following new objects are added to cmEthernetMgmtPortEntry,
          cmEthernetMgmtPortMDIXStatus
    
         Following SNMP tables are new,
          cmPrioMapTable, cmQosFlowPolicerTable, cmAccPortQosShaperTable,
          cmEthernetAccPortCpdV2Table, cmFlowCpdV2Table, 
          cmEthernetNetPortCpdV2Table, bitsPortTable

         Enumeration literals use-group-setting, not-active added to TC CmControlProtocolDispType

         Notes from release 200803030000Z,
         (1)MIB version ready for release FSP150CM 3.1." 
    ::= {fsp150cm 4}    

-- 
-- OID definitions
-- 
cmFacilityObjects      OBJECT IDENTIFIER ::= {cmFacilityMIB 1}
cmFacilityConformance  OBJECT IDENTIFIER ::= {cmFacilityMIB 2}

--
-- Textual Conventions
--

LocationMode ::= TEXTUAL-CONVENTION
    STATUS         current
    DESCRIPTION
        "Describes location mode for the GNSS receiver on OSA540X."
    SYNTAX      INTEGER {
                    not-applicable(0),
                    navigation (1),
                    survey-in (2),
                    fixed (3)
                }

TimeAdvanceMode ::= TEXTUAL-CONVENTION
    STATUS         current
    DESCRIPTION
        "Describes time advance mode for the GNSS on OSA540X."
    SYNTAX      INTEGER {
                    not-applicable(0),
                    auto (1),
                    fixed (2)
                }

SynceRxSsmQl ::= TEXTUAL-CONVENTION
    STATUS         current
    DESCRIPTION
        "Describes how RX quality level is utilized on OSA540X ethernet port."
    SYNTAX      INTEGER {
                    not-applicable(0),
                    ql-dnu (1),
                    ssm-based (2),
                    ql-prc (3)
                }

SynceMode ::= TEXTUAL-CONVENTION
    STATUS         current
    DESCRIPTION
        "Describes SyncE mode (master or slave) on OSA540X ethernet port."
    SYNTAX      INTEGER {
                    not-applicable(0),
                    slave (1),
                    master (2)
                }

SciSignalMode ::= TEXTUAL-CONVENTION
    STATUS         current
    DESCRIPTION
        "Describes the SCI Port Signal Mode."
    SYNTAX      INTEGER {
                    not-applicable(0),
                    sci-1pps (1),
                    sci-2M (2),
                    sci-10M (3)
                }

SciSignalDirection ::= TEXTUAL-CONVENTION
    STATUS         current
    DESCRIPTION
        "Describes the SCI Port Signal Direction."
    SYNTAX      INTEGER {
                    not-applicable(0),
                    output (1),
                    input (2)
                }

SciRxSsmQL ::= TEXTUAL-CONVENTION
    STATUS         current
    DESCRIPTION
        "Describes the SCI Port QL."
    SYNTAX      INTEGER {
                    not-applicable(0),
                    prc (1),
                    dnu (2)
                }

XDSLAnnex ::= TEXTUAL-CONVENTION
    STATUS       current
    DESCRIPTION
        "Specify xdsl annex version depends on modulation.
         annexa -- Annex A
         annexb -- Annex B
         annexc -- Annex C
         annexl -- ADSL2+ Annex L
         annexm -- ADSL2+ Annex M"
    SYNTAX       INTEGER {
                   notApplicable (0),
                   annexa (1),
                   annexb (2),
                   annexc (3),
                   annexl (4),
                   annexm (5)
                 }

XDSLMode ::= TEXTUAL-CONVENTION
    STATUS       current
    DESCRIPTION
        "The xdsl mode."
    SYNTAX       INTEGER {
                   notApplicable (0),
                   vdsl2 (1),
                   adsl2Plus (2),
                   adsl2 (3),
                   unkown (4)
                 }

XDSLCarrierSet ::= TEXTUAL-CONVENTION
    STATUS       current
    DESCRIPTION
        "The xdsl carrier set."
    SYNTAX       INTEGER {
                   notApplicable (0),
                   auto (1),
                   a43 (2),
                   b43 (3),
                   v43 (4),
                   a43c (5)
                 }

XDSLStatus ::= TEXTUAL-CONVENTION
    STATUS       current
    DESCRIPTION
        "The vdsl status."
    SYNTAX       INTEGER {
                   notApplicable (0),
                   showtime (1),
                   training (2),
                   handshake (3),
                   idle (4),
                   other (5)
                 }

XDSLControlChannel ::= TEXTUAL-CONVENTION
    STATUS       current
    DESCRIPTION
        "The xdsl control channel."
    SYNTAX       INTEGER {
                   notApplicable (0),
                   none (1),
                   pppoe (2)
                 }

VDSLProfileField ::= TEXTUAL-CONVENTION
    STATUS       current
    DESCRIPTION
        "The vdsl profile."
    SYNTAX       INTEGER {
                   notApplicable (0),
                   unknown (1),
                   profile-8a (2),
                   profile-8b (3),
                   profile-8c (4),
                   profile-8d (5),
                   profile-12a (6),
                   profile-12b (7),
                   profile-17a (8),
                   profile-30a (9)
                 }

VDSLProfileFields ::= TEXTUAL-CONVENTION
    STATUS       current
    DESCRIPTION
        "The vdsl profile, no bit set means unknow."
    SYNTAX     BITS {
                 profile-8a(0),
                 profile-8b(1),
                 profile-8c(2),
                 profile-8d(3),
                 profile-12a(4),
                 profile-12b(5),
                 profile-17a(6),
                 profile-30a(7)
               }

XDSLModulationMode ::= TEXTUAL-CONVENTION
    STATUS       current
    DESCRIPTION
        "Specify xdsl modulation type."
    SYNTAX       INTEGER {
                   notApplicable (0),
                   vdsl2 (1)
                 }

PPPoEConnectionStatus ::= TEXTUAL-CONVENTION
    STATUS       current
    DESCRIPTION
        "Specify pppoe connection status."
    SYNTAX       INTEGER {
                   notApplicable (0),
                   connected (1),
                   connecting (2),
                   disconnected (3)
                 }

CmEthernetSvcPortMode ::= TEXTUAL-CONVENTION
    STATUS       current
    DESCRIPTION
        "Describes the Ethernet Service Port Mode Type."
    SYNTAX       INTEGER {
                   connection-oriented (1),
                   connection-less (2)
                 }

CmEthernetSvcType ::= TEXTUAL-CONVENTION
    STATUS       current
    DESCRIPTION
        "Describes the Ethernet Service Type.
            epl  - Ethernet Private Linei, Port-based, all-to-one bundling
            evpl - Ethernet Virtual Private Line, VLAN based, 
                   service multiplexed."
    SYNTAX       INTEGER {
                   epl (1),
                   evpl (2)
                 }

CmEthernetTrafficSvcType ::= TEXTUAL-CONVENTION
    STATUS       current
    DESCRIPTION
        "Describes the Ethernet Service Type, including port-based and vlan-based."
    SYNTAX       INTEGER {
                   all-to-one(1),
                   service-multiplexing(2)
                 }
                 
CmAclConfiguration ::= TEXTUAL-CONVENTION
    STATUS       current
    DESCRIPTION
        "This object is defined to set traffic acl resource allocation.
         Supported actions are:
           all-bk-l2 (1)      - all bank allocated to l2.
           all-bk-l2-ipv4(2)  - all bank allocated to l2/ipv4. 
           two-bk-l2-ipv4(3)  - two thirds allocated to l2/ipv4, the left belongs to ipv6.
           one-bk-l2-ipv4(4)  - one thirds allocated to l2/ipv4, the left belongs to ipv6.
           none-bk-l2-ipv4(5) - all bank allocated to ipv6. "
    SYNTAX       INTEGER {
                   all-bk-l2 (1),
                   all-bk-l2-ipv4 (2),
                   two-bk-l2-ipv4 (3),
                   one-bk-l2-ipv4 (4),
                   none-bk-l2-ipv4(5)
                 }
                 
CmAfpType ::= TEXTUAL-CONVENTION
    STATUS       current
    DESCRIPTION
        "Describes the Ethernet Acceptable Framing Policy Type."
    SYNTAX       INTEGER {
                   tagged (1),
                   untagged (2),
                   all (3)
                 }

CmEthernetDiagAction ::= TEXTUAL-CONVENTION
    STATUS       current
    DESCRIPTION
        "Describes the Ethernet Diagnosis Action.
          autoNeg - Auto negotiation capability,
          cable   - Cable diagnostics, cable fault 
          loopback- Terminal loopback with traffic injection and monitoring  
          efm-oam-lpbk- EFM OAM loopback 
          all         - autoNeg, cable tests and loopback, not include efm-oam-lpbk."
    SYNTAX       INTEGER {
                   not-applicable(0),
                   autoneg (1),
                   cable (2),
                   loopback (3),
                   efm-oam-lpbk (4),
                   all (5)
                 }

CmDiagCableCondType ::= TEXTUAL-CONVENTION
    STATUS       current
    DESCRIPTION
        "Describes the Ethernet Diagnosis Cable Condition Result."
    SYNTAX       INTEGER {
                   not-applicable(0),
                   cableshort (1),
                   cableopen (2),
                   cableimpedance (3),
                   cablenotfound (4),
                   cableok (5),
                   cablefailed (6),
                   cablenotrun(7)
                 }

CmDiagAutoNegCondType ::= TEXTUAL-CONVENTION
    STATUS       current
    DESCRIPTION
        "Describes the Ethernet Diagnosis Auto Negotiation Condition Result."
    SYNTAX       INTEGER {
                   not-applicable(0),
                   autonegok (1),
                   autonegfailed (2),
                   autonegnotrun (3)
                 }

CmDiagLpbkCondType ::= TEXTUAL-CONVENTION
    STATUS       current
    DESCRIPTION
        "Describes the Ethernet Diagnosis Loopback Condition Result."
    SYNTAX       INTEGER {
                   not-applicable(0),
                   lpbkok(1),
                   lpbkfailed (2),
                   lpbknotrun (3)
                 }

CmDiagEfmOamLpbkCondType ::= TEXTUAL-CONVENTION
    STATUS       current
    DESCRIPTION
        "Describes the Ethernet Diagnosis EFM OAM Loopback Condition Result."
    SYNTAX       INTEGER {
                   not-applicable(0),
                   efmlpbkok (1),
                   efmlpbkfailed (2),
                   efmlpbkfailednendNA (3),
                   efmlpbkfailedfendNA (4),
                   efmlpbknotrun (5)
                 }

CmDiagTestStatus ::= TEXTUAL-CONVENTION
    STATUS       current
    DESCRIPTION
        "ECPA Test Status."
    SYNTAX       INTEGER {
                   not-applicable(0),
                   initial (1),
                   in-progress (2),
                   stopped (3),
                   completed (4),
                   aborted (5)
                 }

CmControlProtocolFilterType ::= TEXTUAL-CONVENTION
    STATUS       current
    DESCRIPTION
        "Describes the Control Protocol Filter Types."
    SYNTAX       INTEGER {
                   efmoam(1),
                   pause(2)
                 }

CmLoopbackType ::= TEXTUAL-CONVENTION
    STATUS       current
    DESCRIPTION
        "Describes the Loopback Types."
    SYNTAX       INTEGER {
                   lpbk-none (1),
                   efm-oam-remote(2),
                   efm-oam-remote-timed(3),
                   facility-port(4),
                   facility-port-timed(5),
                   facility-vlan(6),
                   terminal-port(7),
                   terminal-port-timed(8),
                   terminal-vlan(9),
                   efm-oam-tailend(10),
                   facility-payload(11),
                   facility-payload-timed(12),
                   remote-facility(13),
                   remote-facility-payload(14),
                   tailend-facility(15),
                   tailend-facility-payload(16),
                   terminal-itag(17),
                   facility-itag(18),
                   jdsu-terminal-port-tailend(19),
                   jdsu-terminal-vlan-tailend(20),
                   jdsu-facility-port-tailend(21),
                   jdsu-facility-vlan-tailend(22),
                   facility-och(23),
                   facility-och-timed(24),
                   terminal-och(25),
                   terminal-och-timed(26),
                   jdsu-facility-port-l3-tailend(27),
                   jdsu-facility-vlan-l3-tailend(28)
                 }

CmSwapSADAType ::= TEXTUAL-CONVENTION
    STATUS    current
    DESCRIPTION
        "Describes the SWAP SADA Types supported.
            no-swapSADA              - No swapping of Source MAC and Destination MAC
            swapSADA                 - Do swapping of Source MAC and Destination MAC
            swapDAOverrideSA         - Swap Destination MAC as Source MAC,
                                       override source MAC with local MAC
            swapSADAMacOnly          - Not supported
            swapDAOverridesSAMacOnly - Not supported
            swapIP                   - Do swapping of Source MAC and Destination MAC,
                                       Source IP and Destination IP
            swapTCPUDP               - Do swapping of Source MAC and Destination MAC,
                                       Source IP and Destination IP,
                                       Source TCP/UDP port and Destination TCP/UDP port."
    SYNTAX       INTEGER {
                   not-applicable(0),
                   noswapSADA(1),
                   swapSADA  (2),
                   swapDAOverrideSA (3),
                   swapSADAMacOnly (4),
                   swapDAOverridesSAMacOnly (5),
                   swapIP(6),
                   swapTCPUDP(7)
                 }


CmControlProtocolDispType ::= TEXTUAL-CONVENTION
    STATUS    current
    DESCRIPTION
        "Describes the Protocol Disposition Type on an interface."
    SYNTAX       INTEGER {
                   not-applicable(0),
                   discard (1),
                   peer  (2),
                   pass-thru (3),
                   --
                   use-group-setting(4), -- Deprecated
                   --
                   not-active(5),
                   use-port-setting(6),
                   --
                   pass-thru-l2pt(7),  -- Layer 2 Protocol Tunneling
                   useMacSetting(8)
                 }

CmLinkLossFwdSignalType ::= TEXTUAL-CONVENTION
    STATUS       current
    DESCRIPTION
        "Describes the Link Loss Forwarding Signal Types."
    SYNTAX       INTEGER {
                   not-applicable(0),
                   llf-efm-signal(1),
                   llf-link-down(2),
                   llf-odu-ais(3),
                   llf-odu-lck(4),
                   llf-odu-tim(5),
                   llf-odu-bdi(6),
                   llf-opu-plm(7),
                   llf-opu-csf(8),
                   llf-eth-epc(9)
                 }

CmLinkLossFwdTriggerTypes ::= TEXTUAL-CONVENTION
    STATUS       current
    DESCRIPTION
        "Describes the Link Loss Forwarding Trigger Types."
    SYNTAX     BITS {
                 trig-efm-signal(1),
                 trig-link-down(2),
                 trig-odu-ais(3),
                 trig-odu-lck(4),
                 trig-odu-tim(5),
                 trig-odu-bdi(6),
                 trig-opu-plm(7),
                 trig-opu-csf(8)
               }

CmLinkLossFwdTxActionType ::= TEXTUAL-CONVENTION
    STATUS       current
    DESCRIPTION
        "Describes the Link Loss Forwarding Tx Action Types."
    SYNTAX       INTEGER {
                   not-applicable(0),
                   llf-tx-no-action(1),  -- perform no link loss forwarding action
                   llf-tx-efm-signal(2),-- EFM signal
                   llf-tx-link-down(3),   -- Link Down
                   llf-odu-ais(4),
                   llf-opu-csf(5),
                   llf-otu-ais(6)
                 }

CmRemoteLinkIds ::= TEXTUAL-CONVENTION
    STATUS       current
    DESCRIPTION
        "Remote Link Ids used to match for Link Loss Forwarding."
    SYNTAX     BITS {
                 remoteLinkId1(1),
                 remoteLinkId2(2),
                 remoteLinkId3(3),
                 remoteLinkId4(4),
                 remoteLinkId5(5),
                 remoteLinkId6(6),
                 remoteLinkId7(7),
                 remoteLinkId8(8),
                 remoteLinkId9(9),
                 remoteLinkId10(10),
                 remoteLinkId11(11),
                 remoteLinkId12(12),
                 remoteLinkId13(13),
                 remoteLinkId14(14),
                 remoteLinkId15(15),
                 remoteLinkId16(16),
                 remoteLinkId17(17),
                 remoteLinkId18(18),
                 remoteLinkId19(19),
                 remoteLinkId20(20),
                 remoteLinkId21(21),
                 remoteLinkId22(22),
                 remoteLinkId23(23),
                 remoteLinkId24(24),
                 remoteLinkId25(25),
                 remoteLinkId26(26)
               }

CmOamMode ::= TEXTUAL-CONVENTION
    STATUS       current
    DESCRIPTION
        "Describes the OAM Mode."
    SYNTAX       INTEGER {
                   unknown (0),
                   active (1),
                   passive (2)
                 }

CmOamAdminState ::= TEXTUAL-CONVENTION
    STATUS       current
    DESCRIPTION
        "Describes the OAM Admin State."
    SYNTAX       INTEGER {
                   not-applicable(0),
                   enabled (1),
                   disabled (2)
                 }


CmOamDiscoveryState ::= TEXTUAL-CONVENTION
    STATUS       current
    DESCRIPTION
        "Describes the OAM Discovery State."
    SYNTAX       INTEGER {
                   unknown (0),
                   fault (1),
                   activesendlocal (2),
                   passivewait (3),
                   sendlocalremote (4),
                   sendlocalremoteok (5),
                   sendany (6)
                 }

CmFlowType ::= TEXTUAL-CONVENTION
    STATUS       current
    DESCRIPTION
        "Describes the Ethernet Flow Type.
          portbased - Port based Flow with full bandwidth of port;
                      this Flow does not do VLAN/MAC based processing 
          regular   - Connection-oriented, VLAN based service 
          default   - Connection-oriented, service that matches all VLANs."
    SYNTAX       INTEGER {
                   portbased (1),
                   regular   (2),
                   default   (3)
                 }

CmEthernetMDIXType ::= TEXTUAL-CONVENTION
    STATUS     current
    DESCRIPTION
        "Describes the Ethernet MDIX Type.
          auto-mdix - Auto MDIX 
          crossed   - Crossed 
          uncrossed - Uncrossed."
    SYNTAX       INTEGER {
                   not-applicable (1),
                   auto-mdix (2),
                   crossed   (3),
                   uncrossed (4),
                   notAvailable (5)
                 }


FlowTrafficType ::= TEXTUAL-CONVENTION
    STATUS     current
    DESCRIPTION
        "Describes the Flow Traffic Type.
          shaped-only, 
          policed-shaped,
          policed-only."
    SYNTAX       INTEGER {
                   shaped-only (1),
                   policed-shaped (2),
                   policed-only (3)
                 }

FlowVlanActionType ::= TEXTUAL-CONVENTION
    STATUS       current
    DESCRIPTION
        "Describes the Ethernet Flow Action.  Used for
         adding/removing VLAN members"
    SYNTAX       INTEGER {
                   no-action (1),
                   add-vlan (2),
                   remove-vlan (3)
                 }

FlowTagControl ::= TEXTUAL-CONVENTION
    STATUS       current
    DESCRIPTION
        "Describes the Ethernet Flow Tag Control Type."
    SYNTAX       INTEGER {
                   none    (1),
                   push    (2),
                   swapvid (3),
                   pushvid (4),
                   pop(5),
                   pushisid(6)
                 }

PrioMapControlType ::= TEXTUAL-CONVENTION
    STATUS       current
    DESCRIPTION
        "Describes the Priority Mapping Control Type."
    SYNTAX       INTEGER {
                   none (1),
                   swap (2)
                 }

PolicerAlgorithmType ::= TEXTUAL-CONVENTION
    STATUS       current
    DESCRIPTION
        "Describes the Policer Algorithm Type."
    SYNTAX       INTEGER {
                   srTCM (1),
                   trTCM (2)
                 }

PolicerColorMode ::= TEXTUAL-CONVENTION
    STATUS       current
    DESCRIPTION
        "Describes the Policer Color Mode."
    SYNTAX       INTEGER {
                   color-aware (1),
                   color-blind (2)
                 }

BitsPortType ::= TEXTUAL-CONVENTION
    STATUS       current
    DESCRIPTION
        "Enumerations for BITS Port Type.
             bits-in, 
             bits-out." 
    SYNTAX       INTEGER {
                   bits-in(1),
                   bits-out(2)
                 }

BitsPortLineType ::= TEXTUAL-CONVENTION
    STATUS       current
    DESCRIPTION
        "Enumerations for BITS Line Type.
         It can be t1, e1, 2048kHz, other." 
    SYNTAX       INTEGER {
                   t1(1),
                   e1(2),
                   type-2048kHz(3),
                   other(4)
                 }

BitsPortLineCode ::= TEXTUAL-CONVENTION
    STATUS       current
    DESCRIPTION
        "Enumerations for BITS Line Code.
             none,  
             t1-b8zs,  
             t1-ami,
             e1-hdb3,
             e1-ami."
    SYNTAX       INTEGER {
                   none(1),
                   t1-b8zs (2),
                   t1-ami (3),
                   e1-hdb3 (4),
                   e1-ami (5)
                 }

BitsFrameFormat ::= TEXTUAL-CONVENTION
    STATUS       current
    DESCRIPTION
        "Enumerations for Bits Frame Format.
             none,
             t1-sf,
             t1-esf,
             e1-unframed,
             e1-crc4,
             e1-dualframe."
    SYNTAX       INTEGER {
                   none(1),
                   t1-sf(2),
                   t1-esf(3),
                   e1-unframed(4),
                   e1-crc4(5),
                   e1-dualframe(6)
                 }

SaBitDesignation ::= TEXTUAL-CONVENTION
    STATUS       current
    DESCRIPTION
        "Enumerations for SA Bit Desgination.
             none,
             bit4,
             bit5,
             bit6,
             bit7,
             bit8."
    SYNTAX   INTEGER {
               none(1),
               bit4(2),
               bit5(3),
               bit6(4),
               bit7(5),
               bit8(6)
             }

CmActiveControlProtocolsType ::= TEXTUAL-CONVENTION
    STATUS       current
    DESCRIPTION
        "Remote Link Ids used to match for Link Loss Forwarding."
    SYNTAX     BITS {
                 ciscoGroup(1),
                 isl(2),
                 pagp(3),
                 udld(4),
                 cdp(5),
                 vtp(6),
                 dtp(7),
                 pvstpplus(8),
                 uplinkfast(9),
                 vlanbridge(10),
                 l2pt(11),
                 bridgegroup(12),
                 bpdu(13),
                 pause(14),
                 lacp(15),
                 lacpmarker(16),
                 efmoam(17),
                 ssm(18),
                 portauthen(19),
                 bridgereserved(20),
                 lanbridges(21),
                 garpgroup(22),
                 gmrp(23),
                 gvrp(24),
                 garp(25),
                 --
                 lldp(26),
                 elmi(27),
                 --
                 mac00(28),
                 mac01(29),
                 mac02(30),
                 mac03(31),
                 mac04(32),
                 mac05(33),
                 mac06(34),
                 mac07(35),
                 mac08(36),
                 mac09(37),
                 mac0A(38),
                 mac0B(39),
                 mac0C(40),
                 mac0D(41),
                 mac0E(42),
                 mac0F(43),
                 --
                 nearestlldp(44),
                 nontpmrlldp(45),
                 customerlldp(46),
                 ptpNonfwdUntagged(47),
                 ptpNonfwdTagged(48)
               }

PcpDEEncType ::= TEXTUAL-CONVENTION
    STATUS       current
    DESCRIPTION
        "Enumerations for PCP Drop Eligibility Encode Type.
             enc-none,
             enc-7p1d,
             enc-6p2d,
             enc-5p3d,
             enc-custom."
    SYNTAX   INTEGER {
               enc-none(1),
               enc-7p1d(2),
               enc-6p2d(3),
               enc-5p3d(4),
               enc-custom(5)
             }

PcpDEPairsAction ::= TEXTUAL-CONVENTION
    STATUS       current
    DESCRIPTION
        "    none,
             apply-pairs."
    SYNTAX   INTEGER {
               none(0),
               apply-pairs(1)
             }

LineBuildOut ::= TEXTUAL-CONVENTION
    STATUS       current
    DESCRIPTION
        "    none,
             0-133ft,
             133-266ft,
             266-399ft,
             399-533ft,
             533-655ft,
             7dot5db,
             15db,
             22dot5db."
    SYNTAX   INTEGER {
               none(0),
               lbo-0-133ft(1),
               lbo-133-266ft(2),
               lbo-266-399ft(3),
               lbo-399-533ft(4),
               lbo-533-655ft(5),
               lbo-7dot5db(6),
               lbo-15db(7),
               lbo-22dot5db(8)
             }

BitsPortImpedanceMode ::= TEXTUAL-CONVENTION
    STATUS       current
    DESCRIPTION
        "Describes the impedance mode of the BITS-IN and BITS-OUT interfaces:
             120OHM."
    SYNTAX   INTEGER {
               bits-120Ohm(1),
               bits-100Ohm(2),
               bits-75Ohm(3),
               bits-50Ohm(4)
             }

ShapingType ::= TEXTUAL-CONVENTION
    STATUS       current
    DESCRIPTION
            "
                port-based - traffic shaping at Port level
                flow-based - traffic shaping at Flow level
                llq - low latency queuing"
    SYNTAX   INTEGER {
               port-based(1),
               flow-based(2),
               llq(3)
             }

XgePhyType ::= TEXTUAL-CONVENTION
    STATUS       current
    DESCRIPTION
            " Specifies the Ethernet 10G port PHY type.
                not-applicable - for non-10G ports
                lan - 10G LAN-PHY mode (10GBASE-R) operating at 10Gb/sec
                wan - 10G WAN-PHY mode (10GBASE-W) operating at 9.29Gb/sec
                "
    SYNTAX   INTEGER {
               not-applicable(0),
               lan(1),
               wan(2),
               otn(3)
             }

F3Usb3GDCNPINCodeActionType ::= TEXTUAL-CONVENTION
    STATUS       current
    DESCRIPTION
        "Describes the 3G Dcn Pin Code Action Types."
    SYNTAX       INTEGER {
                     not-applicable(0),
                     enable-pin(1),
                     disable-pin(2),
                     change-pin(3),
                     authentication-pin(4),
                     unlock-pin(5)
                 }

F3Usb3GSimCardState ::= TEXTUAL-CONVENTION
    STATUS       current
    DESCRIPTION
        "Describes the 3G Usb Sim Card States."
    SYNTAX       INTEGER {
                     not-applicable(0),
                     ok(1),
                     notinserted(2),
                     networkrejected(3),
                     unknown(4)
                 }

F3Usb3GNetworkConnectionState ::= TEXTUAL-CONVENTION
    STATUS       current
    DESCRIPTION
        "Describes the Connection State of the 3G Usb Modem."
    SYNTAX       INTEGER {
                     not-applicable(0),
                     connecting(1),
                     connected(2),
                     disconnected(3)
                 }

F3Usb3GRecvSignalStrengthInd ::= TEXTUAL-CONVENTION
    STATUS       current
    DESCRIPTION
        "Describes the Recived Signal Strength of the 3G Usb Modem."
    SYNTAX       INTEGER {
                     not-applicable(0),
                     high(1),
                     medium(2),
                     low(3),
                     none(4)
                 }

TrailTraceFormat ::= TEXTUAL-CONVENTION
    STATUS       current
    DESCRIPTION
        "Describes the Trail Trace Format."
    SYNTAX       INTEGER {
                   not-applicable (0),
                   onebytemode (1),
                   sixteenbytemode (2),
                   sixtyfourbytemode (3)
                 }

MultiplexingStructure ::= TEXTUAL-CONVENTION
    STATUS       current
    DESCRIPTION
        "Describes the Multiplexing Structure."
    SYNTAX       INTEGER {
                   not-applicable (0),
                   vt-sts1 (1),
                   sts1spe-sts1 (2),
                   sts3cspe-sts3c (3),
                   vc12-vc4-aug (4),
                   vc12-vc3-aug (5),
                   vc3-aug (6),
                   vc3-vc4-aug (7),
                   vc4-aug (8),
                   custom (9)
                 }

EoTDMMode ::= TEXTUAL-CONVENTION
    STATUS       current
    DESCRIPTION
        "Describes the EoTDM Mode."
    SYNTAX       INTEGER {
                   not-applicable (0),
                   eosdh (1),
                   eopdh (2)
                 }

BitErrRate ::= TEXTUAL-CONVENTION
    STATUS       current
    DESCRIPTION
        "."
    SYNTAX       INTEGER {
                   none (0),
                   ber-1e-1 (1),
                   ber-1e-2 (2),
                   ber-1e-3 (3),
                   ber-1e-4 (4),
                   ber-1e-5 (5),
                   ber-1e-6 (6),
                   ber-1e-7 (7),
                   ber-1e-8 (8),
                   ber-1e-9 (9),
                   ber-1e-10 (10)
                 }


GFPEncapsulationType ::= TEXTUAL-CONVENTION
    STATUS       current
    DESCRIPTION
        "Describes the GFP Encapsulation of the traffic port."
    SYNTAX   INTEGER {
               none(0),
               gfp (1),
               gfp-fcs (2),
               gfp-novcat (3),
               gfp-zerovcat (4),
               gfp-fcs-novcat (5),
               gfp-fcs-zerovcat (6),
               x86 (7)
             }

PPSInputRate ::= TEXTUAL-CONVENTION
    STATUS       current
    DESCRIPTION
        "Describes the PPS Input Rate."
    SYNTAX   INTEGER {
               pulse-per-sec(1),
               pulse-per-2sec(2)
             }

PPSPhyInterfaceType ::= TEXTUAL-CONVENTION
    STATUS       current
    DESCRIPTION
        "Describes the PPS physical interface type."
    SYNTAX   INTEGER {
               none(0),
               pps(1),
               tod(2)
             }

OCNSTMPortType ::= TEXTUAL-CONVENTION
    STATUS  current
    DESCRIPTION
        "OCN/STM Port Type."
    SYNTAX  INTEGER {
                oc12(1),
                oc3(2),
                stm4(3),
                stm1(4)
            }

E1T1LineType ::= TEXTUAL-CONVENTION
    STATUS       current
    DESCRIPTION
        "Enumerations for E1/T1 Line Type.
             t1, 
             e1"
    SYNTAX       INTEGER {
                   t1(1),
                   e1(2)
                 }

E1T1LineCode ::= TEXTUAL-CONVENTION
    STATUS       current
    DESCRIPTION
        "Enumerations for E1/T1 Line Code.
             none,  
             t1-b8zs,  
             t1-ami,
             e1-hdb3,
             e1-ami."
    SYNTAX       INTEGER {
                   none(1),
                   t1-b8zs (2),
                   t1-ami (3),
                   e1-hdb3 (4),
                   e1-ami (5)
                 }

E1T1FrameFormat ::= TEXTUAL-CONVENTION
    STATUS       current
    DESCRIPTION
        "Enumerations for E1/T1 Frame Format.
             none,
             t1-sf,
             t1-esf,
             e1-unframed,
             e1-crc4,
             e1-dualframe,
             e1-basicframe."
    SYNTAX       INTEGER {
                   none(1),
                   t1-sf(2),
                   t1-esf(3),
                   e1-unframed(4),
                   e1-crc4(5),
                   e1-dualframe(6),
                   t1-unframed(7),
                   e1-basicframe(8)
                 }

E1T1RcvSensitivity ::= TEXTUAL-CONVENTION
    STATUS       current
    DESCRIPTION
        "Enumerations for E1/T1 Receive Sensitivity
             high-range,
             low-range"
    SYNTAX       INTEGER {
                   high-range(1),
                   low-range(2)
                 }

E3T3FrameFormat ::= TEXTUAL-CONVENTION
    STATUS       current
    DESCRIPTION
        "Describes the Frame Format of E3/T3."
    SYNTAX   INTEGER {
               none(0),
               dsx3CbitParity (1),
               g832 (2),
               e3Unframed (3),
               dsx3M23 (4),
               g751 (5),
               dsx3Unframed (6)
             }

TDMPathType ::= TEXTUAL-CONVENTION
    STATUS       current
    DESCRIPTION
        "Describes the path type."
    SYNTAX       INTEGER {
                   none (0),
                   t1 (1),
                   e1 (2),
                   t3 (3),
                   e3 (4),
                   vc12 (5),
                   vc3 (6),
                   vc4 (7),
                   vt15 (8),
                   sts1 (9),
                   sts3c (10)
                 }

PPSGenCondition ::= TEXTUAL-CONVENTION
    STATUS       current
    DESCRIPTION
        "Enumerations for PPS Generation Condition 
             tracked-1sat,
             tracked-3sat"
    SYNTAX       INTEGER {
                   tracked-1sat(1),
                   tracked-3sat(2)
                 }


GPSAntennaStatus ::= TEXTUAL-CONVENTION
    STATUS       current
    DESCRIPTION
        "Enumerations for GPS Antenna Status"
    SYNTAX       INTEGER {
                   open(1),
                   short(2),
                   normal(3),
                   unavailable(4)
                 }

PolicingControl ::= TEXTUAL-CONVENTION
    STATUS       current
    DESCRIPTION
        "Defines Policing Control options."
    SYNTAX       INTEGER {
                   a2n(1),
                   n2a(2),
                   a2nN2a(3),
                   n2n(4)
                 }

FlowConfigType ::= TEXTUAL-CONVENTION
    STATUS       current
    DESCRIPTION
        "Defines types of Flow."
    SYNTAX       INTEGER {
                   access(1),       -- Flow on an Access Port
                   passThru(2)      -- Pass-thru Flow between the 2 Network Ports
                 }

G3AuthStatus ::= TEXTUAL-CONVENTION
    STATUS       current
    DESCRIPTION
        "Disabled (PIN protection is disabled)
         OK (PIN protection is enabled and PIN code is correct)   
         Input PIN (input PIN to unlock)
         Input PUK (PIN code is locked, input PUK to unlock)
         Locked (must contact with SIM provider)."
    SYNTAX       INTEGER {
                   disabled (1),
                   ok (2),
                   input-pin (3),
                   input-puk (4),
                   locked (5),
                   none (6)
                 }

PsePowerLevel ::= TEXTUAL-CONVENTION
    STATUS       current
    DESCRIPTION
        "Defines the power level for pse port.
        class1 (4.00 Watts) :0
        class2 (7.00 Watts) :1
        class0andclass 3 (15.4 Watts):2
        class4 (30 Watts):3."
    SYNTAX       INTEGER {
                   class1 (1),
                   class2 (2),
                   class0andclass3 (3),
                   class4 (4)
                 }

PSENonStandardPD ::= TEXTUAL-CONVENTION
    STATUS       current
    DESCRIPTION
        "Enumerations for NonStandardPD 
             disabled:don't support non-standard PD,
             enabled:support non-standard PD"
    SYNTAX       INTEGER {
                   enabled (1),
                   disabled (2)
                 }

LearningAction ::= TEXTUAL-CONVENTION
    STATUS       current
    DESCRIPTION
        "Describes Action on ingress frames when the number of MAC 
        Table entires has reached the maximum defined by tableSize"
    SYNTAX       INTEGER {
                   block (1),
                   forward (2)
                 }

SfpChannelIdentifier ::= TEXTUAL-CONVENTION
    STATUS       current
    DESCRIPTION
        "Describes Channel number of WDM tunable XFP setting."
    SYNTAX   INTEGER {
                not-applicable (0),   -- null
                none(1),              -- none
                frequency-19610 (2),  -- 196.10THz  1528.7734nm 
                frequency-19595 (3),  -- 195.95THz  1529.9436nm 
                frequency-19585 (4),  -- 195.85THz  1530.7248nm 
                frequency-19575 (5),  -- 195.75THz  1531.5068nm 
                frequency-19565 (6),  -- 195.65THz  1532.2896nm 
                frequency-19555 (7),  -- 195.55THz  1533.0732nm 
                frequency-19545 (8),  -- 195.45THz  1533.8575nm 
                frequency-19535 (9),  -- 195.35THz  1534.6427nm 
                frequency-19525 (10), -- 195.25THz  1535.4287nm 
                frequency-19515 (11), -- 195.15THz  1536.2155nm 
                frequency-19505 (12), -- 195.05THz  1537.0031nm 
                frequency-19495 (13), -- 194.95THz  1537.7915nm 
                frequency-19485 (14), -- 194.85THz  1538.5807nm 
                frequency-19475 (15), -- 194.75THz  1539.3708nm 
                frequency-19465 (16), -- 194.65THz  1540.1616nm 
                frequency-19455 (17), -- 194.55THz  1540.9533nm 
                frequency-19445 (18), -- 194.45THz  1541.7457nm 
                frequency-19435 (19), -- 194.35THz  1542.5390nm 
                frequency-19425 (20), -- 194.25THz  1543.3331nm 
                frequency-19415 (21), -- 194.15THz  1544.1280nm 
                frequency-19405 (22), -- 194.05THz  1544.9238nm 
                frequency-19395 (23), -- 193.95THz  1545.7203nm 
                frequency-19385 (24), -- 193.85THz  1546.5177nm 
                frequency-19375 (25), -- 193.75THz  1547.3159nm 
                frequency-19365 (26), -- 193.65THz  1548.1149nm 
                frequency-19355 (27), -- 193.55THz  1548.9148nm 
                frequency-19345 (28), -- 193.45THz  1549.7155nm 
                frequency-19335 (29), -- 193.35THz  1550.5170nm 
                frequency-19325 (30), -- 193.25THz  1551.3193nm 
                frequency-19315 (31), -- 193.15THz  1552.1225nm 
                frequency-19305 (32), -- 193.05THz  1552.9265nm 
                frequency-19295 (33), -- 192.95THz  1553.7313nm 
                frequency-19285 (34), -- 192.85THz  1554.5370nm 
                frequency-19275 (35), -- 192.75THz  1555.3435nm 
                frequency-19265 (36), -- 192.65THz  1556.1508nm 
                frequency-19255 (37), -- 192.55THz  1556.9590nm 
                frequency-19245 (38), -- 192.45THz  1557.7680nm 
                frequency-19235 (39), -- 192.35THz  1558.5779nm 
                frequency-19225 (40), -- 192.25THz  1559.3886nm 
                frequency-19215 (41), -- 192.15THz  1560.2001nm 
                frequency-19205 (42), -- 192.05THz  1561.0125nm 
                frequency-19600 (43), -- 196.00THz  1529.55nm D01
                frequency-19590 (44), -- 195.90THz  1530.33nm D02
                frequency-19580 (45), -- 195.80THz  1531.12nm D03
                frequency-19570 (46), -- 195.70THz  1531.90nm D04
                frequency-19560 (47), -- 195.60THz  1532.68nm DC1
                frequency-19550 (48), -- 195.50THz  1533.47nm D05
                frequency-19540 (49), -- 195.40THz  1534.25nm D06
                frequency-19530 (50), -- 195.30THz  1535.04nm D07
                frequency-19520 (51), -- 195.20THz  1535.82nm D08
                frequency-19510 (52), -- 195.10THz  1536.60nm DC2
                frequency-19500 (53), -- 195.00THz  1537.40nm D09
                frequency-19490 (54), -- 194.90THz  1538.19nm D10
                frequency-19480 (55), -- 194.80THz  1538.98nm D11
                frequency-19470 (56), -- 194.70THz  1539.77nm D12
                frequency-19460 (57), -- 194.60THz  1540.55nm DC3
                frequency-19450 (58), -- 194.50THz  1541.35nm D13
                frequency-19440 (59), -- 194.40THz  1542.14nm D14
                frequency-19430 (60), -- 194.30THz  1542.94nm D15
                frequency-19420 (61), -- 194.20THz  1543.73nm D16
                frequency-19410 (62), -- 194.10THz  1544.52nm DC4
                frequency-19400 (63), -- 194.00THz  1545.32nm DC9
                frequency-19390 (64), -- 193.90THz  1546.11nm DC5
                frequency-19380 (65), -- 193.80THz  1546.92nm D17
                frequency-19370 (66), -- 193.70THz  1547.72nm D18
                frequency-19360 (67), -- 193.60THz  1548.51nm D19
                frequency-19350 (68), -- 193.50THz  1549.32nm D20
                frequency-19340 (69), -- 193.40THz  1550.11nm DC6
                frequency-19330 (70), -- 193.30THz  1550.92nm D21
                frequency-19320 (71), -- 193.20THz  1551.72nm D22
                frequency-19310 (72), -- 193.10THz  1552.52nm D23
                frequency-19300 (73), -- 193.00THz  1553.33nm D24
                frequency-19290 (74), -- 192.90THz  1554.13nm DC7
                frequency-19280 (75), -- 192.80THz  1554.94nm D25
                frequency-19270 (76), -- 192.70THz  1555.75nm D26
                frequency-19260 (77), -- 192.60THz  1556.55nm D27
                frequency-19250 (78), -- 192.50THz  1557.36nm D28
                frequency-19240 (79), -- 192.40THz  1558.17nm DC8
                frequency-19230 (80), -- 192.30THz  1558.98nm D29
                frequency-19220 (81), -- 192.20THz  1559.79nm D30
                frequency-19210 (82), -- 192.10THz  1560.61nm D31
                frequency-19200 (83), -- 192.00THz  1561.42nm D32
                frequency-19195 (84), -- 191.95Thz  1561.83nm D33
                frequency-19190 (85), -- 191.90Thz  1562.23nm D34
                frequency-19185 (86), -- 191.85Thz  1562.64nm D35
                frequency-19180 (87), -- 191.80Thz  1561.42nm D36
                frequency-19175 (88), -- 191.75Thz  1563.05nm D37
                frequency-19170 (89), -- 191.70Thz  1563.86nm D38
                frequency-19165 (90), -- 191.65Thz  1564.27nm D39
                frequency-19160 (91), -- 191.60Thz  1564.68nm D40
                frequency-19155 (92), -- 191.55Thz  1565.09nm D41
                frequency-19150 (93), -- 191.50Thz  1565.50nm D42
                frequency-19145 (94), -- 191.45Thz  1565.90nm D43
                frequency-19140 (95), -- 191.40Thz  1566.31nm D44
                frequency-19135 (96), -- 191.35Thz  1566.72nm D45
                frequency-19130 (97), -- 191.30Thz  1567.13nm D46
                frequency-19125 (98), -- 191.25Thz  1567.54nm D47
                notTunable (99),      -- not tunable 
                frequency-19605(100), -- 196.05Thz  1529.1634nm
                autoTuning (101)      -- auto tuning
               }

BandwidthProfileMode ::= TEXTUAL-CONVENTION
    STATUS       current
    DESCRIPTION
        " A Network Element level Frame Rate Bandwidth Profile Mode shall be supported 
         which will indicate if the CIR/EIR is interpreted as Information Rate (IR) or Line Rate 
         (LR). In IR mode BWP is enforced based on number of bytes beginning with DA and 
         ending with FCS as it was received at a port which is called the Service Frame in 
         MEF terminology. In LR mode the BWP is enforced based on the whole frame 
         including IFG, Preamble and SFD."
    SYNTAX       INTEGER {
                   lineRate (1),
                   informationRate (2)
                 }

LearningConfigAction ::= TEXTUAL-CONVENTION
    STATUS       current
    DESCRIPTION
        "Learning Action:
            noAction        - No Action
            flushFwdTable   - Removes all dynamic entries from the Forwarding table
                              of a Flow.
            clearBlock      - removes the secondary state of BLCKD and transitions 
                              the flow to a state where frames are not blocked
            resetAgingTimer - reset the aging timer
            "
    SYNTAX       INTEGER {
                   noAction (1),
                   flushFwdTable (2),
                   clearBlock (3),
                   resetAgingTimer(4)
                 }

TrafficPortDeleteEntitiesAction ::= TEXTUAL-CONVENTION
    STATUS       current
    DESCRIPTION
        "Learning Action:
            no-action        - No Action
            delete-esa-entities   - Removes all esa entities relate to this port.
            delete-cfm-entities   - Removes all cfm entities relate to this port."
    SYNTAX       INTEGER {
                   no-action (1),
                   delete-esa-entities (2),
                   delete-cfm-entities (3)
                 }

UsbDCNMobileNetworkType ::= TEXTUAL-CONVENTION
    STATUS       current
    DESCRIPTION
        "Mobile network type:
            none
            secondGeneration - 2G.
            thirdGeneration  - 3G,
            fourthGeneration - 4G,
            notApplicable."
    SYNTAX       INTEGER {
                   none (1),
                   secondGeneration (2),
                   thirdGeneration (3),
                   fourthGeneration (4),
                   notApplicable(5)
                 }

TxDeiAction ::= TEXTUAL-CONVENTION
    STATUS       current
    DESCRIPTION
        "Transmit DEI Action."
    SYNTAX       INTEGER {
                   setToZero (1),
                   markColor (2),
                   noChange (3)
                 }

RxDeiAction ::= TEXTUAL-CONVENTION
    STATUS       current
    DESCRIPTION
        "Receive DEI Action."
    SYNTAX       INTEGER {
                   ignore (1),
                   use (2)
                 }

DeiOuterTagType ::= TEXTUAL-CONVENTION
    STATUS       current
    DESCRIPTION
        "DEI Outer Tag Type."
    SYNTAX       INTEGER {
                   stag (1),
                   ctagOrStag (2)
                 }

ConstellationType ::= TEXTUAL-CONVENTION
    STATUS       current
    DESCRIPTION
        "Constellation Type of GPS Antenna"
    SYNTAX       INTEGER {
                   gps-only(1),
                   glonass-only(2),
                   gps-and-glonass(3),
                   beidou-and-gps(4),
                   beidou-only(5)
                 }

TODOutputFormat ::= TEXTUAL-CONVENTION
    STATUS       current
    DESCRIPTION
        "Output Format of TOD Port"
    SYNTAX       INTEGER {
                   nmea(1),
                   ccsa(2)
                 }

ConstellationTypesBitMap ::= TEXTUAL-CONVENTION  
   STATUS         current  
   DESCRIPTION    "Indicates GNSS constellation types supported by a GNSS Receiver Port. 
        The valid bits must be set in order for this attribute to contain valid information.  
        The representation of each bit setting (0 or 1) is indicated below.  
     
        Bit Field            Flag Description  
        ---------   ------------------------------------  
           0        1 = GPS is supported; 0 = GPS not supported  
           1        1 = GLONASS is supported; 0 = GLONASS is not supported  
           2        1 = BEIDOU is supported; 0 = BEIDOU is not supported  
           3        1 = GALILEO is supported; 0 = GALILEO is not supported 
           4        1 = SBAS is supported; 0 = SBAS is not supported"  
   SYNTAX        BITS {   
                      gps(0),  
                      glonass(1),  
                      beidou(2),  
                      galileo(3),  
                      sbas(4),
                      qzss(5)
                        
                      }  

InstallationType ::= TEXTUAL-CONVENTION
    STATUS       current
    DESCRIPTION
        "Installation Type of GPS Antenna"
    SYNTAX       INTEGER {
                   full-sky-view(1),
                   limited-sky-view(2)
                 }

WIFIEncryptionType ::= TEXTUAL-CONVENTION
    STATUS       current
    DESCRIPTION
        "Type of WIFI encryption"
    SYNTAX       INTEGER {
                   notApplicable(0),
                   wpa-psk(1),
                   wpa2-psk(2),
                   wpa-wpa2-psk(3)
                 }

DHCPType ::= TEXTUAL-CONVENTION
    STATUS       current
    DESCRIPTION
        "DHCP role type"
    SYNTAX       INTEGER {
                   client(1),
                   server(2)
                 }

CosMappingMode ::= TEXTUAL-CONVENTION
    STATUS       current
    DESCRIPTION
        "EoMpls Cos Mapping mode"
    SYNTAX       INTEGER {
                   ethernet (1),
                   eompls (2),
                   vxlan (3),
                   gre (4),
                   sr-mpls (5)
                 }

EthernetPortTrafficModel ::= TEXTUAL-CONVENTION
    STATUS       current
    DESCRIPTION
        "Traffic Model for Ethernet Port."
    SYNTAX       INTEGER {
                   accessFlow(1),
                   flowpoint(2)
                 }

SatelliteHealth ::= TEXTUAL-CONVENTION
    STATUS       current
    DESCRIPTION
        "Satellite Health of GNSS Satellite"
    SYNTAX       INTEGER {
                   na(1),
                   ok(2),
                   weak(3),
                   dead(4),
                   no-data-modulation(5)
                 }

DelayOption ::= TEXTUAL-CONVENTION
    STATUS       current
    DESCRIPTION
        "Defines the units of GNSS Antenna Cable Delay value"
    SYNTAX       INTEGER {
           nanoseconds(2),
                   meters(3)
                 }

AclRuleOperation ::= TEXTUAL-CONVENTION
    STATUS       current
    DESCRIPTION
        "Describes the acl rule operation."
    SYNTAX       INTEGER {
                   notApplicable (0),
                   accept (1),
                   deny (2)
                 }

EfIdentificationType ::= TEXTUAL-CONVENTION
    STATUS       current
    DESCRIPTION
            "
                five-tuple  - 5-field identifier
                seven-tuple - 7-field identifier"
    SYNTAX       INTEGER {
                   five-tuple(1),
                   seven-tuple(2)
                 }

UsbOperationalMode ::= TEXTUAL-CONVENTION
    STATUS       current
    DESCRIPTION
        "Types of usb operational mode."
    SYNTAX       INTEGER {
                   cellular-modem(1),
                   srv-access (2)
                 }

SaBitsState ::= TEXTUAL-CONVENTION
    STATUS       current
    DESCRIPTION
        "Bit states for the five Sa Bits from bit4 to bit8."
    SYNTAX       BITS {
                   bit4(0),
                   bit5(1),
                   bit6(2),
                   bit7(3),
                   bit8(4)
                 } 

SignalShape ::= TEXTUAL-CONVENTION
    STATUS       current
    DESCRIPTION
        "Enumerations for Frequency Signal Shape.
         It can be sine or square wave signal." 
    SYNTAX       INTEGER {
                   sine(1),
                   square(2)
                 }

SignalFrequency ::= TEXTUAL-CONVENTION
    STATUS       current
    DESCRIPTION
        "Enumerations for Signal Frequency."
    SYNTAX       INTEGER {
                   frequency-100kHz(1),
                   frequency-1MHz(2),
                   frequency-1544kHz(3),
                   frequency-2048kHz(4),
                   frequency-5MHz(5),
                   frequency-10MHz(6),
                   frequency-25MHz(7),
                   frequency-50MHz(8)
                 }

PpsPolarity ::= TEXTUAL-CONVENTION
    STATUS       current
    DESCRIPTION
        "Enumerations for the Polarity of the PPS Port interfaces."
    SYNTAX       INTEGER {
                   positive(1),
                   negative(2)
                 }

PpsPortImpedanceMode ::= TEXTUAL-CONVENTION
    STATUS       current
    DESCRIPTION
        "Enumerations for the impedance mode of the PPS Port interfaces."
    SYNTAX       INTEGER {
                   not-available(0),
                   pps-50Ohm(1),
                   pps-1MOhm(2)
                 }

AclNoMatchDispositionType ::= TEXTUAL-CONVENTION
    STATUS       current
    DESCRIPTION
        "Types of ACL no match disposition."
    SYNTAX       INTEGER {
                   accept(1),
                   deny(2)
                 }

EfIdentificationFieldType ::= TEXTUAL-CONVENTION
    STATUS       current
    DESCRIPTION
        "Describes the Elephant Flow identification fields."
    SYNTAX     BITS {
                 srcMac(0),
                 destMac(1),
                 srcIp(2),
                 destIp(3),
                 ipProtocol(4),
                 srcPort(5),
                 destPort(6)
               }

ToggleValue ::= TEXTUAL-CONVENTION
    STATUS         current
    DESCRIPTION    "Enumerations for functionality that can be enabled or disabled."
    SYNTAX INTEGER    {
        enabled(1),
        disabled(2),
        not-available(3)
        }

IrigTimeCode ::= TEXTUAL-CONVENTION
    STATUS         current
    DESCRIPTION    "Enumerations for ."
    SYNTAX       INTEGER {
                   irig-a002(1),
                   irig-a007(2),
                   irig-a132(3),
                   irig-a137(4),
                   irig-b002(5),
                   irig-b004(6),
                   irig-b006(7),
                   irig-b007(8),
                   irig-b122(9),
                   irig-b124(10),
                   irig-b126(11),
                   irig-b127(12),
                   irig-g002(13),
                   irig-g007(14),
                   irig-g142(15),
                   irig-g146(16),
                   pps(17),
                   ppm(18),
                   pph(19),
                   have-quick(20)
                 }

IrigControlField ::= TEXTUAL-CONVENTION
    STATUS         current
    DESCRIPTION    "Enumerations for IRIG Control Field."
    SYNTAX       INTEGER {
                   ieee1344(1),
                   ieee37-118(2)
                 }

IrigRelayOperation ::= TEXTUAL-CONVENTION
    STATUS         current
    DESCRIPTION
        "Enumerations for IRIG Relay Operation. Relay state can be configured to toggle
         once per hour, once per minute, to stay active (locked), or to stay inactive (alarm)."
    SYNTAX       INTEGER {
                   every-hour(1),
                   every-minute(2),
                   locked(3),
                   alarm(4)
                 }

IrigOutputType ::= TEXTUAL-CONVENTION
    STATUS         current
    DESCRIPTION    "Enumerations for IRIG Output Type."
    SYNTAX       INTEGER {
                   digital(1),
                   analog(2),
                   optical(3)
                 }

IrigDigitalSignalVoltage ::= TEXTUAL-CONVENTION
    STATUS         current
    DESCRIPTION    "Enumerations for ."
    SYNTAX       INTEGER {
                   digital-5v(1),
                   digital-10v(2)
                 }

IrigGroupExtensionType ::= TEXTUAL-CONVENTION
    STATUS         current
    DESCRIPTION    "Enumerations for IRIG Group Extension Type."
    SYNTAX       INTEGER {
                   patch-panel(1),
                   extension-cable(2),
                   none(3)
                 }

CcPortDutyCycle ::= TEXTUAL-CONVENTION
    STATUS         current
    DESCRIPTION    "CC port duty cycle"
    SYNTAX       INTEGER {
                   cycle-63-37(1),
                   cycle-50-50(2)
                 }

CcActivePortState ::= TEXTUAL-CONVENTION
    STATUS       current
    DESCRIPTION
        "Port states for CC group entities."
    SYNTAX       BITS {
                   port1(0),
                   port2(1),
                   port3(2),
                   port4(3),
                   port5(4),
                   port6(5),
                   port7(6),
                   port8(7),
                   port8(8),
                   port8(9)
                 }

DynamicModelType ::= TEXTUAL-CONVENTION
    STATUS       current
    DESCRIPTION
        "Dynamic Model Type of GNSS Receiver"
    SYNTAX       INTEGER {
                   portable(0),
                   stationary(1),
                   pedestrian(2),
                   automotive(3),
                   sea(4),
                   airborne1g(5),
                   airborne2g(6),
                   airborne4g(7)
                }

--
-- Enumeration Type : PoEStatus
--
PoEStatus ::= TEXTUAL-CONVENTION
    STATUS       current
    DESCRIPTION "Power over ethernet status"
    SYNTAX       INTEGER {
                           searching(1),
                           detection(2),
                           classification(3),       
                           powerout(4),       
                           idle(5),
                           failed(6),          
                           na(7)
                         }

PlugType ::= TEXTUAL-CONVENTION
    STATUS       current
    DESCRIPTION
        "Plug Type."
    SYNTAX   INTEGER {
                generic(1),
                gMetro(2)
             }

PlugMode ::= TEXTUAL-CONVENTION
    STATUS       current
    DESCRIPTION
        "Plug Mode."
    SYNTAX   INTEGER {
                tailEnd(1),
                headEnd(2)
             }

RelativeChannelIdentifier ::= TEXTUAL-CONVENTION
    STATUS       current
    DESCRIPTION
        "Relative Channel Identifier."
    SYNTAX   INTEGER {
                channel1(1),
                channel2(2),
                channel3(3),
                channel4(4),
                channel5(5),
                channel6(6),
                channel7(7),
                channel8(8),
                channel9(9)
             }

ChannelType ::= TEXTUAL-CONVENTION
    STATUS       current
    DESCRIPTION
        "Channel Type."
    SYNTAX   INTEGER {
                ituCband(1),
                relativeChannelNumber(2),
                frequency(3)
             }

OutOfBandChannelStatus ::= TEXTUAL-CONVENTION
    STATUS       current
    DESCRIPTION
        "Out Of Band Channel Status."
    SYNTAX   INTEGER {
                notApplicable(1),
                disabled(2),
                idle(3),
                communicationInProgress(4),
                communicationError(5),
                autoTunningInProgress(6)
             }

GMetroAutoTuningMode ::= TEXTUAL-CONVENTION
    STATUS       current
    DESCRIPTION
        "G.Metro Auto Tuning Mode."
    SYNTAX   INTEGER {
                pairedTuning(1),
                blindTuning(2),
                autonomousTuning(3)
             }

FrequencyIdentifier ::= TEXTUAL-CONVENTION
    STATUS       current
    DESCRIPTION
        "Frequency Identifier."
    SYNTAX   INTEGER {
                frequency19120(1),
                frequency19130(2),
                frequency19140(3),
                frequency19150(4),
                frequency19160(5),
                frequency19170(6),
                frequency19180(7),
                frequency19190(8),
                frequency19200(9),
                frequency19210(10),
                frequency19220(11),
                frequency19230(12),
                frequency19240(13),
                frequency19250(14),
                frequency19260(15),
                frequency19270(16),
                frequency19280(17),
                frequency19290(18),
                frequency19300(19),
                frequency19310(20),
                frequency19320(21),
                frequency19330(22),
                frequency19340(23),
                frequency19350(24),
                frequency19360(25),
                frequency19370(26),
                frequency19380(27),
                frequency19390(28),
                frequency19400(29),
                frequency19410(30),
                frequency19420(31),
                frequency19430(32),
                frequency19440(33),
                frequency19450(34),
                frequency19460(35),
                frequency19470(36),
                frequency19480(37),
                frequency19490(38),
                frequency19500(39),
                frequency19510(40),
                frequency19520(41),
                frequency19530(42),
                frequency19540(43),
                frequency19550(44),
                frequency19560(45),
                frequency19570(46),
                frequency19580(47),
                frequency19590(48),
                frequency19600(49)
             }

ITUCBandChannelIdentifier ::= TEXTUAL-CONVENTION
    STATUS       current
    DESCRIPTION
        "ITU C-band Channel Identifier."
    SYNTAX   INTEGER {
                c12(1),
                c13(2),
                c14(3),
                c15(4),
                c16(5),
                c17(6),
                c18(7),
                c19(8),
                c20(9),
                c21(10),
                c22(11),
                c23(12),
                c24(13),
                c25(14),
                c26(15),
                c27(16),
                c28(17),
                c29(18),
                c30(19),
                c31(20),
                c32(21),
                c33(22),
                c34(23),
                c35(24),
                c36(25),
                c37(26),
                c38(27),
                c39(28),
                c40(29),
                c41(30),
                c42(31),
                c43(32),
                c44(33),
                c45(34),
                c46(35),
                c47(36),
                c48(37),
                c49(38),
                c50(39),
                c51(40),
                c52(41),
                c53(42),
                c54(43),
                c55(44),
                c56(45),
                c57(46),
                c58(47),
                c59(48),
                c60(49)
             }

--
--  Ethernet Access Port 
--
cmEthernetAccPortTable  OBJECT-TYPE
    SYNTAX      SEQUENCE OF CmEthernetAccPortEntry
    MAX-ACCESS  not-accessible
    STATUS      current
    DESCRIPTION
            "A list of entries corresponding to Ethernet Access Port 
             Facilities for configuration purposes."
    ::= { cmFacilityObjects 1 }

cmEthernetAccPortEntry OBJECT-TYPE
    SYNTAX      CmEthernetAccPortEntry 
    MAX-ACCESS  not-accessible
    STATUS      current
    DESCRIPTION
            "A conceptual row in the cmEthernetAccPortTable."
    INDEX { neIndex, shelfIndex, slotIndex, cmEthernetAccPortIndex }
    ::= { cmEthernetAccPortTable 1 }

CmEthernetAccPortEntry ::= SEQUENCE {
    -- Port Indices 
    cmEthernetAccPortIndex                           Integer32,
    cmEthernetAccPortIfIndex                         InterfaceIndex,
    cmEthernetAccPortEntityIndex                     PhysicalIndex,

    -- State Management params
    cmEthernetAccPortAdminState                      AdminState,
    cmEthernetAccPortOperationalState                OperationalState,
    cmEthernetAccPortSecondaryState                  SecondaryState,

    -- Generic Port params
    cmEthernetAccPortMTU                             Integer32,

    -- Generic Ethernet Port params
    cmEthernetAccPortMediaType                       EthernetMediaType,
    cmEthernetAccPortConfigSpeed                     EthernetPortSpeed,
    cmEthernetAccPortNegotiatedSpeed                 EthernetPortSpeed,
    cmEthernetAccPortMDIXType                        CmEthernetMDIXType,  
    cmEthernetAccPortJumboFramesEnabled              TruthValue,
    cmEthernetAccPortSfpVendorName                   DisplayString,
    cmEthernetAccPortSfpPartNumber                   DisplayString,
    cmEthernetAccPortSfpSerialNumber                 DisplayString,
    cmEthernetAccPortSfpDateOfManufacture            DateAndTime,
    cmEthernetAccPortSfpConnectorValue               SfpConnectorValue,

    -- EtherJack Diagnosis params
    cmEthernetAccPortInitiateDiag                    CmEthernetDiagAction,
    cmEthernetAccPortDiagnosePair1Cond               CmDiagCableCondType,
    cmEthernetAccPortDiagnosePair2Cond               CmDiagCableCondType,
    cmEthernetAccPortDiagnosePair3Cond               CmDiagCableCondType,
    cmEthernetAccPortDiagnosePair4Cond               CmDiagCableCondType,
    cmEthernetAccPortDiagnoseAutoNegCond             CmDiagAutoNegCondType,
    cmEthernetAccPortDiagnoseLpbkCond                CmDiagLpbkCondType,
    cmEthernetAccPortDiagnoseEfmLpbkCond             CmDiagEfmOamLpbkCondType,
    cmEthernetAccPortDiagnoseResult                  DisplayString,
    cmEthernetAccPortDiagnoseTestStatus              CmDiagTestStatus,
    cmEthernetAccPortDiagnoseTestTime                DateAndTime,

    -- Ethernet Loopback params
    cmEthernetAccPortLoopbackConfig                  CmLoopbackType,
    cmEthernetAccPortLoopbackStatus                  CmLoopbackType,
    cmEthernetAccPortLoopbackTime                    Integer32,
    cmEthernetAccPortLoopbackSwapSADA                CmSwapSADAType,
    cmEthernetAccPortOuterVlanLoopbackMask           INTEGER,
    cmEthernetAccPortOuterVlanLoopback1              DisplayString,
    cmEthernetAccPortOuterVlanLoopback2              DisplayString,
    cmEthernetAccPortOuterVlanLoopback3              DisplayString,
    cmEthernetAccPortInnerVlanLoopbackMask           INTEGER,
    cmEthernetAccPortInnerVlanLoopback1              DisplayString,
    cmEthernetAccPortInnerVlanLoopback2              DisplayString,
    cmEthernetAccPortInnerVlanLoopback3              DisplayString,

    -- Link Loss Forwarding params 
    cmEthernetAccPortLinkLossFwdEnabled              TruthValue,
    cmEthernetAccPortLinkLossFwdSignalType           CmLinkLossFwdSignalType,
    cmEthernetAccPortLinkLossFwdTriggerTypes         CmLinkLossFwdTriggerTypes,
    cmEthernetAccPortLinkLossFwdDelay                Integer32,
    cmEthernetAccPortLinkLossFwdActive               TruthValue,
    cmEthernetAccPortLinkLossFwdPartnerEnabled       TruthValue,
    cmEthernetAccPortLinkLossFwdLocalLinkId          Integer32,
    cmEthernetAccPortLinkLossFwdRemoteLinkIds        CmRemoteLinkIds,

    -- OAM params
    cmEthernetAccPortOamId                           Integer32,
    cmEthernetAccPortOamAdminDisposition             CmControlProtocolDispType,
    cmEthernetAccPortOamDiscoveryState               CmOamDiscoveryState,
    cmEthernetAccPortOamLocalVarRtrvsEnabled         TruthValue,
    cmEthernetAccPortOamLocalLinkEventsEnabled       TruthValue,
    cmEthernetAccPortOamLocalOamLoopbacksSupported   TruthValue,
    cmEthernetAccPortOamLocalUnidirSupportEnabled    TruthValue,
    cmEthernetAccPortOamLocalMaxPDUSize              Integer32,
    cmEthernetAccPortOamLocalMode                    CmOamMode,
    cmEthernetAccPortOamRemoteMacAddress             MacAddress,
    cmEthernetAccPortOamRemoteVarRtrvsEnabled        TruthValue,
    cmEthernetAccPortOamRemoteLinkEventsEnabled      TruthValue,
    cmEthernetAccPortOamRemoteOamLoopbacksSupported  TruthValue,
    cmEthernetAccPortOamRemoteUnidirSupportEnabled   TruthValue,
    cmEthernetAccPortOamRemoteMaxPDUSize             Integer32,
    cmEthernetAccPortOamRemoteMode                   CmOamMode,

    -- Ethernet Port Service params
    cmEthernetAccPortMode                            CmEthernetSvcPortMode,
    cmEthernetAccPortSvcType                         CmEthernetSvcType,

    -- Ethernet Port Traffic params
    cmEthernetAccPortRxPauseDisposition              CmControlProtocolDispType,
    cmEthernetAccPortTxPauseEnabled                  TruthValue,
    cmEthernetAccPortAfpType                         CmAfpType,

    --New objects available with FSP150CC GE206 (Release 4.1CC)
    -- Generic Ethernet Port params
    cmEthernetAccPortMDIXStatus                      CmEthernetMDIXType,
    cmEthernetAccPortSfpReach                        Integer32,
    cmEthernetAccPortSfpLaserWaveLength              Integer32,
    cmEthernetAccPortSfpMediaType                    SfpMediaType,

    -- EFM OAM 
    cmEthernetAccPortOamEnabled                      TruthValue,
    cmEthernetAccPortOamAdminState                   CmOamAdminState,

    -- Ethernet Port Traffic params
    cmEthernetAccPortShapingEnabled                  TruthValue,
    cmEthernetAccPortShapedSpeedLo                   Unsigned32,
    cmEthernetAccPortShapedSpeedHi                   Unsigned32,
    cmEthernetAccPortQinQEtherType                   Unsigned32,
    cmEthernetAccPortRxPauseEnabled                  TruthValue,

    -- EtherJack Diagnosis params
    cmEthernetAccPortAutoDiagEnabled                 TruthValue,

    -- LLF param
    cmEthernetAccPortLinkLossFwdTxActionType         CmLinkLossFwdTxActionType,
    cmEthernetAccPortLinkLossFwdRxRLDLinkIds         CmRemoteLinkIds,

    --Ethernet Port Services params
    cmEthernetAccPortN2AVlanTrunkingEnabled          TruthValue,
    cmEthernetAccPortA2NPushPVIDEnabled              TruthValue,
    cmEthernetAccPortN2APopPVIDEnabled               TruthValue,
    cmEthernetAccPortPortVlanId                      VlanId,
    cmEthernetAccPortPortVlanPriority                VlanPriority,     
    cmEthernetAccPortPrioMapMode                     PriorityMapMode,     

    --Synchronous Port params
    cmEthernetAccPortSyncEEnabled                    TruthValue,
    cmEthernetAccPortQLModeEnabled                   TruthValue,
    cmEthernetAccPortExpectedQL                      SSMQualityLevel,
    cmEthernetAccPortAssumedQL                       SSMQualityLevel,
    cmEthernetAccPortReceivedQL                      SSMQualityLevel,
    cmEthernetAccPortTransmitQL                      SSMQualityLevel,
  
    --PCP DEI params
    cmEthernetAccPortDeiEnable                       TruthValue, 
    cmEthernetAccPortPcpDEEncType                    PcpDEEncType,
    cmEthernetAccPortPcpDEPairsAction                PcpDEPairsAction,

    cmEthernetAccPortSSMRemoteMacAddress             MacAddress,

    --XG params
    cmEthernetAccPortXgePhyType                      XgePhyType,
    
    --Mac Loopback Params
    cmEthernetAccPortLoopbackSourceMacControlEnabled TruthValue,
    cmEthernetAccPortLoopbackDestMacControlEnabled   TruthValue,
    cmEthernetAccPortLoopbackSourceMacAddress        MacAddress,
    cmEthernetAccPortLoopbackDestMacAddress          MacAddress,
    cmEthernetAccPortLoopbackBlockingEnabled         TruthValue,

    -- Ethernet Port Traffic params
    cmEthernetAccPortRxDeiAction                     RxDeiAction,
    cmEthernetAccPortTxDeiAction                     TxDeiAction,
    cmEthernetAccPortRxDeiOuterTagType               DeiOuterTagType,
    cmEthernetAccPortTxDeiOuterTagType               DeiOuterTagType,

    --XFP params
    cmEthernetAccPortLaserWDMChannel                 SfpChannelIdentifier,
    cmEthernetAccPortLaserIsTunable                  TruthValue,
    cmEthernetAccPortLaserFrequency                  Unsigned32,

    -- Generic Ethernet Port params - added in R6.5
    cmEthernetAccPortMediaTypeAutoSelected           EthernetMediaType,

    -- Ethernet Port Traffic params - added in R6.5
    cmEthernetAccPortLowLatencyQueuingEnabled        TruthValue,
    cmEthernetAccPortA2nSwapPriorityVIDEnabled       TruthValue,
    cmEthernetAccPortN2aSwapPriorityVIDEnabled       TruthValue,
    cmEthernetAccPortSwapPriorityVID                 VlanId,
    cmEthernetAccPortDiagnosticMacAddress            MacAddress,
    
    cmEthernetAccPortIngressCOSPriority              VlanTagType,
    cmEthernetAccPortDefaultCOS                      Integer32,
    cmEthernetAccPortTrafficModel                    EthernetPortTrafficModel,
    cmEthernetAccPortIndependentShaperBW             TruthValue,
    cmEthernetAccPortJdsuLoopbackSrcIp               IpAddress,
    cmEthernetAccPortWfqSegmentationCOS              Integer32,
    cmEthernetAccPortWfqGroupCOS                     Integer32,
    cmEthernetAccPortWfqGroupEirLo                   Unsigned32,
    cmEthernetAccPortWfqGroupEirHi                   Unsigned32,
    cmEthernetAccPortSilentStartControl              TruthValue,
    cmEthernetAccPortSfpLinkLength                   Integer32,

    -- Ethernet Port Traffic params 
    cmEthernetAccPortOuterTagTpidOverride            TruthValue,
    cmEthernetAccPortOuterTagTpid                    Unsigned32,

    -- Ethernet Port SFP params
    cmEthernetAccPortSfpName                         DisplayString,
    cmEthernetAccPortSfpHardwareRevision             DisplayString,

    -- Persistent Loopback Control
    cmEthernetAccPortPersistentLoopbackControl       TruthValue,

    -- Ethernet Port Loopback Test Reflector params
    cmEthernetAccPortLoopbackTestReflectorIPv4AddressControl TruthValue,
    cmEthernetAccPortLoopbackTestReflectorIPv4Address        IpAddress,
    cmEthernetAccPortLoopbackTestReflectorIPv6AddressControl TruthValue,
    cmEthernetAccPortLoopbackTestReflectorIPv6Address        Ipv6Address,

    cmEthernetAccPortPowerdDeviceDetection           ToggleValue,
    cmEthernetAccPortPoEStatus                       PoEStatus,

    -- Ethernet Port SFP params
    cmEthernetAccPortSfpIdentifierValue              SfpIdentifierValue
}

-- Port Indices 
cmEthernetAccPortIndex OBJECT-TYPE
    SYNTAX      Integer32 (0|1..65535)
    MAX-ACCESS  read-only
    STATUS      current
    DESCRIPTION
            "An integer index value used to uniquely identify
             this Ethernet Access Port within a card.
             Note that each Ethernet Access Port is uniquely identified
             by the indices neIndex, shelfIndex, 
             slotIndex, cmEthernetAccPortIndex.
             From release 5.6CC zero value becomes valid.
             The zero value is used in Network Element level objects which contain
             cmEthernetAccPortIndex in the index which is not-applicable for 
             these objects e.g. Pass-thru Flows, Shapers or Policers." 
    ::= { cmEthernetAccPortEntry 1 }

cmEthernetAccPortIfIndex OBJECT-TYPE
    SYNTAX      InterfaceIndex 
    MAX-ACCESS  read-only
    STATUS      current
    DESCRIPTION
            "This object has the same value as ifIndex for 
             Ethernet Access Port.  An integer index value used to 
             uniquely identify this Ethernet Access Port."
    ::= { cmEthernetAccPortEntry 2 }

cmEthernetAccPortEntityIndex OBJECT-TYPE
    SYNTAX      PhysicalIndex 
    MAX-ACCESS  read-only
    STATUS      current
    DESCRIPTION
           "Entity Index from ENTITY-MIB for this port."
    ::= { cmEthernetAccPortEntry 3 }

-- State Management params
cmEthernetAccPortAdminState OBJECT-TYPE
    SYNTAX      AdminState 
    MAX-ACCESS  read-write
    STATUS      current
    DESCRIPTION
            "This object represents the Administrative State of the Ethernet 
             Access Port."
    ::= { cmEthernetAccPortEntry 4 }

cmEthernetAccPortOperationalState OBJECT-TYPE
    SYNTAX      OperationalState 
    MAX-ACCESS  read-only
    STATUS      current
    DESCRIPTION
            "This object represents the Operational State of the Ethernet 
             Access Port."
    ::= { cmEthernetAccPortEntry 5 }

cmEthernetAccPortSecondaryState OBJECT-TYPE
    SYNTAX      SecondaryState 
    MAX-ACCESS  read-only
    STATUS      current
    DESCRIPTION
            "This object represents the Secondary State of the Ethernet 
             Access Port."
    ::= { cmEthernetAccPortEntry 6 }

-- Generic Port params
cmEthernetAccPortMTU OBJECT-TYPE
    SYNTAX      Integer32 
    MAX-ACCESS  read-write
    STATUS      current
    DESCRIPTION
            "This object provides the MTU on the Ethernet Access Port.
             The object is made read-write for FSP150CC devices."
    ::= { cmEthernetAccPortEntry 7 }

cmEthernetAccPortMediaType OBJECT-TYPE
    SYNTAX     EthernetMediaType
    MAX-ACCESS read-write
    STATUS     current
    DESCRIPTION
            "This object represents the type of Ethernet Media on the 
             Ethernet Access Port."
    ::= { cmEthernetAccPortEntry 8 }

cmEthernetAccPortConfigSpeed OBJECT-TYPE
    SYNTAX     EthernetPortSpeed
    MAX-ACCESS read-write
    STATUS     current
    DESCRIPTION
            "This object allows to configure the speed of the 
             Ethernet Access Port."
    ::= { cmEthernetAccPortEntry 9 }

cmEthernetAccPortNegotiatedSpeed OBJECT-TYPE
    SYNTAX     EthernetPortSpeed
    MAX-ACCESS read-only
    STATUS     current
    DESCRIPTION
            "This object provides the negotiated speed of the 
             Ethernet Access Port."
    ::= { cmEthernetAccPortEntry 10 }

cmEthernetAccPortMDIXType OBJECT-TYPE
    SYNTAX     CmEthernetMDIXType
    MAX-ACCESS read-write
    STATUS     current
    DESCRIPTION
            "This object allows management of MDIX property on  
             Ethernet Access Port."
    ::= { cmEthernetAccPortEntry 11 }

cmEthernetAccPortJumboFramesEnabled OBJECT-TYPE
    SYNTAX     TruthValue
    MAX-ACCESS read-write
    STATUS     current
    DESCRIPTION
            "This object allows enabling/disabling jumbo frames support on 
             the Ethernet Access Port.  This object is only applicable for
             Ethernet Access Port on R3.1CM NTU Card."
    ::= { cmEthernetAccPortEntry 12 }

cmEthernetAccPortSfpVendorName OBJECT-TYPE
    SYNTAX  DisplayString (SIZE (0..16)) 
    MAX-ACCESS read-only
    STATUS     current
    DESCRIPTION
            "This object provides the vendor name of the SFP. 
             This is applicable when cmEthernetAccPortMediaType is fiber or coppersfp."
     ::= { cmEthernetAccPortEntry 13 }

cmEthernetAccPortSfpPartNumber OBJECT-TYPE
    SYNTAX  DisplayString (SIZE (0..16)) 
    MAX-ACCESS read-only
    STATUS     current
    DESCRIPTION
            "This object provides the part number of the SFP. 
             This is applicable when cmEthernetAccPortMediaType is fiber or coppersfp."
     ::= { cmEthernetAccPortEntry 14 }

cmEthernetAccPortSfpSerialNumber OBJECT-TYPE
    SYNTAX  DisplayString (SIZE (0..32)) 
    MAX-ACCESS read-only
    STATUS     current
    DESCRIPTION
            "This object provides the serial number of the SFP.  
             This is applicable when cmEthernetAccPortMediaType is fiber or coppersfp."
     ::= { cmEthernetAccPortEntry 15 }

cmEthernetAccPortSfpDateOfManufacture OBJECT-TYPE
    SYNTAX     DateAndTime 
    MAX-ACCESS read-only
    STATUS     current
    DESCRIPTION
            "This object provides the date of manufacture of the SFP.
             This is applicable when cmEthernetAccPortMediaType is fiber or coppersfp."
     ::= { cmEthernetAccPortEntry 16 }

cmEthernetAccPortSfpConnectorValue OBJECT-TYPE
    SYNTAX     SfpConnectorValue 
    MAX-ACCESS read-only
    STATUS     current
    DESCRIPTION
            "This object provides the SFP connector value.
             This is applicable when cmEthernetAccPortMediaType is fiber or coppersfp."
     ::= { cmEthernetAccPortEntry 17 }

-- EtherJack Diagnosis params
cmEthernetAccPortInitiateDiag  OBJECT-TYPE
    SYNTAX     CmEthernetDiagAction
    MAX-ACCESS read-write
    STATUS     current
    DESCRIPTION
            "This object allows to initiate Etherjack diagnosis on the
             Ethernet Access Port."
     ::= { cmEthernetAccPortEntry 18 }

cmEthernetAccPortDiagnosePair1Cond OBJECT-TYPE
    SYNTAX     CmDiagCableCondType
    MAX-ACCESS read-only
    STATUS     current
    DESCRIPTION
            "This object provides diagnosis results for the cable Pair 1
             on Ethernet Access Port."
     ::= { cmEthernetAccPortEntry 19 }

cmEthernetAccPortDiagnosePair2Cond OBJECT-TYPE
    SYNTAX     CmDiagCableCondType
    MAX-ACCESS read-only
    STATUS     current
    DESCRIPTION
            "This object provides diagnosis results for the cable Pair 2
             on Ethernet Access Port."
     ::= { cmEthernetAccPortEntry 20 }

cmEthernetAccPortDiagnosePair3Cond OBJECT-TYPE
    SYNTAX     CmDiagCableCondType
    MAX-ACCESS read-only
    STATUS     current
    DESCRIPTION
            "This object provides diagnosis results for the cable Pair 3
             on Ethernet Access Port."
     ::= { cmEthernetAccPortEntry 21 }

cmEthernetAccPortDiagnosePair4Cond OBJECT-TYPE
    SYNTAX     CmDiagCableCondType
    MAX-ACCESS read-only
    STATUS     current
    DESCRIPTION
            "This object provides diagnosis results for the cable Pair 4
             on Ethernet Access Port."
     ::= { cmEthernetAccPortEntry 22 }

cmEthernetAccPortDiagnoseAutoNegCond OBJECT-TYPE
    SYNTAX     CmDiagAutoNegCondType
    MAX-ACCESS read-only
    STATUS     current
    DESCRIPTION
            "This object provides auto negotiation results of the diagnosis
             test on Ethernet Access Port."
     ::= { cmEthernetAccPortEntry 23 }

cmEthernetAccPortDiagnoseLpbkCond OBJECT-TYPE
    SYNTAX     CmDiagLpbkCondType
    MAX-ACCESS read-only
    STATUS     current
    DESCRIPTION
            "This object provides port loopback results of the diagnosis
             test on Ethernet Access Port."
     ::= { cmEthernetAccPortEntry 24 }

cmEthernetAccPortDiagnoseEfmLpbkCond OBJECT-TYPE
    SYNTAX     CmDiagEfmOamLpbkCondType
    MAX-ACCESS read-only
    STATUS     current
    DESCRIPTION
            "This object provides remote EFM loopback results of the diagnosis
             test on Ethernet Access Port."
     ::= { cmEthernetAccPortEntry 25 }

cmEthernetAccPortDiagnoseResult OBJECT-TYPE
    SYNTAX  DisplayString (SIZE (0..256)) 
    MAX-ACCESS read-only
    STATUS     current
    DESCRIPTION
            "This object provides results of the diagnosis
             test in string form on Ethernet Access Port."
     ::= { cmEthernetAccPortEntry 26 }

cmEthernetAccPortDiagnoseTestStatus OBJECT-TYPE
    SYNTAX  CmDiagTestStatus 
    MAX-ACCESS read-only
    STATUS     current
    DESCRIPTION
            "This object provides the current status of the diagnosis
             test on Ethernet Access Port."
     ::= { cmEthernetAccPortEntry 27 }

cmEthernetAccPortDiagnoseTestTime OBJECT-TYPE
    SYNTAX  DateAndTime 
    MAX-ACCESS read-only
    STATUS     current
    DESCRIPTION
       "This object provides the time when diagnosis test was last executed."
     ::= { cmEthernetAccPortEntry 28 }

-- Ethernet Loopback params
cmEthernetAccPortLoopbackConfig OBJECT-TYPE
    SYNTAX     CmLoopbackType
    MAX-ACCESS read-write
    STATUS     current
    DESCRIPTION
            "This object allows to initiate loopbacks on 
             on the Ethernet Access Port."
     ::= { cmEthernetAccPortEntry 29 }

cmEthernetAccPortLoopbackStatus OBJECT-TYPE
    SYNTAX     CmLoopbackType
    MAX-ACCESS read-only
    STATUS     current
    DESCRIPTION
            "This object provides status of the current loopback 
             on the Ethernet Access Port."
     ::= { cmEthernetAccPortEntry 30 }

cmEthernetAccPortLoopbackTime OBJECT-TYPE                   
    SYNTAX     Integer32 (2..300)
    MAX-ACCESS read-write
    STATUS     current
    DESCRIPTION
            "This object allows to specify time for timed-loopbacks on 
             on the Ethernet Access Port."
     ::= { cmEthernetAccPortEntry 31 }

cmEthernetAccPortLoopbackSwapSADA OBJECT-TYPE
    SYNTAX     CmSwapSADAType
    MAX-ACCESS read-write
    STATUS     current
    DESCRIPTION
            "This object allows to specify whether or not the loopbacked
             frame will have the Source Address and Destination Address
             swapped."
     ::= { cmEthernetAccPortEntry 32 }

cmEthernetAccPortOuterVlanLoopbackMask OBJECT-TYPE
    SYNTAX     INTEGER (0..16)
    MAX-ACCESS read-write
    STATUS     current
    DESCRIPTION
             "This object allows specification of the outer VLANs to be 
              looped back when port is in vlan(terminal/facility) 
              loopback configuration. Only 3 VLANs can be specified 
              for vlan loopback. The various bit positions are:
                   1         Outer VLAN 1 Loopback Enabled
                   2         Outer VLAN 2 Loopback Enabled
                   4         Outer VLAN 3 Loopback Enabled
              Value of 0 means that no VLANs are enabled."
     ::= { cmEthernetAccPortEntry 33 }

cmEthernetAccPortOuterVlanLoopback1 OBJECT-TYPE              
    SYNTAX  DisplayString (SIZE (0..6)) 
    MAX-ACCESS read-write
    STATUS     current
    DESCRIPTION
             "This object allows specification of the outer VLAN 1 to be 
              looped back when port is in vlan(terminal/facility) 
              loopback configuration. This is valid only if the
              corresponding bit in cmEthernetAccPortOuterVlanLoopbackMask
              is set.  The value to be specified should be in the form 
              X-Y where X is the VLAN Id and Y is the VLAN Priority.  
              If Y is specified as a *, all Priorities (0 to 7) 
              are looped back."
     ::= { cmEthernetAccPortEntry 34 }

cmEthernetAccPortOuterVlanLoopback2 OBJECT-TYPE
    SYNTAX  DisplayString (SIZE (0..6)) 
    MAX-ACCESS read-write
    STATUS     current
    DESCRIPTION
             "This object allows specification of the outer VLAN 2 to be 
              looped back when port is in vlan(terminal/facility) 
              loopback configuration. This is valid only if the
              corresponding bit in cmEthernetAccPortOuterVlanLoopbackMask
              is set.  The value to be specified should be in the form 
              X-Y where X is the VLAN Id and Y is the VLAN Priority.  
              If Y is specified as a *, all Priorities (0 to 7) 
              are looped back."
     ::= { cmEthernetAccPortEntry 35 }

cmEthernetAccPortOuterVlanLoopback3 OBJECT-TYPE
    SYNTAX  DisplayString (SIZE (0..6)) 
    MAX-ACCESS read-write
    STATUS     current
    DESCRIPTION
             "This object allows specification of the outer VLAN 3 to be 
              looped back when port is in vlan(terminal/facility) 
              loopback configuration. This is valid only if the
              corresponding bit in cmEthernetAccPortOuterVlanLoopbackMask
              is set.  The value to be specified should be in the form 
              X-Y where X is the VLAN Id and Y is the VLAN Priority.  
              If Y is specified as a *, all Priorities (0 to 7) 
              are looped back."
     ::= { cmEthernetAccPortEntry 36 }

cmEthernetAccPortInnerVlanLoopbackMask OBJECT-TYPE
    SYNTAX     INTEGER (0..16)
    MAX-ACCESS read-write
    STATUS     current
    DESCRIPTION
             "This object allows specification of the inner VLANs to be 
              looped back when port is in vlan(terminal/facility) 
              loopback configuration. Only 3 VLANs can be specified 
              for vlan loopback. The various bit positions are:
                   1         Inner VLAN 1 Loopback Enabled
                   2         Inner VLAN 2 Loopback Enabled
                   4         Inner VLAN 3 Loopback Enabled
              Value of 0 means that no VLANs are enabled."
     ::= { cmEthernetAccPortEntry 37 }

cmEthernetAccPortInnerVlanLoopback1 OBJECT-TYPE 
    SYNTAX  DisplayString (SIZE (0..6)) 
    MAX-ACCESS read-write
    STATUS     current
    DESCRIPTION
             "This object allows specification of the inner VLAN 1 to be 
              looped back when port is in vlan(terminal/facility) 
              loopback configuration. This is valid only if the
              corresponding bit in cmEthernetAccPortInnerVlanLoopbackMask
              is set.  The value to be specified should be in the form 
              X-Y where X is the VLAN Id and Y is the VLAN Priority.  
              If Y is specified as a *, all Priorities (0 to 7) 
              are looped back."
     ::= { cmEthernetAccPortEntry 38 }

cmEthernetAccPortInnerVlanLoopback2 OBJECT-TYPE
    SYNTAX  DisplayString (SIZE (0..6)) 
    MAX-ACCESS read-write
    STATUS     current
    DESCRIPTION
             "This object allows specification of the inner VLAN 2 to be 
              looped back when port is in vlan(terminal/facility) 
              loopback configuration. This is valid only if the
              corresponding bit in cmEthernetAccPortInnerVlanLoopbackMask
              is set.  The value to be specified should be in the form 
              X-Y where X is the VLAN Id and Y is the VLAN Priority.  
              If Y is specified as a *, all Priorities (0 to 7) 
              are looped back."
     ::= { cmEthernetAccPortEntry 39 }

cmEthernetAccPortInnerVlanLoopback3 OBJECT-TYPE
    SYNTAX  DisplayString (SIZE (0..6)) 
    MAX-ACCESS read-write
    STATUS     current
    DESCRIPTION
             "This object allows specification of the inner VLAN 3 to be 
              looped back when port is in vlan(terminal/facility) 
              loopback configuration. This is valid only if the
              corresponding bit in cmEthernetAccPortInnerVlanLoopbackMask
              is set.  The value to be specified should be in the form 
              X-Y where X is the VLAN Id and Y is the VLAN Priority.  
              If Y is specified as a *, all Priorities (0 to 7) 
              are looped back."
     ::= { cmEthernetAccPortEntry 40 }


-- Link Loss Forwarding params 
cmEthernetAccPortLinkLossFwdEnabled OBJECT-TYPE
    SYNTAX     TruthValue
    MAX-ACCESS read-write
    STATUS     current
    DESCRIPTION
             "This object allows enabling/disabling link loss forwarding 
              on the Ethernet Access Port." 
     ::= { cmEthernetAccPortEntry 41 }

cmEthernetAccPortLinkLossFwdSignalType  OBJECT-TYPE
    SYNTAX     CmLinkLossFwdSignalType
    MAX-ACCESS read-write
    STATUS     deprecated
    DESCRIPTION
             "This object allows definition of the link loss forwarding
              signalling type.  This is applicable only if 
              cmEthernetAccPortLinkLossFwdEnabled is enabled.
              This object is applicable only for FSP150CM Release 3.1.
              This object is deprecated henceforth. 
              Link Loss signalling will be supported using the object
              cmEthernetAccPortLinkLossFwdTxActionType."
     ::= { cmEthernetAccPortEntry 42 }

cmEthernetAccPortLinkLossFwdTriggerTypes  OBJECT-TYPE
    SYNTAX     CmLinkLossFwdTriggerTypes
    MAX-ACCESS read-write
    STATUS     current
    DESCRIPTION
             "This object allows definition of the link loss forwarding
              trigger types.  This is applicable only if 
              cmEthernetAccPortLinkLossFwdEnabled is enabled."
     ::= { cmEthernetAccPortEntry 43 }

cmEthernetAccPortLinkLossFwdDelay OBJECT-TYPE                
    SYNTAX     Integer32
    MAX-ACCESS read-write
    STATUS     current
    DESCRIPTION
             "This object allows specification of the delay between
              detection of link loss and signalling of link loss forwarding. 
              Time specified is in seconds."
     ::= { cmEthernetAccPortEntry 44 }

cmEthernetAccPortLinkLossFwdActive OBJECT-TYPE 
    SYNTAX     TruthValue
    MAX-ACCESS read-only
    STATUS     current
    DESCRIPTION
             "This object provides the link loss forwarding status indicating
              if link loss forwarding is currently being signaled via 
              the port." 
     ::= { cmEthernetAccPortEntry 45 }

cmEthernetAccPortLinkLossFwdPartnerEnabled OBJECT-TYPE 
    SYNTAX     TruthValue
    MAX-ACCESS read-only
    STATUS     current
    DESCRIPTION
             "This object provides the indication of a link partners ability
              to support link loss forwarding via EFM, i.e. from
              received organization specific OAMPDUs." 
     ::= { cmEthernetAccPortEntry 46 }

cmEthernetAccPortLinkLossFwdLocalLinkId OBJECT-TYPE 
    SYNTAX     Integer32
    MAX-ACCESS read-write
    STATUS     current
    DESCRIPTION
             "This object allows configuration of the Local Link Id on 
              Ethernet access port." 
     ::= { cmEthernetAccPortEntry 47 }

cmEthernetAccPortLinkLossFwdRemoteLinkIds OBJECT-TYPE 
    SYNTAX     CmRemoteLinkIds 
    MAX-ACCESS read-write
    STATUS     current
    DESCRIPTION
             "This object allows enabling/disabling Remote Link Ids 
              on Ethernet access port. By setting the appropriate bit
              positions, the Ethernet access port is able to distinguish
              the remote side client ports from the Remote Link Down
              PDUs coming from remote end."
     ::= { cmEthernetAccPortEntry 48 }

-- OAM params
cmEthernetAccPortOamId  OBJECT-TYPE
    SYNTAX     Integer32 
    MAX-ACCESS read-only
    STATUS     current
    DESCRIPTION
             "OAM Id.  This is unique EFM OAM sublayer port id." 
     ::= { cmEthernetAccPortEntry 49 }

cmEthernetAccPortOamAdminDisposition  OBJECT-TYPE
    SYNTAX     CmControlProtocolDispType
    MAX-ACCESS read-write 
    STATUS     deprecated
    DESCRIPTION
             "Ethernet Access Port's EFM OAM Disposition.
              This object is applicable only for FSP150CM Release 3.1.
              This object is deprecated henceforth.  
              With FSP150CC Release 4.1, this property is managed using 
              the Control Protocol Disposition tables."
     ::= { cmEthernetAccPortEntry 50 }

cmEthernetAccPortOamDiscoveryState  OBJECT-TYPE
    SYNTAX     CmOamDiscoveryState
    MAX-ACCESS read-only
    STATUS     current
    DESCRIPTION
             "Ethernet Access Port's OAM discovery state." 
     ::= { cmEthernetAccPortEntry 51 }

cmEthernetAccPortOamLocalVarRtrvsEnabled  OBJECT-TYPE
    SYNTAX     TruthValue
    MAX-ACCESS read-only
    STATUS     current
    DESCRIPTION
             "This object allows specification of whether the Ethernet
              Access Port supports sending variable response OAMPDUs." 
     ::= { cmEthernetAccPortEntry 52 }

cmEthernetAccPortOamLocalLinkEventsEnabled  OBJECT-TYPE
    SYNTAX     TruthValue 
    MAX-ACCESS read-only
    STATUS     current
    DESCRIPTION
             "This object allows specification of whether the Ethernet
              Access Port supports interpreting Link Events."
     ::= { cmEthernetAccPortEntry 53 }

cmEthernetAccPortOamLocalOamLoopbacksSupported  OBJECT-TYPE
    SYNTAX     TruthValue 
    MAX-ACCESS read-write
    STATUS     current
    DESCRIPTION
             "This object allows specification of whether the Ethernet
              Access Port is capable of OAM remote loopback mode."
     ::= { cmEthernetAccPortEntry 54 }

cmEthernetAccPortOamLocalUnidirSupportEnabled  OBJECT-TYPE
    SYNTAX     TruthValue 
    MAX-ACCESS read-only
    STATUS     current
    DESCRIPTION
             "This object allows specification of whether the Ethernet
              Access Port is capable of sending OAMPDUs when the receive path 
              is non-operational."
     ::= { cmEthernetAccPortEntry 55 }

cmEthernetAccPortOamLocalMaxPDUSize  OBJECT-TYPE
    SYNTAX     Integer32
    MAX-ACCESS read-only
    STATUS     current
    DESCRIPTION
             "This object represents the largest OAMPDU, in octets, 
              supported by the Ethernet Access Port.  This value is
              compared to the remote Maximum PDU Size and the smaller of 
              the two is used." 
     ::= { cmEthernetAccPortEntry 56 }

cmEthernetAccPortOamLocalMode OBJECT-TYPE
    SYNTAX     CmOamMode 
    MAX-ACCESS read-write
    STATUS     current
    DESCRIPTION
             "This object allows to configure the OAM sublayer entity in
              either Active or Passive mode." 
     ::= { cmEthernetAccPortEntry 57 }

cmEthernetAccPortOamRemoteMacAddress OBJECT-TYPE
    SYNTAX     MacAddress
    MAX-ACCESS read-only
    STATUS     current
    DESCRIPTION
             "This object allows retrieval of the Remote Mac Address." 
     ::= { cmEthernetAccPortEntry 58 }

cmEthernetAccPortOamRemoteVarRtrvsEnabled OBJECT-TYPE
    SYNTAX     TruthValue
    MAX-ACCESS read-only
    STATUS     current
    DESCRIPTION
             "This object allows retrieval of whether the remote OAM 
              entity supports sending variable response OAMPDUs." 
     ::= { cmEthernetAccPortEntry 59 }

cmEthernetAccPortOamRemoteLinkEventsEnabled OBJECT-TYPE
    SYNTAX     TruthValue 
    MAX-ACCESS read-only
    STATUS     current
    DESCRIPTION
             "This object allows retrieval of whether the remote OAM 
              entity supports interpreting Link Events."
     ::= { cmEthernetAccPortEntry 60 }

cmEthernetAccPortOamRemoteOamLoopbacksSupported OBJECT-TYPE
    SYNTAX     TruthValue 
    MAX-ACCESS read-only
    STATUS     current
    DESCRIPTION
             "This object allows retrieval of whether the remote OAM 
              entity supports OAM remote loopback mode."
     ::= { cmEthernetAccPortEntry 61 }

cmEthernetAccPortOamRemoteUnidirSupportEnabled OBJECT-TYPE
    SYNTAX     TruthValue 
    MAX-ACCESS read-only
    STATUS     current
    DESCRIPTION
             "This object allows retrieval of whether the remote 
              OAM entity is capable of sending OAMPDUs when the receive path 
              is non-operational."
     ::= { cmEthernetAccPortEntry 62 }

cmEthernetAccPortOamRemoteMaxPDUSize OBJECT-TYPE
    SYNTAX     Integer32
    MAX-ACCESS read-only
    STATUS     current
    DESCRIPTION
             "This object allows retrieval of the remote OAM 
              entity maximum OAMPDU size."
     ::= { cmEthernetAccPortEntry 63 }

cmEthernetAccPortOamRemoteMode OBJECT-TYPE
    SYNTAX     CmOamMode 
    MAX-ACCESS read-only
    STATUS     current
    DESCRIPTION
             "This object allows to retrieve whether the remote OAM 
              sublayer entity is either in Active or Passive mode." 
     ::= { cmEthernetAccPortEntry 64 }


-- Ethernet Port Service params
cmEthernetAccPortMode OBJECT-TYPE 
    SYNTAX     CmEthernetSvcPortMode 
    MAX-ACCESS read-write
    STATUS     current
    DESCRIPTION
             "This object allows specification of whether the 
              Ethernet Access Port is in a connection-oriented 
              (offering VLAN based services) mode or connection-less 
              (offering MAC based services) mode." 
     ::= { cmEthernetAccPortEntry 65 }

cmEthernetAccPortSvcType  OBJECT-TYPE 
    SYNTAX     CmEthernetSvcType 
    MAX-ACCESS read-write
    STATUS     current
    DESCRIPTION
             "This object allows specification of whether the 
              Ethernet Access Port provides transparent port based services,
              or multi-flow VLAN based services." 
     ::= { cmEthernetAccPortEntry 66 }

-- Ethernet Port Traffic params
cmEthernetAccPortRxPauseDisposition OBJECT-TYPE
    SYNTAX     CmControlProtocolDispType
    MAX-ACCESS read-write 
    STATUS     deprecated
    DESCRIPTION
         "This object allows management of RX pause frames on 
          Ethernet Access port. This object is applicable only 
          for FSP150CM Release 3.1.
          This object is deprecated henceforth.  With FSP150CC Release 4.1,
          this property is managed using the Control Protocol
          Disposition tables."
     ::= { cmEthernetAccPortEntry 67 }

cmEthernetAccPortTxPauseEnabled OBJECT-TYPE
    SYNTAX     TruthValue
    MAX-ACCESS read-write
    STATUS     current
    DESCRIPTION
         "This object allows enabling/disabling transmit pause frames on
          Ethernet Access port."
     ::= { cmEthernetAccPortEntry 68 }

cmEthernetAccPortAfpType OBJECT-TYPE
    SYNTAX     CmAfpType
    MAX-ACCESS read-write
    STATUS     current
    DESCRIPTION
         "This object allows specification of the Acceptable Frame Policy on
          Ethernet Access port. Users can specify whether the port supports
          only tagged frames, only untagged frames or both tagged and 
          untagged frames."
     ::= { cmEthernetAccPortEntry 69 }

-- Generic Ethernet Port params
cmEthernetAccPortMDIXStatus OBJECT-TYPE
    SYNTAX     CmEthernetMDIXType
    MAX-ACCESS read-only
    STATUS     current
    DESCRIPTION
         "This object provides the current MDIX status of the 
          Ethernet Access port."
     ::= { cmEthernetAccPortEntry 70 }

cmEthernetAccPortSfpReach OBJECT-TYPE
    SYNTAX     Integer32
    MAX-ACCESS read-only
    STATUS     current
    DESCRIPTION
         "This object provides the SFP Reach in meters.
          This is applicable when cmEthernetAccPortMediaType is fiber or coppersfp."
     ::= { cmEthernetAccPortEntry 71 }

cmEthernetAccPortSfpLaserWaveLength OBJECT-TYPE
    SYNTAX     Integer32
    MAX-ACCESS read-only
    STATUS     current
    DESCRIPTION
         "This object provides the SFP Laser Wave Length in nano meters.
          This is applicable only when cmEthernetAccPortMediaType is fiber."
     ::= { cmEthernetAccPortEntry 72 }

cmEthernetAccPortSfpMediaType OBJECT-TYPE
    SYNTAX     SfpMediaType
    MAX-ACCESS read-only
    STATUS     current
    DESCRIPTION
         "This object provides the SFP Media Type.
          This is applicable when cmEthernetAccPortMediaType is fiber or coppersfp."
     ::= { cmEthernetAccPortEntry 73 }

cmEthernetAccPortOamEnabled  OBJECT-TYPE
    SYNTAX     TruthValue
    MAX-ACCESS read-write 
    STATUS     current
    DESCRIPTION
             "This object allows to manage the EFM OAM on Ethernet Access Port."
     ::= { cmEthernetAccPortEntry 74 }

cmEthernetAccPortOamAdminState OBJECT-TYPE
    SYNTAX     CmOamAdminState
    MAX-ACCESS read-only 
    STATUS     current
    DESCRIPTION
             "This object provides the EFM OAM Admin State."
     ::= { cmEthernetAccPortEntry 75 }

-- Ethernet Port Traffic params
cmEthernetAccPortShapingEnabled OBJECT-TYPE
    SYNTAX     TruthValue
    MAX-ACCESS read-write
    STATUS     current
    DESCRIPTION
         "This object allows to manage the Access Port Shaping.
          When enabled, values in cmEthernetAccPortShapedSpeedLo and
          cmEthernetAccPortShapedSpeedHi are applicable."
     ::= { cmEthernetAccPortEntry 76 }

cmEthernetAccPortShapedSpeedLo OBJECT-TYPE
    SYNTAX     Unsigned32
    MAX-ACCESS read-write
    STATUS     current
    DESCRIPTION
         "This object allows to specify the lower 32 bits of 
          the Access Port Shaped speed. This value is applicable
          when cmEthernetAccPortShapingEnabled is enabled."
     ::= { cmEthernetAccPortEntry 77 }

cmEthernetAccPortShapedSpeedHi OBJECT-TYPE
    SYNTAX     Unsigned32
    MAX-ACCESS read-write
    STATUS     current
    DESCRIPTION
         "This object allows to specify the higher 32 bits of 
          the Access Port Shaped speed. This value is applicable
          when cmEthernetAccPortShapingEnabled is enabled."
     ::= { cmEthernetAccPortEntry 78 }

cmEthernetAccPortQinQEtherType OBJECT-TYPE
    SYNTAX     Unsigned32
    MAX-ACCESS read-write
    STATUS     current
    DESCRIPTION
         "This object allows to specify the Q-in-Q Ether Type 
          on the Access Port.  Setting this value to 0 will disable
          the Q-in-Q override on the Access Port."
     ::= { cmEthernetAccPortEntry 79 }

cmEthernetAccPortRxPauseEnabled OBJECT-TYPE
    SYNTAX     TruthValue
    MAX-ACCESS read-write
    STATUS     current
    DESCRIPTION
         "This object allows to enable/disable the RX PAUSE 
          on the Access Port. This object is not applicable for FSP150CM NTU Card.
          On NTU Card cmEthernetAccPortRxPauseDisposition object should be used to
          provision RxPause disposition."
     ::= { cmEthernetAccPortEntry 80 }

-- EtherJack Diagnosis params
cmEthernetAccPortAutoDiagEnabled OBJECT-TYPE
    SYNTAX     TruthValue
    MAX-ACCESS read-write
    STATUS     current
    DESCRIPTION
         "This object allows to enable or disable the automatic 
          Cable Diagnostic tests when the cable is removed from the port."
     ::= { cmEthernetAccPortEntry 81 }

-- Link Loss Forwarding params
cmEthernetAccPortLinkLossFwdTxActionType OBJECT-TYPE
    SYNTAX     CmLinkLossFwdTxActionType
    MAX-ACCESS read-write
    STATUS     current
    DESCRIPTION
         "This object allows to specify the Access Port's behavior when
          link loss forwarding trigger events occur on the Network Port.
          This provides ability to configure per access port LLF behavior." 
     ::= { cmEthernetAccPortEntry 82 }

cmEthernetAccPortLinkLossFwdRxRLDLinkIds OBJECT-TYPE
    SYNTAX     CmRemoteLinkIds
    MAX-ACCESS read-only
    STATUS     current
    DESCRIPTION
         "This object provides the received Remote Link IDs in 
          EFM RLD messages on the Access Port." 
     ::= { cmEthernetAccPortEntry 83 }

--Ethernet Port Services params
cmEthernetAccPortN2AVlanTrunkingEnabled OBJECT-TYPE
    SYNTAX     TruthValue
    MAX-ACCESS read-write
    STATUS     current
    DESCRIPTION
         "This object allows to enable or disable the VLAN trunking on
          Ethernet Access port. Disabling VLAN trunking removes all
          VLAN tags before transmitting traffic out of the access port. 
          This object is only applicable for connection-oriented, 
          evpl service type."
     ::= { cmEthernetAccPortEntry 84 }

cmEthernetAccPortA2NPushPVIDEnabled OBJECT-TYPE
    SYNTAX     TruthValue
    MAX-ACCESS read-write
    STATUS     current
    DESCRIPTION
         "This object allows to specify whether cmEthernetAccPortPortVlanId
          value will be PUSHed on untagged frames or not in the 
          Access to Network direction.  This object is only applicable 
          for connection-oriented, evpl service type."
     ::= { cmEthernetAccPortEntry 85 }

cmEthernetAccPortN2APopPVIDEnabled OBJECT-TYPE
    SYNTAX     TruthValue
    MAX-ACCESS read-write
    STATUS     current
    DESCRIPTION
         "This object allows to specify whether cmEthernetAccPortPortVlanId
          value will be POPed in the 
          Network to Access direction.  This object is only applicable 
          for connection-oriented, evpl service type."
     ::= { cmEthernetAccPortEntry 86 }

cmEthernetAccPortPortVlanId OBJECT-TYPE
    SYNTAX     VlanId
    MAX-ACCESS read-write
    STATUS     current
    DESCRIPTION
         "This object allows to specify the Ethernet Access Port VLAN Id 
          to PUSH on untagged frames in the Access to Network
          direction.  This object is only applicable for connection-oriented,
          evpl service type, when cmEthernetAccPortA2NPushPVIDEnabled 
          is set to true."
     ::= { cmEthernetAccPortEntry 87 }

cmEthernetAccPortPortVlanPriority OBJECT-TYPE
    SYNTAX     VlanPriority
    MAX-ACCESS read-write
    STATUS     current
    DESCRIPTION
         "This object allows to specify the Ethernet Access Port VLAN Priority 
          for the PUSHed VLAN tag (specified by cmEthernetAccPortPortVlanId) 
          on untagged frames in the Access to Network direction.  
          This object is only applicable for connection-oriented,
          evpl service type, when cmEthernetAccPortA2NPushPVIDEnabled 
          is set to true."
     ::= { cmEthernetAccPortEntry 88 }

cmEthernetAccPortPrioMapMode OBJECT-TYPE
    SYNTAX     PriorityMapMode
    MAX-ACCESS read-write
    STATUS     current
    DESCRIPTION
         "This object allows to specify the Ethernet Access Port 
          Priority Mapping Mode used for classification of frames.
          This object is only applicable for connection-oriented,
          evpl service type."
     ::= { cmEthernetAccPortEntry 89 }

--Synchronous Port params
cmEthernetAccPortSyncEEnabled OBJECT-TYPE 
    SYNTAX     TruthValue
    MAX-ACCESS read-write
    STATUS     current
    DESCRIPTION
         "This object allows to specify whether the Ethernet Access Port 
          can be enabled/disabled for Synchronous Ethernet. This object
          is only applicable for Synchronous Ethernet capable ports.
          When enabled, on receive side 
            -port can extract the frequency of its input signal
             and pass the recovered clock to the system clock
            -port processes the ESMC(Ethernet Synchronization Messaging
             Channel) and extracts the QL (when also QL enabled)   
            -port is eligible to be selected as a system clock reference
          When enabled, on transmit side 
            -port's transmit clock is locked to the system clock
            -port generates an ESMC to generate a QL (when also QL enabled)

          When disabled, on receive side,
            -port does not pass the recovered clock to the system clock 
            -port does not process the ESMC (if present) 
            -port is not eligible to be selected as a 
                     system clock reference
          When disabled, on transmit side 
            -port's output frequency may be synchronized to the system clock
            -port does not generate an ESMC."
     ::= { cmEthernetAccPortEntry 90 }

cmEthernetAccPortQLModeEnabled OBJECT-TYPE 
    SYNTAX     TruthValue
    MAX-ACCESS read-write
    STATUS     current
    DESCRIPTION
         "This object allows to specify whether the Ethernet Access Port 
          can be enabled/disabled for QL Mode. This object
          is only applicable for Synchronous Ethernet capable ports,
          when cmEthernetAccPortQLModeEnabled is set to true.
          When enabled, on receive side 
            -port shall PEER the SSM (Sync Status Messages) slow protocol PDUs 
             and take appropriate action 
          When enabled, on transmit side 
            -port shall periodically (once a second) transmit QL TLV 
             information PDUs
          When disabled, on receive side,
            -port shall terminate and discard any SSM slow protocol PDUs 
          When disabled, on transmit side 
            -port shall not transmit any SSM slow protocol PDUs."
     ::= { cmEthernetAccPortEntry 91 }

cmEthernetAccPortExpectedQL OBJECT-TYPE 
    SYNTAX     SSMQualityLevel
    MAX-ACCESS read-write
    STATUS     current
    DESCRIPTION
         "This object allows to specify the expected QL when the 
          Ethernet Access Port is enabled for QL Mode. This object
          is only applicable for Synchronous Ethernet capable ports,
          when cmEthernetAccPortQLModeEnabled is set to true.
          This object allows the user to set a minimum
          expected received Quality Level on the port. The valid values
          depend upon the SYNC entity's Network Clock Type. A value of
          None represents that a minimum Quality Level is not expected. 
          The default value shall be None."
     ::= { cmEthernetAccPortEntry 92 }

cmEthernetAccPortAssumedQL OBJECT-TYPE 
    SYNTAX     SSMQualityLevel
    MAX-ACCESS read-write
    STATUS     current
    DESCRIPTION
         "This object allows to specify the assumed QL on the 
          Ethernet Access Port. This object is only applicable for 
          Synchronous Ethernet capable ports. 
          The Assumed QL is only meaningful if the Network Clock Type
          (see fsp150cm-sync.mib) is option1 and the 
          port's QL Mode is disabled and the port is being used as 
          an input reference source. Under these conditions, 
          the specified QL value is assumed to be the Quality Level of the
          non-failed reference."
     ::= { cmEthernetAccPortEntry 93 }

cmEthernetAccPortReceivedQL OBJECT-TYPE 
    SYNTAX     SSMQualityLevel
    MAX-ACCESS read-only
    STATUS     current
    DESCRIPTION
         "This object provides the Received QL value for the Ethernet port. 
          If the Ethernet port's QL Mode is disabled, then the received 
          QL value is not applicable.This object is only applicable for 
          Synchronous Ethernet capable ports."
     ::= { cmEthernetAccPortEntry 94 }

cmEthernetAccPortTransmitQL OBJECT-TYPE 
    SYNTAX     SSMQualityLevel
    MAX-ACCESS read-only
    STATUS     current
    DESCRIPTION
         "This object provides the Transmitted QL value for the Ethernet port. 
          If the Ethernet port's QL Mode is disabled, then the received 
          QL value is not applicable. This object is only applicable for 
          Synchronous Ethernet capable ports."
     ::= { cmEthernetAccPortEntry 95 }

cmEthernetAccPortDeiEnable OBJECT-TYPE
    SYNTAX      TruthValue
    MAX-ACCESS  read-write
    STATUS      deprecated
    DESCRIPTION
        "This is a port level control to reset the DEI 
         (Drop Eligibility Indicator) bit in the S-Tag,
         if the downstream equipment supports S-Tag TPID (EtherType) but 
         cannot handle DEI bit set. In the receive direction,
         it uses the S-TAG DEI when enabled, else ignores it.
         The following comment is NOT relevant to OSA8.1.1, 
         since this object is still supported by OSA8.1.1.
         The object has been deprecated.
         The respective configuration should be managed
         by following objects:
         cmEthernetAccPortRxDeiAction, cmEthernetAccPortTxDeiAction,
         cmEthernetAccPortRxDeiOuterTagType, cmEthernetAccPortTxDeiOuterTagType."
    ::= { cmEthernetAccPortEntry 96 }

cmEthernetAccPortPcpDEEncType OBJECT-TYPE
    SYNTAX      PcpDEEncType
    MAX-ACCESS  read-write
    STATUS      current
    DESCRIPTION
        "This is a port level control that specifies the mode of drop
         eligibility encoding in PCP bits of the VLAN tag."
    ::= { cmEthernetAccPortEntry 97 }

cmEthernetAccPortPcpDEPairsAction OBJECT-TYPE
    SYNTAX      PcpDEPairsAction
    MAX-ACCESS  read-write
    STATUS      current
    DESCRIPTION
        "This object allows the SNMP user to manage the Priority 
         Code Point (PCP) Drop Eligibility Pairs.  When the
         cmEthernetAccPortPcpDEEncType is of type 7p1d, 6p2d, 5p3d,
         the cmAccPortPcpDEPairTable can be used to specify 
         alternate pairs of priorities to specify drop eligibility/
         ineligibility."
    ::= { cmEthernetAccPortEntry 98 }

cmEthernetAccPortSSMRemoteMacAddress OBJECT-TYPE
    SYNTAX     MacAddress
    MAX-ACCESS read-only
    STATUS     current
    DESCRIPTION
             "This object allows retrieval of the Remote Mac Address, when
              the port is peering using SSM." 
     ::= { cmEthernetAccPortEntry 99 }

cmEthernetAccPortXgePhyType OBJECT-TYPE
    SYNTAX      XgePhyType  
    MAX-ACCESS  read-write
    STATUS      current
    DESCRIPTION
        "This object allows to specify the PHY type of 10G Ethernet Port.
         10G ports can operate in LAN-PHY or WAN-PHY mode. The default mode is LAN-PHY
         and port rate in this mode is 10Gbps. In WAN-PHY mode the port rate is 9.29Gbps.
         This attribute is only applicable for ports configured to work at speed-10G-full.
         For other speeds the value of this object must be 'not-applicable' and cannot
         be changed.
        "
    ::= { cmEthernetAccPortEntry 100 }

cmEthernetAccPortLoopbackSourceMacControlEnabled OBJECT-TYPE
    SYNTAX      TruthValue  
    MAX-ACCESS  read-write
    STATUS      current
    DESCRIPTION
         "This object allows to Enable/Disable the Acc Port Source MAC 
         Address frame matching criteria for all streams. 
         Not applicable for: efm-oam-remote, efm-oam-remote-timed."
    ::= { cmEthernetAccPortEntry 101 }

cmEthernetAccPortLoopbackDestMacControlEnabled OBJECT-TYPE
    SYNTAX      TruthValue  
    MAX-ACCESS  read-write
    STATUS      current
    DESCRIPTION
         "This object allows to Enable/Disable the Acc Port Destination MAC 
         Address frame matching criteria for all streams. 
         Not applicable for: efm-oam-remote, efm-oam-remote-timed."
    ::= { cmEthernetAccPortEntry 102 }

cmEthernetAccPortLoopbackSourceMacAddress OBJECT-TYPE
    SYNTAX      MacAddress  
    MAX-ACCESS  read-write
    STATUS      current
    DESCRIPTION
         "This object allows to set Acc Port Source MAC Address for frame 
          matching when Acc Port Source MAC Control is enabled."
    ::= { cmEthernetAccPortEntry 103 }

cmEthernetAccPortLoopbackDestMacAddress OBJECT-TYPE
    SYNTAX      MacAddress  
    MAX-ACCESS  read-write
    STATUS      current
    DESCRIPTION
         "This object allows to set Acc Port Destination MAC Address for frame 
          matching when Acc Port Destination MAC Control is enabled."
    ::= { cmEthernetAccPortEntry 104 }

cmEthernetAccPortLoopbackBlockingEnabled OBJECT-TYPE
    SYNTAX      TruthValue  
    MAX-ACCESS  read-write
    STATUS      current
    DESCRIPTION
        "This object allows frame blocking when loopback is active.
         - True: Blocks frames in the non-loopback direction 
           that match the PORT or VLAN received in the 
           non-loopback direction. Discards  frames 
           in the loopback direction that match 
           the PORT or VLAN, but do not match 
           the MAC address criteria,
         - False: No blocking of  frames."
    ::= { cmEthernetAccPortEntry 105 }

cmEthernetAccPortRxDeiAction OBJECT-TYPE
    SYNTAX  RxDeiAction
    MAX-ACCESS read-write
    STATUS     current
    DESCRIPTION
             "This object allows to specify
              the Receive DEI Action."
     ::= { cmEthernetAccPortEntry 106 }

cmEthernetAccPortTxDeiAction OBJECT-TYPE
    SYNTAX  TxDeiAction
    MAX-ACCESS read-write
    STATUS     current
    DESCRIPTION
             "This object allows to specify
              the Transmit DEI Action."
     ::= { cmEthernetAccPortEntry 107 }

cmEthernetAccPortRxDeiOuterTagType OBJECT-TYPE
    SYNTAX  DeiOuterTagType
    MAX-ACCESS read-write
    STATUS     current
    DESCRIPTION
             "This object allows to specify
              the Receive DEI Outer Tag Type."
     ::= { cmEthernetAccPortEntry 108 }

cmEthernetAccPortTxDeiOuterTagType OBJECT-TYPE
    SYNTAX  DeiOuterTagType
    MAX-ACCESS read-write
    STATUS     current
    DESCRIPTION
             "This object allows to specify
              the Transmit DEI Outer Tag Type."
     ::= { cmEthernetAccPortEntry 109 }

cmEthernetAccPortLaserWDMChannel OBJECT-TYPE
    SYNTAX  SfpChannelIdentifier 
    MAX-ACCESS read-write
    STATUS     current
    DESCRIPTION
             "Channel number of WDM tunable XFP setting."
     ::= { cmEthernetAccPortEntry 110 }

cmEthernetAccPortLaserIsTunable OBJECT-TYPE
    SYNTAX  TruthValue 
    MAX-ACCESS read-only
    STATUS     current
    DESCRIPTION
             "Channel number of WDM tunable XFP setting."
     ::= { cmEthernetAccPortEntry 111 }

cmEthernetAccPortLaserFrequency OBJECT-TYPE
    SYNTAX  Unsigned32 
    MAX-ACCESS read-only
    STATUS     current
    DESCRIPTION
             "Channel number of WDM tunable XFP setting."
     ::= { cmEthernetAccPortEntry 112 }

cmEthernetAccPortMediaTypeAutoSelected OBJECT-TYPE
    SYNTAX     EthernetMediaType
    MAX-ACCESS read-only
    STATUS     current
    DESCRIPTION
            "This object provides the auto selected Ethernet Media of the
             Ethernet Access Port."
    ::= { cmEthernetAccPortEntry 113 }

cmEthernetAccPortLowLatencyQueuingEnabled OBJECT-TYPE
    SYNTAX     TruthValue
    MAX-ACCESS read-write
    STATUS     current
    DESCRIPTION
            "This object allows to Enable/Disable the Low Latency Queuing on
             the Ethernet Access Port."
    ::= { cmEthernetAccPortEntry 114 }

cmEthernetAccPortA2nSwapPriorityVIDEnabled OBJECT-TYPE
    SYNTAX     TruthValue
    MAX-ACCESS read-write
    STATUS     current
    DESCRIPTION
            "This object allows to Enable/Disable
             the Swapping of Priority Vlan Id in the A2N direction."
    ::= { cmEthernetAccPortEntry 115 }

cmEthernetAccPortN2aSwapPriorityVIDEnabled OBJECT-TYPE
    SYNTAX     TruthValue
    MAX-ACCESS read-write
    STATUS     current
    DESCRIPTION
            "This object allows to Enable/Disable
             the Swapping of Priority Vlan Id in the N2A direction."
    ::= { cmEthernetAccPortEntry 116 }

cmEthernetAccPortSwapPriorityVID OBJECT-TYPE
    SYNTAX     VlanId
    MAX-ACCESS read-write
    STATUS     current
    DESCRIPTION
            "This object allows to specify the value of
             Vlan Id for the Swapping of Priority Vlan Id operation
             for both the A2N and N2A direction."
    ::= { cmEthernetAccPortEntry 117 }

cmEthernetAccPortDiagnosticMacAddress OBJECT-TYPE
    SYNTAX      MacAddress  
    MAX-ACCESS  read-only
    STATUS      current
    DESCRIPTION
         "This object describes the diagnose mac address for SAT, ECPA, JDSU, Loopback with Override SA etc."
    ::= { cmEthernetAccPortEntry 118 }

cmEthernetAccPortIngressCOSPriority OBJECT-TYPE
    SYNTAX     VlanTagType
    MAX-ACCESS read-write
    STATUS     deprecated
    DESCRIPTION
             "Indicates which VLAN tag to use for PCP Priority to COS mapping 
              when the port Priority Map Mode is 802.1p. Supported values are
              inner-vlantag and outer-vlantag. This attribute is only applicable
              on products when Flowpoint Model is supported.
             
              inner-vlantag: The inner VLAN tag PCP Priority of a frame is 
              used for ingress COS mapping. A frame with no inner VLAN tag 
              (untagged or single-tagged) will have a COS equal to the default
              COS of the port.

              outer-vlantag: The outer VLAN tag PCP Priority of a frame  is used 
              for ingress COS mapping. A frame with no outer VLAN tag (untagged) 
              will have a COS equal to the default COS of the port.

              This attribute has been deprecated and is not supported.  Now,
              the Priority Map Mode indicates whether it is inner or outer.
              Use priomap-8021p(4) for outer and priomap-8021p-inner(5)
              for inner.  "
    DEFVAL { outer-vlantag }
     ::= { cmEthernetAccPortEntry 119 }

cmEthernetAccPortDefaultCOS OBJECT-TYPE
    SYNTAX     Integer32 (0..7)
    MAX-ACCESS read-write
    STATUS     deprecated
    DESCRIPTION
             "The COS assigned to a frame that does not have a valid COS identifier 
              for the Priority Map Mode of the port. This attribute is only applicable
              on products when Flowpoint Model is supported.
            
              This value is assigned to a frame received on a port when:
              - the cmEthernetAccPortPrioMapMode=priomap-8021p, ingressCOSPriority=inner-vlantag; 
                and the frame is untagged
              - the cmEthernetAccPortPrioMapMode=priomap-8021p, ingressCOSPriority=inner-vlantag;
                and the frame has a single VLAN tag
              - the cmEthernetAccPortPrioMapMode=priomap-8021p, ingressCOSPriority=outer-vlantag; 
                and the frame is untagged
              - the cmEthernetAccPortPrioMapMode=priomap-dscp; and the frame does not have an IP ethertype
              - the cmEthernetAccPortPrioMapMode=priomap-tos; and the frame does not have an IP ethertype.

              This attribute has been deprecated and is not supported. The
              Default COS is determined from the flowpoint's associated
              Priority Mapping Profle."
    DEFVAL { 0 }
     ::= { cmEthernetAccPortEntry 120 }

cmEthernetAccPortTrafficModel OBJECT-TYPE
    SYNTAX     EthernetPortTrafficModel
    MAX-ACCESS read-write
    STATUS     current
    DESCRIPTION
             "The Traffic Management connection model available for the port.
              - accessFlow: NID Traffic  Connection model.
              - flowpoint: Multipoint and Aggregation Traffic Connection model."
    DEFVAL { accessFlow }
     ::= { cmEthernetAccPortEntry 121 }

cmEthernetAccPortIndependentShaperBW OBJECT-TYPE
    SYNTAX      TruthValue  
    MAX-ACCESS  read-write
    STATUS      current
    DESCRIPTION
         "This object describes whether the shaper bw independent."
    ::= { cmEthernetAccPortEntry 122 }

cmEthernetAccPortJdsuLoopbackSrcIp OBJECT-TYPE
    SYNTAX      IpAddress  
    MAX-ACCESS  read-only
    STATUS      current
    DESCRIPTION
         "This object is applicable when there is jdsu l3 loopback."
    ::= { cmEthernetAccPortEntry 123 }

cmEthernetAccPortWfqSegmentationCOS OBJECT-TYPE
    SYNTAX      Integer32  
    MAX-ACCESS  read-write
    STATUS      current
    DESCRIPTION
         "This object used to specify the wfq segmentation cos value."
    ::= { cmEthernetAccPortEntry 124 }

cmEthernetAccPortWfqGroupCOS OBJECT-TYPE
    SYNTAX      Integer32  
    MAX-ACCESS  read-write
    STATUS      current
    DESCRIPTION
         "This object used to specify the wfq group cos value."
    ::= { cmEthernetAccPortEntry 125 }

cmEthernetAccPortWfqGroupEirLo OBJECT-TYPE
    SYNTAX      Unsigned32  
    MAX-ACCESS  read-write
    STATUS      current
    DESCRIPTION
         "This object used to specify the wfq group eir low 32 bits value."
    ::= { cmEthernetAccPortEntry 126 }

cmEthernetAccPortWfqGroupEirHi OBJECT-TYPE
    SYNTAX      Unsigned32  
    MAX-ACCESS  read-write
    STATUS      current
    DESCRIPTION
         "This object used to specify the wfq group eir high 32 bits value."
    ::= { cmEthernetAccPortEntry 127 }

cmEthernetAccPortSilentStartControl OBJECT-TYPE
    SYNTAX      TruthValue  
    MAX-ACCESS  read-write
    STATUS      current
    DESCRIPTION
         "Allows enabling/disabling of silent start."
    ::= { cmEthernetAccPortEntry 128 }

cmEthernetAccPortSfpLinkLength OBJECT-TYPE
    SYNTAX     Integer32
    MAX-ACCESS read-only
    STATUS     current
    DESCRIPTION
         "This object provides the SFP Link Length.
          This is applicable only when cmEthernetTrafficPortMediaType is fiber or coppersfp."
    ::= { cmEthernetAccPortEntry 129 }

cmEthernetAccPortOuterTagTpidOverride OBJECT-TYPE
    SYNTAX      TruthValue  
    MAX-ACCESS  read-write
    STATUS      current
    DESCRIPTION
         "This object allows enabling/disabling of Outer Tag TPID override.
          When enabled, values in Outer Tag TPID is applicable on egress
          Ethernet Access Port."
    ::= { cmEthernetAccPortEntry 130 }

cmEthernetAccPortOuterTagTpid OBJECT-TYPE
    SYNTAX     Unsigned32
    MAX-ACCESS read-write
    STATUS     current
    DESCRIPTION
         "This object allows to specify the egress Outer Tag TPID 
          on the Ethernet Access Port."
    ::= { cmEthernetAccPortEntry 131 }

-- Ethernet Port SFP params
cmEthernetAccPortSfpName OBJECT-TYPE
    SYNTAX  DisplayString (SIZE (0..32))
    MAX-ACCESS read-only
    STATUS     current
    DESCRIPTION
         "This object provides the official name of the SFP."
    ::= { cmEthernetAccPortEntry 132 }

cmEthernetAccPortSfpHardwareRevision OBJECT-TYPE
    SYNTAX  DisplayString (SIZE (0..16)) 
    MAX-ACCESS read-only
    STATUS     current
    DESCRIPTION
         "This object provides the hardware revision of the SFP."
    ::= { cmEthernetAccPortEntry 133 }

cmEthernetAccPortPersistentLoopbackControl OBJECT-TYPE
    SYNTAX      TruthValue  
    MAX-ACCESS  read-write
    STATUS      current
    DESCRIPTION
         "This object allows enabling/disabling of Persistent Loopback Control.
          The loopback configuration parameters do not survive restart as typically 
          maintenance actions are not persist. Setting this attribute to true shall 
          persist the loopback configuration parameters. When it is set to false the
          loopback configuration parameters shall not survive a restart."
    ::= { cmEthernetAccPortEntry 134 }

cmEthernetAccPortLoopbackTestReflectorIPv4AddressControl OBJECT-TYPE
    SYNTAX      TruthValue
    MAX-ACCESS  read-write
    STATUS      current
    DESCRIPTION
         "Control that enables/disables Test Reflector IPv4 Address
          to be used for Test Reflector IP Interface."
    ::= { cmEthernetAccPortEntry 135 }

cmEthernetAccPortLoopbackTestReflectorIPv4Address OBJECT-TYPE
    SYNTAX      IpAddress
    MAX-ACCESS  read-write
    STATUS      current
    DESCRIPTION
         "This is the Test Reflector Interface IPv4 address."
    ::= { cmEthernetAccPortEntry 136 }

cmEthernetAccPortLoopbackTestReflectorIPv6AddressControl OBJECT-TYPE
    SYNTAX      TruthValue
    MAX-ACCESS  read-write
    STATUS      current
    DESCRIPTION
         "Control that enables/disables Test Reflector IPv6 Address
          to be used for Test Reflector IP Interface."
    ::= { cmEthernetAccPortEntry 137 }

cmEthernetAccPortLoopbackTestReflectorIPv6Address OBJECT-TYPE
    SYNTAX      Ipv6Address
    MAX-ACCESS  read-write
    STATUS      current
    DESCRIPTION
         "This is the Test Reflector Interface IPv6 address."
    ::= { cmEthernetAccPortEntry 138 }

cmEthernetAccPortPowerdDeviceDetection OBJECT-TYPE
    SYNTAX      ToggleValue  
    MAX-ACCESS  read-write
    STATUS      current
    DESCRIPTION
         "This object allows to manage (enable/disable) Power Over Ethernet Detection."
    ::= { cmEthernetAccPortEntry 139 }


cmEthernetAccPortPoEStatus OBJECT-TYPE
    SYNTAX     PoEStatus
    MAX-ACCESS read-only
    STATUS     current
    DESCRIPTION
         "This object provides the status of Power Over Ethernet Detection."
     ::= { cmEthernetAccPortEntry 140 }

-- Ethernet Port SFP params
cmEthernetAccPortSfpIdentifierValue OBJECT-TYPE
    SYNTAX     SfpIdentifierValue
    MAX-ACCESS read-only
    STATUS     current
    DESCRIPTION
         "This object provides the SFP identifier value."
     ::= { cmEthernetAccPortEntry 141 }

--
--  Ethernet Access Port Control Protocol Disposition 
--
cmEthernetAccPortCpdTable  OBJECT-TYPE
    SYNTAX      SEQUENCE OF CmEthernetAccPortCpdEntry
    MAX-ACCESS  not-accessible
    STATUS      current
    DESCRIPTION
            "A list of entries corresponding to Ethernet Access Port 
             Control Protocol Disposition.  

             This table is only
             applicable for FSP150CM Hub Shelf Release 3.x."
    ::= { cmFacilityObjects 2 }

cmEthernetAccPortCpdEntry OBJECT-TYPE
    SYNTAX      CmEthernetAccPortCpdEntry 
    MAX-ACCESS  not-accessible
    STATUS      current
    DESCRIPTION
            "A conceptual row in the cmEthernetAccPortCpdTable. 
             These entries represent a Control Protocol Disposition 
             filtering criteria on the Ethernet Access Port."
    INDEX { neIndex, shelfIndex, slotIndex, cmEthernetAccPortIndex, 
            cmEthernetAccPortCpdIndex }
    ::= { cmEthernetAccPortCpdTable 1 }


CmEthernetAccPortCpdEntry ::= SEQUENCE {
    -- Index
    cmEthernetAccPortCpdIndex             Integer32,

    -- Filtering Criteria
    cmEthernetAccPortCpdFilterType        CmControlProtocolFilterType,
    cmEthernetAccPortCpdFilterDescr       DisplayString,
    cmEthernetAccPortCpdDispType          CmControlProtocolDispType,
    cmEthernetAccPortCpdMacAddressMatch   MacAddress,
    cmEthernetAccPortCpdMacAddressMask    MacAddress,
    cmEthernetAccPortCpdEthertype         Integer32,
    cmEthernetAccPortCpdEthertypeMask     Integer32,
    cmEthernetAccPortCpdSubtype           Integer32,
    cmEthernetAccPortCpdSubtypeMask       Integer32
}


cmEthernetAccPortCpdIndex OBJECT-TYPE
    SYNTAX      Integer32 (1..65535)
    MAX-ACCESS  read-only
    STATUS      current
    DESCRIPTION
            "An arbitrary integer index value used to uniquely identify
             this CPD Service Entry."
    ::= { cmEthernetAccPortCpdEntry 1 }

cmEthernetAccPortCpdFilterType OBJECT-TYPE
    SYNTAX     CmControlProtocolFilterType
    MAX-ACCESS read-only
    STATUS     current
    DESCRIPTION
            "This enables specification of type of CPD Filter."
    ::= { cmEthernetAccPortCpdEntry 2 }

cmEthernetAccPortCpdFilterDescr OBJECT-TYPE
    SYNTAX  DisplayString (SIZE (0..32)) 
    MAX-ACCESS read-only
    STATUS     current
    DESCRIPTION
            "This provides description of CPD Filter."
    ::= { cmEthernetAccPortCpdEntry 3 }

cmEthernetAccPortCpdDispType OBJECT-TYPE
    SYNTAX     CmControlProtocolDispType
    MAX-ACCESS read-write
    STATUS     current
    DESCRIPTION
            "This enables specification of disposion type of CPD Filter."
    ::= { cmEthernetAccPortCpdEntry 4 }

cmEthernetAccPortCpdMacAddressMatch OBJECT-TYPE
    SYNTAX     MacAddress
    MAX-ACCESS read-write
    STATUS     current
    DESCRIPTION
         "This enables provides the Filter MAC Address to match."
    ::= { cmEthernetAccPortCpdEntry 5 }

cmEthernetAccPortCpdMacAddressMask OBJECT-TYPE
    SYNTAX     MacAddress
    MAX-ACCESS read-write
    STATUS     current
    DESCRIPTION
         "This enables provides the Filter MAC Address Mask to match."
    ::= { cmEthernetAccPortCpdEntry 6 }

cmEthernetAccPortCpdEthertype OBJECT-TYPE
    SYNTAX     Integer32 (0..65535)
    MAX-ACCESS read-write
    STATUS     current
    DESCRIPTION
         "This enables provides the Filter Ethertype to match."
    ::= { cmEthernetAccPortCpdEntry 7 }

cmEthernetAccPortCpdEthertypeMask OBJECT-TYPE
    SYNTAX     Integer32
    MAX-ACCESS read-write
    STATUS     current
    DESCRIPTION
         "This enables provides the Filter Ethertype Mask to match."
    ::= { cmEthernetAccPortCpdEntry 8 }

cmEthernetAccPortCpdSubtype OBJECT-TYPE
    SYNTAX     Integer32
    MAX-ACCESS read-write
    STATUS     current
    DESCRIPTION
         "This enables provides the Filter Subtype to match."
    ::= { cmEthernetAccPortCpdEntry 9 }

cmEthernetAccPortCpdSubtypeMask OBJECT-TYPE
    SYNTAX     Integer32
    MAX-ACCESS read-write
    STATUS     current
    DESCRIPTION
         "This enables provides the Filter Subtype Mask to match."
    ::= { cmEthernetAccPortCpdEntry 10 }


--
--  Ethernet Access Port Cable Length Benchmark 
--
cmEthernetAccPortClbTable  OBJECT-TYPE
    SYNTAX      SEQUENCE OF CmEthernetAccPortClbEntry
    MAX-ACCESS  not-accessible
    STATUS      current
    DESCRIPTION
            "A list of entries corresponding to Ethernet Access Port 
             Cable Length Benchmark."
    ::= { cmFacilityObjects 3 }

cmEthernetAccPortClbEntry OBJECT-TYPE
    SYNTAX      CmEthernetAccPortClbEntry 
    MAX-ACCESS  not-accessible
    STATUS      current
    DESCRIPTION
            "A conceptual row in the cmEthernetAccPortClbTable. 
             These entries represent Cable Length Benchmarks 
             on the Ethernet Access Port."
    INDEX { neIndex, shelfIndex, slotIndex, cmEthernetAccPortIndex, 
            cmEthernetAccPortClbIndex }
    ::= { cmEthernetAccPortClbTable 1 }


CmEthernetAccPortClbEntry ::= SEQUENCE {
    cmEthernetAccPortClbIndex          Integer32,
    cmEthernetAccPortClbEnabled        TruthValue,
    cmEthernetAccPortClbLength         DisplayString,
    cmEthernetAccPortClbDescr          DisplayString
}

cmEthernetAccPortClbIndex OBJECT-TYPE
    SYNTAX      Integer32 (1..5)
    MAX-ACCESS  read-only
    STATUS      current
    DESCRIPTION
            "An integer index value used to uniquely identify
             this Cable Length Benchmark Entry specification."
    ::= { cmEthernetAccPortClbEntry 1 }

cmEthernetAccPortClbEnabled OBJECT-TYPE
    SYNTAX     TruthValue
    MAX-ACCESS read-write
    STATUS     current
    DESCRIPTION
            "This enables specification of Cable Length Benchmark entry."
    ::= { cmEthernetAccPortClbEntry 2 }

cmEthernetAccPortClbLength OBJECT-TYPE
    SYNTAX  DisplayString 
    MAX-ACCESS read-write
    STATUS     current
    DESCRIPTION
            "Cable length of Cable Points Entry. The cable length is of
             the form XXX[.YY] where XX can be any integer value and YY
             allows precision of 2 decimals after the floating point. Note
             that .YY is optional."
    ::= { cmEthernetAccPortClbEntry 3 }

cmEthernetAccPortClbDescr OBJECT-TYPE
    SYNTAX     DisplayString (SIZE (0..256))
    MAX-ACCESS read-write
    STATUS     current
    DESCRIPTION
         "A textual string containing description of cable span."
    ::= { cmEthernetAccPortClbEntry 4 }

--
--  Ethernet Flow 
--
cmFlowTable  OBJECT-TYPE
    SYNTAX      SEQUENCE OF CmFlowEntry
    MAX-ACCESS  not-accessible
    STATUS      current
    DESCRIPTION
            "A list of entries corresponding to Ethernet Flows 
             for configuration purposes.  If the corresponding
             Ethernet Access Port's  cmEthernetAccPortMode is 
             connection-oriented and cmEthernetAccPortSvcType is epl,
             there exists a single Flow in this table.  

             No Flow creation or deletion is allowed on this table
             for FSP150CM NTU based services.
                
             Since Fsp150 R5.6CC release this table is used to manage 2 types of Flows:
               - Access Port Flow as in the previous releases
               - Tranparent Flow (new in 5.6CC)
              A Transparent Flow is Flow between Network-1 and Network-2 ports used
              to convey pass-thru traffic in the ring topology e.g. ERP.
              Few of the existing attributes will have new semantix for Transperent Flow.
              Transparent Flow is a NE level object and hence has different indexing 
              than the Access Port Flow. The valid indices are neIndex and cmFlowIndex.
              The remaining indices will have constant values as follows:
                  shelfIndex = 1
                  slotIndex = 255
                  cmEthernetAccPortIndex = 0
              "
    ::= { cmFacilityObjects 4 }

cmFlowEntry OBJECT-TYPE
    SYNTAX      CmFlowEntry 
    MAX-ACCESS  not-accessible
    STATUS      current
    DESCRIPTION
            "A conceptual row in the cmFlowTable. These entries represent
             an Ethernet Flow."
    INDEX { neIndex, shelfIndex, slotIndex, cmEthernetAccPortIndex, cmFlowIndex }
    ::= { cmFlowTable 1 }

CmFlowEntry ::= SEQUENCE {
    -- Flow Index/Id
    cmFlowIndex                           Integer32,
    cmFlowCircuitName                     DisplayString,

    -- State Management params
    cmFlowAdminState                      AdminState,
    cmFlowOperationalState                OperationalState,
    cmFlowSecondaryState                  SecondaryState,

    -- Flow Properties
    cmFlowType                            CmFlowType,
    cmFlowMultiCOS                        TruthValue,
    cmFlowA2NCIR                          Unsigned32,
    cmFlowA2NEIR                          Unsigned32,
    cmFlowN2ARateLimitingEnabled          TruthValue,
    cmFlowN2ACIR                          Unsigned32,
    cmFlowN2AEIR                          Unsigned32,
  
    --SNMP row creation 
    cmFlowStorageType                     StorageType,
    cmFlowRowStatus                       RowStatus,

    --New objects available with FSP150CC GE206 devices (Release 4.1CC)
    cmFlowTrafficType                     FlowTrafficType,
    cmFlowCOS                             Integer32,

    --flow membership
    cmFlowVlanMemberList                  DisplayString, 
    cmFlowAction                          FlowVlanActionType, 
    cmFlowActionVlan                      DisplayString, 
    cmFlowUntaggedMemberEnabled           TruthValue,

    --flow bandwidth
    cmFlowA2NCIRHi                        Unsigned32,
    cmFlowA2NEIRHi                        Unsigned32,
    cmFlowN2ACIRHi                        Unsigned32,
    cmFlowN2AEIRHi                        Unsigned32,
    cmFlowHCOSMgmtEnabled                 TruthValue,
    cmFlowGuaranteedA2NBandwidthLo        Unsigned32,
    cmFlowGuaranteedA2NBandwidthHi        Unsigned32,
    cmFlowMaximumA2NBandwidthLo           Unsigned32,
    cmFlowMaximumA2NBandwidthHi           Unsigned32,

    --flow tag management
    cmFlowCTagControl                     FlowTagControl,
    cmFlowCTagVlanId                      VlanId,
    cmFlowCTagVlanPriority                VlanPriority,
    cmFlowCTagMatchRxPrio                 TruthValue,
    cmFlowSTagControl                     FlowTagControl,
    cmFlowSTagVlanId                      VlanId,
    cmFlowSTagVlanPriority                VlanPriority,
    cmFlowOuterTagPrioEnabled             TruthValue,

    --N2A COS Priority
    cmFlowN2ACOSPriorityTagType           VlanTagType,

    --flow frame loss thresholds
    cmFlowESFramesLossThreshold           Integer32,
    cmFlowSESFramesLossThresholdRatio     Integer32,

    --New objects available with FSP150CC GE201 (Release 4.3CC)
    cmFlowPolicingEnabled                 TruthValue,
    cmFlowPreserveSTagProperties          TruthValue,
    cmFlowInnerTagPrioEnabled             TruthValue,

    --New objects available with FSP150CC GE206 (Release 4.4.2CC)
    cmFlowN2AOuterTagPrioEnabled          TruthValue,

    --New objects available with FSP150CC GE206V (Release 5.3CC)
    cmFlowA2NShapingType                  ShapingType, 
    cmFlowN2AShapingType                  ShapingType,

    cmFlowSTagMatchRxPrio                 TruthValue,

    --New objects available with FSP150CC GE206V (Release 5.4CC)
    cmFlowAutoBandwidthConfigEnabled      TruthValue,

    --New objects available with FSP150CC GE206V/GE201/GE206/XG210 (Release 5.6CC)
    cmFlowPort1                           VariablePointer,
    cmFlowPort2                           VariablePointer,
    cmFlowPolicingControl                 PolicingControl,
    cmFlowAutoCIRPercentage               Integer32,
    cmFlowLoopAvoidanceObject             VariablePointer,
    cmFlowConfigType                      FlowConfigType,
    cmFlowN2NForwardingEnabled            TruthValue,

    --New objects available with FSP150CC GE206V/XG210 (Release 7.1CC)
    cmFlowA2NMulticastRateLimitControl    TruthValue,
    cmFlowA2NMulticastRateLimitLo         Unsigned32,
    cmFlowA2NMulticastRateLimitHi         Unsigned32,
    cmFlowA2NBroadcastRateLimitControl    TruthValue,
    cmFlowA2NBroadcastRateLimitLo         Unsigned32,
    cmFlowA2NBroadcastRateLimitHi         Unsigned32,
    cmFlowA2NCombinedRateLimitControl     TruthValue,
    cmFlowA2NCombinedRateLimitLo          Unsigned32,
    cmFlowA2NCombinedRateLimitHi          Unsigned32,
    cmFlowRefPrioMapProfile               VariablePointer,
    cmFlowRefEoMplsPwObject               VariablePointer,
    cmFlowRefN2APrioMapProfile            VariablePointer,
    cmFlowSecureBlockingEnabled           TruthValue,
    cmFlowRefConnectGuardFlowList         DisplayString,
    cmFlowSecureStateList                 DisplayString,
    cmFlowIndependentA2NShaperBW          TruthValue,
    cmFlowWfqSegmentationCOS              Integer32,
    cmFlowWfqGroupCOS                     Integer32,
    cmFlowWfqGroupEirLo                   Unsigned32,
    cmFlowWfqGroupEirHi                   Unsigned32
}

cmFlowIndex OBJECT-TYPE
    SYNTAX      Integer32 (1..400)
    MAX-ACCESS  read-create
    STATUS      current
    DESCRIPTION
            "The integer index value corresponding to an Ethernet Flow." 
    ::= { cmFlowEntry 1 }

cmFlowCircuitName    OBJECT-TYPE
    SYNTAX      DisplayString (SIZE(0..256))
    MAX-ACCESS  read-create
    STATUS      current
    DESCRIPTION
         "This object allows SNMP management entities to provide a
          circuit identifier with the Flow."
     ::= { cmFlowEntry 2 }

-- State Management params
cmFlowAdminState OBJECT-TYPE
    SYNTAX      AdminState 
    MAX-ACCESS  read-write
    STATUS      current
    DESCRIPTION
            "This object represents the Administrative State of the Flow." 
    ::= { cmFlowEntry 3 }

cmFlowOperationalState OBJECT-TYPE
    SYNTAX      OperationalState 
    MAX-ACCESS  read-only
    STATUS      current
    DESCRIPTION
            "This object represents the Operational State of the Flow." 
    ::= { cmFlowEntry 4 }

cmFlowSecondaryState OBJECT-TYPE
    SYNTAX      SecondaryState 
    MAX-ACCESS  read-only
    STATUS      current
    DESCRIPTION
            "This object represents the Secondary State of the Flow." 
    ::= { cmFlowEntry 5 }

cmFlowType OBJECT-TYPE
    SYNTAX      CmFlowType
    MAX-ACCESS  read-create
    STATUS      current
    DESCRIPTION
            "This object represents the type of the Flow." 
    ::= { cmFlowEntry 6 }

cmFlowMultiCOS OBJECT-TYPE
    SYNTAX     TruthValue
    MAX-ACCESS read-create
    STATUS     current
    DESCRIPTION
         "This object allows specification of multiple COS (Class of Service)
          Flow." 
     ::= { cmFlowEntry 7 }

cmFlowA2NCIR OBJECT-TYPE
    SYNTAX     Unsigned32
    MAX-ACCESS read-create
    STATUS     current
    DESCRIPTION
         "This object represents the Commited Information
          Rate(CIR) of an Flow in the Access to Network (A2N) direction. 
          For a portbased Flow(FSP150CM NTU, CPMR), 
          this object is not settable. This value represents the lower 
          32-bits of the CIR. For a Multi COS flow, this value
          is settable only at creation time.
          
          In case of Tranparent Flow this object represents N1 to N2 CIR."
     ::= { cmFlowEntry 8 }

cmFlowA2NEIR OBJECT-TYPE
    SYNTAX     Unsigned32
    MAX-ACCESS read-create
    STATUS     current
    DESCRIPTION
         "This object represents the Excess Information
          Rate(EIR) on an Flow in the Access to Network (A2N) direction.  
          For a portbased Flow(FSP150CM NTU, CPMR), 
          this object is not settable.  This value represents the lower
          32-bits of the CIR. For a Multi COS flow, this value
          is settable only at creation time.

          In case of Tranparent Flow this object represents N1 to N2 EIR."
     ::= { cmFlowEntry 9 }

cmFlowN2ARateLimitingEnabled    OBJECT-TYPE
    SYNTAX      TruthValue
    MAX-ACCESS  read-create
    STATUS      current
    DESCRIPTION
         "This object allows management of the N2A rate limiting,
          independent of A2N rate limiting. When not enabled,
          N2A specification is the same as A2N.
          
          This object is not applicable for Tranparent Flow; the value should be FALSE."
    ::= { cmFlowEntry 10 }

cmFlowN2ACIR OBJECT-TYPE
    SYNTAX     Unsigned32
    MAX-ACCESS read-create
    STATUS     current
    DESCRIPTION
         "This object represents the Commited Information
          Rate(CIR) of an Flow in the Network to Access (N2A) direction. 
          For a portbased Flow, this object is not settable. This is
          only settable if cmFlowN2ARateLimitingEnabled is enabled.

          In case of Tranparent Flow this object represents N2 to N1 CIR."
     ::= { cmFlowEntry 11 }

cmFlowN2AEIR OBJECT-TYPE
    SYNTAX     Unsigned32
    MAX-ACCESS read-create
    STATUS     current
    DESCRIPTION
         "This object represents the Excess Information
          Rate(CIR) of an Flow in the Network to Access (N2A) direction. 
          For a portbased Flow, this object is not settable. This is
          only settable if cmFlowN2ARateLimitingEnabled is enabled.

          In case of Tranparent Flow this object represents N2 to N1 EIR."
     ::= { cmFlowEntry 12 }

cmFlowStorageType OBJECT-TYPE
    SYNTAX     StorageType
    MAX-ACCESS read-create
    STATUS     current
    DESCRIPTION
            "The type of storage configured for this entry."
    ::= { cmFlowEntry 13 }

cmFlowRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmFlowRowStatus supported are
            createAndGo(4) and destroy(6).  All mandatory attributes
            must be specified in a single SNMP SET request with
            cmFlowRowStatus value as createAndGo(4).
            Upon successful row creation, this object has a
            value of active(1).

            The cmFlowRowStatus object may be modified if
            the associated instance of this object is equal to active(1).
            
            Note that flow creation and deletion is only supported
            with access port in connection-oriented evpl mode."
    ::= { cmFlowEntry 14 }

--New objects available with FSP150CC GE206 devices (Release 4.1CC)
cmFlowTrafficType OBJECT-TYPE 
    SYNTAX     FlowTrafficType
    MAX-ACCESS read-only
    STATUS     current
    DESCRIPTION
            "This object provides information on the type of traffic flow 
             supported by the system, i.e.'shaped-only' flows (support
             only shaping) or 'policed-shaped' (support policing and shaping) flows.  
             'shaped-only' flow exists for FSP150CM NTU and CPMR access ports. 
             'policed-shaped' flows are supported in FSP150CC devices.
             Please note that this object refers to how traffic profiles
             are managed on devices and is independent of the policing enabling/disabling
             feature."
    ::= { cmFlowEntry 15 }

cmFlowCOS  OBJECT-TYPE
    SYNTAX     Integer32 (0..7)
    MAX-ACCESS read-create
    STATUS     current
    DESCRIPTION
            "This object allows specification of the COS (Class of Service)
             value for the Traffic Flow. This value is used at flow creation
             time to identify the COS level of the A2N and N2A shaper.
             In case of a multi-COS flow, this value is not applicable
             when multiple policers/shapers exist on the flow.
             This object is also applicable to specify the COS of a
             connection-oriented epl service."
    ::= { cmFlowEntry 16 }

--flow membership
cmFlowVlanMemberList OBJECT-TYPE
    SYNTAX     DisplayString (SIZE (0..512))
    MAX-ACCESS read-create
    STATUS     current
    DESCRIPTION
         "This object is applicable only when Port is in connection-oriented
          evpl mode. This attribute is mandatory if creation of
          connection-oriented evpl regular flow is desired.
          It allows specification of VLAN members of the Flow.
          VLAN members are comma separated, of the form X-Y where X is the
          VLAN Id and Y is the VLAN Priority.  VLAN members can be of
          the form X-* or X (vlan X with all priorities), 
          *-Y (all vlans with priority Y), and X1:X2 
          (range of vlans from X1 to X2, all priorities). Members 
          with specific VLAN Id and specific VLAN Priority are not supported.
          Once the flow is created, this attribute can only be updated
          using cmFlowAction and cmFlowActionVlan objects."
     ::= { cmFlowEntry 17 }

cmFlowAction OBJECT-TYPE
    SYNTAX     FlowVlanActionType 
    MAX-ACCESS read-write
    STATUS     current
    DESCRIPTION
         "This object is applicable only when Port is in connection-oriented
          evpl mode and the cmFlowType is regular.  This object allows to
          add or remove the VLAN members specified by
          cmFlowActionVlan object.  SNMP manager must first
          configure the VLAN member to be added/removed in the object
          cmFlowActionVlan and then should specify
          cmFlowAction on whether to add/remove the specified
          VLAN member."
     ::= { cmFlowEntry 18 }

cmFlowActionVlan OBJECT-TYPE
    SYNTAX     DisplayString (SIZE (0..16))
    MAX-ACCESS read-create
    STATUS     current
    DESCRIPTION
         "This object is applicable only when Port is in connection-oriented
          evpl mode. This object allows adding/removing VLAN members
          to a connection-oriented evpl regular flow.
          VLAN member is of the form X-Y where X is the
          VLAN Id and Y is the VLAN Priority.  VLAN members can be of
          the form X-* (vlan X with all priorities), 
          *-Y (all vlans with priority Y), and X1:X2 
          (range of vlans from X1 to X2, all priorities).  
          Members with specific VLAN Id and 
          specific VLAN Priority are not supported.
          In order to add/remove VLAN member to a flow, user must
          specify this object with appropriate VLAN and then invoke
          cmFlowAction."
     ::= { cmFlowEntry 19 }

cmFlowUntaggedMemberEnabled OBJECT-TYPE
    SYNTAX     TruthValue 
    MAX-ACCESS read-create
    STATUS     current
    DESCRIPTION
         "This object is applicable only when Port is in connection-oriented
          evpl mode for a regular flow as well as default flow. 
          This object allows to specify whether or not the flow 
          supports untagged traffic."
     ::= { cmFlowEntry 20 }

--flow bandwidth
cmFlowA2NCIRHi OBJECT-TYPE
    SYNTAX     Unsigned32
    MAX-ACCESS read-create
    STATUS     current
    DESCRIPTION
         "This object represents the Commited Information
          Rate(CIR) of an Flow in the Access to Network (A2N) direction. 
          This value represents the upper 32 bits of CIR (lower is 
          provided in cmFlowA2NCIR). For a Multi COS flow, this value
          is settable only at creation time.

          In case of Tranparent Flow this object represents N1 to N2 CIR."
     ::= { cmFlowEntry 21 }

cmFlowA2NEIRHi OBJECT-TYPE
    SYNTAX     Unsigned32
    MAX-ACCESS read-create
    STATUS     current
    DESCRIPTION
         "This object represents the Excess Information
          Rate(EIR) on an Flow in the Access to Network (A2N) direction.  
          For a portbased Flow(FSP150CM NTU, CPMR), 
          this object is not settable.  This value represents the higher
          32-bits of the CIR.  For a Multi COS flow, this value
          is settable only at creation time.

          In case of Tranparent Flow this object represents N1 to N2 EIR."
     ::= { cmFlowEntry 22 }

cmFlowN2ACIRHi OBJECT-TYPE
    SYNTAX     Unsigned32
    MAX-ACCESS read-create
    STATUS     current
    DESCRIPTION
         "This object represents the Commited Information
          Rate(CIR) of an Flow in the Network to Access (N2A) direction. 
          This value represents the upper 32 bits of CIR (lower is 
          provided in cmFlowN2ACIR). For a Multi COS flow, this value
          is settable only at creation time. This is
          only settable if cmFlowN2ARateLimitingEnabled is enabled.

          In case of Tranparent Flow this object represents N2 to N1 CIR."
     ::= { cmFlowEntry 23 }

cmFlowN2AEIRHi OBJECT-TYPE
    SYNTAX     Unsigned32
    MAX-ACCESS read-create
    STATUS     current
    DESCRIPTION
         "This object represents the Excess Information
          Rate(EIR) on an Flow in the Network to Access (N2A) direction.  
          For a portbased Flow(FSP150CM NTU, CPMR), 
          this object is not settable.  This value represents the higher
          32-bits of the CIR.  For a Multi COS flow, this value
          is settable only at creation time. This is
          only settable if cmFlowN2ARateLimitingEnabled is enabled.

          In case of Tranparent Flow this object represents N2 to N1 EIR."
     ::= { cmFlowEntry 24 }

cmFlowHCOSMgmtEnabled OBJECT-TYPE
    SYNTAX     TruthValue
    MAX-ACCESS read-create
    STATUS     current
    DESCRIPTION
         "This object allows management of Hierarchical COS on the Flow." 
     ::= { cmFlowEntry 25 }

cmFlowGuaranteedA2NBandwidthLo OBJECT-TYPE
    SYNTAX     Unsigned32
    MAX-ACCESS read-write
    STATUS     current
    DESCRIPTION
         "This object supports the Hierarchical Class of Service (HCOS)
          feature.  It is only applicable for a flow with multiple
          class of services. This allows the provisioning of 
          guaranteed bandwidth (lower 32 bits) of a flow.
          This value must be greater than or equal to the sum of all
          individual COS CIRs.

          In case of Tranparent Flow this object represents N1 to N2 and N2 to N1
          guaranteed bandwidth."
     ::= { cmFlowEntry 26 }

cmFlowGuaranteedA2NBandwidthHi OBJECT-TYPE
    SYNTAX     Unsigned32
    MAX-ACCESS read-write
    STATUS     current
    DESCRIPTION
         "This object supports the Hierarchical Class of Service (HCOS)
          feature.  It is only applicable for a flow with multiple
          class of services. This allows the provisioning of 
          guaranteed bandwidth (upper 32 bits) of a flow.
          This value must be greater than or equal to the sum of all
          individual COS CIRs.

          In case of Tranparent Flow this object represents N1 to N2 and N2 to N1
          guaranteed bandwidth."
     ::= { cmFlowEntry 27 }

cmFlowMaximumA2NBandwidthLo OBJECT-TYPE
    SYNTAX     Unsigned32
    MAX-ACCESS read-write
    STATUS     current
    DESCRIPTION
         "This object supports the Hierarchical Class of Service (HCOS)
          feature.  It is only applicable for a flow with multiple
          class of services. This allows the provisioning of 
          maximum bandwidth (lower 32 bits) of a flow.  This is the peak
          limit of a flow.  This value must be greater than or equal 
          to the sum of all individual COS CIRs.

          In case of Tranparent Flow this object represents N1 to N2 and N2 to N1
          maximum bandwidth."
     ::= { cmFlowEntry 28 }

cmFlowMaximumA2NBandwidthHi OBJECT-TYPE
    SYNTAX     Unsigned32
    MAX-ACCESS read-write
    STATUS     current
    DESCRIPTION
         "This object supports the Hierarchical Class of Service (HCOS)
          feature.  It is only applicable for a flow with multiple
          class of services. This allows the provisioning of 
          maximum bandwidth (upper 32 bits) of a flow.  This is the peak
          limit of a flow.  This value must be greater than or equal 
          to the sum of all individual COS CIRs.

          In case of Tranparent Flow this object represents N1 to N2 and N2 to N1
          maximum bandwidth."
     ::= { cmFlowEntry 29 }

--flow tag management
cmFlowCTagControl  OBJECT-TYPE
    SYNTAX     FlowTagControl
    MAX-ACCESS read-create
    STATUS     current
    DESCRIPTION
         "This object allows specification of the tag management 
          operation on the C-TAG.  Supported types are 'push', 'pushvid',
          'swapvid' and 'none'. If the type is 'push', 
          the VLAN Id (cmFlowCTagVlanId) and priority
          (cmFlowCTagVlanPriority) are pushed onto the frame;
          if the type is 'pushvid', only the VLAN Id (12 bits) is pushed,
          the Priority is copied from incoming tag's priority;
          if the type is 'swapvid', only the VLAN Id (12 bits) are 
          swapped with the specified cmFlowCTagVlanId; 
          if the type is 'none', no C-TAG management is performed.

          This object is not applicable for Tranparent Flow; the value should be 'none'."
     ::= { cmFlowEntry 30 }

cmFlowCTagVlanId  OBJECT-TYPE
    SYNTAX     VlanId
    MAX-ACCESS read-create
    STATUS     current
    DESCRIPTION
         "This object allows specification of the VLAN Id to
          be pushed or swapped, based on the value of cmFlowCTagControl.
          It is applicable for 'push', 'swapvid' and 'pushvid'
          control types.

          This object is not applicable for Tranparent Flow; the value should be 0."
     ::= { cmFlowEntry 31 }

cmFlowCTagVlanPriority  OBJECT-TYPE
    SYNTAX     VlanPriority
    MAX-ACCESS read-create
    STATUS     current
    DESCRIPTION
         "This object allows specification of the VLAN Priority to
          be pushed or swapped, based on the value of cmFlowCTagControl.
          It is applicable for 'push' control type.

          This object is not applicable for Tranparent Flow; the value should be 0."
     ::= { cmFlowEntry 32 }

cmFlowCTagMatchRxPrio  OBJECT-TYPE
    SYNTAX     TruthValue
    MAX-ACCESS read-create
    STATUS     current
    DESCRIPTION
         "This object is used to specify whether the C-TAG  priority
          be used or ignored for traffic in the N2A direction.
          This is only applicable if  cmFlowCTagControl
          is 'push'.

          This object is not applicable for Tranparent Flow; the value should be FALSE."
     ::= { cmFlowEntry 33 }

cmFlowSTagControl  OBJECT-TYPE
    SYNTAX     FlowTagControl
    MAX-ACCESS read-create
    STATUS     current
    DESCRIPTION
         "This object allows specification of the tag management 
          operation on the S-TAG.  Supported types are 'push', 'swapvid', and 'none'.
          If the type is 'push', the VLAN Id (cmFlowSTagVlanId) and priority
          (cmFlowSTagVlanPriority) are pushed onto the frame; if the type is
          'swapvid', the VLAN Id(12 bits) is swapped with the specified
          cmFlowSTagVlanId; type is 'none', no S-TAG manament is performed.

          This object is not applicable for Tranparent Flow; the value should be 'none'."
     ::= { cmFlowEntry 34 }

cmFlowSTagVlanId  OBJECT-TYPE
    SYNTAX     VlanId
    MAX-ACCESS read-create
    STATUS     current
    DESCRIPTION
         "This object allows specification of the VLAN Id to
          be pushed, based on the value of cmFlowSTagControl.
          It is applicable for 'push' control type.

          This object is not applicable for Tranparent Flow; the value should be 0."
     ::= { cmFlowEntry 35 }

cmFlowSTagVlanPriority  OBJECT-TYPE
    SYNTAX     VlanPriority
    MAX-ACCESS read-create
    STATUS     current
    DESCRIPTION
         "This object allows specification of the VLAN Priority to
          be pushed, based on the value of cmFlowSTagControl.
          It is applicable for 'push' control type.

          This object is not applicable for Tranparent Flow; the value should be 0."
     ::= { cmFlowEntry 36 }

cmFlowOuterTagPrioEnabled  OBJECT-TYPE
    SYNTAX     TruthValue
    MAX-ACCESS read-create
    STATUS     current
    DESCRIPTION
         "This object is used to specify whether the flow
          participates in outer-tag priority swap.  The Priority 
          Mapping Table cmPrioMapTable allows the A2N outer-tag
          priority to be specified based on incoming priority at
          Access Port (based on priority mapping mode - 802.1P, TOS, DSCP).

          This object is not applicable for Tranparent Flow; the value should be FALSE."
     ::= { cmFlowEntry 37 }

cmFlowN2ACOSPriorityTagType  OBJECT-TYPE
    SYNTAX     VlanTagType
    MAX-ACCESS read-create
    STATUS     current
    DESCRIPTION
         "This object is used to specify whether the flow
          uses the inner-tag or the outer-tag in determining the COS (Class of Service) in the
          N2A direction.  This object is applicable in the case of a Multi COS Flow.

          This object is not supported for Tranparent Flow;"
     ::= { cmFlowEntry 38 }

--flow frame loss thresholds
cmFlowESFramesLossThreshold  OBJECT-TYPE
    SYNTAX     Integer32 (1..2147483647)
    MAX-ACCESS read-write
    STATUS     current
    DESCRIPTION
         "This object is used to specify the number of frames lost
          per flow that starts counting Errored Seconds (ES) on the flow.
          This functionality is applicable if the flow is monitored
          using the Y.1731 ESA functionality." 
     ::= { cmFlowEntry 39 }
           
cmFlowSESFramesLossThresholdRatio OBJECT-TYPE 
    SYNTAX     Integer32 (1..100)
    MAX-ACCESS read-write
    STATUS     current
    DESCRIPTION
         "This object is used to specify the frame-loss ratio 
          per flow that starts counting Severely Errored Seconds (SES) 
          on the flow.
          This functionality is applicable if the flow is monitored
          using the Y.1731 ESA functionality." 
     ::= { cmFlowEntry 40 }

cmFlowPolicingEnabled OBJECT-TYPE
    SYNTAX     TruthValue 
    MAX-ACCESS read-create
    STATUS     current
    DESCRIPTION
         "This object is applicable only when Port is in connection-oriented mode.
          This object is applicable to both epl and evpl mode flows. 
          This object allows to enable/disable the policing function on the flow." 
     ::= { cmFlowEntry 41 }

cmFlowPreserveSTagProperties OBJECT-TYPE
    SYNTAX     TruthValue 
    MAX-ACCESS read-create
    STATUS     current
    DESCRIPTION
         "This object is applicable only when Port is in connection-oriented mode.
          This object is applicable to evpl mode Regular flows, when S-TAG control
          is specified as SWAPVID.
          When enabled, this attribute preserves the EtherType (0x88a8) and 
          DEI (Drop Eligibility Indicator) bit
          in the incoming S-TAG (both from Access and Network Port perspective)
          into the outgoing S-TAG.
          When not enabled, the incoming tag is considered as a Q-TAG (0x8100)
          and both EtherType and CFI (Canonical Form Indicator) bits are over-written 
          by the S-TAG Ethertype (0x88a8) and DEI bit. 

          This object is not applicable for Tranparent Flow; the value should be FALSE." 
     ::= { cmFlowEntry 42 }

cmFlowInnerTagPrioEnabled  OBJECT-TYPE
    SYNTAX     TruthValue
    MAX-ACCESS read-create
    STATUS     current
    DESCRIPTION
         "This object is used to specify whether the flow
          participates in inner-tag (second) priority swap.  The Priority 
          Mapping Table cmPrioMapTable allows the A2N inner-tag
          priority to be specified based on incoming priority at
          Access Port (based on priority mapping mode - 802.1P, TOS, DSCP).

          This object is not applicable for Tranparent Flow; the value should FALSE." 
     ::= { cmFlowEntry 43 }

cmFlowN2AOuterTagPrioEnabled  OBJECT-TYPE
    SYNTAX     TruthValue
    MAX-ACCESS read-create
    STATUS     current
    DESCRIPTION
         "This object is used to specify whether the flow
          participates in outer-tag priority swap in the A2N direction.
          The Priority Mapping Table cmNetPortPrioMapTable allows the N2A outer-tag
          priority to be specified based on incoming priority at
          Network Port (based on priority mapping mode - 802.1P, TOS, DSCP).

          This object is not applicable for Tranparent Flow; the value should be FALSE." 
     ::= { cmFlowEntry 44 }

cmFlowA2NShapingType  OBJECT-TYPE
    SYNTAX     ShapingType  
    MAX-ACCESS read-create
    STATUS     current
    DESCRIPTION
         "This object is used to specify whether the traffic in A2N direction
          passing through this flow is shaped by port-level or flow-level Shapers.
          In case of portbased flows the value of this attribute is flow-based and 
          cannot be changed. In case of regular and default flows Fsp150 products
          may support both port-based and flow-based shaping."
     ::= { cmFlowEntry 45 }

cmFlowN2AShapingType  OBJECT-TYPE
    SYNTAX     ShapingType  
    MAX-ACCESS read-create
    STATUS     current
    DESCRIPTION
         "This object is used to specify whether the traffic in N2A direction
          passing through this flow is shaped by port-level or flow-level Shapers.
          In case of portbased flows the value of this attribute is flow-based and 
          cannot be changed. In case of regular and default flows Fsp150 products
          may support both port-based and flow-based shaping."
     ::= { cmFlowEntry 46 }

cmFlowSTagMatchRxPrio  OBJECT-TYPE
    SYNTAX     TruthValue
    MAX-ACCESS read-create
    STATUS     current
    DESCRIPTION
         "This object indicates whether the S-TAG  priority
          is used or ignored for traffic in the N2A direction.
          This is only applicable if  cmFlowSTagControl
          is 'push'.

          This object is not applicable for Tranparent Flow; the value should be FALSE." 
     ::= { cmFlowEntry 47 }

cmFlowAutoBandwidthConfigEnabled OBJECT-TYPE
    SYNTAX     TruthValue
    MAX-ACCESS read-create
    STATUS     current
    DESCRIPTION
         "This object is applicable for Flows on the PWE3 Ethernet Backplane Port.
          When set to TRUE bandwidth of this Flow will be automatically adjusted when
          PWE3 SATOPs are provisioned. The bandwidth will be adjusted based on the
          TDM entities of associated SATOPs.
          Flow on ports other than PWE3 Ethernet Backplane Port will always have
          this value set to FALSE and it is not configurable."
     ::= { cmFlowEntry 48 }

cmFlowPort1 OBJECT-TYPE
    SYNTAX     VariablePointer
    MAX-ACCESS read-create
    STATUS     current
    DESCRIPTION
         "This object specifies a physical or logical port on the Access side of the 
          Flow. This can be Access Port, Access LAG or Access Split Horizion Group.
          
          In case of Tranparent Flow this object specifies port1 of the Flow which is
          Network-1."
     ::= { cmFlowEntry 49 }

cmFlowPort2 OBJECT-TYPE
    SYNTAX     VariablePointer
    MAX-ACCESS read-create
    STATUS     current
    DESCRIPTION
         "This object specifies a physical or logical port on the Network side of the 
          Flow. This can be Network Port, Network LAG, Network Split Horizion Group
          ERP or Protection Group.

          In case of Tranparent Flow this object specifies port2 of the Flow which is
          Network-2."
     ::= { cmFlowEntry 50 }

cmFlowPolicingControl OBJECT-TYPE
    SYNTAX     PolicingControl
    MAX-ACCESS read-create
    STATUS     current
    DESCRIPTION
         "This object specifies the direction(s) in which Poling is enabled on traffic 
          within this Flow when cmFlowPolicingEnabled is TRUE."

     ::= { cmFlowEntry 51 }

cmFlowAutoCIRPercentage OBJECT-TYPE
    SYNTAX     Integer32 (0..100)
    MAX-ACCESS read-create
    STATUS     current
    DESCRIPTION
         "This object specifies the percentage of available CIR on the Network 
          ports assigned to this Flow when cmFlowAutoBandwidthConfigEnabled is TRUE.  
          The flow guaranteedBW is set to available BW multiplied by this value.
          This object is only applicable to Tranparent Flow.
          The value of this object should be 0 for Access Flow."
     ::= { cmFlowEntry 52 }

cmFlowLoopAvoidanceObject OBJECT-TYPE
    SYNTAX     VariablePointer
    MAX-ACCESS read-create
    STATUS     current
    DESCRIPTION
          "This object specifies the Loop Avoidance instance to which this Flow belongs.
           This object is appicable only for Transparent Flow and should point to the
           ERP instance for which this Flows carries pass-thru traffic.
           
           In case of Access Flow the value of this object should be zeroDotZero."
     ::= { cmFlowEntry 53 }

cmFlowConfigType OBJECT-TYPE
    SYNTAX     FlowConfigType
    MAX-ACCESS read-only
    STATUS     current
    DESCRIPTION
          "This object specifies if this Flow is an Access Flow or Pass-thru Flow."
     ::= { cmFlowEntry 54 }

cmFlowN2NForwardingEnabled OBJECT-TYPE
    SYNTAX     TruthValue
    MAX-ACCESS read-create
    STATUS     current
    DESCRIPTION
          "This object is used to specify whether n2n forwarding 
           is enabled on particular Flow."
     ::= { cmFlowEntry 55 }

cmFlowA2NMulticastRateLimitControl OBJECT-TYPE
    SYNTAX     TruthValue
    MAX-ACCESS read-write
    STATUS     current
    DESCRIPTION
        "Whether multicast frames are limited per Flow."
    ::= { cmFlowEntry 56 }

cmFlowA2NMulticastRateLimitLo OBJECT-TYPE
    SYNTAX     Unsigned32
    MAX-ACCESS read-write
    STATUS     current
    DESCRIPTION
        "The rate limit for multicast packets per Flow.
         When cmFlowA2NMulticastRateLimiteControl is set and value is 0,
         then all multicast frames are dropped.

         This object represents the low-order 32-bits."
    ::= { cmFlowEntry 57 }

cmFlowA2NMulticastRateLimitHi OBJECT-TYPE
    SYNTAX     Unsigned32
    MAX-ACCESS read-write
    STATUS     current
    DESCRIPTION
        "The rate limit for multicast packets per Flow.
         When cmFlowA2NMulticastRateLimiteControl is set and value is 0,
         then all multicast frames are dropped.

         This object represents the high-order 32-bits."
    ::= { cmFlowEntry 58 }

cmFlowA2NBroadcastRateLimitControl OBJECT-TYPE
    SYNTAX     TruthValue
    MAX-ACCESS read-write
    STATUS     current
    DESCRIPTION
        "Whether broadcast frames are limited per Flow."
    ::= { cmFlowEntry 59 }

cmFlowA2NBroadcastRateLimitLo OBJECT-TYPE
    SYNTAX     Unsigned32
    MAX-ACCESS read-write
    STATUS     current
    DESCRIPTION
        "The rate limit for multicast packets per Flow.
         When cmFlowA2NBroadcastRateLimiteControl is set and value is 0,
         then all multicast frames are dropped.

         This object represents the low-order 32-bits."
    ::= { cmFlowEntry 60 }

cmFlowA2NBroadcastRateLimitHi OBJECT-TYPE
    SYNTAX     Unsigned32
    MAX-ACCESS read-write
    STATUS     current
    DESCRIPTION
        "The rate limit for multicast packets per Flow.
         When cmFlowA2NBroadcastRateLimiteControl is set and value is 0,
         then all multicast frames are dropped.

         This object represents the high-order 32-bits."
    ::= { cmFlowEntry 61 }

cmFlowA2NCombinedRateLimitControl OBJECT-TYPE
    SYNTAX     TruthValue
    MAX-ACCESS read-write
    STATUS     current
    DESCRIPTION
        "Whether both multicast and broadcast frames are limited per Flow."
    ::= { cmFlowEntry 62 }

cmFlowA2NCombinedRateLimitLo OBJECT-TYPE
    SYNTAX     Unsigned32
    MAX-ACCESS read-write
    STATUS     current
    DESCRIPTION
        "The rate limit for multicast packets per Flow.
         When cmFlowA2NCombinedRateLimiteControl is set and value is 0,
         then all multicast frames are dropped.

         This object represents the low-order 32-bits."
    ::= { cmFlowEntry 63 }

cmFlowA2NCombinedRateLimitHi OBJECT-TYPE
    SYNTAX     Unsigned32
    MAX-ACCESS read-write
    STATUS     current
    DESCRIPTION
        "The rate limit for multicast packets per Flow.
         When cmFlowA2NCombinedRateLimiteControl is set and value is 0,
         then all multicast frames are dropped.

         This object represents the high-order 32-bits."
    ::= { cmFlowEntry 64 }

cmFlowRefPrioMapProfile OBJECT-TYPE
    SYNTAX      VariablePointer
    MAX-ACCESS  read-write
    STATUS      current
    DESCRIPTION
            "This object used to specify the flow's profile." 
    ::= { cmFlowEntry 65 }

cmFlowRefEoMplsPwObject OBJECT-TYPE
    SYNTAX     VariablePointer
    MAX-ACCESS read-write
    STATUS     current
    DESCRIPTION
          "This object specifies EoMpls Pw object OID."
     ::= { cmFlowEntry 66 }

cmFlowRefN2APrioMapProfile OBJECT-TYPE
    SYNTAX      VariablePointer
    MAX-ACCESS  read-write
    STATUS      current
    DESCRIPTION
            "This object used to specify the flow's N2A direction profile." 
    ::= { cmFlowEntry 67 }

cmFlowSecureBlockingEnabled OBJECT-TYPE
    SYNTAX     TruthValue
    MAX-ACCESS read-write
    STATUS     current
    DESCRIPTION
          "This object can be used to enable/disable secure block."
     ::= { cmFlowEntry 68 }

cmFlowRefConnectGuardFlowList OBJECT-TYPE
    SYNTAX     DisplayString
    MAX-ACCESS read-write
    STATUS     current
    DESCRIPTION
          "This object specifies the secure flow list, 
           it should be f3ConnectGuardFlowIndex value list split with comma."
     ::= { cmFlowEntry 69 }

cmFlowSecureStateList OBJECT-TYPE
    SYNTAX     DisplayString
    MAX-ACCESS read-only
    STATUS     current
    DESCRIPTION
          "This object specifies the secure state list, 
           it should be secure state value list and split with comma.
           For detailed description how to identify values, please see 
           FlowSecState in CM-COMMON-MIB."
     ::= { cmFlowEntry 70 }

cmFlowIndependentA2NShaperBW OBJECT-TYPE
    SYNTAX      TruthValue
    MAX-ACCESS  read-write
    STATUS      current
    DESCRIPTION
            "This object used to specify the flow related A2N shaper BW whether independent." 
    ::= { cmFlowEntry 71 }

cmFlowWfqSegmentationCOS OBJECT-TYPE
    SYNTAX      Integer32
    MAX-ACCESS  read-write
    STATUS      current
    DESCRIPTION
            "This object used to specify the flow related wfq segmentation COS value." 
    ::= { cmFlowEntry 72 }

cmFlowWfqGroupCOS OBJECT-TYPE
    SYNTAX      Integer32
    MAX-ACCESS  read-write
    STATUS      current
    DESCRIPTION
            "This object used to specify the flow related wfq group COS value." 
    ::= { cmFlowEntry 73 }

cmFlowWfqGroupEirLo OBJECT-TYPE
    SYNTAX      Unsigned32
    MAX-ACCESS  read-write
    STATUS      current
    DESCRIPTION
            "This object used to specify the flow related wfq group EIR low 32 bits value." 
    ::= { cmFlowEntry 74 }

cmFlowWfqGroupEirHi OBJECT-TYPE
    SYNTAX      Unsigned32
    MAX-ACCESS  read-write
    STATUS      current
    DESCRIPTION
            "This object used to specify the flow related wfq group EIR high 32 bits value." 
    ::= { cmFlowEntry 75 }

--
--  Ethernet Flow Control Protocol Disposition 
--
cmFlowCpdTable  OBJECT-TYPE
    SYNTAX      SEQUENCE OF CmFlowCpdEntry
    MAX-ACCESS  not-accessible
    STATUS      current
    DESCRIPTION
            "A list of entries corresponding to Flow 
             Control Protocol Disposition.
             This table is only
             applicable for FSP150CM Hub Shelf Release 3.x."
    ::= { cmFacilityObjects 5 }

cmFlowCpdEntry OBJECT-TYPE
    SYNTAX      CmFlowCpdEntry 
    MAX-ACCESS  not-accessible
    STATUS      current
    DESCRIPTION
            "A conceptual row in the cmFlowCpdTable. 
             These entries represent a Control Protocol Disposition 
             filtering criteria on the Ethernet Network Port."
    INDEX { neIndex, shelfIndex, slotIndex, cmEthernetAccPortIndex, 
            cmFlowIndex, cmFlowCpdIndex }
    ::= { cmFlowCpdTable 1 }


CmFlowCpdEntry ::= SEQUENCE {
    -- Index
    cmFlowCpdIndex             Integer32,

    -- Filter parameters
    cmFlowCpdFilterType        CmControlProtocolFilterType,
    cmFlowCpdFilterDescr       DisplayString,
    cmFlowCpdDispType          CmControlProtocolDispType,
    cmFlowCpdMacAddressMatch   MacAddress,
    cmFlowCpdMacAddressMask    MacAddress,
    cmFlowCpdEthertype         Integer32,
    cmFlowCpdEthertypeMask     Integer32,
    cmFlowCpdSubtype           Integer32,
    cmFlowCpdSubtypeMask       Integer32
}

cmFlowCpdIndex OBJECT-TYPE
    SYNTAX      Integer32 (1..65535)
    MAX-ACCESS  read-only
    STATUS      current
    DESCRIPTION
            "An arbitrary integer index value used to uniquely identify
             this CPD Service Entry."
    ::= { cmFlowCpdEntry 1 }

cmFlowCpdFilterType OBJECT-TYPE
    SYNTAX     CmControlProtocolFilterType
    MAX-ACCESS read-only
    STATUS     current
    DESCRIPTION
            "This enables specification of type of CPD Filter."
    ::= { cmFlowCpdEntry 2 }

cmFlowCpdFilterDescr OBJECT-TYPE
    SYNTAX  DisplayString (SIZE (0..32)) 
    MAX-ACCESS read-only
    STATUS     current
    DESCRIPTION
            "This provides description of CPD Filter."
    ::= { cmFlowCpdEntry 3 }

cmFlowCpdDispType OBJECT-TYPE
    SYNTAX     CmControlProtocolDispType
    MAX-ACCESS read-write
    STATUS     current
    DESCRIPTION
            "This enables specification of disposion type of CPD Filter."
    ::= { cmFlowCpdEntry 4 }

cmFlowCpdMacAddressMatch OBJECT-TYPE
    SYNTAX     MacAddress
    MAX-ACCESS read-write
    STATUS     current
    DESCRIPTION
         "This enables provides the Filter MAC Address to match."
    ::= { cmFlowCpdEntry 5 }

cmFlowCpdMacAddressMask OBJECT-TYPE
    SYNTAX     MacAddress
    MAX-ACCESS read-write
    STATUS     current
    DESCRIPTION
         "This enables provides the Filter MAC Address Mask to match."
    ::= { cmFlowCpdEntry 6 }

cmFlowCpdEthertype OBJECT-TYPE
    SYNTAX     Integer32 (0..65535)
    MAX-ACCESS read-write
    STATUS     current
    DESCRIPTION
         "This enables provides the Filter Ethertype to match."
    ::= { cmFlowCpdEntry 7 }

cmFlowCpdEthertypeMask OBJECT-TYPE
    SYNTAX     Integer32
    MAX-ACCESS read-write
    STATUS     current
    DESCRIPTION
         "This enables provides the Filter Ethertype Mask to match."
    ::= { cmFlowCpdEntry 8 }

cmFlowCpdSubtype OBJECT-TYPE
    SYNTAX     Integer32
    MAX-ACCESS read-write
    STATUS     current
    DESCRIPTION
         "This enables provides the Filter Subtype to match."
    ::= { cmFlowCpdEntry 9 }

cmFlowCpdSubtypeMask OBJECT-TYPE
    SYNTAX     Integer32
    MAX-ACCESS read-write
    STATUS     current
    DESCRIPTION
         "This enables provides the Filter Subtype Mask to match."
    ::= { cmFlowCpdEntry 10 }


--
--  Ethernet Flow Quality of Service Shaper 
--
cmQosShaperTable  OBJECT-TYPE
    SYNTAX      SEQUENCE OF CmQosShaperEntry
    MAX-ACCESS  not-accessible
    STATUS      current
    DESCRIPTION
            "A list of entries corresponding to Ethernet Quality of Service 
             Shaper for configuration purposes."
    ::= { cmFacilityObjects 6 }

cmQosShaperEntry OBJECT-TYPE
    SYNTAX      CmQosShaperEntry 
    MAX-ACCESS  not-accessible
    STATUS      current
    DESCRIPTION
            "A conceptual row in the cmQosShaperTable. 
             These entries represent a Quality of Service Shaper."
    INDEX { neIndex, shelfIndex, slotIndex, cmEthernetAccPortIndex, 
            cmFlowIndex, cmQosShaperTypeIndex, cmQosShaperIndex }
    ::= { cmQosShaperTable 1 }

CmQosShaperEntry ::= SEQUENCE {
    -- QOS Shaper Index/Id
    cmQosShaperTypeIndex           Integer32,
    cmQosShaperIndex               Integer32,
    cmQosShaperDirection           TrafficDirection,

    -- State Management params
    cmQosShaperAdminState          AdminState,
    cmQosShaperOperationalState    OperationalState,
    cmQosShaperSecondaryState      SecondaryState,

    -- QOS Shaper Properties
    cmQosShaperCIR                 Unsigned32,
    cmQosShaperCBS                 Unsigned32,
    cmQosShaperEIR                 Unsigned32,
    cmQosShaperEBS                 Unsigned32,
    cmQosShaperBufferSize          Unsigned32,

    --SNMP row creation 
    cmQosShaperStorageType         StorageType,
    cmQosShaperRowStatus           RowStatus,

    --New objects available with FSP150CC GE206 device  (Release 4.1CC)
    cmQosShaperCOS                 Integer32,
    cmQosShaperCIRHi               Unsigned32,
    cmQosShaperEIRHi               Unsigned32,
    cmQosShaperSoamCIRLo           Unsigned32,
    cmQosShaperSoamCIRHi           Unsigned32,
    cmQosShaperSoamEIRLo           Unsigned32,
    cmQosShaperSoamEIRHi           Unsigned32,
    
    -- wred threshold
    cmQosShaperWredGreenMinQueueThreshold       Unsigned32,
    cmQosShaperWredGreenMaxQueueThreshold       Unsigned32,
    cmQosShaperWredGreenDropProbability         Unsigned32,
    cmQosShaperWredYellowMinQueueThreshold      Unsigned32,
    cmQosShaperWredYellowMaxQueueThreshold      Unsigned32,
    cmQosShaperWredYellowDropProbability        Unsigned32,
    cmQosShaperAvgFrameSizeBeforeFragment       Integer32,
    cmQosShaperWfqWeight                        Integer32
}

cmQosShaperTypeIndex OBJECT-TYPE
    SYNTAX      Integer32 (1..4)
    MAX-ACCESS  read-create
    STATUS      current
    DESCRIPTION
          "The unique index value corresponding to a Quality of Service 
           Shaper's direction.
           Values 1 and 2 are applicable to the Access Flow Shaper:
           - value of 1 stands for A2N direction,
           - value of 2 stands for N2A direction.
           Values 3 and 4 are applicable to Pass-thru Flow Shaper (new in 5.6CC release):
           - value of 3 stands for N1toN2 direction
           - value of 4 stands for N2toN1 direction
           "
    ::= { cmQosShaperEntry 1 }

cmQosShaperIndex OBJECT-TYPE
    SYNTAX      Integer32 (1..16)
    MAX-ACCESS  read-create
    STATUS      current
    DESCRIPTION
            "The unique integer index value corresponding to a 
             Quality of Service Shaper.
             
             In release 5.6CC the range is extended to 1..16 to support duplicate
             A2N shapers on a Flow. The duplicate shapers are created under a Flow 
             if network interface of the Flow is ERP Group or Split Horizon Group. 
             In case of multi-cos Flow indices 1..8 represent shapers of COS 0..7 
             going to Network 1 port; indices 9..16 represent shapers for COS 0..7 
             going to Network 2 port.
             In case of single-cos Flow index 1 represents shaper going to Network 1
             port; index 9 represents shaper going to Network 2 port.
             "
    ::= { cmQosShaperEntry 2 }

cmQosShaperDirection OBJECT-TYPE
    SYNTAX      TrafficDirection 
    MAX-ACCESS  read-only
    STATUS      current
    DESCRIPTION
            "The direction of the Quality of Service Shaper."
    ::= { cmQosShaperEntry 3 }

-- State Management params
cmQosShaperAdminState OBJECT-TYPE
    SYNTAX      AdminState 
    MAX-ACCESS  read-write
    STATUS      current
    DESCRIPTION
            "This object represents the Administrative State of 
             the QOS Shaper." 
    ::= { cmQosShaperEntry 4 }

cmQosShaperOperationalState OBJECT-TYPE
    SYNTAX      OperationalState 
    MAX-ACCESS  read-only
    STATUS      current
    DESCRIPTION
            "This object represents the Operational State of the QOS Shaper." 
    ::= { cmQosShaperEntry 5 }

cmQosShaperSecondaryState OBJECT-TYPE
    SYNTAX      SecondaryState 
    MAX-ACCESS  read-only
    STATUS      current
    DESCRIPTION
            "This object represents the Secondary State of the QOS Shaper." 
    ::= { cmQosShaperEntry 6 }

cmQosShaperCIR OBJECT-TYPE
    SYNTAX     Unsigned32
    MAX-ACCESS read-create
    STATUS     current
    DESCRIPTION
         "This object represents the Commited Information
          Rate(CIR) (Lower 32 bits)of a Shaper."
     ::= { cmQosShaperEntry 7 }

cmQosShaperCBS OBJECT-TYPE
    SYNTAX     Unsigned32
    MAX-ACCESS read-create
    STATUS     current
    DESCRIPTION
         "This object represents the Commited Burst Size (CBS) of the Shaper."
     ::= { cmQosShaperEntry 8 }

cmQosShaperEIR OBJECT-TYPE
    SYNTAX     Unsigned32
    MAX-ACCESS read-create
    STATUS     current
    DESCRIPTION
         "This object represents the Excess Information
          Rate(EIR) (Lower 32 bits) of a Shaper."
     ::= { cmQosShaperEntry 9 }

cmQosShaperEBS OBJECT-TYPE
    SYNTAX     Unsigned32
    MAX-ACCESS read-create
    STATUS     current
    DESCRIPTION
         "This object represents the Excess Burst Size (EBS) of the Shaper."
     ::= { cmQosShaperEntry 10 }

cmQosShaperBufferSize OBJECT-TYPE
    SYNTAX     Unsigned32
    MAX-ACCESS read-create
    STATUS     current
    DESCRIPTION
         "This object represents the Buffer Size of the Shaper."
     ::= { cmQosShaperEntry 11 }

cmQosShaperStorageType OBJECT-TYPE
    SYNTAX     StorageType
    MAX-ACCESS read-create
    STATUS     current
    DESCRIPTION
            "The type of storage configured for this entry."
    ::= { cmQosShaperEntry 12 }

cmQosShaperRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmQosShaperRowStatus supported are
            createAndGo(4) and destroy(6).  All mandatory attributes
            must be specified in a single SNMP SET request with
            cmQosShaperRowStatus value as createAndGo(4).
            Upon successful row creation, this object has a
            value of active(1).

            The cmQosShaperRowStatus object may be modified if
            the associated instance of this object is equal to active(1)."
    ::= { cmQosShaperEntry 13 }

cmQosShaperCOS OBJECT-TYPE
    SYNTAX     Integer32 (0..7)
    MAX-ACCESS read-only
    STATUS     current
    DESCRIPTION
            "This object provides the COS (Class of Service)
             value for the QOS Shaper."
    ::= { cmQosShaperEntry 14 }

cmQosShaperCIRHi OBJECT-TYPE
    SYNTAX     Unsigned32
    MAX-ACCESS read-create
    STATUS     current
    DESCRIPTION
         "This object represents the Commited Information
          Rate(CIR) (Higher 32 bits) of a Shaper."
     ::= { cmQosShaperEntry 15 }

cmQosShaperEIRHi OBJECT-TYPE
    SYNTAX     Unsigned32
    MAX-ACCESS read-create
    STATUS     current
    DESCRIPTION
         "This object represents the Excess Information
          Rate(EIR) (Higher 32 bits) on the Shaper."
     ::= { cmQosShaperEntry 16 }

cmQosShaperSoamCIRLo OBJECT-TYPE
    SYNTAX     Unsigned32
    MAX-ACCESS read-create
    STATUS     current
    DESCRIPTION
         "This object represents the Soam Commited Information
          Rate(SOAM-CIR) (Lower 32 bits) of a Shaper."
     ::= { cmQosShaperEntry 17 }

cmQosShaperSoamCIRHi OBJECT-TYPE
    SYNTAX     Unsigned32
    MAX-ACCESS read-create
    STATUS     current
    DESCRIPTION
         "This object represents the Soam Commited Information
          Rate(SOAM-CIR) (Higher 32 bits) on the Shaper."
     ::= { cmQosShaperEntry 18 }

cmQosShaperSoamEIRLo OBJECT-TYPE
    SYNTAX     Unsigned32
    MAX-ACCESS read-create
    STATUS     current
    DESCRIPTION
         "This object represents the Soam Excess Information
          Rate(SOAM-EIR) (Lower 32 bits) of a Shaper."
     ::= { cmQosShaperEntry 19 }

cmQosShaperSoamEIRHi OBJECT-TYPE
    SYNTAX     Unsigned32
    MAX-ACCESS read-create
    STATUS     current
    DESCRIPTION
         "This object represents the Soam Excess Information
          Rate(SOAM-EIR) (Higher 32 bits) on the Shaper."
     ::= { cmQosShaperEntry 20 }

cmQosShaperWredGreenMinQueueThreshold OBJECT-TYPE
    SYNTAX     Unsigned32
    MAX-ACCESS read-create
    STATUS     current
    DESCRIPTION
         "This object represents the Wred green packet min queue threshold value."
     ::= { cmQosShaperEntry 21 }

cmQosShaperWredGreenMaxQueueThreshold OBJECT-TYPE
    SYNTAX     Unsigned32
    MAX-ACCESS read-create
    STATUS     current
    DESCRIPTION
         "This object represents the Wred green packet max queue threshold value."
     ::= { cmQosShaperEntry 22 }

cmQosShaperWredGreenDropProbability OBJECT-TYPE
    SYNTAX     Unsigned32
    MAX-ACCESS read-create
    STATUS     current
    DESCRIPTION
         "This object represents the Wred green packet drop probability."
     ::= { cmQosShaperEntry 23 }

cmQosShaperWredYellowMinQueueThreshold OBJECT-TYPE
    SYNTAX     Unsigned32
    MAX-ACCESS read-create
    STATUS     current
    DESCRIPTION
         "This object represents the Wred yellow packet min queue threshold value."
     ::= { cmQosShaperEntry 24 }

cmQosShaperWredYellowMaxQueueThreshold OBJECT-TYPE
    SYNTAX     Unsigned32
    MAX-ACCESS read-create
    STATUS     current
    DESCRIPTION
         "This object represents the Wred yellow packet max queue threshold value."
     ::= { cmQosShaperEntry 25 }

cmQosShaperWredYellowDropProbability OBJECT-TYPE
    SYNTAX     Unsigned32
    MAX-ACCESS read-create
    STATUS     current
    DESCRIPTION
         "This object represents the Wred yellow packet drop probability."
     ::= { cmQosShaperEntry 26 }

cmQosShaperAvgFrameSizeBeforeFragment OBJECT-TYPE
    SYNTAX     Integer32
    MAX-ACCESS read-write
    STATUS     current
    DESCRIPTION
         "This object specifies the average frame size before fragmentation."
     ::= { cmQosShaperEntry 27 }

cmQosShaperWfqWeight OBJECT-TYPE
    SYNTAX     Integer32
    MAX-ACCESS read-write
    STATUS     current
    DESCRIPTION
         "This object specifies the wfq weight value."
     ::= { cmQosShaperEntry 28 }

--
--  Ethernet Network Port 
--
cmEthernetNetPortTable  OBJECT-TYPE
    SYNTAX      SEQUENCE OF CmEthernetNetPortEntry
    MAX-ACCESS  not-accessible
    STATUS      current
    DESCRIPTION
            "A list of entries corresponding to Ethernet Network Port 
             Facilities for configuration purposes."
    ::= { cmFacilityObjects 7 }

cmEthernetNetPortEntry OBJECT-TYPE
    SYNTAX      CmEthernetNetPortEntry 
    MAX-ACCESS  not-accessible
    STATUS      current
    DESCRIPTION
            "A conceptual row in the cmEthernetNetPortTable."
    INDEX { neIndex, shelfIndex, slotIndex, cmEthernetNetPortIndex }
    ::= { cmEthernetNetPortTable 1 }

CmEthernetNetPortEntry ::= SEQUENCE {
    -- Port Indices 
    cmEthernetNetPortIndex                           Integer32,
    cmEthernetNetPortIfIndex                         InterfaceIndex,
    cmEthernetNetPortEntityIndex                     PhysicalIndex,

    -- State Management params
    cmEthernetNetPortAdminState                      AdminState,
    cmEthernetNetPortOperationalState                OperationalState,
    cmEthernetNetPortSecondaryState                  SecondaryState,

    -- Generic Port params
    cmEthernetNetPortMTU                             Integer32,

    -- Generic Ethernet Port params
    cmEthernetNetPortMediaType                       EthernetMediaType,
    cmEthernetNetPortConfigSpeed                     EthernetPortSpeed,
    cmEthernetNetPortNegotiatedSpeed                 EthernetPortSpeed,
    cmEthernetNetPortMDIXType                        CmEthernetMDIXType,
    cmEthernetNetPortJumboFramesEnabled              TruthValue,
    cmEthernetNetPortSfpVendorName                   DisplayString,
    cmEthernetNetPortSfpPartNumber                   DisplayString,
    cmEthernetNetPortSfpSerialNumber                 DisplayString,
    cmEthernetNetPortSfpDateOfManufacture            DateAndTime,
    cmEthernetNetPortSfpConnectorValue               SfpConnectorValue,

    -- EtherJack Diagnosis params
    cmEthernetNetPortInitiateDiag                    CmEthernetDiagAction,
    cmEthernetNetPortDiagnosePair1Cond               CmDiagCableCondType,
    cmEthernetNetPortDiagnosePair2Cond               CmDiagCableCondType,
    cmEthernetNetPortDiagnosePair3Cond               CmDiagCableCondType,
    cmEthernetNetPortDiagnosePair4Cond               CmDiagCableCondType,
    cmEthernetNetPortDiagnoseAutoNegCond             CmDiagAutoNegCondType,
    cmEthernetNetPortDiagnoseLpbkCond                CmDiagLpbkCondType,
    cmEthernetNetPortDiagnoseEfmLpbkCond             CmDiagEfmOamLpbkCondType,
    cmEthernetNetPortDiagnoseResult                  DisplayString,
    cmEthernetNetPortDiagnoseTestStatus              CmDiagTestStatus,
    cmEthernetNetPortDiagnoseTestTime                DateAndTime,

    -- Ethernet Loopback params
    cmEthernetNetPortLoopbackConfig                  CmLoopbackType,
    cmEthernetNetPortLoopbackStatus                  CmLoopbackType,
    cmEthernetNetPortLoopbackTime                    Integer32,
    cmEthernetNetPortLoopbackSwapSADA                CmSwapSADAType,
    cmEthernetNetPortOuterVlanLoopbackMask           INTEGER,
    cmEthernetNetPortOuterVlanLoopback1              DisplayString,
    cmEthernetNetPortOuterVlanLoopback2              DisplayString,
    cmEthernetNetPortOuterVlanLoopback3              DisplayString,
    cmEthernetNetPortInnerVlanLoopbackMask           INTEGER,
    cmEthernetNetPortInnerVlanLoopback1              DisplayString,
    cmEthernetNetPortInnerVlanLoopback2              DisplayString,
    cmEthernetNetPortInnerVlanLoopback3              DisplayString,

    -- Link Loss Forwarding params 
    cmEthernetNetPortLinkLossFwdEnabled              TruthValue,
    cmEthernetNetPortLinkLossFwdSignalType           CmLinkLossFwdSignalType,
    cmEthernetNetPortLinkLossFwdTriggerTypes         CmLinkLossFwdTriggerTypes,
    cmEthernetNetPortLinkLossFwdDelay                Integer32,
    cmEthernetNetPortLinkLossFwdActive               TruthValue,
    cmEthernetNetPortLinkLossFwdPartnerEnabled       TruthValue,
    cmEthernetNetPortLinkLossFwdLocalLinkId          Integer32,
    cmEthernetNetPortLinkLossFwdRemoteLinkIds        CmRemoteLinkIds,

    -- OAM params
    cmEthernetNetPortOamId                           Integer32,
    cmEthernetNetPortOamAdminDisposition             CmControlProtocolDispType,
    cmEthernetNetPortOamDiscoveryState               CmOamDiscoveryState,
    cmEthernetNetPortOamLocalVarRtrvsEnabled         TruthValue,
    cmEthernetNetPortOamLocalLinkEventsEnabled       TruthValue,
    cmEthernetNetPortOamLocalOamLoopbacksSupported   TruthValue,
    cmEthernetNetPortOamLocalUnidirSupportEnabled    TruthValue,
    cmEthernetNetPortOamLocalMaxPDUSize              Integer32,
    cmEthernetNetPortOamLocalMode                    CmOamMode,
    cmEthernetNetPortOamRemoteMacAddress             MacAddress,
    cmEthernetNetPortOamRemoteVarRtrvsEnabled        TruthValue,
    cmEthernetNetPortOamRemoteLinkEventsEnabled      TruthValue,
    cmEthernetNetPortOamRemoteOamLoopbacksSupported  TruthValue,
    cmEthernetNetPortOamRemoteUnidirSupportEnabled   TruthValue,
    cmEthernetNetPortOamRemoteMaxPDUSize             Integer32,
    cmEthernetNetPortOamRemoteMode                   CmOamMode,

    -- Ethernet Port Traffic params
    cmEthernetNetPortRxPauseDisposition              CmControlProtocolDispType,
    cmEthernetNetPortTxPauseEnabled                  TruthValue,
    cmEthernetNetPortAfpType                         CmAfpType,

    --New objects available with FSP150CC GE206 device (Release 4.1CC)
    -- Generic Ethernet Port params
    cmEthernetNetPortMDIXStatus                      CmEthernetMDIXType,
    cmEthernetNetPortSfpReach                        Integer32,
    cmEthernetNetPortSfpLaserWaveLength              Integer32,
    cmEthernetNetPortSfpMediaType                    SfpMediaType,

    -- EFM OAM params
    cmEthernetNetPortOamEnabled                      TruthValue,
    cmEthernetNetPortOamAdminState                   CmOamAdminState,

    -- Ethernet Port Traffic params
    cmEthernetNetPortShapingEnabled                  TruthValue,
    cmEthernetNetPortShapedSpeedLo                   Unsigned32,
    cmEthernetNetPortShapedSpeedHi                   Unsigned32,
    cmEthernetNetPortQinQEtherType                   Unsigned32,

    -- LLF params
    cmEthernetNetPortLinkLossFwdTxActionType         CmLinkLossFwdTxActionType,
    cmEthernetNetPortLinkLossFwdRxRLDLinkIds         CmRemoteLinkIds,

    -- EtherJack Diagnosis params
    cmEthernetNetPortAutoDiagEnabled                 TruthValue,

    --Synchronous Port params
    cmEthernetNetPortSyncEEnabled                    TruthValue,
    cmEthernetNetPortQLModeEnabled                   TruthValue,
    cmEthernetNetPortExpectedQL                      SSMQualityLevel,
    cmEthernetNetPortAssumedQL                       SSMQualityLevel,
    cmEthernetNetPortReceivedQL                      SSMQualityLevel,
    cmEthernetNetPortTransmitQL                      SSMQualityLevel,

    --Network Port Priority Mapping Mode
    cmEthernetNetPortPrioMapMode                     PriorityMapMode,

    --PCP DE Pairs
    cmEthernetNetPortDeiEnable                       TruthValue, 
    cmEthernetNetPortPcpDEEncType                    PcpDEEncType,
    cmEthernetNetPortPcpDEPairsAction                PcpDEPairsAction,

    cmEthernetNetPortSSMRemoteMacAddress             MacAddress,

    --XG params
    cmEthernetNetPortXgePhyType                      XgePhyType,

    --Mac Loopback Params
    cmEthernetNetPortLoopbackSourceMacControlEnabled TruthValue,
    cmEthernetNetPortLoopbackDestMacControlEnabled   TruthValue,
    cmEthernetNetPortLoopbackSourceMacAddress        MacAddress,
    cmEthernetNetPortLoopbackDestMacAddress          MacAddress,
    cmEthernetNetPortLoopbackBlockingEnabled         TruthValue,

    -- Ethernet Port Traffic params
    cmEthernetNetPortRxDeiAction                     RxDeiAction,
    cmEthernetNetPortTxDeiAction                     TxDeiAction,
    cmEthernetNetPortRxDeiOuterTagType               DeiOuterTagType,
    cmEthernetNetPortTxDeiOuterTagType               DeiOuterTagType,

    -- XFP params
    cmEthernetNetPortLaserWDMChannel                 SfpChannelIdentifier,
    cmEthernetNetPortLaserIsTunable                  TruthValue,
    cmEthernetNetPortLaserFrequency                  Unsigned32,

    -- Generic Ethernet Port params - added in R6.5
    cmEthernetNetPortMediaTypeAutoSelected           EthernetMediaType,

    -- Ethernet Port Traffic params - added in R6.5
    cmEthernetNetPortLowLatencyQueuingEnabled        TruthValue,

    cmEthernetNetPortDiagnosticMacAddress            MacAddress,
    
    cmEthernetNetPortIngressCOSPriority              VlanTagType,
    cmEthernetNetPortDefaultCOS                      Integer32,
    cmEthernetNetPortTrafficModel                    EthernetPortTrafficModel,
    cmEthernetNetPortIndependentShaperBW             TruthValue,
    cmEthernetNetPortExpDEEncType                    PcpDEEncType,
    cmEthernetNetPortExpDEPairsAction                PcpDEPairsAction,
    cmEthernetNetPortIpPrecDEEncType                 PcpDEEncType,
    cmEthernetNetPortIpPrecDEPairsAction             PcpDEPairsAction,
    cmEthernetNetPortEncapPcpDEEncodingType          PcpDEEncType,
    cmEthernetNetPortEncapPcpDEPairsAction           PcpDEPairsAction,
    cmEthernetNetPortJdsuLoopbackSrcIp               IpAddress,
    cmEthernetNetPortWfqSegmentationCOS              Integer32,
    cmEthernetNetPortWfqGroupCOS                     Integer32,
    cmEthernetNetPortWfqGroupEirLo                   Unsigned32,
    cmEthernetNetPortWfqGroupEirHi                   Unsigned32,
    cmEthernetNetPortSilentStartControl              TruthValue,
    cmEthernetNetPortSfpLinkLength                   Integer32,

    -- Ethernet Port Traffic params
    cmEthernetNetPortOuterTagTpidOverride            TruthValue,
    cmEthernetNetPortOuterTagTpid                    Unsigned32,

    -- Ethernet Port SFP params
    cmEthernetNetPortSfpName                         DisplayString,
    cmEthernetNetPortSfpHardwareRevision             DisplayString,

    -- Persistent Loopback Control
    cmEthernetNetPortPersistentLoopbackControl       TruthValue,

    -- Ethernet Port Loopback Test Reflector params
    cmEthernetNetPortLoopbackTestReflectorIPv4AddressControl TruthValue,
    cmEthernetNetPortLoopbackTestReflectorIPv4Address        IpAddress,
    cmEthernetNetPortLoopbackTestReflectorIPv6AddressControl TruthValue,
    cmEthernetNetPortLoopbackTestReflectorIPv6Address        Ipv6Address,
    -- Ethernet Port SFP params
    cmEthernetNetPortSfpIdentifierValue              SfpIdentifierValue
}
    
-- Port Indices 
cmEthernetNetPortIndex OBJECT-TYPE
    SYNTAX      Integer32 (1..65535)
    MAX-ACCESS  read-only
    STATUS      current
    DESCRIPTION
            "An integer index value used to uniquely identify
             this Ethernet Network Port within a card.
             Note that each Ethernet Network Port is uniquely identified
             by the indices neIndex, shelfIndex, 
             slotIndex, cmEthernetNetPortIndex." 
    ::= { cmEthernetNetPortEntry 1 }

cmEthernetNetPortIfIndex OBJECT-TYPE
    SYNTAX      InterfaceIndex
    MAX-ACCESS  read-only
    STATUS      current
    DESCRIPTION
            "This object has the same value as ifIndex for 
             Ethernet Network Port.  An integer index value used to 
             uniquely identify this Ethernet Network Port."
    ::= { cmEthernetNetPortEntry 2 }

cmEthernetNetPortEntityIndex OBJECT-TYPE
    SYNTAX      PhysicalIndex 
    MAX-ACCESS  read-only
    STATUS      current
    DESCRIPTION
           "Entity Index from ENTITY-MIB for this port."
    ::= { cmEthernetNetPortEntry 3 }

-- State Management params
cmEthernetNetPortAdminState OBJECT-TYPE
    SYNTAX      AdminState 
    MAX-ACCESS  read-write
    STATUS      current
    DESCRIPTION
            "This object represents the Administrative State of the Ethernet 
             Network Port."
    ::= { cmEthernetNetPortEntry 4 }

cmEthernetNetPortOperationalState OBJECT-TYPE
    SYNTAX      OperationalState 
    MAX-ACCESS  read-only
    STATUS      current
    DESCRIPTION
            "This object represents the Operational State of the Ethernet 
             Network Port."
    ::= { cmEthernetNetPortEntry 5 }

cmEthernetNetPortSecondaryState OBJECT-TYPE
    SYNTAX      SecondaryState 
    MAX-ACCESS  read-only
    STATUS      current
    DESCRIPTION
            "This object represents the Secondary State of the Ethernet 
             Network Port."
    ::= { cmEthernetNetPortEntry 6 }

-- Generic Port params
cmEthernetNetPortMTU OBJECT-TYPE
    SYNTAX      Integer32 
    MAX-ACCESS  read-write
    STATUS      current
    DESCRIPTION
            "This object provides the MTU on the Ethernet Network Port."
    ::= { cmEthernetNetPortEntry 7 }

cmEthernetNetPortMediaType OBJECT-TYPE
    SYNTAX     EthernetMediaType
    MAX-ACCESS read-write
    STATUS     current
    DESCRIPTION
            "This object represents the type of Ethernet Media on the 
             Ethernet Network Port."
    ::= { cmEthernetNetPortEntry 8 }

cmEthernetNetPortConfigSpeed OBJECT-TYPE
    SYNTAX     EthernetPortSpeed
    MAX-ACCESS read-write
    STATUS     current
    DESCRIPTION
            "This object allows to configure the speed of the 
             Ethernet Network Port."
    ::= { cmEthernetNetPortEntry 9 }

cmEthernetNetPortNegotiatedSpeed OBJECT-TYPE
    SYNTAX     EthernetPortSpeed
    MAX-ACCESS read-only
    STATUS     current
    DESCRIPTION
            "This object provides the negotiated speed of the 
             Ethernet Network Port."
    ::= { cmEthernetNetPortEntry 10 }

cmEthernetNetPortMDIXType OBJECT-TYPE
    SYNTAX     CmEthernetMDIXType
    MAX-ACCESS read-write
    STATUS     current
    DESCRIPTION
            "This object allows management of MDIX property on  
             Ethernet Network Port."
    ::= { cmEthernetNetPortEntry 11 }

cmEthernetNetPortJumboFramesEnabled OBJECT-TYPE
    SYNTAX     TruthValue
    MAX-ACCESS read-write
    STATUS     current
    DESCRIPTION
            "This object allows enabling/disabling jumbo frames support on 
             the Ethernet Network Port.  This object is only applicable for
             Ethernet Network Port on R3.1CM NTU Card."
    ::= { cmEthernetNetPortEntry 12 }

cmEthernetNetPortSfpVendorName OBJECT-TYPE
    SYNTAX  DisplayString (SIZE (0..16)) 
    MAX-ACCESS read-only
    STATUS     current
    DESCRIPTION
            "This object provides the vendor name of the SFP. 
             This is applicable when cmEthernetNetPortMediaType is fiber or coppersfp."
     ::= { cmEthernetNetPortEntry 13 }

cmEthernetNetPortSfpPartNumber OBJECT-TYPE
    SYNTAX  DisplayString (SIZE (0..16)) 
    MAX-ACCESS read-only
    STATUS     current
    DESCRIPTION
            "This object provides the part number of the SFP. 
             This is applicable when cmEthernetNetPortMediaType is fiber or coppersfp."
     ::= { cmEthernetNetPortEntry 14 }

cmEthernetNetPortSfpSerialNumber OBJECT-TYPE
    SYNTAX  DisplayString (SIZE (0..32)) 
    MAX-ACCESS read-only
    STATUS     current
    DESCRIPTION
            "This object provides the serial number of the SFP.  
             This is applicable when cmEthernetNetPortMediaType is fiber or coppersfp."
     ::= { cmEthernetNetPortEntry 15 }

cmEthernetNetPortSfpDateOfManufacture OBJECT-TYPE
    SYNTAX     DateAndTime
    MAX-ACCESS read-only
    STATUS     current
    DESCRIPTION
            "This object provides the date of manufacture of the SFP.
             This is applicable when cmEthernetNetPortMediaType is fiber or coppersfp."
     ::= { cmEthernetNetPortEntry 16 }

cmEthernetNetPortSfpConnectorValue OBJECT-TYPE
    SYNTAX     SfpConnectorValue 
    MAX-ACCESS read-only
    STATUS     current
    DESCRIPTION
            "This object provides the SFP connector value.
             This is applicable when cmEthernetNetPortMediaType is fiber or coppersfp."
     ::= { cmEthernetNetPortEntry 17 }

-- EtherJack Diagnosis params
cmEthernetNetPortInitiateDiag  OBJECT-TYPE
    SYNTAX     CmEthernetDiagAction
    MAX-ACCESS read-write
    STATUS     current
    DESCRIPTION
            "This object allows to initiate Etherjack diagnosis on the
             Ethernet Network Port."
     ::= { cmEthernetNetPortEntry 18 }

cmEthernetNetPortDiagnosePair1Cond OBJECT-TYPE
    SYNTAX     CmDiagCableCondType
    MAX-ACCESS read-only
    STATUS     current
    DESCRIPTION
            "This object provides diagnosis results for the cable Pair 1
             on Ethernet Network Port."
     ::= { cmEthernetNetPortEntry 19 }

cmEthernetNetPortDiagnosePair2Cond OBJECT-TYPE
    SYNTAX     CmDiagCableCondType
    MAX-ACCESS read-only
    STATUS     current
    DESCRIPTION
            "This object provides diagnosis results for the cable Pair 2
             on Ethernet Network Port."
     ::= { cmEthernetNetPortEntry 20 }

cmEthernetNetPortDiagnosePair3Cond OBJECT-TYPE
    SYNTAX     CmDiagCableCondType
    MAX-ACCESS read-only
    STATUS     current
    DESCRIPTION
            "This object provides diagnosis results for the cable Pair 3
             on Ethernet Network Port."
     ::= { cmEthernetNetPortEntry 21 }

cmEthernetNetPortDiagnosePair4Cond OBJECT-TYPE
    SYNTAX     CmDiagCableCondType
    MAX-ACCESS read-only
    STATUS     current
    DESCRIPTION
            "This object provides diagnosis results for the cable Pair 4
             on Ethernet Network Port."
     ::= { cmEthernetNetPortEntry 22 }

cmEthernetNetPortDiagnoseAutoNegCond OBJECT-TYPE
    SYNTAX     CmDiagAutoNegCondType
    MAX-ACCESS read-only
    STATUS     current
    DESCRIPTION
            "This object provides auto negotiation results of the diagnosis
             test on Ethernet Network Port."
     ::= { cmEthernetNetPortEntry 23 }

cmEthernetNetPortDiagnoseLpbkCond OBJECT-TYPE
    SYNTAX     CmDiagLpbkCondType
    MAX-ACCESS read-only
    STATUS     current
    DESCRIPTION
            "This object provides port loopback results of the diagnosis
             test on Ethernet Network Port."
     ::= { cmEthernetNetPortEntry 24 }

cmEthernetNetPortDiagnoseEfmLpbkCond OBJECT-TYPE
    SYNTAX     CmDiagEfmOamLpbkCondType
    MAX-ACCESS read-only
    STATUS     current
    DESCRIPTION
            "This object provides remote EFM loopback results of the diagnosis
             test on Ethernet Network Port."
     ::= { cmEthernetNetPortEntry 25 }

cmEthernetNetPortDiagnoseResult OBJECT-TYPE
    SYNTAX  DisplayString (SIZE (0..256)) 
    MAX-ACCESS read-only
    STATUS     current
    DESCRIPTION
            "This object provides results of the diagnosis
             test in string form on Ethernet Network Port."
     ::= { cmEthernetNetPortEntry 26 }

cmEthernetNetPortDiagnoseTestStatus OBJECT-TYPE
    SYNTAX  CmDiagTestStatus 
    MAX-ACCESS read-only
    STATUS     current
    DESCRIPTION
            "This object provides the current status of the diagnosis
             test on Ethernet Access Port."
     ::= { cmEthernetNetPortEntry 27 }

cmEthernetNetPortDiagnoseTestTime OBJECT-TYPE
    SYNTAX  DateAndTime 
    MAX-ACCESS read-only
    STATUS     current
    DESCRIPTION
            "This object provides the time when diagnosis test was last executed."
     ::= { cmEthernetNetPortEntry 28 }

-- Ethernet Loopback params
cmEthernetNetPortLoopbackConfig OBJECT-TYPE 
    SYNTAX     CmLoopbackType
    MAX-ACCESS read-write
    STATUS     current
    DESCRIPTION
            "This object allows to initiate loopbacks on 
             on the Ethernet Network Port."
     ::= { cmEthernetNetPortEntry 29 }

cmEthernetNetPortLoopbackStatus OBJECT-TYPE
    SYNTAX     CmLoopbackType
    MAX-ACCESS read-only
    STATUS     current
    DESCRIPTION
            "This object provides status of the current loopback 
             on the Ethernet Network Port."
     ::= { cmEthernetNetPortEntry 30 }

cmEthernetNetPortLoopbackTime OBJECT-TYPE 
    SYNTAX     Integer32 (2..300)
    MAX-ACCESS read-write
    STATUS     current
    DESCRIPTION
            "This object allows to specify time for timed-loopbacks on 
             on the Ethernet Network Port."
     ::= { cmEthernetNetPortEntry 31 }

cmEthernetNetPortLoopbackSwapSADA OBJECT-TYPE
    SYNTAX     CmSwapSADAType
    MAX-ACCESS read-write
    STATUS     current
    DESCRIPTION
            "This object allows to specify whether or not the loopbacked
             frame will have the Source Address and Destination Address
             swapped."
     ::= { cmEthernetNetPortEntry 32 }

cmEthernetNetPortOuterVlanLoopbackMask OBJECT-TYPE
    SYNTAX     INTEGER (0..16)
    MAX-ACCESS read-write
    STATUS     current
    DESCRIPTION
             "This object allows specification of the outer VLANs to be 
              looped back when port is in vlan(terminal/facility) 
              loopback configuration. Only 3 VLANs can be specified 
              for vlan loopback. The various bit positions are:
                   1         Outer VLAN 1 Loopback Enabled
                   2         Outer VLAN 2 Loopback Enabled
                   4         Outer VLAN 3 Loopback Enabled
              Value of 0 means that no VLANs are enabled."
     ::= { cmEthernetNetPortEntry 33 }

cmEthernetNetPortOuterVlanLoopback1 OBJECT-TYPE 
    SYNTAX  DisplayString (SIZE (0..6)) 
    MAX-ACCESS read-write
    STATUS     current
    DESCRIPTION
             "This object allows specification of the outer VLAN 1 to be 
              looped back when port is in vlan(terminal/facility) 
              loopback configuration. This is valid only if the
              corresponding bit in cmEthernetNetPortOuterVlanLoopbackMask
              is set.  The value to be specified should be in the form 
              X-Y where X is the VLAN Id and Y is the VLAN Priority.  
              If Y is specified as a *, all Priorities (0 to 7) 
              are looped back."
     ::= { cmEthernetNetPortEntry 34 }

cmEthernetNetPortOuterVlanLoopback2 OBJECT-TYPE
    SYNTAX  DisplayString (SIZE (0..6)) 
    MAX-ACCESS read-write
    STATUS     current
    DESCRIPTION
             "This object allows specification of the outer VLAN 2 to be 
              looped back when port is in vlan(terminal/facility) 
              loopback configuration. This is valid only if the
              corresponding bit in cmEthernetNetPortOuterVlanLoopbackMask
              is set.  The value to be specified should be in the form 
              X-Y where X is the VLAN Id and Y is the VLAN Priority.  
              If Y is specified as a *, all Priorities (0 to 7) 
              are looped back."
     ::= { cmEthernetNetPortEntry 35 }

cmEthernetNetPortOuterVlanLoopback3 OBJECT-TYPE
    SYNTAX  DisplayString (SIZE (0..6)) 
    MAX-ACCESS read-write
    STATUS     current
    DESCRIPTION
             "This object allows specification of the outer VLAN 3 to be 
              looped back when port is in vlan(terminal/facility) 
              loopback configuration. This is valid only if the
              corresponding bit in cmEthernetNetPortOuterVlanLoopbackMask
              is set.  The value to be specified should be in the form 
              X-Y where X is the VLAN Id and Y is the VLAN Priority.  
              If Y is specified as a *, all Priorities (0 to 7) 
              are looped back."
     ::= { cmEthernetNetPortEntry 36 }

cmEthernetNetPortInnerVlanLoopbackMask OBJECT-TYPE
    SYNTAX     INTEGER (0..16)
    MAX-ACCESS read-write
    STATUS     current
    DESCRIPTION
             "This object allows specification of the inner VLANs to be 
              looped back when port is in vlan(terminal/facility) 
              loopback configuration. Only 3 VLANs can be specified 
              for vlan loopback. The various bit positions are:
                   1         Inner VLAN 1 Loopback Enabled
                   2         Inner VLAN 2 Loopback Enabled
                   4         Inner VLAN 3 Loopback Enabled
              Value of 0 means that no VLANs are enabled."
     ::= { cmEthernetNetPortEntry 37 }

cmEthernetNetPortInnerVlanLoopback1 OBJECT-TYPE 
    SYNTAX  DisplayString (SIZE (0..6)) 
    MAX-ACCESS read-write
    STATUS     current
    DESCRIPTION
             "This object allows specification of the inner VLAN 1 to be 
              looped back when port is in vlan(terminal/facility) 
              loopback configuration. This is valid only if the
              corresponding bit in cmEthernetNetPortInnerVlanLoopbackMask
              is set.  The value to be specified should be in the form 
              X-Y where X is the VLAN Id and Y is the VLAN Priority.  
              If Y is specified as a *, all Priorities (0 to 7) 
              are looped back."
     ::= { cmEthernetNetPortEntry 38 }

cmEthernetNetPortInnerVlanLoopback2 OBJECT-TYPE
    SYNTAX  DisplayString (SIZE (0..6)) 
    MAX-ACCESS read-write
    STATUS     current
    DESCRIPTION
             "This object allows specification of the inner VLAN 2 to be 
              looped back when port is in vlan(terminal/facility) 
              loopback configuration. This is valid only if the
              corresponding bit in cmEthernetNetPortInnerVlanLoopbackMask
              is set.  The value to be specified should be in the form 
              X-Y where X is the VLAN Id and Y is the VLAN Priority.  
              If Y is specified as a *, all Priorities (0 to 7) 
              are looped back."
     ::= { cmEthernetNetPortEntry 39 }

cmEthernetNetPortInnerVlanLoopback3 OBJECT-TYPE
    SYNTAX  DisplayString (SIZE (0..6)) 
    MAX-ACCESS read-write
    STATUS     current
    DESCRIPTION
             "This object allows specification of the inner VLAN 3 to be 
              looped back when port is in vlan(terminal/facility) 
              loopback configuration. This is valid only if the
              corresponding bit in cmEthernetNetPortInnerVlanLoopbackMask
              is set.  The value to be specified should be in the form 
              X-Y where X is the VLAN Id and Y is the VLAN Priority.  
              If Y is specified as a *, all Priorities (0 to 7) 
              are looped back."
     ::= { cmEthernetNetPortEntry 40 }


-- Link Loss Forwarding params 
cmEthernetNetPortLinkLossFwdEnabled OBJECT-TYPE
    SYNTAX     TruthValue
    MAX-ACCESS read-write
    STATUS     current
    DESCRIPTION
             "This object allows enabling/disabling link loss forwarding 
              on the Ethernet Network Port." 
     ::= { cmEthernetNetPortEntry 41 }

cmEthernetNetPortLinkLossFwdSignalType OBJECT-TYPE 
    SYNTAX     CmLinkLossFwdSignalType
    MAX-ACCESS read-write
    STATUS     deprecated
    DESCRIPTION
             "This object allows definition of the link loss forwarding
              signalling type.  This is applicable only if 
              cmEthernetNetPortLinkLossFwdEnabled is enabled.
              This object is only valid for FSP150CM Release 3.1. 
              This object is deprecated henceforth. 
              Link Loss signalling will be supported using the object
              cmEthernetAccPortLinkLossFwdTxActionType."
     ::= { cmEthernetNetPortEntry 42 }

cmEthernetNetPortLinkLossFwdTriggerTypes  OBJECT-TYPE
    SYNTAX     CmLinkLossFwdTriggerTypes
    MAX-ACCESS read-write
    STATUS     current
    DESCRIPTION
             "This object allows definition of the link loss forwarding
              trigger types.  This is applicable only if 
              cmEthernetAccPortLinkLossFwdEnabled is enabled."
     ::= { cmEthernetNetPortEntry 43 }

cmEthernetNetPortLinkLossFwdDelay OBJECT-TYPE 
    SYNTAX     Integer32
    MAX-ACCESS read-write
    STATUS     current
    DESCRIPTION
             "This object allows specification of the delay between
              detection of link loss and signalling of link loss forwarding. 
              Time specified is in seconds."
     ::= { cmEthernetNetPortEntry 44 }

cmEthernetNetPortLinkLossFwdActive OBJECT-TYPE 
    SYNTAX     TruthValue
    MAX-ACCESS read-only
    STATUS     current
    DESCRIPTION
             "This object provides the link loss forwarding status indicating
              if link loss forwarding is currently being signaled via 
              the port." 
     ::= { cmEthernetNetPortEntry 45 }

cmEthernetNetPortLinkLossFwdPartnerEnabled OBJECT-TYPE 
    SYNTAX     TruthValue
    MAX-ACCESS read-only
    STATUS     current
    DESCRIPTION
             "This object provides the indication of a link partners ability
              to support link loss forwarding via EFM, i.e. from
              received organization specific OAMPDUs." 
     ::= { cmEthernetNetPortEntry 46 }

cmEthernetNetPortLinkLossFwdLocalLinkId  OBJECT-TYPE 
    SYNTAX     Integer32
    MAX-ACCESS read-write
    STATUS     current
    DESCRIPTION
             "This object allows configuration of the Local Link Id on 
              Ethernet Network port." 
     ::= { cmEthernetNetPortEntry 47 }

cmEthernetNetPortLinkLossFwdRemoteLinkIds OBJECT-TYPE 
    SYNTAX     CmRemoteLinkIds 
    MAX-ACCESS read-write
    STATUS     current
    DESCRIPTION
             "This object allows enabling/disabling Remote Link Ids 
              on Ethernet Network port. By setting the appropriate bit
              positions, the Ethernet Network port is able to distinguish
              the remote side client ports from the Remote Link Down
              PDUs coming from remote end."
     ::= { cmEthernetNetPortEntry 48 }

-- OAM params
cmEthernetNetPortOamId  OBJECT-TYPE
    SYNTAX     Integer32 
    MAX-ACCESS read-only
    STATUS     current
    DESCRIPTION
             "OAM Id.  This is unique EFM OAM sublayer port id." 
     ::= { cmEthernetNetPortEntry 49 }

cmEthernetNetPortOamAdminDisposition OBJECT-TYPE
    SYNTAX     CmControlProtocolDispType
    MAX-ACCESS read-write
    STATUS     deprecated
    DESCRIPTION
             "Ethernet Network Port's EFM OAM Administrative Disposition. 
              This object is applicable only for FSP150CM Release 3.1.
              This object is deprecated henceforth.  
              With FSP150CC Release 4.1, this property is managed using 
              the Control Protocol Disposition tables."
     ::= { cmEthernetNetPortEntry 50 }

cmEthernetNetPortOamDiscoveryState OBJECT-TYPE
    SYNTAX     CmOamDiscoveryState
    MAX-ACCESS read-only
    STATUS     current
    DESCRIPTION
             "Ethernet Network Port's OAM discovery state." 
     ::= { cmEthernetNetPortEntry 51 }

cmEthernetNetPortOamLocalVarRtrvsEnabled OBJECT-TYPE
    SYNTAX     TruthValue
    MAX-ACCESS read-only
    STATUS     current
    DESCRIPTION
             "This object allows specification of whether the Ethernet
              Network Port supports sending variable response OAMPDUs." 
     ::= { cmEthernetNetPortEntry 52 }

cmEthernetNetPortOamLocalLinkEventsEnabled OBJECT-TYPE
    SYNTAX     TruthValue 
    MAX-ACCESS read-only
    STATUS     current
    DESCRIPTION
             "This object allows specification of whether the Ethernet
              Network Port supports interpreting Link Events."
     ::= { cmEthernetNetPortEntry 53 }

cmEthernetNetPortOamLocalOamLoopbacksSupported OBJECT-TYPE
    SYNTAX     TruthValue 
    MAX-ACCESS read-write
    STATUS     current
    DESCRIPTION
             "This object allows specification of whether the Ethernet
              Network Port is capable of OAM remote loopback mode."
     ::= { cmEthernetNetPortEntry 54 }

cmEthernetNetPortOamLocalUnidirSupportEnabled OBJECT-TYPE
    SYNTAX     TruthValue 
    MAX-ACCESS read-only
    STATUS     current
    DESCRIPTION
             "This object allows specification of whether the Ethernet
              Network Port is capable of sending OAMPDUs when the receive path 
              is non-operational."
     ::= { cmEthernetNetPortEntry 55 }

cmEthernetNetPortOamLocalMaxPDUSize OBJECT-TYPE
    SYNTAX     Integer32
    MAX-ACCESS read-only
    STATUS     current
    DESCRIPTION
             "This object represents the largest OAMPDU, in octets, 
              supported by the Ethernet Network Port.  This value is
              compared to the remote Maximum PDU Size and the smaller of 
              the two is used." 
     ::= { cmEthernetNetPortEntry 56 }

cmEthernetNetPortOamLocalMode OBJECT-TYPE
    SYNTAX     CmOamMode 
    MAX-ACCESS read-write
    STATUS     current
    DESCRIPTION
             "This object allows to configure the OAM sublayer entity in
              either Active or Passive mode." 
     ::= { cmEthernetNetPortEntry 57 }

cmEthernetNetPortOamRemoteMacAddress OBJECT-TYPE
    SYNTAX     MacAddress
    MAX-ACCESS read-only
    STATUS     current
    DESCRIPTION
             "This object allows retrieval of the Remote Mac Address." 
     ::= { cmEthernetNetPortEntry 58 }

cmEthernetNetPortOamRemoteVarRtrvsEnabled OBJECT-TYPE
    SYNTAX     TruthValue
    MAX-ACCESS read-only
    STATUS     current
    DESCRIPTION
             "This object allows retrieval of whether the remote OAM 
              entity supports sending variable response OAMPDUs." 
     ::= { cmEthernetNetPortEntry 59 }

cmEthernetNetPortOamRemoteLinkEventsEnabled OBJECT-TYPE
    SYNTAX     TruthValue 
    MAX-ACCESS read-only
    STATUS     current
    DESCRIPTION
             "This object allows retrieval of whether the remote OAM 
              entity supports interpreting Link Events."
     ::= { cmEthernetNetPortEntry 60 }

cmEthernetNetPortOamRemoteOamLoopbacksSupported OBJECT-TYPE
    SYNTAX     TruthValue 
    MAX-ACCESS read-only
    STATUS     current
    DESCRIPTION
             "This object allows retrieval of whether the remote OAM 
              entity supports OAM remote loopback mode."
     ::= { cmEthernetNetPortEntry 61 }

cmEthernetNetPortOamRemoteUnidirSupportEnabled OBJECT-TYPE
    SYNTAX     TruthValue 
    MAX-ACCESS read-only
    STATUS     current
    DESCRIPTION
             "This object allows retrieval of whether the remote 
              OAM entity is capable of sending OAMPDUs when the receive path 
              is non-operational."
     ::= { cmEthernetNetPortEntry 62 }

cmEthernetNetPortOamRemoteMaxPDUSize OBJECT-TYPE
    SYNTAX     Integer32
    MAX-ACCESS read-only
    STATUS     current
    DESCRIPTION
             "This object allows retrieval of the remote OAM 
              entity maximum OAMPDU size."
     ::= { cmEthernetNetPortEntry 63 }

cmEthernetNetPortOamRemoteMode OBJECT-TYPE
    SYNTAX     CmOamMode 
    MAX-ACCESS read-only
    STATUS     current
    DESCRIPTION
             "This object allows to retrieve whether the remote OAM 
              sublayer entity is either in Active or Passive mode." 
     ::= { cmEthernetNetPortEntry 64 }


-- Ethernet Port Traffic params
cmEthernetNetPortRxPauseDisposition OBJECT-TYPE
    SYNTAX     CmControlProtocolDispType
    MAX-ACCESS read-write
    STATUS     current
    DESCRIPTION
         "This object allows enabling/disabling receive pause frames on
          Ethernet Network port.  This object is not applicable 
          for FSP150CC Release 4.1 products."
     ::= { cmEthernetNetPortEntry 65 }

cmEthernetNetPortTxPauseEnabled OBJECT-TYPE
    SYNTAX     TruthValue
    MAX-ACCESS read-write
    STATUS     current
    DESCRIPTION
         "This object allows enabling/disabling transmit pause frames on
          Ethernet Network port.
          This object is not applicable for FSP150CC Release 4.1 products."
     ::= { cmEthernetNetPortEntry 66 }

cmEthernetNetPortAfpType OBJECT-TYPE
    SYNTAX     CmAfpType
    MAX-ACCESS read-write
    STATUS     current
    DESCRIPTION
         "This object allows specification of the Acceptable Frame Policy on
          Ethernet Network port. Users can specify whether the port supports
          only tagged frames, only untagged frames or both tagged and 
          untagged frames.
          This object is not applicable for FSP150CC Release 4.1 products."
     ::= { cmEthernetNetPortEntry 67 }

-- Generic Ethernet Port params
cmEthernetNetPortMDIXStatus OBJECT-TYPE
    SYNTAX     CmEthernetMDIXType
    MAX-ACCESS read-only
    STATUS     current
    DESCRIPTION
         "This object provides the current MDIX status of the 
          Ethernet Network port."
     ::= { cmEthernetNetPortEntry 68 }

cmEthernetNetPortSfpReach OBJECT-TYPE
    SYNTAX     Integer32
    MAX-ACCESS read-only
    STATUS     current
    DESCRIPTION
         "This object provides the SFP Reach in meters.
          This is applicable when cmEthernetNetPortMediaType is fiber or coppersfp."
     ::= { cmEthernetNetPortEntry 69 }

cmEthernetNetPortSfpLaserWaveLength OBJECT-TYPE
    SYNTAX     Integer32
    MAX-ACCESS read-only
    STATUS     current
    DESCRIPTION
         "This object provides the SFP Laser Wave Length in nano meters.
          This is applicable only when cmEthernetNetPortMediaType is fiber."
     ::= { cmEthernetNetPortEntry 70 }

cmEthernetNetPortSfpMediaType OBJECT-TYPE
    SYNTAX     SfpMediaType
    MAX-ACCESS read-only
    STATUS     current
    DESCRIPTION
         "This object provides the SFP Media Type.
          This is applicable when cmEthernetNetPortMediaType is fiber or coppersfp."
     ::= { cmEthernetNetPortEntry 71 }

cmEthernetNetPortOamEnabled  OBJECT-TYPE
    SYNTAX     TruthValue
    MAX-ACCESS read-write 
    STATUS     current
    DESCRIPTION
             "This object allows to manage the EFM OAM on Ethernet Network Port."
     ::= { cmEthernetNetPortEntry 72 }

cmEthernetNetPortOamAdminState OBJECT-TYPE
    SYNTAX     CmOamAdminState
    MAX-ACCESS read-only 
    STATUS     current
    DESCRIPTION
             "This object provides the EFM OAM Admin State."
     ::= { cmEthernetNetPortEntry 73 }

-- Ethernet Port Traffic params
cmEthernetNetPortShapingEnabled OBJECT-TYPE
    SYNTAX     TruthValue
    MAX-ACCESS read-write
    STATUS     current
    DESCRIPTION
         "This object allows to manage the Network Port Shaping.
          When enabled, values in cmEthernetNetPortShapedSpeedLo and
          cmEthernetNetPortShapedSpeedHi are applicable."
     ::= { cmEthernetNetPortEntry 74 }

cmEthernetNetPortShapedSpeedLo OBJECT-TYPE
    SYNTAX     Unsigned32
    MAX-ACCESS read-write
    STATUS     current
    DESCRIPTION
         "This object allows to specify the lower 32 bits of 
          the Network Port Shaped speed. This value is applicable
          when cmEthernetNetPortShapingEnabled is enabled."
     ::= { cmEthernetNetPortEntry 75 }

cmEthernetNetPortShapedSpeedHi OBJECT-TYPE
    SYNTAX     Unsigned32
    MAX-ACCESS read-write
    STATUS     current
    DESCRIPTION
         "This object allows to specify the higher 32 bits of 
          the Network Port Shaped speed. This value is applicable
          when cmEthernetNetPortShapingEnabled is enabled."
     ::= { cmEthernetNetPortEntry 76 }

cmEthernetNetPortQinQEtherType OBJECT-TYPE
    SYNTAX     Unsigned32
    MAX-ACCESS read-write
    STATUS     current
    DESCRIPTION
         "This object allows to specify the Q-in-Q Ether Type 
          on the Network Port.  Setting this value to 0 will disable
          the Q-in-Q override on the Network Port."
     ::= { cmEthernetNetPortEntry 77 }

-- Link Loss Forwarding params
cmEthernetNetPortLinkLossFwdTxActionType OBJECT-TYPE
    SYNTAX     CmLinkLossFwdTxActionType
    MAX-ACCESS read-write
    STATUS     current
    DESCRIPTION
         "This object allows to specify the Network Port's behavior when
          link loss forwarding trigger events occur on the Access Port." 
     ::= { cmEthernetNetPortEntry 78 }

cmEthernetNetPortLinkLossFwdRxRLDLinkIds OBJECT-TYPE
    SYNTAX     CmRemoteLinkIds
    MAX-ACCESS read-only
    STATUS     current
    DESCRIPTION
         "This object provides the received Remote Link IDs in 
          EFM RLD messages on the Network Port." 
     ::= { cmEthernetNetPortEntry 79 }

-- EtherJack Diagnosis params
cmEthernetNetPortAutoDiagEnabled OBJECT-TYPE
    SYNTAX     TruthValue
    MAX-ACCESS read-write
    STATUS     current
    DESCRIPTION
         "This object allows to enable or disable the automatic 
          Cable Diagnostic tests when the cable is removed from the port."
     ::= { cmEthernetNetPortEntry 80 }

--Synchronous Port params
cmEthernetNetPortSyncEEnabled OBJECT-TYPE 
    SYNTAX     TruthValue
    MAX-ACCESS read-write
    STATUS     current
    DESCRIPTION
         "This object allows to specify whether the Ethernet Network Port 
          can be enabled/disabled for Synchronous Ethernet. This object
          is only applicable for Synchronous Ethernet capable ports.
          When enabled, on receive side 
            -port can extract the frequency of its input signal
             and pass the recovered clock to the system clock
            -port processes the ESMC(Ethernet Synchronization Messaging
             Channel) and extracts the QL (when also QL enabled)   
            -port is eligible to be selected as a system clock reference
          When enabled, on transmit side 
            -port's transmit clock is locked to the system clock
            -port generates an ESMC to generate a QL (when also QL enabled)

          When disabled, on receive side,
            -port does not pass the recovered clock to the system clock 
            -port does not process the ESMC (if present) 
            -port is not eligible to be selected as a 
                     system clock reference
          When disabled, on transmit side 
            -port's output frequency may be synchronized to the system clock
            -port does not generate an ESMC."
     ::= { cmEthernetNetPortEntry 81 }

cmEthernetNetPortQLModeEnabled OBJECT-TYPE 
    SYNTAX     TruthValue
    MAX-ACCESS read-write
    STATUS     current
    DESCRIPTION
         "This object allows to specify whether the Ethernet Network Port 
          can be enabled/disabled for QL Mode. This object
          is only applicable for Synchronous Ethernet capable ports,
          when cmEthernetNetPortQLModeEnabled is set to true.
          When enabled, on receive side 
            -port shall PEER the SSM (Sync Status Messages) slow protocol PDUs 
             and take appropriate action 
          When enabled, on transmit side 
            -port shall periodically (once a second) transmit QL TLV 
             information PDUs
          When disabled, on receive side,
            -port shall terminate and discard any SSM slow protocol PDUs 
          When disabled, on transmit side 
            -port shall not transmit any SSM slow protocol PDUs."
     ::= { cmEthernetNetPortEntry 82 }

cmEthernetNetPortExpectedQL OBJECT-TYPE 
    SYNTAX     SSMQualityLevel
    MAX-ACCESS read-write
    STATUS     current
    DESCRIPTION
         "This object allows to specify the expected QL when the 
          Ethernet Network Port is enabled for QL Mode. This object
          is only applicable for Synchronous Ethernet capable ports,
          when cmEthernetNetPortQLModeEnabled is set to true.
          This object allows the user to set a minimum
          expected received Quality Level on the port. The valid values
          depend upon the SYNC entity's Network Clock Type. A value of
          None represents that a minimum Quality Level is not expected. 
          The default value shall be None."
     ::= { cmEthernetNetPortEntry 83 }

cmEthernetNetPortAssumedQL OBJECT-TYPE 
    SYNTAX     SSMQualityLevel
    MAX-ACCESS read-write
    STATUS     current
    DESCRIPTION
         "This object allows to specify the assumed QL on the 
          Ethernet Network Port. This object is only applicable for 
          Synchronous Ethernet capable ports. 
          The Assumed QL is only meaningful if the Network Clock Type
          (see fsp150cm-sync.mib) is option1 and the 
          port's QL Mode is disabled and the port is being used as 
          an input reference source. Under these conditions, 
          the specified QL value is assumed to be the Quality Level of the
          non-failed reference."
     ::= { cmEthernetNetPortEntry 84 }

cmEthernetNetPortReceivedQL OBJECT-TYPE 
    SYNTAX     SSMQualityLevel
    MAX-ACCESS read-only
    STATUS     current
    DESCRIPTION
         "This object provides the Received QL value for the Ethernet port. 
          If the Ethernet port's QL Mode is disabled, then the received 
          QL value is not applicable.This object is only applicable for 
          Synchronous Ethernet capable ports."
     ::= { cmEthernetNetPortEntry 85 }

cmEthernetNetPortTransmitQL OBJECT-TYPE 
    SYNTAX     SSMQualityLevel
    MAX-ACCESS read-only
    STATUS     current
    DESCRIPTION
         "This object provides the Transmitted QL value for the Ethernet port. 
          If the Ethernet port's QL Mode is disabled, then the received 
          QL value is not applicable. This object is only applicable for 
          Synchronous Ethernet capable ports."
     ::= { cmEthernetNetPortEntry 86 }

cmEthernetNetPortPrioMapMode OBJECT-TYPE
    SYNTAX     PriorityMapMode
    MAX-ACCESS read-only
    STATUS     current
    DESCRIPTION
         "This object provides the  Priority Mapping Mode used for
          classification of frames."
     ::= { cmEthernetNetPortEntry 87 }

cmEthernetNetPortDeiEnable OBJECT-TYPE
    SYNTAX      TruthValue
    MAX-ACCESS  read-write
    STATUS      deprecated
    DESCRIPTION
        "This is a port level control to reset the DEI 
         (Drop Eligibility Indicator) bit in the S-Tag,
         if the downstream equipment supports S-Tag TPID (EtherType) but 
         cannot handle DEI bit set. In the receive direction,
         it uses the S-TAG DEI when enabled, else ignores it.
         The following comment is NOT relevant to OSA8.1.1, 
         since this object is still supported by OSA8.1.1.   
         The object has been deprecated.
         The respective configuration should be managed
         by following objects:
         cmEthernetNetPortRxDeiAction, cmEthernetNetPortTxDeiAction,
         cmEthernetNetPortRxDeiOuterTagType, cmEthernetNetPortTxDeiOuterTagType."
    ::= { cmEthernetNetPortEntry 88 }

cmEthernetNetPortPcpDEEncType OBJECT-TYPE
    SYNTAX      PcpDEEncType
    MAX-ACCESS  read-write
    STATUS      current
    DESCRIPTION
        "This is a port level control that specifies the mode of drop
         eligibility encoding in PCP bits of the VLAN tag."
    ::= { cmEthernetNetPortEntry 89 }

cmEthernetNetPortPcpDEPairsAction OBJECT-TYPE
    SYNTAX      PcpDEPairsAction
    MAX-ACCESS  read-write
    STATUS      current
    DESCRIPTION
        "This object allows the SNMP user to manage the Priority 
         Code Point (PCP) Drop Eligibility Pairs.  When the
         cmEthernetNetPortPcpDEEncType is of type 7p1d, 6p2d, 5p3d,
         the cmNetPortPcpDEPairTable can be used to specify 
         alternate pairs of priorities to specify drop eligibility/
         ineligibility."
    ::= { cmEthernetNetPortEntry 90 }

cmEthernetNetPortSSMRemoteMacAddress OBJECT-TYPE
    SYNTAX     MacAddress
    MAX-ACCESS read-only
    STATUS     current
    DESCRIPTION
             "This object allows retrieval of the Remote Mac Address, when
              the port is peering using SSM." 
     ::= { cmEthernetNetPortEntry 91 }

cmEthernetNetPortXgePhyType OBJECT-TYPE
    SYNTAX      XgePhyType  
    MAX-ACCESS  read-write
    STATUS      current
    DESCRIPTION
        "This object allows to specify the PHY type of 10G Ethernet Port.
         10G ports can operate in LAN-PHY or WAN-PHY mode. The default mode is LAN-PHY
         and port rate in this mode is 10Gbps. In WAN-PHY mode the port rate is 9.29Gbps.
         This attribute is only applicable for ports configured to work at speed-10G-full.
         For other speeds the value of this object must be 'not-applicable' and cannot
         be changed.
        "
    ::= { cmEthernetNetPortEntry 92 }

cmEthernetNetPortLoopbackSourceMacControlEnabled OBJECT-TYPE
    SYNTAX      TruthValue  
    MAX-ACCESS  read-write
    STATUS      current
    DESCRIPTION
         "This object allows to Enable/Disable the Net Port Source MAC 
         Address frame matching criteria for all streams. 
         Not applicable for: efm-oam-remote, efm-oam-remote-timed."
    ::= { cmEthernetNetPortEntry 93 }

cmEthernetNetPortLoopbackDestMacControlEnabled OBJECT-TYPE
    SYNTAX      TruthValue  
    MAX-ACCESS  read-write
    STATUS      current
    DESCRIPTION
         "This object allows to Enable/Disable the Net Port Destination MAC 
         Address frame matching criteria for all streams. 
         Not applicable for: efm-oam-remote, efm-oam-remote-timed."
    ::= { cmEthernetNetPortEntry 94 }

cmEthernetNetPortLoopbackSourceMacAddress OBJECT-TYPE
    SYNTAX      MacAddress  
    MAX-ACCESS  read-write
    STATUS      current
    DESCRIPTION
         "This object allows to set Net Port Source MAC Address for frame 
          matching when Net Port Source MAC Control is enabled."
    ::= { cmEthernetNetPortEntry 95 }

cmEthernetNetPortLoopbackDestMacAddress OBJECT-TYPE
    SYNTAX      MacAddress  
    MAX-ACCESS  read-write
    STATUS      current
    DESCRIPTION
         "This object allows to set Net Port Destination MAC Address for frame 
          matching when Net Port Destination MAC Control is enabled."
    ::= { cmEthernetNetPortEntry 96 }

cmEthernetNetPortLoopbackBlockingEnabled OBJECT-TYPE
    SYNTAX      TruthValue  
    MAX-ACCESS  read-write
    STATUS      current
    DESCRIPTION
        "This object allows frame blocking when loopback is active.
         - True: Blocks frames in the non-loopback direction 
           that match the PORT or VLAN received in the 
           non-loopback direction. Discards  frames 
           in the loopback direction that match 
           the PORT or VLAN, but do not match 
           the MAC address criteria,
         - False: No blocking of  frames."
    ::= { cmEthernetNetPortEntry 97 }

cmEthernetNetPortRxDeiAction OBJECT-TYPE
    SYNTAX  RxDeiAction
    MAX-ACCESS read-write
    STATUS     current
    DESCRIPTION
             "This object allows to specify
              the Receive DEI Action."
     ::= { cmEthernetNetPortEntry 98 }

cmEthernetNetPortTxDeiAction OBJECT-TYPE
    SYNTAX  TxDeiAction
    MAX-ACCESS read-write
    STATUS     current
    DESCRIPTION
             "This object allows to specify
              the Transmit DEI Action."
     ::= { cmEthernetNetPortEntry 99 }

cmEthernetNetPortRxDeiOuterTagType OBJECT-TYPE
    SYNTAX  DeiOuterTagType
    MAX-ACCESS read-write
    STATUS     current
    DESCRIPTION
             "This object allows to specify
              the Receive DEI Outer Tag Type."
     ::= { cmEthernetNetPortEntry 100 }

cmEthernetNetPortTxDeiOuterTagType OBJECT-TYPE
    SYNTAX  DeiOuterTagType
    MAX-ACCESS read-write
    STATUS     current
    DESCRIPTION
             "This object allows to specify
              the Transmit DEI Outer Tag Type."
     ::= { cmEthernetNetPortEntry 101 }

cmEthernetNetPortLaserWDMChannel OBJECT-TYPE
    SYNTAX  SfpChannelIdentifier 
    MAX-ACCESS read-write
    STATUS     current
    DESCRIPTION
             "Channel number of WDM tunable XFP setting."
     ::= { cmEthernetNetPortEntry 102 }

cmEthernetNetPortLaserIsTunable OBJECT-TYPE
    SYNTAX  TruthValue 
    MAX-ACCESS read-only
    STATUS     current
    DESCRIPTION
             "Channel number of WDM tunable XFP setting."
     ::= { cmEthernetNetPortEntry 103 }

cmEthernetNetPortLaserFrequency OBJECT-TYPE
    SYNTAX  Unsigned32 
    MAX-ACCESS read-only
    STATUS     current
    DESCRIPTION
             "Channel number of WDM tunable XFP setting."
     ::= { cmEthernetNetPortEntry 104 }

cmEthernetNetPortMediaTypeAutoSelected OBJECT-TYPE
    SYNTAX     EthernetMediaType
    MAX-ACCESS read-only
    STATUS     current
    DESCRIPTION
            "This object provides the auto selected Ethernet Media of the
             Ethernet Network Port."
    ::= { cmEthernetNetPortEntry 105 }

cmEthernetNetPortLowLatencyQueuingEnabled OBJECT-TYPE
    SYNTAX     TruthValue
    MAX-ACCESS read-write
    STATUS     current
    DESCRIPTION
            "This object allows to Enable/Disable the Low Latency Queuing on
             the Ethernet Network Port."
    ::= { cmEthernetNetPortEntry 106 }

cmEthernetNetPortDiagnosticMacAddress OBJECT-TYPE
    SYNTAX      MacAddress  
    MAX-ACCESS  read-only
    STATUS      current
    DESCRIPTION
         "This object describes the diagnose mac address for SAT, ECPA, JDSU, Loopback with Override SA etc."
    ::= { cmEthernetNetPortEntry 107 }

cmEthernetNetPortIngressCOSPriority OBJECT-TYPE
    SYNTAX     VlanTagType
    MAX-ACCESS read-write
    STATUS     deprecated
    DESCRIPTION
             "Indicates the VLAN tag to use for PCP Priority to COS mapping 
              when the port Priority Map Mode is 802.1p. Supported values are
              inner-vlantag and outer-vlantag. This attribute is only applicable
              on products when Flowpoint Model is supported.
             
              inner-vlantag: The inner VLAN tag PCP Priority of a frame is 
              used for ingress COS mapping. A frame with no inner VLAN tag 
              (untagged or single-tagged) will have a COS equal to the default
              COS of the port.

              outer-vlantag: The outer VLAN tag PCP Priority of a frame  is used 
              for ingress COS mapping. A frame with no outer VLAN tag (untagged) 
              will have a COS equal to the default COS of the port.

              This attribute has been deprecated and is not supported.  Now,
              the Priority Map Mode indicates whether it is inner or outer.
              Use priomap-8021p(4) for outer and priomap-8021p-inner(5)
              for inner.  "
    DEFVAL { outer-vlantag }
     ::= { cmEthernetNetPortEntry 108 }

cmEthernetNetPortDefaultCOS OBJECT-TYPE
    SYNTAX     Integer32 (0..7)
    MAX-ACCESS read-write
    STATUS     deprecated
    DESCRIPTION
             "The COS assigned to a frame that does not have a valid COS identifier 
              for the Priority Map Mode of the port. This attribute is only applicable
              on products when Flowpoint Model is supported.
             
              This value is assigned to a frame received on a port when:
              - the cmEthernetNetPortPrioMapMode=priomap-8021p, ingressCOSPriority=inner-vlantag; 
                and the frame is untagged
              - the cmEthernetNetPortPrioMapMode=priomap-8021p, ingressCOSPriority=inner-vlantag;
                and the frame has a single VLAN tag
              - the cmEthernetNetPortPrioMapMode=priomap-8021p, ingressCOSPriority=outer-vlantag; 
                and the frame is untagged
              - the cmEthernetNetPortPrioMapMode=priomap-dscp; and the frame does not have an IP ethertype
              - the cmEthernetNetPortPrioMapMode=priomap-tos; and the frame does not have an IP ethertype.

              This attribute has been deprecated and is not supported. The
              Default COS is determined from the flowpoint's associated
              Priority Mapping Profle."
    DEFVAL { 0 } 
     ::= { cmEthernetNetPortEntry 109 }

cmEthernetNetPortTrafficModel OBJECT-TYPE
    SYNTAX     EthernetPortTrafficModel
    MAX-ACCESS read-write
    STATUS     current
    DESCRIPTION
             "The Traffic Management connection model available for the port.
              - accessFlow: NID Traffic Connection model.
              - flowpoint: Multipoint and Aggregation Traffic Connection model."
    DEFVAL { accessFlow }            
     ::= { cmEthernetNetPortEntry 110 }

cmEthernetNetPortIndependentShaperBW OBJECT-TYPE
    SYNTAX      TruthValue  
    MAX-ACCESS  read-write
    STATUS      current
    DESCRIPTION
         "This object describes the shaper BW whether independent."
    ::= { cmEthernetNetPortEntry 111 }

cmEthernetNetPortExpDEEncType OBJECT-TYPE
    SYNTAX      PcpDEEncType
    MAX-ACCESS  read-write
    STATUS      current
    DESCRIPTION
        "This is a port level control that specifies the mode of drop
         eligibility encoding in exp bits of the VLAN tag."
    ::= { cmEthernetNetPortEntry 112 }

cmEthernetNetPortExpDEPairsAction OBJECT-TYPE
    SYNTAX      PcpDEPairsAction
    MAX-ACCESS  read-write
    STATUS      current
    DESCRIPTION
        "This object allows the SNMP user to manage the Priority 
         Code Point (PCP) Drop Eligibility Pairs.  When the
         cmEthernetNetPortExpDEEncType is of type 7p1d, 6p2d, 5p3d,
         the cmNetPortExpDEPairTable can be used to specify 
         alternate pairs of priorities to specify drop eligibility/
         ineligibility."
    ::= { cmEthernetNetPortEntry 113 }

cmEthernetNetPortIpPrecDEEncType OBJECT-TYPE
    SYNTAX      PcpDEEncType
    MAX-ACCESS  read-write
    STATUS      current
    DESCRIPTION
        "This is a port level control that specifies the mode of drop
         eligibility encoding in Ip Prec bits of the VLAN tag."
    ::= { cmEthernetNetPortEntry 114 }

cmEthernetNetPortIpPrecDEPairsAction OBJECT-TYPE
    SYNTAX      PcpDEPairsAction
    MAX-ACCESS  read-write
    STATUS      current
    DESCRIPTION
        "This object allows the SNMP user to manage the Ip Prec Drop Eligibility Pairs.  When the
         cmEthernetNetPortIpPrecDEEncType is of type 7p1d, 6p2d, 5p3d,
         the cmNetPortIpPrecDEPairTable can be used to specify 
         alternate pairs of priorities to specify drop eligibility/
         ineligibility."
    ::= { cmEthernetNetPortEntry 115 }

cmEthernetNetPortEncapPcpDEEncodingType OBJECT-TYPE
    SYNTAX      PcpDEEncType
    MAX-ACCESS  read-write
    STATUS      current
    DESCRIPTION
        "This is a port level control the mode of drop
         eligibility encoding in PCP bits of the VLAN tag in encapsulation header."
    ::= { cmEthernetNetPortEntry 116 }

cmEthernetNetPortEncapPcpDEPairsAction OBJECT-TYPE
    SYNTAX      PcpDEPairsAction
    MAX-ACCESS  read-write
    STATUS      current
    DESCRIPTION
        "This object allows the SNMP user to manage the Priority 
         Code Point (PCP) Drop Eligibility Pairs.  When the
         cmEthernetNetPortEncapPcpDEEncodingType is of type 7p1d, 6p2d, 5p3d,
         the cmNetPortEncapPcpDEPairTable can be used to specify 
         alternate pairs of priorities to specify drop eligibility/
         ineligibility."
    ::= { cmEthernetNetPortEntry 117 }

cmEthernetNetPortJdsuLoopbackSrcIp OBJECT-TYPE
    SYNTAX      IpAddress
    MAX-ACCESS  read-only
    STATUS      current
    DESCRIPTION
        "This object is applicable when there is jdsu l3 loopback."
    ::= { cmEthernetNetPortEntry 118 }

cmEthernetNetPortWfqSegmentationCOS OBJECT-TYPE
    SYNTAX      Integer32
    MAX-ACCESS  read-write
    STATUS      current
    DESCRIPTION
        "This object is used to specify the wfq segmentation COS value."
    ::= { cmEthernetNetPortEntry 119 }

cmEthernetNetPortWfqGroupCOS OBJECT-TYPE
    SYNTAX      Integer32
    MAX-ACCESS  read-write
    STATUS      current
    DESCRIPTION
        "This object is used to specify the wfq group COS value."
    ::= { cmEthernetNetPortEntry 120 }

cmEthernetNetPortWfqGroupEirLo OBJECT-TYPE
    SYNTAX      Unsigned32
    MAX-ACCESS  read-write
    STATUS      current
    DESCRIPTION
        "This object is used to specify the wfq group eir low 32 bits value."
    ::= { cmEthernetNetPortEntry 121 }

cmEthernetNetPortWfqGroupEirHi OBJECT-TYPE
    SYNTAX      Unsigned32
    MAX-ACCESS  read-write
    STATUS      current
    DESCRIPTION
        "This object is used to specify the wfq group eir high 32 bits value."
    ::= { cmEthernetNetPortEntry 122 }

cmEthernetNetPortSilentStartControl OBJECT-TYPE
    SYNTAX      TruthValue  
    MAX-ACCESS  read-write
    STATUS      current
    DESCRIPTION
         "Allows enabling/disabling of silent start."
    ::= { cmEthernetNetPortEntry 123 }

cmEthernetNetPortSfpLinkLength OBJECT-TYPE
    SYNTAX     Integer32
    MAX-ACCESS read-only
    STATUS     current
    DESCRIPTION
         "This object provides the SFP Link Length.
          This is applicable only when cmEthernetTrafficPortMediaType is fiber or coppersfp."
     ::= { cmEthernetNetPortEntry 124 }

cmEthernetNetPortOuterTagTpidOverride OBJECT-TYPE
    SYNTAX      TruthValue  
    MAX-ACCESS  read-write
    STATUS      current
    DESCRIPTION
         "This object allows enabling/disabling of Outer Tag TPID override.
          When enabled, values in Outer Tag TPID is applicable on egress
          Ethernet Network Port."
    ::= { cmEthernetNetPortEntry 125 }

cmEthernetNetPortOuterTagTpid OBJECT-TYPE
    SYNTAX     Unsigned32
    MAX-ACCESS read-write
    STATUS     current
    DESCRIPTION
         "This object allows to specify the egress Outer Tag TPID 
          on the Ethernet Network Port."
     ::= { cmEthernetNetPortEntry 126 }

-- Ethernet Port SFP params
cmEthernetNetPortSfpName OBJECT-TYPE
    SYNTAX  DisplayString (SIZE (0..32))
    MAX-ACCESS read-only
    STATUS     current
    DESCRIPTION
         "This object provides the official name of the SFP."
    ::= { cmEthernetNetPortEntry 127 }

cmEthernetNetPortSfpHardwareRevision OBJECT-TYPE
    SYNTAX  DisplayString (SIZE (0..16)) 
    MAX-ACCESS read-only
    STATUS     current
    DESCRIPTION
         "This object provides the hardware revision of the SFP."
    ::= { cmEthernetNetPortEntry 128 }

cmEthernetNetPortPersistentLoopbackControl OBJECT-TYPE
    SYNTAX      TruthValue  
    MAX-ACCESS  read-write
    STATUS      current
    DESCRIPTION
         "This object allows enabling/disabling of Persistent Loopback Control.
          The loopback configuration parameters do not survive restart as typically 
          maintenance actions are not persist. Setting this attribute to true shall 
          persist the loopback configuration parameters. When it is set to false the
          loopback configuration parameters shall not survive a restart."
    ::= { cmEthernetNetPortEntry 129 }

cmEthernetNetPortLoopbackTestReflectorIPv4AddressControl OBJECT-TYPE
    SYNTAX      TruthValue
    MAX-ACCESS  read-write
    STATUS      current
    DESCRIPTION
         "Control that enables/disables Test Reflector IPv4 Address
          to be used for Test Reflector IP Interface."
    ::= { cmEthernetNetPortEntry 130 }

cmEthernetNetPortLoopbackTestReflectorIPv4Address OBJECT-TYPE
    SYNTAX      IpAddress
    MAX-ACCESS  read-write
    STATUS      current
    DESCRIPTION
         "This is the Test Reflector Interface IPv4 address."
    ::= { cmEthernetNetPortEntry 131 }

cmEthernetNetPortLoopbackTestReflectorIPv6AddressControl OBJECT-TYPE
    SYNTAX      TruthValue
    MAX-ACCESS  read-write
    STATUS      current
    DESCRIPTION
         "Control that enables/disables Test Reflector IPv6 Address
          to be used for Test Reflector IP Interface."
    ::= { cmEthernetNetPortEntry 132 }

cmEthernetNetPortLoopbackTestReflectorIPv6Address OBJECT-TYPE
    SYNTAX      Ipv6Address
    MAX-ACCESS  read-write
    STATUS      current
    DESCRIPTION
         "This is the Test Reflector Interface IPv6 address."
    ::= { cmEthernetNetPortEntry 133 }

-- Ethernet Port SFP params
cmEthernetNetPortSfpIdentifierValue OBJECT-TYPE
    SYNTAX     SfpIdentifierValue
    MAX-ACCESS read-only
    STATUS     current
    DESCRIPTION
         "This object provides the SFP identifier value."
     ::= { cmEthernetNetPortEntry 134 }

--
--  Ethernet Network Port Control Protocol Disposition 
--
cmEthernetNetPortCpdTable  OBJECT-TYPE
    SYNTAX      SEQUENCE OF CmEthernetNetPortCpdEntry
    MAX-ACCESS  not-accessible
    STATUS      current
    DESCRIPTION
            "A list of entries corresponding to Ethernet Network Port 
             Control Protocol Disposition.
             This table is only
             applicable for FSP150CM Hub Shelf Release 3.x."
    ::= { cmFacilityObjects 8 }

cmEthernetNetPortCpdEntry OBJECT-TYPE
    SYNTAX      CmEthernetNetPortCpdEntry 
    MAX-ACCESS  not-accessible
    STATUS      current
    DESCRIPTION
            "A conceptual row in the cmEthernetNetPortCpdTable. 
             These entries represent a Control Protocol Disposition 
             filtering criteria on the Ethernet Network Port."
    INDEX { neIndex, shelfIndex, slotIndex, cmEthernetNetPortIndex, 
            cmEthernetNetPortCpdIndex }
    ::= { cmEthernetNetPortCpdTable 1 }


CmEthernetNetPortCpdEntry ::= SEQUENCE {
    -- Index
    cmEthernetNetPortCpdIndex             Integer32,

    -- CPD Filter Params
    cmEthernetNetPortCpdFilterType        CmControlProtocolFilterType,
    cmEthernetNetPortCpdFilterDescr       DisplayString,
    cmEthernetNetPortCpdDispType          CmControlProtocolDispType,
    cmEthernetNetPortCpdMacAddressMatch   MacAddress,
    cmEthernetNetPortCpdMacAddressMask    MacAddress,
    cmEthernetNetPortCpdEthertype         Integer32,
    cmEthernetNetPortCpdEthertypeMask     Integer32,
    cmEthernetNetPortCpdSubtype           Integer32,
    cmEthernetNetPortCpdSubtypeMask       Integer32
}

cmEthernetNetPortCpdIndex OBJECT-TYPE
    SYNTAX      Integer32 (1..65535)
    MAX-ACCESS  read-only
    STATUS      current
    DESCRIPTION
            "An arbitrary integer index value used to uniquely identify
             this CPD Service Entry."
    ::= { cmEthernetNetPortCpdEntry 1 }

cmEthernetNetPortCpdFilterType OBJECT-TYPE
    SYNTAX     CmControlProtocolFilterType
    MAX-ACCESS read-only
    STATUS     current
    DESCRIPTION
            "This enables specification of type of CPD Filter."
    ::= { cmEthernetNetPortCpdEntry 2 }

cmEthernetNetPortCpdFilterDescr OBJECT-TYPE
    SYNTAX  DisplayString (SIZE (0..32)) 
    MAX-ACCESS read-only
    STATUS     current
    DESCRIPTION
            "This provides description of CPD Filter."
    ::= { cmEthernetNetPortCpdEntry 3 }

cmEthernetNetPortCpdDispType OBJECT-TYPE
    SYNTAX     CmControlProtocolDispType
    MAX-ACCESS read-write
    STATUS     current
    DESCRIPTION
            "This enables specification of disposion type of CPD Filter."
    ::= { cmEthernetNetPortCpdEntry 4 }

cmEthernetNetPortCpdMacAddressMatch OBJECT-TYPE
    SYNTAX     MacAddress
    MAX-ACCESS read-write
    STATUS     current
    DESCRIPTION
         "This enables provides the Filter MAC Address to match."
    ::= { cmEthernetNetPortCpdEntry 5 }

cmEthernetNetPortCpdMacAddressMask OBJECT-TYPE
    SYNTAX     MacAddress
    MAX-ACCESS read-write
    STATUS     current
    DESCRIPTION
         "This enables provides the Filter MAC Address Mask to match."
    ::= { cmEthernetNetPortCpdEntry 6 }

cmEthernetNetPortCpdEthertype OBJECT-TYPE
    SYNTAX     Integer32 (0..65535)
    MAX-ACCESS read-write
    STATUS     current
    DESCRIPTION
         "This enables provides the Filter Ethertype to match."
    ::= { cmEthernetNetPortCpdEntry 7 }

cmEthernetNetPortCpdEthertypeMask OBJECT-TYPE
    SYNTAX     Integer32
    MAX-ACCESS read-write
    STATUS     current
    DESCRIPTION
         "This enables provides the Filter Ethertype Mask to match."
    ::= { cmEthernetNetPortCpdEntry 8 }

cmEthernetNetPortCpdSubtype OBJECT-TYPE
    SYNTAX     Integer32
    MAX-ACCESS read-write
    STATUS     current
    DESCRIPTION
         "This enables provides the Filter Subtype to match."
    ::= { cmEthernetNetPortCpdEntry 9 }

cmEthernetNetPortCpdSubtypeMask OBJECT-TYPE
    SYNTAX     Integer32
    MAX-ACCESS read-write
    STATUS     current
    DESCRIPTION
         "This enables provides the Filter Subtype Mask to match."
    ::= { cmEthernetNetPortCpdEntry 10 }


--
--  Ethernet Management Port 
--
cmEthernetMgmtPortTable  OBJECT-TYPE
    SYNTAX      SEQUENCE OF CmEthernetMgmtPortEntry
    MAX-ACCESS  not-accessible
    STATUS      current
    DESCRIPTION
            "A list of entries corresponding to Ethernet Management Port 
             Facilities for configuration purposes."
    ::= { cmFacilityObjects 9 }

cmEthernetMgmtPortEntry OBJECT-TYPE
    SYNTAX      CmEthernetMgmtPortEntry 
    MAX-ACCESS  not-accessible
    STATUS      current
    DESCRIPTION
            "A conceptual row in the cmEthernetMgmtPortTable."
    INDEX { neIndex, shelfIndex, slotIndex, cmEthernetMgmtPortIndex }
    ::= { cmEthernetMgmtPortTable 1 }

CmEthernetMgmtPortEntry ::= SEQUENCE {
    -- Port Indices 
    cmEthernetMgmtPortIndex                  Integer32,
    cmEthernetMgmtPortEntityIndex            PhysicalIndex,

    -- State Management params
    cmEthernetMgmtPortAdminState             AdminState,
    cmEthernetMgmtPortOperationalState       OperationalState,
    cmEthernetMgmtPortSecondaryState         SecondaryState,

    -- Generic Port params
    cmEthernetMgmtPortMTU                    Integer32,

    -- Generic Ethernet Port params
    cmEthernetMgmtPortConfigSpeed            EthernetPortSpeed,
    cmEthernetMgmtPortNegotiatedSpeed        EthernetPortSpeed,
    cmEthernetMgmtPortMDIXType               CmEthernetMDIXType,

    --New objects available with FSP150CC GE206 device (Release 4.1CC)
    cmEthernetMgmtPortMDIXStatus             CmEthernetMDIXType,  

    cmEthernetMgmtPortMediaType              EthernetMediaType
}
    
-- Port Indices 
cmEthernetMgmtPortIndex OBJECT-TYPE
    SYNTAX      Integer32 (1..65535)
    MAX-ACCESS  read-only
    STATUS      current
    DESCRIPTION
            "An integer index value used to uniquely identify
             this Ethernet Management Port within a card.
             Note that each Ethernet Management Port is uniquely identified
             by the indices neIndex, shelfIndex, 
             slotIndex, cmEthernetMgmtPortIndex." 
    ::= { cmEthernetMgmtPortEntry 1 }

cmEthernetMgmtPortEntityIndex OBJECT-TYPE
    SYNTAX      PhysicalIndex 
    MAX-ACCESS  read-only
    STATUS      current
    DESCRIPTION
           "Entity Index from ENTITY-MIB for this port."
    ::= { cmEthernetMgmtPortEntry 2 }

-- State Management params
cmEthernetMgmtPortAdminState OBJECT-TYPE
    SYNTAX      AdminState 
    MAX-ACCESS  read-write
    STATUS      current
    DESCRIPTION
            "This object represents the Administrative State of the Ethernet 
             Management Port."
    ::= { cmEthernetMgmtPortEntry 3 }

cmEthernetMgmtPortOperationalState OBJECT-TYPE
    SYNTAX      OperationalState 
    MAX-ACCESS  read-only
    STATUS      current
    DESCRIPTION
            "This object represents the Operational State of the Ethernet 
             Management Port."
    ::= { cmEthernetMgmtPortEntry 4 }

cmEthernetMgmtPortSecondaryState OBJECT-TYPE
    SYNTAX      SecondaryState 
    MAX-ACCESS  read-only
    STATUS      current
    DESCRIPTION
            "This object represents the Secondary State of the Ethernet 
             Management Port."
    ::= { cmEthernetMgmtPortEntry 5 }

-- Generic Port params
cmEthernetMgmtPortMTU OBJECT-TYPE
    SYNTAX      Integer32 
    MAX-ACCESS  read-only
    STATUS      current
    DESCRIPTION
            "This object provides the MTU on the Ethernet Management Port."
    ::= { cmEthernetMgmtPortEntry 6 }

cmEthernetMgmtPortConfigSpeed OBJECT-TYPE
    SYNTAX     EthernetPortSpeed
    MAX-ACCESS read-write
    STATUS     current
    DESCRIPTION
            "This object allows to configure the speed of the 
             Ethernet Management Port."
    ::= { cmEthernetMgmtPortEntry 7 }

cmEthernetMgmtPortNegotiatedSpeed OBJECT-TYPE
    SYNTAX     EthernetPortSpeed
    MAX-ACCESS read-only
    STATUS     current
    DESCRIPTION
            "This object provides the negotiated speed of the 
             Ethernet Management Port."
    ::= { cmEthernetMgmtPortEntry 8 }

cmEthernetMgmtPortMDIXType OBJECT-TYPE
    SYNTAX     CmEthernetMDIXType
    MAX-ACCESS read-write
    STATUS     current
    DESCRIPTION
            "This object allows management of MDIX property on  
             Ethernet Management Port."
    ::= { cmEthernetMgmtPortEntry 9 }

cmEthernetMgmtPortMDIXStatus OBJECT-TYPE
    SYNTAX     CmEthernetMDIXType
    MAX-ACCESS read-only
    STATUS     current
    DESCRIPTION
         "This object provides the current MDIX status of the 
          Ethernet Management port."
     ::= { cmEthernetMgmtPortEntry 10 }

cmEthernetMgmtPortMediaType OBJECT-TYPE
    SYNTAX     EthernetMediaType
    MAX-ACCESS read-only
    STATUS     current
    DESCRIPTION
            "This object represents the type of Ethernet Media on the 
             Ethernet Management Port."
    ::= { cmEthernetMgmtPortEntry 11 }


--Priority Mapping
cmPrioMapTable  OBJECT-TYPE
    SYNTAX      SEQUENCE OF CmPrioMapEntry
    MAX-ACCESS  not-accessible
    STATUS      current
    DESCRIPTION
            "A list of entries corresponding to Ethernet Priority Mappings
             in multi Class of Service (COS) mode. This table is applicable
             only when the Access Port is in connection-oriented evpl mode."
    ::= { cmFacilityObjects 10 }

cmPrioMapEntry OBJECT-TYPE
    SYNTAX      CmPrioMapEntry
    MAX-ACCESS  not-accessible
    STATUS      current
    DESCRIPTION
            "A conceptual row in the cmPrioMapTable."
    INDEX { neIndex, shelfIndex, slotIndex, 
            cmEthernetAccPortIndex, cmPrioMapIndex }
    ::= { cmPrioMapTable 1 }

CmPrioMapEntry ::= SEQUENCE {
    cmPrioMapIndex            Integer32,
    cmPrioMapInPriority       Integer32,
    cmPrioMapXTagControl      PrioMapControlType,
    cmPrioMapXTagPriority     VlanPriority,
    cmPrioMapCOS              Integer32,
    cmPrioMapOuterTagPriority VlanPriority,
    cmPrioMapInnerTagPriority VlanPriority
}

cmPrioMapIndex OBJECT-TYPE
    SYNTAX      Integer32 (1..64)
    MAX-ACCESS  read-only
    STATUS      current
    DESCRIPTION
            "The integer index value corresponding to a priority value
             based on the cmEthernetAccPortPrioMapMode.
             In case of TOS and 8021P, valid indices are 1 to 8,
             in case of DSCP, valid indices are 1 to 64."
    ::= { cmPrioMapEntry 1 }

cmPrioMapInPriority OBJECT-TYPE
    SYNTAX      Integer32 (0..63)
    MAX-ACCESS  read-write
    STATUS      current
    DESCRIPTION
            "The integer index value corresponding to a priority value
             based on the cmEthernetAccPortPrioMapMode.
             In case of TOS and 8021P, valid indices are 0 to 7,
             in case of DSCP, valid indices are 0 to 63."
    ::= { cmPrioMapEntry 2 }

cmPrioMapXTagControl OBJECT-TYPE
    SYNTAX      PrioMapControlType
    MAX-ACCESS  read-write
    STATUS      current
    DESCRIPTION
            "This allows specification of whether the priority of
             incoming X-TAG should be swapped with cmPrioMapXTagPriority."
    ::= { cmPrioMapEntry 3 }

cmPrioMapXTagPriority OBJECT-TYPE
    SYNTAX      VlanPriority
    MAX-ACCESS  read-write
    STATUS      current
    DESCRIPTION
            "This allows specification of the VLAN priority that
             will replace the incoming X-TAG's priority.  This is
             applicable with cmPrioMapXTagControl as 'swap'."
    ::= { cmPrioMapEntry 4 }

cmPrioMapCOS OBJECT-TYPE
    SYNTAX      Integer32 (0..7)
    MAX-ACCESS  read-write
    STATUS      current
    DESCRIPTION
            "This allows specification of the COS Priority, i.e.
             this helps in determining the appropriate COS Policer for
             the Flow."
    ::= { cmPrioMapEntry 5 }

cmPrioMapOuterTagPriority OBJECT-TYPE
    SYNTAX      VlanPriority
    MAX-ACCESS  read-write
    STATUS      current
    DESCRIPTION
            "This allows specification of the VLAN priority that
             will replace the outgoing (A2N direction) outer-tag's priority.  
             Note that, each flow participates or not in outer-tag 
             priority mapping, using the object 'cmFlowOuterTagPrioEnabled'."
    ::= { cmPrioMapEntry 6 }

cmPrioMapInnerTagPriority OBJECT-TYPE
    SYNTAX      VlanPriority
    MAX-ACCESS  read-write
    STATUS      current
    DESCRIPTION
            "This allows specification of the VLAN priority that
             will replace the outgoing (A2N direction) inner-tag's (i.e. second tag) 
             priority.  Note that, each flow participates or not in inner-tag 
             priority mapping, using the object 'cmFlowInnerTagPrioEnabled'."
    ::= { cmPrioMapEntry 7 }

--Flow Policer
cmQosFlowPolicerTable  OBJECT-TYPE
    SYNTAX      SEQUENCE OF CmQosFlowPolicerEntry
    MAX-ACCESS  not-accessible
    STATUS      current
    DESCRIPTION
        "A list of entries corresponding to Ethernet Quality of Service 
         Policer for configuration purposes."
    ::= { cmFacilityObjects 11 }

cmQosFlowPolicerEntry OBJECT-TYPE
    SYNTAX      CmQosFlowPolicerEntry 
    MAX-ACCESS  not-accessible
    STATUS      current
    DESCRIPTION
         "A conceptual row in the cmQosFlowPolicerTable. 
          These entries represent a Quality of Service Policer."
    INDEX { neIndex, shelfIndex, slotIndex, cmEthernetAccPortIndex, 
            cmFlowIndex, cmQosFlowPolicerTypeIndex, cmQosFlowPolicerIndex }
    ::= { cmQosFlowPolicerTable 1 }

CmQosFlowPolicerEntry ::= SEQUENCE {
    cmQosFlowPolicerTypeIndex             Integer32,
    cmQosFlowPolicerIndex                 Integer32,
    cmQosFlowPolicerDirection             TrafficDirection,

    -- State Management params
    cmQosFlowPolicerAdminState            AdminState,
    cmQosFlowPolicerOperationalState      OperationalState,
    cmQosFlowPolicerSecondaryState        SecondaryState,

    cmQosFlowPolicerCIRLo                 Unsigned32,
    cmQosFlowPolicerCIRHi                 Unsigned32,
    cmQosFlowPolicerEIRLo                 Unsigned32,
    cmQosFlowPolicerEIRHi                 Unsigned32,
    cmQosFlowPolicerCBS                   Integer32,
    cmQosFlowPolicerEBS                   Integer32,
    cmQosFlowPolicerAlgorithm             PolicerAlgorithmType,
    cmQosFlowPolicerColorMode             PolicerColorMode,
    cmQosFlowPolicerColorMarkingFlag      TruthValue,
    cmQosFlowPolicerCouplingFlag          TruthValue,
    cmQosFlowPolicerAssociatedShaper      VariablePointer,
    cmQosFlowPolicerStorageType           StorageType,
    cmQosFlowPolicerRowStatus             RowStatus,
    cmQosFlowPolicerCIRMaxHi              Unsigned32,
    cmQosFlowPolicerCIRMaxLo              Unsigned32,
    cmQosFlowPolicerEIRMaxHi              Unsigned32,
    cmQosFlowPolicerEIRMaxLo              Unsigned32,
    cmQosFlowPolicerEnvelopeObject        VariablePointer,
    cmQosFlowPolicerRank                  Integer32,
    cmQosFlowPolicerPolicingEnabled       TruthValue
}

cmQosFlowPolicerTypeIndex OBJECT-TYPE
    SYNTAX      Integer32 (1..4)
    MAX-ACCESS  read-create
    STATUS      current
    DESCRIPTION
            "The unique index value corresponding to a Quality of Service 
             Policer's direction.
             Values 1 and 2 are applicable to the Access Flow Policer
              - value of 1 stands for A2N direction,
              - value of 2 stands for N2A direction.
             Values 3 and 4 are applicable to Pass-thru Flow Policer 
               (new in 5.6CC release):
               - value of 3 stands for N1toN2 direction
               - value of 4 stands for N2toN1 direction
           "
    ::= { cmQosFlowPolicerEntry 1 }

cmQosFlowPolicerIndex OBJECT-TYPE
    SYNTAX      Integer32 (1..16)
    MAX-ACCESS  read-create
    STATUS      current
    DESCRIPTION
            "The Policer Index that represents the COS level.  This
             is applicable in case of a Multi COS flow. Index 1
             represents COS 0; Index 2 represents COS 1 and so on. 

             In release 5.6CC the range is extended to 1..16 to support duplicate
             N2A policers on a Flow. The duplicate policers are created under a Flow 
             if network interface of the Flow is ERP Group or Split Horizon Group. 
             In case of multi-cos Flow indices 1..8 represent policers of COS 0..7 
             going from Network 1 port; indices 9..16 represent policers for COS 0..7 
             going from Network 2 port.
             In case of single-cos Flow index 1 represents policer going from Network 1
             port; index 9 represents policer going from Network 2 port.
             "
    ::= { cmQosFlowPolicerEntry 2 }

cmQosFlowPolicerDirection OBJECT-TYPE
    SYNTAX      TrafficDirection 
    MAX-ACCESS  read-create
    STATUS      current
    DESCRIPTION
            "This object is allows specification of Policer direction as
             'a2n' or 'n2a'."
    ::= { cmQosFlowPolicerEntry 3 }

-- State Management params
cmQosFlowPolicerAdminState OBJECT-TYPE
    SYNTAX      AdminState 
    MAX-ACCESS  read-write
    STATUS      current
    DESCRIPTION
            "This object represents the Administrative State of 
             the QOS Flow Policer." 
    ::= { cmQosFlowPolicerEntry 4 }

cmQosFlowPolicerOperationalState OBJECT-TYPE
    SYNTAX      OperationalState 
    MAX-ACCESS  read-only
    STATUS      current
    DESCRIPTION
            "This object represents the Operational State of the QOS Flow Policer." 
    ::= { cmQosFlowPolicerEntry 5 }

cmQosFlowPolicerSecondaryState OBJECT-TYPE
    SYNTAX      SecondaryState 
    MAX-ACCESS  read-only
    STATUS      current
    DESCRIPTION
            "This object represents the Secondary State of the QOS Flow Policer." 
    ::= { cmQosFlowPolicerEntry 6 }

cmQosFlowPolicerCIRLo OBJECT-TYPE
    SYNTAX     Unsigned32
    MAX-ACCESS read-create
    STATUS     current
    DESCRIPTION
         "This object allows specification of the Commited Information
          Rate(CIR) on Policer.  This represents the lower 32 bits of the
          CIR."
     ::= { cmQosFlowPolicerEntry 7 }

cmQosFlowPolicerCIRHi OBJECT-TYPE
    SYNTAX     Unsigned32
    MAX-ACCESS read-create
    STATUS     current
    DESCRIPTION
         "This object allows specification of the Commited Information
          Rate(CIR) on Policer.  This represents the upper 32 bits of the
          CIR."
     ::= { cmQosFlowPolicerEntry 8 }

cmQosFlowPolicerEIRLo OBJECT-TYPE
    SYNTAX     Unsigned32
    MAX-ACCESS read-create
    STATUS     current
    DESCRIPTION
         "This object allows specification of the Excess Information
          Rate(EIR) on the Policer.  This represents the lower 32 bits
          of the EIR."
     ::= { cmQosFlowPolicerEntry 9 }

cmQosFlowPolicerEIRHi OBJECT-TYPE
    SYNTAX     Unsigned32
    MAX-ACCESS read-create
    STATUS     current
    DESCRIPTION
         "This object allows specification of the Excess Information
          Rate(EIR) on the Policer.  This represents the upper 32 bits
          of the EIR."
     ::= { cmQosFlowPolicerEntry 10 }

cmQosFlowPolicerCBS OBJECT-TYPE
    SYNTAX     Integer32
    MAX-ACCESS read-create
    STATUS     current
    DESCRIPTION
         "This object allows specification of the Commited Burst Size
          (CBS) on Policer."
     ::= { cmQosFlowPolicerEntry 11 }

cmQosFlowPolicerEBS OBJECT-TYPE
    SYNTAX     Integer32
    MAX-ACCESS read-create
    STATUS     current
    DESCRIPTION
         "This object allows specification of the Excess Burst Size
          (EBS) on the Policer."
     ::= { cmQosFlowPolicerEntry 12 }

cmQosFlowPolicerAlgorithm OBJECT-TYPE
    SYNTAX      PolicerAlgorithmType 
    MAX-ACCESS  read-only
    STATUS      current
    DESCRIPTION
          "This object allows specification of Policer algorithm as
           'srTCM' (Single Rate Triple Color Marking) or 'trTCM' (Two Rate
           Triple Color Marking)."
    ::= { cmQosFlowPolicerEntry 13 }

cmQosFlowPolicerColorMode OBJECT-TYPE
    SYNTAX      PolicerColorMode 
    MAX-ACCESS  read-create
    STATUS      current
    DESCRIPTION
          "This object allows specification of Policer Color Mode as
           'color-aware' or 'color-blind'."
    ::= { cmQosFlowPolicerEntry 14 }

cmQosFlowPolicerColorMarkingFlag OBJECT-TYPE
    SYNTAX      TruthValue 
    MAX-ACCESS  read-create
    STATUS      deprecated
    DESCRIPTION
          "This object allows specification of Policer Color Marking Flag.
           The policer will set/clear the DEI (Drop Eligibility Indication) 
           bit of the frame on an S-TAG if this flag is enabled.
           This object is not supported - setting any value will not have effect
           on the System."
    ::= { cmQosFlowPolicerEntry 15 }

cmQosFlowPolicerCouplingFlag OBJECT-TYPE
    SYNTAX      TruthValue
    MAX-ACCESS  read-create
    STATUS      current
    DESCRIPTION
       "This object allows specification of Policer Coupling Flag.
        When coupling is enabled, tokens that would normally be 
        added to the C-bucket are passed to the E-bucket only once the CIR
        bucket has reached its CBS level. Therefore under this condition
        the E-bucket is being filled at the rate of CIR + EIR. 
        Normally the long term average of frames declared yellow is 
        bounded by the EIR. Coupling is a function to allow the 
        long term average of frames declared yellow to be bounded by 
        CIR + EIR. This allows a higher volume of yellow frames 
        to be delivered/received if the arrival of green marked frames 
        is low.  Tokens from the E-bucket do NOT get passed to the 
        C-bucket once the EBS level has been reached.
        Enabling coupling in combination with a provisioned EIR of 0 
        allows for a single rate three color marking (srTCM) algorithm 
        to be established.  In this situation the E-bucket is filled at the 
        CIR rate in the case the C-bucket is filled to its CBS level."
    ::= { cmQosFlowPolicerEntry 16 }

cmQosFlowPolicerAssociatedShaper OBJECT-TYPE
    SYNTAX     VariablePointer 
    MAX-ACCESS read-create
    STATUS     current
    DESCRIPTION
         "This object allows specification of the QOS Shaper
          associated with this Policer. Multiple Policers can map
          to single Shaper. The corresponding row with the 
          specified QOS value must exist in 
          cmQosShaperTable when this value is specified."
     ::= { cmQosFlowPolicerEntry 17 }

cmQosFlowPolicerStorageType OBJECT-TYPE
    SYNTAX     StorageType
    MAX-ACCESS read-create
    STATUS     current
    DESCRIPTION
            "The type of storage configured for this entry."
    ::= { cmQosFlowPolicerEntry 18 }

cmQosFlowPolicerRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmQosFlowPolicerRowStatus supported are
            createAndGo(4) and destroy(6).  All mandatory attributes
            must be specified in a single SNMP SET request with
            cmQosFlowPolicerRowStatus value as createAndGo(4).
            Upon successful row creation, this object has a
            value of active(1).

            The cmQosFlowPolicerRowStatus object may be modified if
            the associated instance of this object is equal to active(1)."
    ::= { cmQosFlowPolicerEntry 19 }

cmQosFlowPolicerCIRMaxHi OBJECT-TYPE
    SYNTAX     Unsigned32
    MAX-ACCESS read-write
    STATUS     current
    DESCRIPTION
         "This object allows specification of the Commited Information
          Rate(CIR) MAX on Policer.  This represents the high 32 bits."
     ::= { cmQosFlowPolicerEntry 20 }

cmQosFlowPolicerCIRMaxLo OBJECT-TYPE
    SYNTAX     Unsigned32
    MAX-ACCESS read-write
    STATUS     current
    DESCRIPTION
         "This object allows specification of the Commited Information
          Rate(CIR) MAX on Policer.  This represents the lower 32 bits."
     ::= { cmQosFlowPolicerEntry 21 }

cmQosFlowPolicerEIRMaxHi OBJECT-TYPE
    SYNTAX     Unsigned32
    MAX-ACCESS read-write
    STATUS     current
    DESCRIPTION
         "This object allows specification of the Excess Information
          Rate(EIR) MAX on the Policer.  This represents the high 32 bits."
     ::= { cmQosFlowPolicerEntry 22 }

cmQosFlowPolicerEIRMaxLo OBJECT-TYPE
    SYNTAX     Unsigned32
    MAX-ACCESS read-write
    STATUS     current
    DESCRIPTION
         "This object allows specification of the Excess Information
          Rate(EIR) MAX on the Policer.  This represents the lower 32 bits."
     ::= { cmQosFlowPolicerEntry 23 }

cmQosFlowPolicerEnvelopeObject OBJECT-TYPE
    SYNTAX     VariablePointer
    MAX-ACCESS read-write
    STATUS     current
    DESCRIPTION
         "This object allows specification of envelope object."
     ::= { cmQosFlowPolicerEntry 24 }

cmQosFlowPolicerRank OBJECT-TYPE
    SYNTAX     Integer32
    MAX-ACCESS read-write
    STATUS     current
    DESCRIPTION
         "This object allows specification of rank value."
     ::= { cmQosFlowPolicerEntry 25 }

cmQosFlowPolicerPolicingEnabled OBJECT-TYPE
    SYNTAX     TruthValue
    MAX-ACCESS read-write
    STATUS     current
    DESCRIPTION
         "This object describes whether the policing is enabled."
     ::= { cmQosFlowPolicerEntry 26 }


--
--  Ethernet Access Port Quality of Service Shaper 
--
cmAccPortQosShaperTable  OBJECT-TYPE
    SYNTAX      SEQUENCE OF CmAccPortQosShaperEntry
    MAX-ACCESS  not-accessible
    STATUS      current
    DESCRIPTION
            "A list of entries corresponding to Ethernet Access Port 
             Quality of Service Shaper for configuration purposes.
             These shapers can be managed when the Access Port is
             in evpl mode and are relevant for traffic in the
             network to access direction."
    ::= { cmFacilityObjects 12 }

cmAccPortQosShaperEntry OBJECT-TYPE
    SYNTAX      CmAccPortQosShaperEntry 
    MAX-ACCESS  not-accessible
    STATUS      current
    DESCRIPTION
            "A conceptual row in the cmAccPortQosShaperTable. 
             These entries represent a Quality of Service Shaper."
    INDEX { neIndex, shelfIndex, slotIndex, cmEthernetAccPortIndex, 
            cmAccPortQosShaperIndex }
    ::= { cmAccPortQosShaperTable 1 }

CmAccPortQosShaperEntry ::= SEQUENCE {
    -- QOS Shaper Index/Id
    cmAccPortQosShaperIndex               Integer32,
    cmAccPortQosShaperDirection           TrafficDirection,

    -- State Management params
    cmAccPortQosShaperAdminState          AdminState,
    cmAccPortQosShaperOperationalState    OperationalState,
    cmAccPortQosShaperSecondaryState      SecondaryState,

    -- QOS Shaper Properties
    cmAccPortQosShaperCIRLo               Unsigned32,
    cmAccPortQosShaperCIRHi               Unsigned32,
    cmAccPortQosShaperEIRLo               Unsigned32,
    cmAccPortQosShaperEIRHi               Unsigned32,
    cmAccPortQosShaperCBS                 Unsigned32,
    cmAccPortQosShaperEBS                 Unsigned32,
    cmAccPortQosShaperBufferSize          Unsigned32,
    cmAccPortQosShaperCOS                 Integer32,
    cmAccPortQosShaperSoamCIRLo           Unsigned32,
    cmAccPortQosShaperSoamCIRHi           Unsigned32,
    cmAccPortQosShaperSoamEIRLo           Unsigned32,
    cmAccPortQosShaperSoamEIRHi           Unsigned32,

    --wred threshold
    cmAccPortQosShaperWredGreenMinQueueThreshold       Unsigned32,
    cmAccPortQosShaperWredGreenMaxQueueThreshold       Unsigned32,
    cmAccPortQosShaperWredGreenDropProbability         Unsigned32,
    cmAccPortQosShaperWredYellowMinQueueThreshold      Unsigned32,
    cmAccPortQosShaperWredYellowMaxQueueThreshold      Unsigned32,
    cmAccPortQosShaperWredYellowDropProbability        Unsigned32,
    cmAccPortQosShaperAvgFrameSizeBeforeFragment       Integer32,
    cmAccPortQosShaperWfqWeight                        Integer32
}

cmAccPortQosShaperIndex OBJECT-TYPE
    SYNTAX      Integer32 (1..8)
    MAX-ACCESS  read-create
    STATUS      current
    DESCRIPTION
            "The unique integer index value corresponding to a 
             Quality of Service Shaper."
    ::= { cmAccPortQosShaperEntry 1 }

cmAccPortQosShaperDirection OBJECT-TYPE
    SYNTAX      TrafficDirection 
    MAX-ACCESS  read-only
    STATUS      current
    DESCRIPTION
            "The direction of the Quality of Service Shaper."
    ::= { cmAccPortQosShaperEntry 2 }

-- State Management params
cmAccPortQosShaperAdminState OBJECT-TYPE
    SYNTAX      AdminState 
    MAX-ACCESS  read-write
    STATUS      current
    DESCRIPTION
            "This object represents the Administrative State of 
             the QOS Shaper." 
    ::= { cmAccPortQosShaperEntry 3 }

cmAccPortQosShaperOperationalState OBJECT-TYPE
    SYNTAX      OperationalState 
    MAX-ACCESS  read-only
    STATUS      current
    DESCRIPTION
            "This object represents the Operational State of the QOS Shaper." 
    ::= { cmAccPortQosShaperEntry 4 }

cmAccPortQosShaperSecondaryState OBJECT-TYPE
    SYNTAX      SecondaryState 
    MAX-ACCESS  read-only
    STATUS      current
    DESCRIPTION
            "This object represents the Secondary State of the QOS Shaper." 
    ::= { cmAccPortQosShaperEntry 5 }

cmAccPortQosShaperCIRLo OBJECT-TYPE
    SYNTAX     Unsigned32
    MAX-ACCESS read-create
    STATUS     current
    DESCRIPTION
         "This object represents the Commited Information
          Rate(CIR) (Lower 32 bits)of a Shaper."
     ::= { cmAccPortQosShaperEntry 6 }

cmAccPortQosShaperCIRHi OBJECT-TYPE
    SYNTAX     Unsigned32
    MAX-ACCESS read-create
    STATUS     current
    DESCRIPTION
         "This object represents the Commited Information
          Rate(CIR) (Higher 32 bits) of a Shaper."
     ::= { cmAccPortQosShaperEntry 7 }

cmAccPortQosShaperEIRLo OBJECT-TYPE
    SYNTAX     Unsigned32
    MAX-ACCESS read-create
    STATUS     current
    DESCRIPTION
         "This object represents the Excess Information
          Rate(EIR) (Higher 32 bits) on the Shaper."
     ::= { cmAccPortQosShaperEntry 8 }

cmAccPortQosShaperEIRHi OBJECT-TYPE
    SYNTAX     Unsigned32
    MAX-ACCESS read-create
    STATUS     current
    DESCRIPTION
         "This object represents the Excess Information
          Rate(EIR) (Higher 32 bits) on the Shaper."
     ::= { cmAccPortQosShaperEntry 9 }

cmAccPortQosShaperCBS OBJECT-TYPE
    SYNTAX     Unsigned32
    MAX-ACCESS read-create
    STATUS     current
    DESCRIPTION
         "This object represents the Commited Burst Size (CBS) of the Shaper."
     ::= { cmAccPortQosShaperEntry 10 }

cmAccPortQosShaperEBS OBJECT-TYPE
    SYNTAX     Unsigned32
    MAX-ACCESS read-create
    STATUS     current
    DESCRIPTION
         "This object represents the Excess Burst Size (EBS) of the Shaper."
     ::= { cmAccPortQosShaperEntry 11 }

cmAccPortQosShaperBufferSize OBJECT-TYPE
    SYNTAX     Unsigned32
    MAX-ACCESS read-create
    STATUS     current
    DESCRIPTION
         "This object represents the Buffer Size of the Shaper."
     ::= { cmAccPortQosShaperEntry 12 }

cmAccPortQosShaperCOS OBJECT-TYPE
    SYNTAX     Integer32 (0..7)
    MAX-ACCESS read-only
    STATUS     current
    DESCRIPTION
            "This object provides the COS (Class of Service)
             value for the QOS Shaper."
    ::= { cmAccPortQosShaperEntry 13 }

cmAccPortQosShaperSoamCIRLo OBJECT-TYPE
    SYNTAX     Unsigned32
    MAX-ACCESS read-create
    STATUS     current
    DESCRIPTION
         "This object represents the Soam Commited Information
          Rate(SOAM-CIR) (Lower 32 bits)of a Shaper."
     ::= { cmAccPortQosShaperEntry 14 }

cmAccPortQosShaperSoamCIRHi OBJECT-TYPE
    SYNTAX     Unsigned32
    MAX-ACCESS read-create
    STATUS     current
    DESCRIPTION
         "This object represents the Soam Commited Information
          Rate(SOAM-CIR) (Higher 32 bits) of a Shaper."
     ::= { cmAccPortQosShaperEntry 15 }

cmAccPortQosShaperSoamEIRLo OBJECT-TYPE
    SYNTAX     Unsigned32
    MAX-ACCESS read-create
    STATUS     current
    DESCRIPTION
         "This object represents the Soam Excess Information
          Rate(SOAM-EIR) (Higher 32 bits) on the Shaper."
     ::= { cmAccPortQosShaperEntry 16 }

cmAccPortQosShaperSoamEIRHi OBJECT-TYPE
    SYNTAX     Unsigned32
    MAX-ACCESS read-create
    STATUS     current
    DESCRIPTION
         "This object represents the Soam Excess Information
          Rate(SOAM-EIR) (Higher 32 bits) on the Shaper."
     ::= { cmAccPortQosShaperEntry 17 }

cmAccPortQosShaperWredGreenMinQueueThreshold OBJECT-TYPE
    SYNTAX     Unsigned32
    MAX-ACCESS read-create
    STATUS     current
    DESCRIPTION
         "This object represents the Wred green packet min queue threshold value."
     ::= { cmAccPortQosShaperEntry 18 }

cmAccPortQosShaperWredGreenMaxQueueThreshold OBJECT-TYPE
    SYNTAX     Unsigned32
    MAX-ACCESS read-create
    STATUS     current
    DESCRIPTION
         "This object represents the Wred green packet max queue threshold value."
     ::= { cmAccPortQosShaperEntry 19 }

cmAccPortQosShaperWredGreenDropProbability OBJECT-TYPE
    SYNTAX     Unsigned32
    MAX-ACCESS read-create
    STATUS     current
    DESCRIPTION
         "This object represents the Wred green packet drop probability."
     ::= { cmAccPortQosShaperEntry 20 }

cmAccPortQosShaperWredYellowMinQueueThreshold OBJECT-TYPE
    SYNTAX     Unsigned32
    MAX-ACCESS read-create
    STATUS     current
    DESCRIPTION
         "This object represents the Wred yellow packet min queue threshold value."
     ::= { cmAccPortQosShaperEntry 21 }

cmAccPortQosShaperWredYellowMaxQueueThreshold OBJECT-TYPE
    SYNTAX     Unsigned32
    MAX-ACCESS read-create
    STATUS     current
    DESCRIPTION
         "This object represents the Wred yellow packet max queue threshold value."
     ::= { cmAccPortQosShaperEntry 22 }

cmAccPortQosShaperWredYellowDropProbability OBJECT-TYPE
    SYNTAX     Unsigned32
    MAX-ACCESS read-create
    STATUS     current
    DESCRIPTION
         "This object represents the Wred yellow packet drop probability."
     ::= { cmAccPortQosShaperEntry 23 }

cmAccPortQosShaperAvgFrameSizeBeforeFragment OBJECT-TYPE
    SYNTAX     Integer32
    MAX-ACCESS read-write
    STATUS     current
    DESCRIPTION
         "This object specifies the average frame size before fragmentation."
     ::= { cmAccPortQosShaperEntry 24 }

cmAccPortQosShaperWfqWeight OBJECT-TYPE
    SYNTAX     Integer32
    MAX-ACCESS read-write
    STATUS     current
    DESCRIPTION
         "This object specifies the wfq weight value."
     ::= { cmAccPortQosShaperEntry 25 }

--
--
--  Ethernet Access Port Control Protocol Disposition V2
--
cmEthernetAccPortCpdV2Table  OBJECT-TYPE
    SYNTAX      SEQUENCE OF CmEthernetAccPortCpdV2Entry
    MAX-ACCESS  not-accessible
    STATUS      current
    DESCRIPTION
            "A list of entries corresponding to Ethernet Access Port 
             Control Protocol Disposition (CPD) V2.  This support of
             CPD is provided on the GE206/GE201 device."
    ::= { cmFacilityObjects 13 }

cmEthernetAccPortCpdV2Entry OBJECT-TYPE
    SYNTAX      CmEthernetAccPortCpdV2Entry 
    MAX-ACCESS  not-accessible
    STATUS      current
    DESCRIPTION
            "A conceptual row in the cmEthernetAccPortCpdV2Table. 
             These entries represent a Control Protocol Disposition 
             filtering criteria on the Ethernet Access Port."
    INDEX { neIndex, shelfIndex, slotIndex, cmEthernetAccPortIndex, 
            cmEthernetAccPortCpdV2Index }
    ::= { cmEthernetAccPortCpdV2Table 1 }

CmEthernetAccPortCpdV2Entry ::= SEQUENCE {
    -- Index
    cmEthernetAccPortCpdV2Index            Integer32,

    -- Filtering Criteria
    cmEthernetAccPortCpdV2CiscoGroupDispType        CmControlProtocolDispType,
    cmEthernetAccPortCpdV2IslDispType               CmControlProtocolDispType,
    cmEthernetAccPortCpdV2PagpDispType              CmControlProtocolDispType,
    cmEthernetAccPortCpdV2UdldDispType              CmControlProtocolDispType,
    cmEthernetAccPortCpdV2CdpDispType               CmControlProtocolDispType,
    cmEthernetAccPortCpdV2VtpDispType               CmControlProtocolDispType,
    cmEthernetAccPortCpdV2DtpDispType               CmControlProtocolDispType,
    cmEthernetAccPortCpdV2PvstpPlusDispType         CmControlProtocolDispType,
    cmEthernetAccPortCpdV2UplinkFastDispType        CmControlProtocolDispType,
    cmEthernetAccPortCpdV2VlanBridgeDispType        CmControlProtocolDispType,
    cmEthernetAccPortCpdV2L2PTDispType              CmControlProtocolDispType,
    cmEthernetAccPortCpdV2BridgeGroupDispType       CmControlProtocolDispType,
    cmEthernetAccPortCpdV2BPDUDispType              CmControlProtocolDispType,
    cmEthernetAccPortCpdV2PauseDispType             CmControlProtocolDispType,
    cmEthernetAccPortCpdV2LACPDispType              CmControlProtocolDispType,
    cmEthernetAccPortCpdV2LACPMarkerDispType        CmControlProtocolDispType,
    cmEthernetAccPortCpdV2EfmOamDispType            CmControlProtocolDispType,
    cmEthernetAccPortCpdV2SSMDispType               CmControlProtocolDispType,
    cmEthernetAccPortCpdV2PortAuthenDispType        CmControlProtocolDispType,
    cmEthernetAccPortCpdV2BridgeReservedDispType    CmControlProtocolDispType,
    cmEthernetAccPortCpdV2LANBridgesDispType        CmControlProtocolDispType,
    cmEthernetAccPortCpdV2GARPGroupDispType         CmControlProtocolDispType,
    cmEthernetAccPortCpdV2GMRPDispType              CmControlProtocolDispType,
    cmEthernetAccPortCpdV2GVRPDispType              CmControlProtocolDispType,
    cmEthernetAccPortCpdV2GARPDispType              CmControlProtocolDispType,
    --
    cmEthernetAccPortCpdV2LLDPDispType              CmControlProtocolDispType,
    cmEthernetAccPortCpdV2ELMIDispType              CmControlProtocolDispType,
    cmEthernetAccPortCpdV2L2PTTunnelMac             MacAddress,
    --
    cmEthernetAccPortCpdV2Mac00DispType             CmControlProtocolDispType,
    cmEthernetAccPortCpdV2Mac01DispType             CmControlProtocolDispType,
    cmEthernetAccPortCpdV2Mac02DispType             CmControlProtocolDispType,
    cmEthernetAccPortCpdV2Mac03DispType             CmControlProtocolDispType,
    cmEthernetAccPortCpdV2Mac04DispType             CmControlProtocolDispType,
    cmEthernetAccPortCpdV2Mac05DispType             CmControlProtocolDispType,
    cmEthernetAccPortCpdV2Mac06DispType             CmControlProtocolDispType,
    cmEthernetAccPortCpdV2Mac07DispType             CmControlProtocolDispType,
    cmEthernetAccPortCpdV2Mac08DispType             CmControlProtocolDispType,
    cmEthernetAccPortCpdV2Mac09DispType             CmControlProtocolDispType,
    cmEthernetAccPortCpdV2Mac0ADispType             CmControlProtocolDispType,
    cmEthernetAccPortCpdV2Mac0BDispType             CmControlProtocolDispType,
    cmEthernetAccPortCpdV2Mac0CDispType             CmControlProtocolDispType,
    cmEthernetAccPortCpdV2Mac0DDispType             CmControlProtocolDispType,
    cmEthernetAccPortCpdV2Mac0EDispType             CmControlProtocolDispType,
    cmEthernetAccPortCpdV2Mac0FDispType             CmControlProtocolDispType,
    cmEthernetAccPortCpdV2NearestLLDPDispType       CmControlProtocolDispType,
    cmEthernetAccPortCpdV2NonTpmrLLDPDispType       CmControlProtocolDispType,
    cmEthernetAccPortCpdV2CustomerLLDPDispType      CmControlProtocolDispType,
    cmEthernetAccPortCpdV2PtpUntaggedDispType       CmControlProtocolDispType,
    cmEthernetAccPortCpdV2PtpTaggedDispType         CmControlProtocolDispType
}

cmEthernetAccPortCpdV2Index OBJECT-TYPE
    SYNTAX      Integer32 
    MAX-ACCESS  read-only
    STATUS      current
    DESCRIPTION
        "Unique Index value to access the CPD row."
    ::= { cmEthernetAccPortCpdV2Entry 1 }

cmEthernetAccPortCpdV2CiscoGroupDispType OBJECT-TYPE
    SYNTAX      CmControlProtocolDispType 
    MAX-ACCESS  read-write
    STATUS      deprecated
    DESCRIPTION
        "Deprecated - each Cisco protocol has its own disposition.
         Control Protocol Disposition for Cisco Group.  This includes
         ISL, PAGP, UDLD, CDP, VTP, DTP, PSVTP+, UplinkFast, VLAN Bridge,
         L2PT.  Note that a specific protocol filter overrides the
         group setting."
    ::= { cmEthernetAccPortCpdV2Entry 2 }

cmEthernetAccPortCpdV2IslDispType OBJECT-TYPE
    SYNTAX      CmControlProtocolDispType 
    MAX-ACCESS  read-write
    STATUS      current
    DESCRIPTION
        "Control Protocol Disposition for ISL (Inter Switch Link).
         MAC Address (01:00:0C:00:00:00)."
    ::= { cmEthernetAccPortCpdV2Entry 3 }

cmEthernetAccPortCpdV2PagpDispType OBJECT-TYPE
    SYNTAX      CmControlProtocolDispType 
    MAX-ACCESS  read-write
    STATUS      current
    DESCRIPTION
        "Control Protocol Disposition for PAGP (Port Aggregation Protocol).
         MAC Address (01:00:0C:CC:CC:CC), Ethertype(0x104)."
    ::= { cmEthernetAccPortCpdV2Entry 4 }

cmEthernetAccPortCpdV2UdldDispType OBJECT-TYPE
    SYNTAX      CmControlProtocolDispType 
    MAX-ACCESS  read-write
    STATUS      current
    DESCRIPTION
        "Control Protocol Disposition for UDLD (Unidirectional Link Detection).
         MAC Address (01:00:0C:CC:CC:CC), Ethertype(0x111)."
    ::= { cmEthernetAccPortCpdV2Entry 5 }

cmEthernetAccPortCpdV2CdpDispType OBJECT-TYPE
    SYNTAX      CmControlProtocolDispType 
    MAX-ACCESS  read-write
    STATUS      current
    DESCRIPTION
        "Control Protocol Disposition for CDP (Cisco Discovery Protocol).
         MAC Address (01:00:0C:CC:CC:CC), Ethertype(0x2000)."
    ::= { cmEthernetAccPortCpdV2Entry 6 }

cmEthernetAccPortCpdV2VtpDispType OBJECT-TYPE
    SYNTAX      CmControlProtocolDispType 
    MAX-ACCESS  read-write
    STATUS      current
    DESCRIPTION
        "Control Protocol Disposition for VTP (VLAN Trunking Protocol).
         MAC Address (01:00:0C:CC:CC:CC), Ethertype(0x2003)."
    ::= { cmEthernetAccPortCpdV2Entry 7 }

cmEthernetAccPortCpdV2DtpDispType OBJECT-TYPE
    SYNTAX      CmControlProtocolDispType 
    MAX-ACCESS  read-write
    STATUS      current
    DESCRIPTION
        "Control Protocol Disposition for DTP (Dynamic Trunking).
         MAC Address (01:00:0C:CC:CC:CC), Ethertype(0x2004)."
    ::= { cmEthernetAccPortCpdV2Entry 8 }

cmEthernetAccPortCpdV2PvstpPlusDispType OBJECT-TYPE
    SYNTAX      CmControlProtocolDispType 
    MAX-ACCESS  read-write
    STATUS      current
    DESCRIPTION
        "Control Protocol Disposition for Spanning Tree PVSTP+.
         MAC Address (01:00:0C:CC:CC:CC), Ethertype(0x10B)."
    ::= { cmEthernetAccPortCpdV2Entry 9 }

cmEthernetAccPortCpdV2UplinkFastDispType OBJECT-TYPE
    SYNTAX      CmControlProtocolDispType 
    MAX-ACCESS  read-write
    STATUS      current
    DESCRIPTION
        "Control Protocol Disposition for STP UplinkFast.
         MAC Address (01:00:0C:CD:CD:CD), Ethertype(0x200A)."
    ::= { cmEthernetAccPortCpdV2Entry 10 }

cmEthernetAccPortCpdV2VlanBridgeDispType OBJECT-TYPE
    SYNTAX      CmControlProtocolDispType 
    MAX-ACCESS  read-write
    STATUS      current
    DESCRIPTION
        "Control Protocol Disposition for VLAN Bridge.
         MAC Address (01:00:0C:CD:CD:CE), Ethertype(0x10C)."
    ::= { cmEthernetAccPortCpdV2Entry 11 }

cmEthernetAccPortCpdV2L2PTDispType OBJECT-TYPE
    SYNTAX      CmControlProtocolDispType 
    MAX-ACCESS  read-write
    STATUS      current
    DESCRIPTION
        "Control Protocol Disposition for Layer 2 Protocol Tunnelling(L2PT).
         MAC Address (01:00:0C:CD:CD:D0)."
    ::= { cmEthernetAccPortCpdV2Entry 12 }

cmEthernetAccPortCpdV2BridgeGroupDispType OBJECT-TYPE
    SYNTAX      CmControlProtocolDispType 
    MAX-ACCESS  read-write
    STATUS      deprecated
    DESCRIPTION
        "Deprecated - individual dispositions available for each MAC.
         Bridge Group Control Protocol Disposition Type.  This
         includes BPDU, PAUSE (IEEE 802.3x Flow Control), 
         LACP (Link Aggregation), LACP Marker (Marker), 
         EFM OAM (IEEE 802.3 ah) and IEEE 802.1x Port Authentication, 
         besides reserved MAC addresses from 
         01:80:C2:00:00:04 thru 01:80:C2:00:00:0F."
    ::= { cmEthernetAccPortCpdV2Entry 13 }

cmEthernetAccPortCpdV2BPDUDispType OBJECT-TYPE
    SYNTAX      CmControlProtocolDispType 
    MAX-ACCESS  read-write
    STATUS      current
    DESCRIPTION
        "Control Protocol Disposition for IEEE Spanning Tree(STP),
         MSTP (Multiple Spanning Tree) and RSTP (Rapid Reconfiguration of
         Spanning Tree). MAC Address (01:80:C2:00:00:00)."
    ::= { cmEthernetAccPortCpdV2Entry 14 }

cmEthernetAccPortCpdV2PauseDispType OBJECT-TYPE
    SYNTAX      CmControlProtocolDispType 
    MAX-ACCESS  read-write
    STATUS      current
    DESCRIPTION
        "Control Protocol Disposition for IEEE 802.3x Flow Control 
         (PAUSE frames)."
    ::= { cmEthernetAccPortCpdV2Entry 15 }

cmEthernetAccPortCpdV2LACPDispType OBJECT-TYPE
    SYNTAX      CmControlProtocolDispType 
    MAX-ACCESS  read-write
    STATUS      current
    DESCRIPTION
        "Control Protocol Disposition for 802.3ad Link Aggregation
         Protocol.
         MAC Address (01:80:C2:00:00:03), Ethertype (0x8809), Subtype(01)."
    ::= { cmEthernetAccPortCpdV2Entry 16 }

cmEthernetAccPortCpdV2LACPMarkerDispType OBJECT-TYPE
    SYNTAX      CmControlProtocolDispType 
    MAX-ACCESS  read-write
    STATUS      current
    DESCRIPTION
        "Control Protocol Disposition for IEEE 802.3ad Marker Protocol.
         MAC Address (01:80:C2:00:00:03), Ethertype (0x8809), Subtype(02)."
    ::= { cmEthernetAccPortCpdV2Entry 17 }

cmEthernetAccPortCpdV2EfmOamDispType OBJECT-TYPE
    SYNTAX      CmControlProtocolDispType 
    MAX-ACCESS  read-write
    STATUS      current
    DESCRIPTION
        "Control Protocol Disposition for IEEE 802.3ah EFM OAM.
         MAC Address (01:80:C2:00:00:03), Ethertype (0x8809), Subtype(03)."
    ::= { cmEthernetAccPortCpdV2Entry 18 }

cmEthernetAccPortCpdV2SSMDispType OBJECT-TYPE
    SYNTAX      CmControlProtocolDispType 
    MAX-ACCESS  read-write
    STATUS      current
    DESCRIPTION
        "Control Protocol Disposition for Sync Status Messages.
         MAC Address (01:80:C2:00:00:02), Ethertype (0x19A7), Subtype(0A)."
    ::= { cmEthernetAccPortCpdV2Entry 19 }

cmEthernetAccPortCpdV2PortAuthenDispType OBJECT-TYPE
    SYNTAX      CmControlProtocolDispType 
    MAX-ACCESS  read-write
    STATUS      current
    DESCRIPTION
        "Control Protocol Disposition for IEEE 802.1x Protocol.
         MAC Address (01:80:C2:00:00:03), Ethertype (0x888E)."
    ::= { cmEthernetAccPortCpdV2Entry 20 }

cmEthernetAccPortCpdV2BridgeReservedDispType OBJECT-TYPE
    SYNTAX      CmControlProtocolDispType 
    MAX-ACCESS  read-write
    STATUS      deprecated
    DESCRIPTION
        "Deprecated - individual dispositions available for each MAC.
         Control Protocol Disposition for Range of MAC Addresses
         from 01:80:C2:00:00:04 to 01:80:C2:00:00:0F."
    ::= { cmEthernetAccPortCpdV2Entry 21 }

cmEthernetAccPortCpdV2LANBridgesDispType OBJECT-TYPE
    SYNTAX      CmControlProtocolDispType 
    MAX-ACCESS  read-write
    STATUS      current
    DESCRIPTION
        "Control Protocol Disposition for IEEE 802.1d LAN Bridge Managment.
         MAC Address (01:80:C2:00:00:10)."
    ::= { cmEthernetAccPortCpdV2Entry 22 }

cmEthernetAccPortCpdV2GARPGroupDispType OBJECT-TYPE
    SYNTAX      CmControlProtocolDispType 
    MAX-ACCESS  read-write
    STATUS      deprecated
    DESCRIPTION
        "Deprecated - each GARP Group protocol has its own disposition.
         Group Disposition type which includes GMRP, GVRP and
         MAC Address from range 01:80:C2:00:00:20 to 01:80:C2:00:00:2F."
    ::= { cmEthernetAccPortCpdV2Entry 23 }

cmEthernetAccPortCpdV2GMRPDispType OBJECT-TYPE
    SYNTAX      CmControlProtocolDispType 
    MAX-ACCESS  read-write
    STATUS      current
    DESCRIPTION
        "Control Protocol Disposition for GARP Multicast Registration
         Protocol. MAC Address (01:80:C2:00:00:20)."
    ::= { cmEthernetAccPortCpdV2Entry 24 }

cmEthernetAccPortCpdV2GVRPDispType OBJECT-TYPE
    SYNTAX      CmControlProtocolDispType 
    MAX-ACCESS  read-write
    STATUS      current
    DESCRIPTION
        "Control Protocol Disposition for GARP VLAN Registration
         Protocol. MAC Address (01:80:C2:00:00:21)."
    ::= { cmEthernetAccPortCpdV2Entry 25 }

cmEthernetAccPortCpdV2GARPDispType OBJECT-TYPE
    SYNTAX      CmControlProtocolDispType 
    MAX-ACCESS  read-write
    STATUS      current
    DESCRIPTION
        "Group Disposition type which includes GARP Reserved 
         MAC Address from range 01:80:C2:00:00:22 to 01:80:C2:00:00:2F."
    ::= { cmEthernetAccPortCpdV2Entry 26 }

cmEthernetAccPortCpdV2LLDPDispType OBJECT-TYPE
    SYNTAX      CmControlProtocolDispType 
    MAX-ACCESS  read-write
    STATUS      deprecated
    DESCRIPTION
        "Deprecated - each LLDP MAC protocol has its own disposition.
         LLDP (Link Layer Discovery Protocol) Disposition type. 
         MAC Address 01:80:C2:00:00:0e, 01:80:C2:00:00:03, or
         01:80:C2:00:00:00."
    ::= { cmEthernetAccPortCpdV2Entry 27 }

cmEthernetAccPortCpdV2ELMIDispType OBJECT-TYPE
    SYNTAX      CmControlProtocolDispType 
    MAX-ACCESS  read-write
    STATUS      current
    DESCRIPTION
        "ELMI (Ethernet Local Management Interface) Disposition type. 
         MAC Address 01:80:C2:00:00:07 and EtherType of 0x88EE."
    ::= { cmEthernetAccPortCpdV2Entry 28 }

cmEthernetAccPortCpdV2L2PTTunnelMac    OBJECT-TYPE
    SYNTAX      MacAddress 
    MAX-ACCESS  read-write
    STATUS      current
    DESCRIPTION
        "Configurable Layer 2 Protocol Tunneling MAC Address.  
         For protocols STP, CDP and VTP, with control protocol disposition as 
         pass-thru-l2pt, this configured MAC address replaces the DA, upon
         encapsulation.  For decapsulation, protocol signature and this 
         configured MAC address are matched and the MAC address is replaced
         with the protocol's inferred MAC address." 
    ::= { cmEthernetAccPortCpdV2Entry 29 }

cmEthernetAccPortCpdV2Mac00DispType OBJECT-TYPE
    SYNTAX      CmControlProtocolDispType 
    MAX-ACCESS  read-write
    STATUS      current
    DESCRIPTION
        "MAC Address 01:80:C2:00:00:00 Disposition type."
    ::= { cmEthernetAccPortCpdV2Entry 30 }

cmEthernetAccPortCpdV2Mac01DispType OBJECT-TYPE
    SYNTAX      CmControlProtocolDispType 
    MAX-ACCESS  read-write
    STATUS      current
    DESCRIPTION
        "MAC Address 01:80:C2:00:00:01 Disposition type."
    ::= { cmEthernetAccPortCpdV2Entry 31 }

cmEthernetAccPortCpdV2Mac02DispType OBJECT-TYPE
    SYNTAX      CmControlProtocolDispType 
    MAX-ACCESS  read-write
    STATUS      current
    DESCRIPTION
        "MAC Address 01:80:C2:00:00:02 Disposition type."
    ::= { cmEthernetAccPortCpdV2Entry 32 }

cmEthernetAccPortCpdV2Mac03DispType OBJECT-TYPE
    SYNTAX      CmControlProtocolDispType 
    MAX-ACCESS  read-write
    STATUS      current
    DESCRIPTION
        "MAC Address 01:80:C2:00:00:03 Disposition type."
    ::= { cmEthernetAccPortCpdV2Entry 33 }

cmEthernetAccPortCpdV2Mac04DispType OBJECT-TYPE
    SYNTAX      CmControlProtocolDispType 
    MAX-ACCESS  read-write
    STATUS      current
    DESCRIPTION
        "MAC Address 01:80:C2:00:00:04 Disposition type."
    ::= { cmEthernetAccPortCpdV2Entry 34 }

cmEthernetAccPortCpdV2Mac05DispType OBJECT-TYPE
    SYNTAX      CmControlProtocolDispType 
    MAX-ACCESS  read-write
    STATUS      current
    DESCRIPTION
        "MAC Address 01:80:C2:00:00:05 Disposition type."
    ::= { cmEthernetAccPortCpdV2Entry 35 }

cmEthernetAccPortCpdV2Mac06DispType OBJECT-TYPE
    SYNTAX      CmControlProtocolDispType 
    MAX-ACCESS  read-write
    STATUS      current
    DESCRIPTION
        "MAC Address 01:80:C2:00:00:06 Disposition type."
    ::= { cmEthernetAccPortCpdV2Entry 36 }

cmEthernetAccPortCpdV2Mac07DispType OBJECT-TYPE
    SYNTAX      CmControlProtocolDispType 
    MAX-ACCESS  read-write
    STATUS      current
    DESCRIPTION
        "MAC Address 01:80:C2:00:00:07 Disposition type."
    ::= { cmEthernetAccPortCpdV2Entry 37 }

cmEthernetAccPortCpdV2Mac08DispType OBJECT-TYPE
    SYNTAX      CmControlProtocolDispType 
    MAX-ACCESS  read-write
    STATUS      current
    DESCRIPTION
        "MAC Address 01:80:C2:00:00:08 Disposition type."
    ::= { cmEthernetAccPortCpdV2Entry 38 }

cmEthernetAccPortCpdV2Mac09DispType OBJECT-TYPE
    SYNTAX      CmControlProtocolDispType 
    MAX-ACCESS  read-write
    STATUS      current
    DESCRIPTION
        "MAC Address 01:80:C2:00:00:09 Disposition type."
    ::= { cmEthernetAccPortCpdV2Entry 39 }

cmEthernetAccPortCpdV2Mac0ADispType OBJECT-TYPE
    SYNTAX      CmControlProtocolDispType 
    MAX-ACCESS  read-write
    STATUS      current
    DESCRIPTION
        "MAC Address 01:80:C2:00:00:0A Disposition type."
    ::= { cmEthernetAccPortCpdV2Entry 40 }

cmEthernetAccPortCpdV2Mac0BDispType OBJECT-TYPE
    SYNTAX      CmControlProtocolDispType 
    MAX-ACCESS  read-write
    STATUS      current
    DESCRIPTION
        "MAC Address 01:80:C2:00:00:0B Disposition type."
    ::= { cmEthernetAccPortCpdV2Entry 41 }

cmEthernetAccPortCpdV2Mac0CDispType OBJECT-TYPE
    SYNTAX      CmControlProtocolDispType 
    MAX-ACCESS  read-write
    STATUS      current
    DESCRIPTION
        "MAC Address 01:80:C2:00:00:0C Disposition type."
    ::= { cmEthernetAccPortCpdV2Entry 42 }

cmEthernetAccPortCpdV2Mac0DDispType OBJECT-TYPE
    SYNTAX      CmControlProtocolDispType 
    MAX-ACCESS  read-write
    STATUS      current
    DESCRIPTION
        "MAC Address 01:80:C2:00:00:0D Disposition type."
    ::= { cmEthernetAccPortCpdV2Entry 43 }

cmEthernetAccPortCpdV2Mac0EDispType OBJECT-TYPE
    SYNTAX      CmControlProtocolDispType 
    MAX-ACCESS  read-write
    STATUS      current
    DESCRIPTION
        "MAC Address 01:80:C2:00:00:0E Disposition type."
    ::= { cmEthernetAccPortCpdV2Entry 44 }

cmEthernetAccPortCpdV2Mac0FDispType OBJECT-TYPE
    SYNTAX      CmControlProtocolDispType 
    MAX-ACCESS  read-write
    STATUS      current
    DESCRIPTION
        "MAC Address 01:80:C2:00:00:0F Disposition type."
    ::= { cmEthernetAccPortCpdV2Entry 45 }

cmEthernetAccPortCpdV2NearestLLDPDispType OBJECT-TYPE
    SYNTAX      CmControlProtocolDispType 
    MAX-ACCESS  read-write
    STATUS      current
    DESCRIPTION
        "LLDP (Link Layer Discovery Protocol) Nearest Bridge Disposition type."
    ::= { cmEthernetAccPortCpdV2Entry 46 }

cmEthernetAccPortCpdV2NonTpmrLLDPDispType OBJECT-TYPE
    SYNTAX      CmControlProtocolDispType 
    MAX-ACCESS  read-write
    STATUS      current
    DESCRIPTION
        "LLDP (Link Layer Discovery Protocol) Non-TPMR Bridge Disposition type."
    ::= { cmEthernetAccPortCpdV2Entry 47 }

cmEthernetAccPortCpdV2CustomerLLDPDispType OBJECT-TYPE
    SYNTAX      CmControlProtocolDispType 
    MAX-ACCESS  read-write
    STATUS      current
    DESCRIPTION
        "LLDP (Link Layer Discovery Protocol) Customer Bridge Disposition type."
    ::= { cmEthernetAccPortCpdV2Entry 48 }

cmEthernetAccPortCpdV2PtpUntaggedDispType OBJECT-TYPE
    SYNTAX      CmControlProtocolDispType
    MAX-ACCESS  read-write
    STATUS      current
    DESCRIPTION
        "PTP untagged frame Disposition type."
    ::= { cmEthernetAccPortCpdV2Entry 49 }

cmEthernetAccPortCpdV2PtpTaggedDispType OBJECT-TYPE
    SYNTAX      CmControlProtocolDispType
    MAX-ACCESS  read-write
    STATUS      current
    DESCRIPTION
        "PTP tagged frame Disposition type."
    ::= { cmEthernetAccPortCpdV2Entry 50 }

--Flow CPDv2
cmFlowCpdV2Table  OBJECT-TYPE
    SYNTAX      SEQUENCE OF CmFlowCpdV2Entry
    MAX-ACCESS  not-accessible
    STATUS      current
    DESCRIPTION
            "A list of entries corresponding to Ethernet Flow 
             Control Protocol Disposition V2.
             This table is supported for the GE206/GE201 devices."
    ::= { cmFacilityObjects 14 }

cmFlowCpdV2Entry OBJECT-TYPE
    SYNTAX      CmFlowCpdV2Entry 
    MAX-ACCESS  not-accessible
    STATUS      current
    DESCRIPTION
            "A conceptual row in the cmFlowCpdV2Table. 
             These entries represent a Control Protocol Disposition 
             filtering criteria on the Ethernet Flow."
    INDEX { neIndex, shelfIndex, slotIndex, cmEthernetAccPortIndex, 
            cmFlowIndex, cmFlowCpdV2Index }
    ::= { cmFlowCpdV2Table 1 }

CmFlowCpdV2Entry ::= SEQUENCE {
    -- Index
    cmFlowCpdV2Index                    Integer32,

    -- Filtering Criteria
    cmFlowCpdV2CiscoGroupDispType        CmControlProtocolDispType,
    cmFlowCpdV2IslDispType               CmControlProtocolDispType,
    cmFlowCpdV2PagpDispType              CmControlProtocolDispType,
    cmFlowCpdV2UdldDispType              CmControlProtocolDispType,
    cmFlowCpdV2CdpDispType               CmControlProtocolDispType,
    cmFlowCpdV2VtpDispType               CmControlProtocolDispType,
    cmFlowCpdV2DtpDispType               CmControlProtocolDispType,
    cmFlowCpdV2PvstpPlusDispType         CmControlProtocolDispType,
    cmFlowCpdV2UplinkFastDispType        CmControlProtocolDispType,
    cmFlowCpdV2VlanBridgeDispType        CmControlProtocolDispType,
    cmFlowCpdV2L2PTDispType              CmControlProtocolDispType,
    cmFlowCpdV2BridgeGroupDispType       CmControlProtocolDispType,
    cmFlowCpdV2BPDUDispType              CmControlProtocolDispType,
    cmFlowCpdV2PauseDispType             CmControlProtocolDispType,
    cmFlowCpdV2LACPDispType              CmControlProtocolDispType,
    cmFlowCpdV2LACPMarkerDispType        CmControlProtocolDispType,
    cmFlowCpdV2EfmOamDispType            CmControlProtocolDispType,
    cmFlowCpdV2SSMDispType               CmControlProtocolDispType,
    cmFlowCpdV2PortAuthenDispType        CmControlProtocolDispType,
    cmFlowCpdV2BridgeReservedDispType    CmControlProtocolDispType,
    cmFlowCpdV2LANBridgesDispType        CmControlProtocolDispType,
    cmFlowCpdV2GARPGroupDispType         CmControlProtocolDispType,
    cmFlowCpdV2GMRPDispType              CmControlProtocolDispType,
    cmFlowCpdV2GVRPDispType              CmControlProtocolDispType,
    cmFlowCpdV2GARPDispType              CmControlProtocolDispType,
    cmFlowCpdV2ActiveControlProtocols    CmActiveControlProtocolsType,
    --
    cmFlowCpdV2LLDPDispType              CmControlProtocolDispType,
    cmFlowCpdV2ELMIDispType              CmControlProtocolDispType,
    --
    cmFlowCpdV2Mac00DispType             CmControlProtocolDispType,
    cmFlowCpdV2Mac01DispType             CmControlProtocolDispType,
    cmFlowCpdV2Mac02DispType             CmControlProtocolDispType,
    cmFlowCpdV2Mac03DispType             CmControlProtocolDispType,
    cmFlowCpdV2Mac04DispType             CmControlProtocolDispType,
    cmFlowCpdV2Mac05DispType             CmControlProtocolDispType,
    cmFlowCpdV2Mac06DispType             CmControlProtocolDispType,
    cmFlowCpdV2Mac07DispType             CmControlProtocolDispType,
    cmFlowCpdV2Mac08DispType             CmControlProtocolDispType,
    cmFlowCpdV2Mac09DispType             CmControlProtocolDispType,
    cmFlowCpdV2Mac0ADispType             CmControlProtocolDispType,
    cmFlowCpdV2Mac0BDispType             CmControlProtocolDispType,
    cmFlowCpdV2Mac0CDispType             CmControlProtocolDispType,
    cmFlowCpdV2Mac0DDispType             CmControlProtocolDispType,
    cmFlowCpdV2Mac0EDispType             CmControlProtocolDispType,
    cmFlowCpdV2Mac0FDispType             CmControlProtocolDispType,
    cmFlowCpdV2NearestLLDPDispType       CmControlProtocolDispType,
    cmFlowCpdV2NonTpmrLLDPDispType       CmControlProtocolDispType,
    cmFlowCpdV2CustomerLLDPDispType      CmControlProtocolDispType
}


cmFlowCpdV2Index OBJECT-TYPE
    SYNTAX      Integer32 
    MAX-ACCESS  read-only
    STATUS      current
    DESCRIPTION
        "Unique Index value to access the CPD row."
    ::= { cmFlowCpdV2Entry 1 }

cmFlowCpdV2CiscoGroupDispType OBJECT-TYPE
    SYNTAX      CmControlProtocolDispType 
    MAX-ACCESS  read-write
    STATUS      deprecated
    DESCRIPTION
        "Deprecated - each Cisco protocol has its own disposition.
         Control Protocol Disposition for Cisco Group.  This includes
         ISL, PAGP, UDLD, CDP, VTP, DTP, PSVTP+, UplinkFast, VLAN Bridge,
         L2PT.  Note that a specific protocol filter overrides the
         group setting."
    ::= { cmFlowCpdV2Entry 2 }

cmFlowCpdV2IslDispType OBJECT-TYPE
    SYNTAX      CmControlProtocolDispType 
    MAX-ACCESS  read-write
    STATUS      current
    DESCRIPTION
        "Control Protocol Disposition for ISL (Inter Switch Link).
         MAC Address (01:00:0C:00:00:00)."
    ::= { cmFlowCpdV2Entry 3 }

cmFlowCpdV2PagpDispType OBJECT-TYPE
    SYNTAX      CmControlProtocolDispType 
    MAX-ACCESS  read-write
    STATUS      current
    DESCRIPTION
        "Control Protocol Disposition for PAGP (Port Aggregation Protocol).
         MAC Address (01:00:0C:CC:CC:CC), Ethertype(0x104)."
    ::= { cmFlowCpdV2Entry 4 }

cmFlowCpdV2UdldDispType OBJECT-TYPE
    SYNTAX      CmControlProtocolDispType 
    MAX-ACCESS  read-write
    STATUS      current
    DESCRIPTION
        "Control Protocol Disposition for UDLD (Unidirectional Link Detection).
         MAC Address (01:00:0C:CC:CC:CC), Ethertype(0x111)."
    ::= { cmFlowCpdV2Entry 5 }

cmFlowCpdV2CdpDispType OBJECT-TYPE
    SYNTAX      CmControlProtocolDispType 
    MAX-ACCESS  read-write
    STATUS      current
    DESCRIPTION
        "Control Protocol Disposition for CDP (Cisco Discovery Protocol).
         MAC Address (01:00:0C:CC:CC:CC), Ethertype(0x2000)."
    ::= { cmFlowCpdV2Entry 6 }

cmFlowCpdV2VtpDispType OBJECT-TYPE
    SYNTAX      CmControlProtocolDispType 
    MAX-ACCESS  read-write
    STATUS      current
    DESCRIPTION
        "Control Protocol Disposition for VTP (VLAN Trunking Protocol).
         MAC Address (01:00:0C:CC:CC:CC), Ethertype(0x2003)."
    ::= { cmFlowCpdV2Entry 7 }

cmFlowCpdV2DtpDispType OBJECT-TYPE
    SYNTAX      CmControlProtocolDispType 
    MAX-ACCESS  read-write
    STATUS      current
    DESCRIPTION
        "Control Protocol Disposition for DTP (Dynamic Trunking).
         MAC Address (01:00:0C:CC:CC:CC), Ethertype(0x2004)."
    ::= { cmFlowCpdV2Entry 8 }

cmFlowCpdV2PvstpPlusDispType OBJECT-TYPE
    SYNTAX      CmControlProtocolDispType 
    MAX-ACCESS  read-write
    STATUS      current
    DESCRIPTION
        "Control Protocol Disposition for Spanning Tree PVSTP+.
         MAC Address (01:00:0C:CC:CC:CC), Ethertype(0x10B)."
    ::= { cmFlowCpdV2Entry 9 }

cmFlowCpdV2UplinkFastDispType OBJECT-TYPE
    SYNTAX      CmControlProtocolDispType 
    MAX-ACCESS  read-write
    STATUS      current
    DESCRIPTION
        "Control Protocol Disposition for STP UplinkFast.
         MAC Address (01:00:0C:CD:CD:CD), Ethertype(0x200A)."
    ::= { cmFlowCpdV2Entry 10 }

cmFlowCpdV2VlanBridgeDispType OBJECT-TYPE
    SYNTAX      CmControlProtocolDispType 
    MAX-ACCESS  read-write
    STATUS      current
    DESCRIPTION
        "Control Protocol Disposition for VLAN Bridge.
         MAC Address (01:00:0C:CD:CD:CE), Ethertype(0x10C)."
    ::= { cmFlowCpdV2Entry 11 }

cmFlowCpdV2L2PTDispType OBJECT-TYPE
    SYNTAX      CmControlProtocolDispType 
    MAX-ACCESS  read-write
    STATUS      current
    DESCRIPTION
        "Control Protocol Disposition for Layer 2 Protocol Tunnelling(L2PT).
         MAC Address (01:00:0C:CD:CD:D0)."
    ::= { cmFlowCpdV2Entry 12 }

cmFlowCpdV2BridgeGroupDispType OBJECT-TYPE
    SYNTAX      CmControlProtocolDispType 
    MAX-ACCESS  read-write
    STATUS      deprecated
    DESCRIPTION
        "Deprecated - individual dispositions available for each MAC.
         Bridge Group Control Protocol Disposition Type.  This
         includes BPDU, PAUSE (IEEE 802.3x Flow Control), 
         LACP (Link Aggregation), LACP Marker (Marker), 
         EFM OAM (IEEE 802.3 ah) and IEEE 802.1x Port Authentication, 
         besides reserved MAC addresses from 
         01:80:C2:00:00:04 thru 01:80:C2:00:00:0F."
    ::= { cmFlowCpdV2Entry 13 }

cmFlowCpdV2BPDUDispType OBJECT-TYPE
    SYNTAX      CmControlProtocolDispType 
    MAX-ACCESS  read-write
    STATUS      current
    DESCRIPTION
        "Control Protocol Disposition for IEEE Spanning Tree(STP),
         MSTP (Multiple Spanning Tree) and RSTP (Rapid Reconfiguration of
         Spanning Tree). MAC Address (01:80:C2:00:00:00)."
    ::= { cmFlowCpdV2Entry 14 }

cmFlowCpdV2PauseDispType OBJECT-TYPE
    SYNTAX      CmControlProtocolDispType 
    MAX-ACCESS  read-write
    STATUS      current
    DESCRIPTION
        "Control Protocol Disposition for IEEE 802.3x Flow Control 
         (PAUSE frames)."
    ::= { cmFlowCpdV2Entry 15 }

cmFlowCpdV2LACPDispType OBJECT-TYPE
    SYNTAX      CmControlProtocolDispType 
    MAX-ACCESS  read-write
    STATUS      current
    DESCRIPTION
        "Control Protocol Disposition for 802.3ad Link Aggregation
         Protocol.
         MAC Address (01:80:C2:00:00:03), Ethertype (0x8809), Subtype(01)."
    ::= { cmFlowCpdV2Entry 16 }

cmFlowCpdV2LACPMarkerDispType OBJECT-TYPE
    SYNTAX      CmControlProtocolDispType 
    MAX-ACCESS  read-write
    STATUS      current
    DESCRIPTION
        "Control Protocol Disposition for IEEE 802.3ad Marker Protocol.
         MAC Address (01:80:C2:00:00:03), Ethertype (0x8809), Subtype(02)."
    ::= { cmFlowCpdV2Entry 17 }

cmFlowCpdV2EfmOamDispType OBJECT-TYPE
    SYNTAX      CmControlProtocolDispType 
    MAX-ACCESS  read-write
    STATUS      current
    DESCRIPTION
        "Control Protocol Disposition for IEEE 802.3ah EFM OAM.
         MAC Address (01:80:C2:00:00:03), Ethertype (0x8809), Subtype(03)."
    ::= { cmFlowCpdV2Entry 18 }

cmFlowCpdV2SSMDispType OBJECT-TYPE
    SYNTAX      CmControlProtocolDispType 
    MAX-ACCESS  read-write
    STATUS      current
    DESCRIPTION
        "Control Protocol Disposition for Sync Status Messages.
         MAC Address (01:80:C2:00:00:02), Ethertype (0x19A7), Subtype(0A)."
    ::= { cmFlowCpdV2Entry 19 }

cmFlowCpdV2PortAuthenDispType OBJECT-TYPE
    SYNTAX      CmControlProtocolDispType 
    MAX-ACCESS  read-write
    STATUS      current
    DESCRIPTION
        "Control Protocol Disposition for IEEE 802.1x Protocol.
         MAC Address (01:80:C2:00:00:03), Ethertype (0x888E)."
    ::= { cmFlowCpdV2Entry 20 }

cmFlowCpdV2BridgeReservedDispType OBJECT-TYPE
    SYNTAX      CmControlProtocolDispType 
    MAX-ACCESS  read-write
    STATUS      deprecated
    DESCRIPTION
        "Deprecated - individual dispositions available for each MAC.
         Control Protocol Disposition for Range of MAC Addresses
         from 01:80:C2:00:00:04 to 01:80:C2:00:00:0F."
    ::= { cmFlowCpdV2Entry 21 }

cmFlowCpdV2LANBridgesDispType OBJECT-TYPE
    SYNTAX      CmControlProtocolDispType 
    MAX-ACCESS  read-write
    STATUS      current
    DESCRIPTION
        "Control Protocol Disposition for IEEE 802.1d LAN Bridge Managment.
         MAC Address (01:80:C2:00:00:10)."
    ::= { cmFlowCpdV2Entry 22 }

cmFlowCpdV2GARPGroupDispType OBJECT-TYPE
    SYNTAX      CmControlProtocolDispType 
    MAX-ACCESS  read-write
    STATUS      deprecated
    DESCRIPTION
        "Deprecated - each GARP Group protocol has its own disposition.
         Group Disposition type which includes GMRP, GVRP and
         MAC Address from range 01:80:C2:00:00:20 to 01:80:C2:00:00:2F."
    ::= { cmFlowCpdV2Entry 23 }

cmFlowCpdV2GMRPDispType OBJECT-TYPE
    SYNTAX      CmControlProtocolDispType 
    MAX-ACCESS  read-write
    STATUS      current
    DESCRIPTION
        "Control Protocol Disposition for GARP Multicast Registration
         Protocol. MAC Address (01:80:C2:00:00:20)."
    ::= { cmFlowCpdV2Entry 24 }

cmFlowCpdV2GVRPDispType OBJECT-TYPE
    SYNTAX      CmControlProtocolDispType 
    MAX-ACCESS  read-write
    STATUS      current
    DESCRIPTION
        "Control Protocol Disposition for GARP VLAN Registration
         Protocol. MAC Address (01:80:C2:00:00:21)."
    ::= { cmFlowCpdV2Entry 25 }

cmFlowCpdV2GARPDispType OBJECT-TYPE
    SYNTAX      CmControlProtocolDispType 
    MAX-ACCESS  read-write
    STATUS      current
    DESCRIPTION
        "Group Disposition type which includes GARP Reserved 
         MAC Address from range 01:80:C2:00:00:22 to 01:80:C2:00:00:2F."
    ::= { cmFlowCpdV2Entry 26 }

cmFlowCpdV2ActiveControlProtocols OBJECT-TYPE
    SYNTAX  CmActiveControlProtocolsType
    MAX-ACCESS  read-only
    STATUS      current
    DESCRIPTION
        "List of Active Control Protocol Dispositions. Note that
         if the Port Level Disposition control is set to PEER or 
         DISCARD, the flow level disposition is no longer active.
         This object provides information on all the active
         dispositions."
    ::= { cmFlowCpdV2Entry 27 }

cmFlowCpdV2LLDPDispType OBJECT-TYPE
    SYNTAX      CmControlProtocolDispType 
    MAX-ACCESS  read-write
    STATUS      deprecated
    DESCRIPTION
        "Deprecated - each LLDP MAC protocol has its own disposition.
         LLDP (Link Layer Discovery Protocol) Disposition type. 
         MAC Address 01:80:C2:00:00:0e, 01:80:C2:00:00:03, or
         01:80:C2:00:00:00."
    ::= { cmFlowCpdV2Entry 28 }

cmFlowCpdV2ELMIDispType OBJECT-TYPE
    SYNTAX      CmControlProtocolDispType 
    MAX-ACCESS  read-write
    STATUS      current
    DESCRIPTION
        "ELMI (Ethernet Local Management Interface) Disposition type. 
         MAC Address 01:80:C2:00:00:07 and EtherType of 0x88EE."
    ::= { cmFlowCpdV2Entry 29 }

cmFlowCpdV2Mac00DispType OBJECT-TYPE
    SYNTAX      CmControlProtocolDispType 
    MAX-ACCESS  read-write
    STATUS      current
    DESCRIPTION
        "MAC Address 01:80:C2:00:00:00 Disposition type."
    ::= { cmFlowCpdV2Entry 30 }

cmFlowCpdV2Mac01DispType OBJECT-TYPE
    SYNTAX      CmControlProtocolDispType 
    MAX-ACCESS  read-write
    STATUS      current
    DESCRIPTION
        "MAC Address 01:80:C2:00:00:01 Disposition type."
    ::= { cmFlowCpdV2Entry 31 }

cmFlowCpdV2Mac02DispType OBJECT-TYPE
    SYNTAX      CmControlProtocolDispType 
    MAX-ACCESS  read-write
    STATUS      current
    DESCRIPTION
        "MAC Address 01:80:C2:00:00:02 Disposition type."
    ::= { cmFlowCpdV2Entry 32 }

cmFlowCpdV2Mac03DispType OBJECT-TYPE
    SYNTAX      CmControlProtocolDispType 
    MAX-ACCESS  read-write
    STATUS      current
    DESCRIPTION
        "MAC Address 01:80:C2:00:00:03 Disposition type."
    ::= { cmFlowCpdV2Entry 33 }

cmFlowCpdV2Mac04DispType OBJECT-TYPE
    SYNTAX      CmControlProtocolDispType 
    MAX-ACCESS  read-write
    STATUS      current
    DESCRIPTION
        "MAC Address 01:80:C2:00:00:04 Disposition type."
    ::= { cmFlowCpdV2Entry 34 }

cmFlowCpdV2Mac05DispType OBJECT-TYPE
    SYNTAX      CmControlProtocolDispType 
    MAX-ACCESS  read-write
    STATUS      current
    DESCRIPTION
        "MAC Address 01:80:C2:00:00:05 Disposition type."
    ::= { cmFlowCpdV2Entry 35 }

cmFlowCpdV2Mac06DispType OBJECT-TYPE
    SYNTAX      CmControlProtocolDispType 
    MAX-ACCESS  read-write
    STATUS      current
    DESCRIPTION
        "MAC Address 01:80:C2:00:00:06 Disposition type."
    ::= { cmFlowCpdV2Entry 36 }

cmFlowCpdV2Mac07DispType OBJECT-TYPE
    SYNTAX      CmControlProtocolDispType 
    MAX-ACCESS  read-write
    STATUS      current
    DESCRIPTION
        "MAC Address 01:80:C2:00:00:07 Disposition type."
    ::= { cmFlowCpdV2Entry 37 }

cmFlowCpdV2Mac08DispType OBJECT-TYPE
    SYNTAX      CmControlProtocolDispType 
    MAX-ACCESS  read-write
    STATUS      current
    DESCRIPTION
        "MAC Address 01:80:C2:00:00:08 Disposition type."
    ::= { cmFlowCpdV2Entry 38 }

cmFlowCpdV2Mac09DispType OBJECT-TYPE
    SYNTAX      CmControlProtocolDispType 
    MAX-ACCESS  read-write
    STATUS      current
    DESCRIPTION
        "MAC Address 01:80:C2:00:00:09 Disposition type."
    ::= { cmFlowCpdV2Entry 39 }

cmFlowCpdV2Mac0ADispType OBJECT-TYPE
    SYNTAX      CmControlProtocolDispType 
    MAX-ACCESS  read-write
    STATUS      current
    DESCRIPTION
        "MAC Address 01:80:C2:00:00:0A Disposition type."
    ::= { cmFlowCpdV2Entry 40 }

cmFlowCpdV2Mac0BDispType OBJECT-TYPE
    SYNTAX      CmControlProtocolDispType 
    MAX-ACCESS  read-write
    STATUS      current
    DESCRIPTION
        "MAC Address 01:80:C2:00:00:0B Disposition type."
    ::= { cmFlowCpdV2Entry 41 }

cmFlowCpdV2Mac0CDispType OBJECT-TYPE
    SYNTAX      CmControlProtocolDispType 
    MAX-ACCESS  read-write
    STATUS      current
    DESCRIPTION
        "MAC Address 01:80:C2:00:00:0C Disposition type."
    ::= { cmFlowCpdV2Entry 42 }

cmFlowCpdV2Mac0DDispType OBJECT-TYPE
    SYNTAX      CmControlProtocolDispType 
    MAX-ACCESS  read-write
    STATUS      current
    DESCRIPTION
        "MAC Address 01:80:C2:00:00:0D Disposition type."
    ::= { cmFlowCpdV2Entry 43 }

cmFlowCpdV2Mac0EDispType OBJECT-TYPE
    SYNTAX      CmControlProtocolDispType 
    MAX-ACCESS  read-write
    STATUS      current
    DESCRIPTION
        "MAC Address 01:80:C2:00:00:0E Disposition type."
    ::= { cmFlowCpdV2Entry 44 }

cmFlowCpdV2Mac0FDispType OBJECT-TYPE
    SYNTAX      CmControlProtocolDispType 
    MAX-ACCESS  read-write
    STATUS      current
    DESCRIPTION
        "MAC Address 01:80:C2:00:00:0F Disposition type."
    ::= { cmFlowCpdV2Entry 45 }

cmFlowCpdV2NearestLLDPDispType OBJECT-TYPE
    SYNTAX      CmControlProtocolDispType 
    MAX-ACCESS  read-write
    STATUS      current
    DESCRIPTION
        "LLDP (Link Layer Discovery Protocol) Nearest Bridge Disposition type."
    ::= { cmFlowCpdV2Entry 46 }

cmFlowCpdV2NonTpmrLLDPDispType OBJECT-TYPE
    SYNTAX      CmControlProtocolDispType 
    MAX-ACCESS  read-write
    STATUS      current
    DESCRIPTION
        "LLDP (Link Layer Discovery Protocol) Non-TPMR Bridge Disposition type."
    ::= { cmFlowCpdV2Entry 47 }

cmFlowCpdV2CustomerLLDPDispType OBJECT-TYPE
    SYNTAX      CmControlProtocolDispType 
    MAX-ACCESS  read-write
    STATUS      current
    DESCRIPTION
        "LLDP (Link Layer Discovery Protocol) Customer Bridge Disposition type."
    ::= { cmFlowCpdV2Entry 48 }

--
--  Ethernet Network Port Control Protocol Disposition V2
--
cmEthernetNetPortCpdV2Table  OBJECT-TYPE
    SYNTAX      SEQUENCE OF CmEthernetNetPortCpdV2Entry
    MAX-ACCESS  not-accessible
    STATUS      current
    DESCRIPTION
            "A list of entries corresponding to Ethernet Network Port 
             Control Protocol Disposition V2.
             This table is supported for the GE206/GE201 devices."
    ::= { cmFacilityObjects 15 }

cmEthernetNetPortCpdV2Entry OBJECT-TYPE
    SYNTAX      CmEthernetNetPortCpdV2Entry 
    MAX-ACCESS  not-accessible
    STATUS      current
    DESCRIPTION
            "A conceptual row in the cmEthernetNetPortCpdV2Table. 
             These entries represent a Control Protocol Disposition 
             filtering criteria on the Ethernet Network Port."
    INDEX { neIndex, shelfIndex, slotIndex, cmEthernetNetPortIndex, 
            cmEthernetNetPortCpdV2Index }
    ::= { cmEthernetNetPortCpdV2Table 1 }


CmEthernetNetPortCpdV2Entry ::= SEQUENCE {
    -- Index
    cmEthernetNetPortCpdV2Index                 Integer32,

    -- Filtering Criteria
    cmEthernetNetPortCpdV2CiscoGroupDispType      CmControlProtocolDispType,
    cmEthernetNetPortCpdV2IslDispType             CmControlProtocolDispType,
    cmEthernetNetPortCpdV2PagpDispType            CmControlProtocolDispType,
    cmEthernetNetPortCpdV2UdldDispType            CmControlProtocolDispType,
    cmEthernetNetPortCpdV2CdpDispType             CmControlProtocolDispType,
    cmEthernetNetPortCpdV2VtpDispType             CmControlProtocolDispType,
    cmEthernetNetPortCpdV2DtpDispType             CmControlProtocolDispType,
    cmEthernetNetPortCpdV2PvstpPlusDispType       CmControlProtocolDispType,
    cmEthernetNetPortCpdV2UplinkFastDispType      CmControlProtocolDispType,
    cmEthernetNetPortCpdV2VlanBridgeDispType      CmControlProtocolDispType,
    cmEthernetNetPortCpdV2L2PTDispType            CmControlProtocolDispType,
    cmEthernetNetPortCpdV2BridgeGroupDispType     CmControlProtocolDispType,
    cmEthernetNetPortCpdV2BPDUDispType            CmControlProtocolDispType,
    cmEthernetNetPortCpdV2PauseDispType           CmControlProtocolDispType,
    cmEthernetNetPortCpdV2LACPDispType            CmControlProtocolDispType,
    cmEthernetNetPortCpdV2LACPMarkerDispType      CmControlProtocolDispType,
    cmEthernetNetPortCpdV2EfmOamDispType          CmControlProtocolDispType,
    cmEthernetNetPortCpdV2SSMDispType             CmControlProtocolDispType,
    cmEthernetNetPortCpdV2PortAuthenDispType      CmControlProtocolDispType,
    cmEthernetNetPortCpdV2BridgeReservedDispType  CmControlProtocolDispType,
    cmEthernetNetPortCpdV2LANBridgesDispType      CmControlProtocolDispType,
    cmEthernetNetPortCpdV2GARPGroupDispType       CmControlProtocolDispType,
    cmEthernetNetPortCpdV2GMRPDispType            CmControlProtocolDispType,
    cmEthernetNetPortCpdV2GVRPDispType            CmControlProtocolDispType,
    cmEthernetNetPortCpdV2GARPDispType            CmControlProtocolDispType,
    --
    cmEthernetNetPortCpdV2LLDPDispType            CmControlProtocolDispType,
    cmEthernetNetPortCpdV2ELMIDispType            CmControlProtocolDispType,
    cmEthernetNetPortCpdV2L2PTTunnelMac           MacAddress,
    --
    cmEthernetNetPortCpdV2Mac00DispType           CmControlProtocolDispType,
    cmEthernetNetPortCpdV2Mac01DispType           CmControlProtocolDispType,
    cmEthernetNetPortCpdV2Mac02DispType           CmControlProtocolDispType,
    cmEthernetNetPortCpdV2Mac03DispType           CmControlProtocolDispType,
    cmEthernetNetPortCpdV2Mac04DispType           CmControlProtocolDispType,
    cmEthernetNetPortCpdV2Mac05DispType           CmControlProtocolDispType,
    cmEthernetNetPortCpdV2Mac06DispType           CmControlProtocolDispType,
    cmEthernetNetPortCpdV2Mac07DispType           CmControlProtocolDispType,
    cmEthernetNetPortCpdV2Mac08DispType           CmControlProtocolDispType,
    cmEthernetNetPortCpdV2Mac09DispType           CmControlProtocolDispType,
    cmEthernetNetPortCpdV2Mac0ADispType           CmControlProtocolDispType,
    cmEthernetNetPortCpdV2Mac0BDispType           CmControlProtocolDispType,
    cmEthernetNetPortCpdV2Mac0CDispType           CmControlProtocolDispType,
    cmEthernetNetPortCpdV2Mac0DDispType           CmControlProtocolDispType,
    cmEthernetNetPortCpdV2Mac0EDispType           CmControlProtocolDispType,
    cmEthernetNetPortCpdV2Mac0FDispType           CmControlProtocolDispType,
    cmEthernetNetPortCpdV2NearestLLDPDispType     CmControlProtocolDispType,
    cmEthernetNetPortCpdV2NonTpmrLLDPDispType     CmControlProtocolDispType,
    cmEthernetNetPortCpdV2CustomerLLDPDispType    CmControlProtocolDispType,
    cmEthernetNetPortCpdV2PtpUntaggedDispType     CmControlProtocolDispType,
    cmEthernetNetPortCpdV2PtpTaggedDispType       CmControlProtocolDispType
}

cmEthernetNetPortCpdV2Index OBJECT-TYPE
    SYNTAX      Integer32 
    MAX-ACCESS  read-only
    STATUS      current
    DESCRIPTION
        "Unique Index value to access the CPD row."
    ::= { cmEthernetNetPortCpdV2Entry 1 }

cmEthernetNetPortCpdV2CiscoGroupDispType OBJECT-TYPE
    SYNTAX      CmControlProtocolDispType 
    MAX-ACCESS  read-write
    STATUS      deprecated
    DESCRIPTION
        "Deprecated - each Cisco protocol has its own disposition.
         Control Protocol Disposition for Cisco Group.  This includes
         ISL, PAGP, UDLD, CDP, VTP, DTP, PSVTP+, UplinkFast, VLAN Bridge,
         L2PT.  Note that a specific protocol filter overrides the
         group setting."
    ::= { cmEthernetNetPortCpdV2Entry 2 }

cmEthernetNetPortCpdV2IslDispType OBJECT-TYPE
    SYNTAX      CmControlProtocolDispType 
    MAX-ACCESS  read-write
    STATUS      current
    DESCRIPTION
        "Control Protocol Disposition for ISL (Inter Switch Link).
         MAC Address (01:00:0C:00:00:00)."
    ::= { cmEthernetNetPortCpdV2Entry 3 }

cmEthernetNetPortCpdV2PagpDispType OBJECT-TYPE
    SYNTAX      CmControlProtocolDispType 
    MAX-ACCESS  read-write
    STATUS      current
    DESCRIPTION
        "Control Protocol Disposition for PAGP (Port Aggregation Protocol).
         MAC Address (01:00:0C:CC:CC:CC), Ethertype(0x104)."
    ::= { cmEthernetNetPortCpdV2Entry 4 }

cmEthernetNetPortCpdV2UdldDispType OBJECT-TYPE
    SYNTAX      CmControlProtocolDispType 
    MAX-ACCESS  read-write
    STATUS      current
    DESCRIPTION
        "Control Protocol Disposition for UDLD (Unidirectional Link Detection).
         MAC Address (01:00:0C:CC:CC:CC), Ethertype(0x111)."
    ::= { cmEthernetNetPortCpdV2Entry 5 }

cmEthernetNetPortCpdV2CdpDispType OBJECT-TYPE
    SYNTAX      CmControlProtocolDispType 
    MAX-ACCESS  read-write
    STATUS      current
    DESCRIPTION
        "Control Protocol Disposition for CDP (Cisco Discovery Protocol).
         MAC Address (01:00:0C:CC:CC:CC), Ethertype(0x2000)."
    ::= { cmEthernetNetPortCpdV2Entry 6 }

cmEthernetNetPortCpdV2VtpDispType OBJECT-TYPE
    SYNTAX      CmControlProtocolDispType 
    MAX-ACCESS  read-write
    STATUS      current
    DESCRIPTION
        "Control Protocol Disposition for VTP (VLAN Trunking Protocol).
         MAC Address (01:00:0C:CC:CC:CC), Ethertype(0x2003)."
    ::= { cmEthernetNetPortCpdV2Entry 7 }

cmEthernetNetPortCpdV2DtpDispType OBJECT-TYPE
    SYNTAX      CmControlProtocolDispType 
    MAX-ACCESS  read-write
    STATUS      current
    DESCRIPTION
        "Control Protocol Disposition for DTP (Dynamic Trunking).
         MAC Address (01:00:0C:CC:CC:CC), Ethertype(0x2004)."
    ::= { cmEthernetNetPortCpdV2Entry 8 }

cmEthernetNetPortCpdV2PvstpPlusDispType OBJECT-TYPE
    SYNTAX      CmControlProtocolDispType 
    MAX-ACCESS  read-write
    STATUS      current
    DESCRIPTION
        "Control Protocol Disposition for Spanning Tree PVSTP+.
         MAC Address (01:00:0C:CC:CC:CC), Ethertype(0x10B)."
    ::= { cmEthernetNetPortCpdV2Entry 9 }

cmEthernetNetPortCpdV2UplinkFastDispType OBJECT-TYPE
    SYNTAX      CmControlProtocolDispType 
    MAX-ACCESS  read-write
    STATUS      current
    DESCRIPTION
        "Control Protocol Disposition for STP UplinkFast.
         MAC Address (01:00:0C:CD:CD:CD), Ethertype(0x200A)."
    ::= { cmEthernetNetPortCpdV2Entry 10 }

cmEthernetNetPortCpdV2VlanBridgeDispType OBJECT-TYPE
    SYNTAX      CmControlProtocolDispType 
    MAX-ACCESS  read-write
    STATUS      current
    DESCRIPTION
        "Control Protocol Disposition for VLAN Bridge.
         MAC Address (01:00:0C:CD:CD:CE), Ethertype(0x10C)."
    ::= { cmEthernetNetPortCpdV2Entry 11 }

cmEthernetNetPortCpdV2L2PTDispType OBJECT-TYPE
    SYNTAX      CmControlProtocolDispType 
    MAX-ACCESS  read-write
    STATUS      current
    DESCRIPTION
        "Control Protocol Disposition for Layer 2 Protocol Tunnelling(L2PT).
         MAC Address (01:00:0C:CD:CD:D0)."
    ::= { cmEthernetNetPortCpdV2Entry 12 }

cmEthernetNetPortCpdV2BridgeGroupDispType OBJECT-TYPE
    SYNTAX      CmControlProtocolDispType 
    MAX-ACCESS  read-write
    STATUS      deprecated
    DESCRIPTION
        "Deprecated - individual dispositions available for each MAC.
         Bridge Group Control Protocol Disposition Type.  This
         includes BPDU, PAUSE (IEEE 802.3x Flow Control), 
         LACP (Link Aggregation), LACP Marker (Marker), 
         EFM OAM (IEEE 802.3 ah) and IEEE 802.1x Port Authentication, 
         besides reserved MAC addresses from 
         01:80:C2:00:00:04 thru 01:80:C2:00:00:0F."
    ::= { cmEthernetNetPortCpdV2Entry 13 }

cmEthernetNetPortCpdV2BPDUDispType OBJECT-TYPE
    SYNTAX      CmControlProtocolDispType 
    MAX-ACCESS  read-write
    STATUS      current
    DESCRIPTION
        "Control Protocol Disposition for IEEE Spanning Tree(STP),
         MSTP (Multiple Spanning Tree) and RSTP (Rapid Reconfiguration of
         Spanning Tree). MAC Address (01:80:C2:00:00:00)."
    ::= { cmEthernetNetPortCpdV2Entry 14 }

cmEthernetNetPortCpdV2PauseDispType OBJECT-TYPE
    SYNTAX      CmControlProtocolDispType 
    MAX-ACCESS  read-write
    STATUS      current
    DESCRIPTION
        "Control Protocol Disposition for IEEE 802.3x Flow Control 
         (PAUSE frames)."
    ::= { cmEthernetNetPortCpdV2Entry 15 }

cmEthernetNetPortCpdV2LACPDispType OBJECT-TYPE
    SYNTAX      CmControlProtocolDispType 
    MAX-ACCESS  read-write
    STATUS      current
    DESCRIPTION
        "Control Protocol Disposition for 802.3ad Link Aggregation
         Protocol.
         MAC Address (01:80:C2:00:00:03), Ethertype (0x8809), Subtype(01)."
    ::= { cmEthernetNetPortCpdV2Entry 16 }

cmEthernetNetPortCpdV2LACPMarkerDispType OBJECT-TYPE
    SYNTAX      CmControlProtocolDispType 
    MAX-ACCESS  read-write
    STATUS      current
    DESCRIPTION
        "Control Protocol Disposition for IEEE 802.3ad Marker Protocol.
         MAC Address (01:80:C2:00:00:03), Ethertype (0x8809), Subtype(02)."
    ::= { cmEthernetNetPortCpdV2Entry 17 }

cmEthernetNetPortCpdV2EfmOamDispType OBJECT-TYPE
    SYNTAX      CmControlProtocolDispType 
    MAX-ACCESS  read-write
    STATUS      current
    DESCRIPTION
        "Control Protocol Disposition for IEEE 802.3ah EFM OAM.
         MAC Address (01:80:C2:00:00:03), Ethertype (0x8809), Subtype(03)."
    ::= { cmEthernetNetPortCpdV2Entry 18 }

cmEthernetNetPortCpdV2SSMDispType OBJECT-TYPE
    SYNTAX      CmControlProtocolDispType 
    MAX-ACCESS  read-write
    STATUS      current
    DESCRIPTION
        "Control Protocol Disposition for Sync Status Messages.
         MAC Address (01:80:C2:00:00:02), Ethertype (0x19A7), Subtype(0A)."
    ::= { cmEthernetNetPortCpdV2Entry 19 }

cmEthernetNetPortCpdV2PortAuthenDispType OBJECT-TYPE
    SYNTAX      CmControlProtocolDispType 
    MAX-ACCESS  read-write
    STATUS      current
    DESCRIPTION
        "Control Protocol Disposition for IEEE 802.1x Protocol.
         MAC Address (01:80:C2:00:00:03), Ethertype (0x888E)."
    ::= { cmEthernetNetPortCpdV2Entry 20 }

cmEthernetNetPortCpdV2BridgeReservedDispType OBJECT-TYPE
    SYNTAX      CmControlProtocolDispType 
    MAX-ACCESS  read-write
    STATUS      deprecated
    DESCRIPTION
        "Deprecated - individual dispositions available for each MAC.
         Control Protocol Disposition for Range of MAC Addresses
         from 01:80:C2:00:00:04 to 01:80:C2:00:00:0F."
    ::= { cmEthernetNetPortCpdV2Entry 21 }

cmEthernetNetPortCpdV2LANBridgesDispType OBJECT-TYPE
    SYNTAX      CmControlProtocolDispType 
    MAX-ACCESS  read-write
    STATUS      current
    DESCRIPTION
        "Control Protocol Disposition for IEEE 802.1d LAN Bridge Managment.
         MAC Address (01:80:C2:00:00:10)."
    ::= { cmEthernetNetPortCpdV2Entry 22 }

cmEthernetNetPortCpdV2GARPGroupDispType OBJECT-TYPE
    SYNTAX      CmControlProtocolDispType 
    MAX-ACCESS  read-write
    STATUS      deprecated
    DESCRIPTION
        "Deprecated - each GARP Group protocol has its own disposition.
         Group Disposition type which includes GMRP, GVRP and
         MAC Address from range 01:80:C2:00:00:20 to 01:80:C2:00:00:2F."
    ::= { cmEthernetNetPortCpdV2Entry 23 }

cmEthernetNetPortCpdV2GMRPDispType OBJECT-TYPE
    SYNTAX      CmControlProtocolDispType 
    MAX-ACCESS  read-write
    STATUS      current
    DESCRIPTION
        "Control Protocol Disposition for GARP Multicast Registration
         Protocol. MAC Address (01:80:C2:00:00:20)."
    ::= { cmEthernetNetPortCpdV2Entry 24 }

cmEthernetNetPortCpdV2GVRPDispType OBJECT-TYPE
    SYNTAX      CmControlProtocolDispType 
    MAX-ACCESS  read-write
    STATUS      current
    DESCRIPTION
        "Control Protocol Disposition for GARP VLAN Registration
         Protocol. MAC Address (01:80:C2:00:00:21)."
    ::= { cmEthernetNetPortCpdV2Entry 25 }

cmEthernetNetPortCpdV2GARPDispType OBJECT-TYPE
    SYNTAX      CmControlProtocolDispType 
    MAX-ACCESS  read-write
    STATUS      current
    DESCRIPTION
        "Group Disposition type which includes GARP Reserved 
         MAC Address from range 01:80:C2:00:00:22 to 01:80:C2:00:00:2F."
    ::= { cmEthernetNetPortCpdV2Entry 26 }

cmEthernetNetPortCpdV2LLDPDispType OBJECT-TYPE
    SYNTAX      CmControlProtocolDispType 
    MAX-ACCESS  read-write
    STATUS      deprecated
    DESCRIPTION
        "Deprecated - each LLDP MAC protocol has its own disposition.
         LLDP (Link Layer Discovery Protocol) Disposition type. 
         MAC Address 01:80:C2:00:00:0e, 01:80:C2:00:00:03, or
         01:80:C2:00:00:00."
    ::= { cmEthernetNetPortCpdV2Entry 27 }

cmEthernetNetPortCpdV2ELMIDispType OBJECT-TYPE
    SYNTAX      CmControlProtocolDispType 
    MAX-ACCESS  read-write
    STATUS      current
    DESCRIPTION
        "ELMI (Ethernet Local Management Interface) Disposition type. 
         MAC Address 01:80:C2:00:00:07 and EtherType of 0x88EE."
    ::= { cmEthernetNetPortCpdV2Entry 28 }

cmEthernetNetPortCpdV2L2PTTunnelMac  OBJECT-TYPE
    SYNTAX      MacAddress 
    MAX-ACCESS  read-write
    STATUS      current
    DESCRIPTION
        "Configurable Layer 2 Protocol Tunneling MAC Address.  
         For protocols STP, CDP and VTP, with control protocol disposition as 
         pass-thru-l2pt, this configured MAC address replaces the DA, upon
         encapsulation.  For decapsulation, protocol signature and this 
         configured MAC address are matched and the MAC address is replaced
         with the protocol's inferred MAC address." 
    ::= { cmEthernetNetPortCpdV2Entry 29 }

cmEthernetNetPortCpdV2Mac00DispType OBJECT-TYPE
    SYNTAX      CmControlProtocolDispType 
    MAX-ACCESS  read-write
    STATUS      current
    DESCRIPTION
        "MAC Address 01:80:C2:00:00:00 Disposition type."
    ::= { cmEthernetNetPortCpdV2Entry 30 }

cmEthernetNetPortCpdV2Mac01DispType OBJECT-TYPE
    SYNTAX      CmControlProtocolDispType 
    MAX-ACCESS  read-write
    STATUS      current
    DESCRIPTION
        "MAC Address 01:80:C2:00:00:01 Disposition type."
    ::= { cmEthernetNetPortCpdV2Entry 31 }

cmEthernetNetPortCpdV2Mac02DispType OBJECT-TYPE
    SYNTAX      CmControlProtocolDispType 
    MAX-ACCESS  read-write
    STATUS      current
    DESCRIPTION
        "MAC Address 01:80:C2:00:00:02 Disposition type."
    ::= { cmEthernetNetPortCpdV2Entry 32 }

cmEthernetNetPortCpdV2Mac03DispType OBJECT-TYPE
    SYNTAX      CmControlProtocolDispType 
    MAX-ACCESS  read-write
    STATUS      current
    DESCRIPTION
        "MAC Address 01:80:C2:00:00:03 Disposition type."
    ::= { cmEthernetNetPortCpdV2Entry 33 }

cmEthernetNetPortCpdV2Mac04DispType OBJECT-TYPE
    SYNTAX      CmControlProtocolDispType 
    MAX-ACCESS  read-write
    STATUS      current
    DESCRIPTION
        "MAC Address 01:80:C2:00:00:04 Disposition type."
    ::= { cmEthernetNetPortCpdV2Entry 34 }

cmEthernetNetPortCpdV2Mac05DispType OBJECT-TYPE
    SYNTAX      CmControlProtocolDispType 
    MAX-ACCESS  read-write
    STATUS      current
    DESCRIPTION
        "MAC Address 01:80:C2:00:00:05 Disposition type."
    ::= { cmEthernetNetPortCpdV2Entry 35 }

cmEthernetNetPortCpdV2Mac06DispType OBJECT-TYPE
    SYNTAX      CmControlProtocolDispType 
    MAX-ACCESS  read-write
    STATUS      current
    DESCRIPTION
        "MAC Address 01:80:C2:00:00:06 Disposition type."
    ::= { cmEthernetNetPortCpdV2Entry 36 }

cmEthernetNetPortCpdV2Mac07DispType OBJECT-TYPE
    SYNTAX      CmControlProtocolDispType 
    MAX-ACCESS  read-write
    STATUS      current
    DESCRIPTION
        "MAC Address 01:80:C2:00:00:07 Disposition type."
    ::= { cmEthernetNetPortCpdV2Entry 37 }

cmEthernetNetPortCpdV2Mac08DispType OBJECT-TYPE
    SYNTAX      CmControlProtocolDispType 
    MAX-ACCESS  read-write
    STATUS      current
    DESCRIPTION
        "MAC Address 01:80:C2:00:00:08 Disposition type."
    ::= { cmEthernetNetPortCpdV2Entry 38 }

cmEthernetNetPortCpdV2Mac09DispType OBJECT-TYPE
    SYNTAX      CmControlProtocolDispType 
    MAX-ACCESS  read-write
    STATUS      current
    DESCRIPTION
        "MAC Address 01:80:C2:00:00:09 Disposition type."
    ::= { cmEthernetNetPortCpdV2Entry 39 }

cmEthernetNetPortCpdV2Mac0ADispType OBJECT-TYPE
    SYNTAX      CmControlProtocolDispType 
    MAX-ACCESS  read-write
    STATUS      current
    DESCRIPTION
        "MAC Address 01:80:C2:00:00:0A Disposition type."
    ::= { cmEthernetNetPortCpdV2Entry 40 }

cmEthernetNetPortCpdV2Mac0BDispType OBJECT-TYPE
    SYNTAX      CmControlProtocolDispType 
    MAX-ACCESS  read-write
    STATUS      current
    DESCRIPTION
        "MAC Address 01:80:C2:00:00:0B Disposition type."
    ::= { cmEthernetNetPortCpdV2Entry 41 }

cmEthernetNetPortCpdV2Mac0CDispType OBJECT-TYPE
    SYNTAX      CmControlProtocolDispType 
    MAX-ACCESS  read-write
    STATUS      current
    DESCRIPTION
        "MAC Address 01:80:C2:00:00:0C Disposition type."
    ::= { cmEthernetNetPortCpdV2Entry 42 }

cmEthernetNetPortCpdV2Mac0DDispType OBJECT-TYPE
    SYNTAX      CmControlProtocolDispType 
    MAX-ACCESS  read-write
    STATUS      current
    DESCRIPTION
        "MAC Address 01:80:C2:00:00:0D Disposition type."
    ::= { cmEthernetNetPortCpdV2Entry 43 }

cmEthernetNetPortCpdV2Mac0EDispType OBJECT-TYPE
    SYNTAX      CmControlProtocolDispType 
    MAX-ACCESS  read-write
    STATUS      current
    DESCRIPTION
        "MAC Address 01:80:C2:00:00:0E Disposition type."
    ::= { cmEthernetNetPortCpdV2Entry 44 }

cmEthernetNetPortCpdV2Mac0FDispType OBJECT-TYPE
    SYNTAX      CmControlProtocolDispType 
    MAX-ACCESS  read-write
    STATUS      current
    DESCRIPTION
        "MAC Address 01:80:C2:00:00:0F Disposition type."
    ::= { cmEthernetNetPortCpdV2Entry 45 }

cmEthernetNetPortCpdV2NearestLLDPDispType OBJECT-TYPE
    SYNTAX      CmControlProtocolDispType 
    MAX-ACCESS  read-write
    STATUS      current
    DESCRIPTION
        "LLDP (Link Layer Discovery Protocol) Nearest Bridge Disposition type."
    ::= { cmEthernetNetPortCpdV2Entry 46 }

cmEthernetNetPortCpdV2NonTpmrLLDPDispType OBJECT-TYPE
    SYNTAX      CmControlProtocolDispType 
    MAX-ACCESS  read-write
    STATUS      current
    DESCRIPTION
        "LLDP (Link Layer Discovery Protocol) Non-TPMR Bridge Disposition type."
    ::= { cmEthernetNetPortCpdV2Entry 47 }

cmEthernetNetPortCpdV2CustomerLLDPDispType OBJECT-TYPE
    SYNTAX      CmControlProtocolDispType 
    MAX-ACCESS  read-write
    STATUS      current
    DESCRIPTION
        "LLDP (Link Layer Discovery Protocol) Customer Bridge Disposition type."
    ::= { cmEthernetNetPortCpdV2Entry 48 }

cmEthernetNetPortCpdV2PtpUntaggedDispType OBJECT-TYPE
    SYNTAX      CmControlProtocolDispType
    MAX-ACCESS  read-write
    STATUS      current
    DESCRIPTION
        "PTP non forwarding untagged frame Disposition type."
    ::= { cmEthernetNetPortCpdV2Entry 49 }

cmEthernetNetPortCpdV2PtpTaggedDispType OBJECT-TYPE
    SYNTAX      CmControlProtocolDispType
    MAX-ACCESS  read-write
    STATUS      current
    DESCRIPTION
        "PTP tagged frame Disposition type."
    ::= { cmEthernetNetPortCpdV2Entry 50 }

--
--  BITS (Building Integrated Timing System) Port 
--
bitsPortTable OBJECT-TYPE
    SYNTAX      SEQUENCE OF BitsPortEntry
    MAX-ACCESS  not-accessible
    STATUS      current
    DESCRIPTION
            "A list of entries corresponding to BITS Port 
             Facilities for configuration purposes."
    ::= { cmFacilityObjects 16 }

bitsPortEntry OBJECT-TYPE
    SYNTAX      BitsPortEntry 
    MAX-ACCESS  not-accessible
    STATUS      current
    DESCRIPTION
            "A conceptual row in the bitsPortTable."
    INDEX { neIndex, shelfIndex, slotIndex, bitsPortTypeIndex, bitsPortIndex }
    ::= { bitsPortTable 1 }

BitsPortEntry ::= SEQUENCE {
    -- Port Indices 
    bitsPortTypeIndex                  Integer32,
    bitsPortIndex                      Integer32,
    bitsPortIfIndex                    InterfaceIndex,
    bitsPortEntityIndex                PhysicalIndex,

    -- State Management params
    bitsPortAdminState                 AdminState,
    bitsPortOperationalState           OperationalState,
    bitsPortSecondaryState             SecondaryState,

    -- bits port specific params 
    bitsPortType                       BitsPortType,
    bitsPortLineType                   BitsPortLineType,
    bitsPortLineCode                   BitsPortLineCode,
    bitsPortFrameFormat                BitsFrameFormat,
    bitsPortSaBitDesignation           SaBitDesignation,

    --Synchronous Port params
    bitsPortQLModeEnabled              TruthValue,
    bitsPortExpectedQL                 SSMQualityLevel,
    bitsPortAssumedQL                  SSMQualityLevel,
    bitsPortReceivedQL                 SSMQualityLevel,
    bitsPortTransmitQL                 SSMQualityLevel,
    bitsPortSquelchQL                  SSMQualityLevel,
    bitsPortLineBuildOut               LineBuildOut,
    bitsPortImpedance                  BitsPortImpedanceMode,
    
    bitsPortCrc4                       TruthValue,
    bitsPortIdleCode                   INTEGER,
    bitsPortAis                        TruthValue,
    bitsPortSaBitsAdminState           SaBitsState,
    bitsPortSquelchControl             SquelchControl,
    bitsPortSignalShape                SignalShape,
    bitsPortSignalFrequency            SignalFrequency
}
    
-- Port Indices 
bitsPortTypeIndex OBJECT-TYPE
    SYNTAX      Integer32 (1..2)
    MAX-ACCESS  read-only
    STATUS      current
    DESCRIPTION
         "An integer index value used to uniquely identify
          this BITS Port within the card. Value 1 stands for
          BITS-IN, 2 for BITS-OUT."
    ::= { bitsPortEntry 1 }

bitsPortIndex OBJECT-TYPE
    SYNTAX      Integer32 (1..65535)
    MAX-ACCESS  read-only
    STATUS      current
    DESCRIPTION
         "An integer index value used to uniquely identify
          this BITS Port within the card.
          Note that each BITs Port is uniquely identified
          by the indices neIndex, shelfIndex, 
          slotIndex, bitsPortIndex." 
    ::= { bitsPortEntry 2 }

bitsPortIfIndex OBJECT-TYPE
    SYNTAX      InterfaceIndex
    MAX-ACCESS  read-only
    STATUS      current
    DESCRIPTION
         "This object has the same value as ifIndex for 
          Bits Port.  An integer index value used to 
          uniquely identify this Bits Port."
    ::= { bitsPortEntry 3 }

bitsPortEntityIndex OBJECT-TYPE
    SYNTAX      PhysicalIndex 
    MAX-ACCESS  read-only
    STATUS      current
    DESCRIPTION
           "Entity Index from ENTITY-MIB for this port."
    ::= { bitsPortEntry 4 }

-- State Management params
bitsPortAdminState OBJECT-TYPE
    SYNTAX      AdminState 
    MAX-ACCESS  read-write
    STATUS      current
    DESCRIPTION
            "This object represents the Administrative State of the BITS 
             Port."
    ::= { bitsPortEntry 5 }

bitsPortOperationalState OBJECT-TYPE
    SYNTAX      OperationalState 
    MAX-ACCESS  read-only
    STATUS      current
    DESCRIPTION
            "This object represents the Operational State of the BITS 
             Port."
    ::= { bitsPortEntry 6 }

bitsPortSecondaryState OBJECT-TYPE
    SYNTAX      SecondaryState 
    MAX-ACCESS  read-only
    STATUS      current
    DESCRIPTION
            "This object represents the Secondary State of the BITS 
             Port."
    ::= { bitsPortEntry 7 }

bitsPortType OBJECT-TYPE
    SYNTAX      BitsPortType 
    MAX-ACCESS  read-only
    STATUS      current
    DESCRIPTION
            "This object represents the BITS Port Type."
    ::= { bitsPortEntry 8 }

bitsPortLineType OBJECT-TYPE
    SYNTAX      BitsPortLineType 
    MAX-ACCESS  read-write
    STATUS      current
    DESCRIPTION
            "This object represents the BITS Port Line Type.
             Determines whether the T1/E1 BITS port operates in T1, E1, 
             or 2048kHz mode."
    ::= { bitsPortEntry 9 }

bitsPortLineCode OBJECT-TYPE
    SYNTAX      BitsPortLineCode 
    MAX-ACCESS  read-write
    STATUS      current
    DESCRIPTION
            "This object represents the BITS Port Line Code.
             When the port is configured for a Line Type of T1, 
             the valid values are t1-b8zs and t1-ami and the default value
             is t1-b8zs. When the port is configured for a Line Type of E1, 
             the valid values are e1-hdb3 and e1-ami and the default value 
             is e1-hdb3. When the port is configured for a Line Type of 
             2048kHz, the value is none."
    ::= { bitsPortEntry 10 }

bitsPortFrameFormat OBJECT-TYPE
    SYNTAX      BitsFrameFormat 
    MAX-ACCESS  read-write
    STATUS      current
    DESCRIPTION
            "This object represents the BITS Port Frame Format.
             When the port is configured for a Line Type of T1, the
             valid values are t1-sf and t1-esf and the default value is t1-esf.
             When the port is configured for a Line Type of E1, the
             valid values are e1-unframed, e1-crc4, and e1-dualFrame 
             and the default value is e1-crc4. When the port is configured 
             for a Line Type of 2048kHz, the value is none.

             R4.1CC and R4.3CC do not support e1-unframed."
    ::= { bitsPortEntry 11 }

bitsPortSaBitDesignation OBJECT-TYPE
    SYNTAX      SaBitDesignation 
    MAX-ACCESS  read-write
    STATUS      current
    DESCRIPTION
            "This object represents the BITS Port Sa Bit Designation.
             Determines which E1 Sa Bit is used to transmit/receive the SSM. 
             For T1 and 2048khz Line Types, the only allowed value is None. 
             For E1 Line Type, the default value is bit4 and it can 
             only have a value of None if QL Mode is disabled, otherwise, 
             None is an invalid value."
    ::= { bitsPortEntry 12 }

bitsPortQLModeEnabled OBJECT-TYPE 
    SYNTAX     TruthValue
    MAX-ACCESS read-write
    STATUS     current
    DESCRIPTION
         "This object allows to specify whether the BITS Port 
          can be enabled/disabled for QL Mode. 
          When enabled, on receive side 
            -port shall PEER the SSM (Sync Status Messages) slow protocol PDUs 
             and take appropriate action 
          When enabled, on transmit side 
            -port shall periodically (once a second) transmit QL TLV 
             information PDUs
          When disabled, on receive side,
            -port shall terminate and discard any SSM slow protocol PDUs 
          When disabled, on transmit side 
            -port shall not transmit any SSM slow protocol PDUs."
     ::= { bitsPortEntry 13 }

bitsPortExpectedQL OBJECT-TYPE 
    SYNTAX     SSMQualityLevel
    MAX-ACCESS read-write
    STATUS     current
    DESCRIPTION
         "This object allows to specify the expected QL when the 
          BITS Port is enabled for QL Mode. 
          This object allows the user to set a minimum
          expected received Quality Level on the port. 
          The default value shall be None."
     ::= { bitsPortEntry 14 }

bitsPortAssumedQL OBJECT-TYPE 
    SYNTAX     SSMQualityLevel
    MAX-ACCESS read-write
    STATUS     current
    DESCRIPTION
         "This object allows to specify the assumed QL on the 
          BITS Port.  The Assumed QL is only meaningful if the 
          Network Clock Type (see fsp150cm-sync.mib) is option1 and the 
          port's QL Mode is disabled and the port is being used as 
          an input reference source. Under these conditions, 
          the specified QL value is assumed to be the Quality Level of the
          non-failed reference."
     ::= { bitsPortEntry 15 }

bitsPortReceivedQL OBJECT-TYPE 
    SYNTAX     SSMQualityLevel
    MAX-ACCESS read-only
    STATUS     current
    DESCRIPTION
         "This object provides the Received QL value for the BITS port. 
          If the BITS port's QL Mode is disabled, then the received 
          QL value is not applicable."
     ::= { bitsPortEntry 16 }

bitsPortTransmitQL OBJECT-TYPE 
    SYNTAX     SSMQualityLevel
    MAX-ACCESS read-only
    STATUS     current
    DESCRIPTION
         "This object provides the Transmitted QL value for the BITS port. 
          If the BITS port's QL Mode is disabled, then the received 
          QL value is not applicable."
     ::= { bitsPortEntry 17 }

bitsPortSquelchQL OBJECT-TYPE 
    SYNTAX     SSMQualityLevel
    MAX-ACCESS read-write
    STATUS     current
    DESCRIPTION
         "This object allows to set the Squelch QL for the BITS-OUT port. 
          The Squelch QL is only meaningful if the QL Mode is Enabled. 
          The Squelch QL is used to determine whether or not to squelch 
          the output of the BITS-OUT port. If the system's QL is lower 
          than the Squelch QL, the output is squelched.
          If the BITS port's QL Mode is disabled, then the received 
          QL value is not applicable."
     ::= { bitsPortEntry 18 }

bitsPortLineBuildOut OBJECT-TYPE 
    SYNTAX     LineBuildOut
    MAX-ACCESS read-write
    STATUS     current
    DESCRIPTION
         "This object allows to manage the line build out on the BITS-OUT port when
          the Line Type is T1."
     ::= { bitsPortEntry 19 }

bitsPortImpedance OBJECT-TYPE 
    SYNTAX     BitsPortImpedanceMode
    MAX-ACCESS read-only
    STATUS     current
    DESCRIPTION
         "This object provides the impedance mode for the BITS-OUT port."
     ::= { bitsPortEntry 20 }

bitsPortCrc4 OBJECT-TYPE 
    SYNTAX     TruthValue
    MAX-ACCESS read-write
    STATUS     current
    DESCRIPTION
         "This object allows to include or not the CRC to the signal
         of the BITS-OUT port."
     ::= { bitsPortEntry 21 }

bitsPortIdleCode OBJECT-TYPE 
    SYNTAX     INTEGER (0..255)
    MAX-ACCESS read-write
    STATUS     current
    DESCRIPTION
         "This object allows to manage the Idle Code for the BITS-OUT port."
     ::= { bitsPortEntry 22 }

bitsPortAis OBJECT-TYPE 
    SYNTAX     TruthValue
    MAX-ACCESS read-write
    STATUS     current
    DESCRIPTION
         "This object allows to set the AIS signal for the BITS-OUT port."
     ::= { bitsPortEntry 23 }

bitsPortSaBitsAdminState OBJECT-TYPE 
    SYNTAX     SaBitsState
    MAX-ACCESS read-write
    STATUS     current
    DESCRIPTION
         "This object allows to manage the five Sa Bit values, from bit4 to bit8,
         for the BITS-OUT port.
         The object value is a BIT string that concatenate the Sa Bit values. 
         The Sa Bit values are applied to each of the five Sa Bits of the output
         signal except to the one that carries SSM information when QL Mode is
         enabled."
     ::= { bitsPortEntry 24 }

bitsPortSquelchControl OBJECT-TYPE
    SYNTAX      SquelchControl 
    MAX-ACCESS  read-only
    STATUS      current
    DESCRIPTION
         "This object indicates the Squelch Control for the port. 
          The Squelch Control determines the type of squelch control 
          used to squelch an output of the port."
    ::= { bitsPortEntry 25 }

bitsPortSignalShape OBJECT-TYPE
    SYNTAX      SignalShape 
    MAX-ACCESS  read-only
    STATUS      current
    DESCRIPTION
         "This object represents the Port Signal Shape.
          Indicates whether the signal has a sine or a square shape."
    ::= { bitsPortEntry 26 }

bitsPortSignalFrequency OBJECT-TYPE
    SYNTAX      SignalFrequency 
    MAX-ACCESS  read-write
    STATUS      current
    DESCRIPTION
         "Indicates the signal frequency of the port.
          Possible value are 100 kHz, 1 MHz, 1544 kHz, 2048 kHz, 5 MHz, 
          25 Mhz or 50 MHz. 
          It can be set only to a port that is dedicated to yield a 
          variety of frequencies."
    ::= { bitsPortEntry 27 }

--
--  IEEE 1588 EthernetPort 
--
ieee1588EthernetPortTable OBJECT-TYPE
    SYNTAX      SEQUENCE OF IEEE1588EthernetPortEntry
    MAX-ACCESS  not-accessible
    STATUS      current
    DESCRIPTION
            "A list of entries corresponding to IEEE Ethernet Port
             Facilities for configuration purposes."
    ::= { cmFacilityObjects 17 }

ieee1588EthernetPortEntry OBJECT-TYPE
    SYNTAX      IEEE1588EthernetPortEntry 
    MAX-ACCESS  not-accessible
    STATUS      current
    DESCRIPTION
            "A conceptual row in the IEEE Ethernet Port Table."
    INDEX { neIndex, shelfIndex, slotIndex, ieee1588EthernetPortIndex }
    ::= { ieee1588EthernetPortTable 1 }

IEEE1588EthernetPortEntry ::= SEQUENCE {
    -- Port Indices 
    ieee1588EthernetPortIndex              Integer32,
    ieee1588EthernetPortIfIndex            InterfaceIndex,
    ieee1588EthernetPortEntityIndex        PhysicalIndex,

    -- State Management params
    ieee1588EthernetPortAdminState         AdminState,
    ieee1588EthernetPortOperationalState   OperationalState,
    ieee1588EthernetPortSecondaryState     SecondaryState,

    -- Port specific params
    ieee1588EthernetPortMTU                Integer32,

    -- Generic Ethernet Port params
    ieee1588EthernetPortMediaType          EthernetMediaType,
    ieee1588EthernetPortConfigSpeed        EthernetPortSpeed,
    ieee1588EthernetPortNegotiatedSpeed    EthernetPortSpeed,

    ieee1588EthernetPortMDIXType           CmEthernetMDIXType  
}
    
-- Port Indices 
ieee1588EthernetPortIndex OBJECT-TYPE
    SYNTAX      Integer32 
    MAX-ACCESS  read-only
    STATUS      current
    DESCRIPTION
         "An integer index value used to uniquely identify
          the IEEE Ethernet Port." 
    ::= { ieee1588EthernetPortEntry 1 }

ieee1588EthernetPortIfIndex OBJECT-TYPE
    SYNTAX      InterfaceIndex
    MAX-ACCESS  read-only
    STATUS      current
    DESCRIPTION
         "This object has the same value as ifIndex for 
          the IEEE Ethernet Port."
    ::= { ieee1588EthernetPortEntry 2 }

ieee1588EthernetPortEntityIndex OBJECT-TYPE
    SYNTAX      PhysicalIndex 
    MAX-ACCESS  read-only
    STATUS      current
    DESCRIPTION
           "Entity Index from ENTITY-MIB for this port."
    ::= { ieee1588EthernetPortEntry 3 }

-- State Management params
ieee1588EthernetPortAdminState OBJECT-TYPE
    SYNTAX      AdminState 
    MAX-ACCESS  read-write
    STATUS      current
    DESCRIPTION
            "This object represents the Administrative State of the 
             Port."
    ::= { ieee1588EthernetPortEntry 4 }

ieee1588EthernetPortOperationalState OBJECT-TYPE
    SYNTAX      OperationalState 
    MAX-ACCESS  read-only
    STATUS      current
    DESCRIPTION
            "This object represents the Operational State of the 
             Port."
    ::= { ieee1588EthernetPortEntry 5 }

ieee1588EthernetPortSecondaryState OBJECT-TYPE
    SYNTAX      SecondaryState 
    MAX-ACCESS  read-only
    STATUS      current
    DESCRIPTION
            "This object represents the Secondary State of the 
             Port."
    ::= { ieee1588EthernetPortEntry 6 }

ieee1588EthernetPortMTU OBJECT-TYPE
    SYNTAX      Integer32 
    MAX-ACCESS  read-write
    STATUS      current
    DESCRIPTION
            "This object provides the MTU on the Port."
    ::= { ieee1588EthernetPortEntry 7 }

ieee1588EthernetPortMediaType OBJECT-TYPE
    SYNTAX     EthernetMediaType
    MAX-ACCESS read-write
    STATUS     current
    DESCRIPTION
            "This object represents the type of Media."
    ::= { ieee1588EthernetPortEntry 8 }

ieee1588EthernetPortConfigSpeed OBJECT-TYPE
    SYNTAX     EthernetPortSpeed
    MAX-ACCESS read-write
    STATUS     current
    DESCRIPTION
            "This object allows to configure the speed of the Port."
    ::= { ieee1588EthernetPortEntry 9 }

ieee1588EthernetPortNegotiatedSpeed OBJECT-TYPE
    SYNTAX     EthernetPortSpeed
    MAX-ACCESS read-only
    STATUS     current
    DESCRIPTION
            "This object provides the negotiated speed of the 
             Port."
    ::= { ieee1588EthernetPortEntry 10 }

ieee1588EthernetPortMDIXType OBJECT-TYPE
    SYNTAX     CmEthernetMDIXType
    MAX-ACCESS read-write
    STATUS     current
    DESCRIPTION
            "This object allows management of MDIX property on  
             Port."
    ::= { ieee1588EthernetPortEntry 11 }


--
--  GPS 10MHz Port 
--
gps10MHzPortTable OBJECT-TYPE
    SYNTAX      SEQUENCE OF GPS10MHzPortEntry
    MAX-ACCESS  not-accessible
    STATUS      current
    DESCRIPTION
            "A list of entries corresponding to GPS 10MHz 
             Facilities for configuration purposes."
    ::= { cmFacilityObjects 18 }

gps10MHzPortEntry OBJECT-TYPE
    SYNTAX      GPS10MHzPortEntry 
    MAX-ACCESS  not-accessible
    STATUS      current
    DESCRIPTION
            "A conceptual row in the GPS 10MHz Port Table."
    INDEX { neIndex, shelfIndex, slotIndex, gps10MHzPortIndex }
    ::= { gps10MHzPortTable 1 }

GPS10MHzPortEntry ::= SEQUENCE {
    -- Port Indices 
    gps10MHzPortIndex              Integer32,
    gps10MHzPortIfIndex            InterfaceIndex,
    gps10MHzPortEntityIndex        PhysicalIndex,

    -- State Management params
    gps10MHzPortAdminState         AdminState,
    gps10MHzPortOperationalState   OperationalState,
    gps10MHzPortSecondaryState     SecondaryState,
    gps10MHzPortSignalDirection    SignalDirectionType,

    gps10MHzPortSquelchControl     SquelchControl,
    gps10MHzPortSquelchQL          SSMQualityLevel,

    gps10MHzPortFrequencySource    VariablePointer,
    gps10MHzPortClockClass         Unsigned32, -- deprecated, should not be in this group.
    gps10MHzPortClockAccuracy      Unsigned32, -- deprecated, should not be in this group.
    gps10MHzPortTimeSource         TimeSource, -- deprecated, should not be in this group.
    gps10MHzPortAssumedQL          SSMQualityLevel,
    gps10MHzPortAlias              DisplayString,
    gps10MHzPortInputSignalType    ClkSignalType
}
    
-- Port Indices 
gps10MHzPortIndex OBJECT-TYPE
    SYNTAX      Integer32 
    MAX-ACCESS  read-only
    STATUS      current
    DESCRIPTION
         "An integer index value used to uniquely identify
          the IEEE Ethernet Port." 
    ::= { gps10MHzPortEntry 1 }

gps10MHzPortIfIndex OBJECT-TYPE
    SYNTAX      InterfaceIndex
    MAX-ACCESS  read-only
    STATUS      current
    DESCRIPTION
         "This object has the same value as ifIndex for 
          the IEEE Ethernet Port."
    ::= { gps10MHzPortEntry 2 }

gps10MHzPortEntityIndex OBJECT-TYPE
    SYNTAX      PhysicalIndex 
    MAX-ACCESS  read-only
    STATUS      current
    DESCRIPTION
           "Entity Index from ENTITY-MIB for this port."
    ::= { gps10MHzPortEntry 3 }

-- State Management params
gps10MHzPortAdminState OBJECT-TYPE
    SYNTAX      AdminState 
    MAX-ACCESS  read-write
    STATUS      current
    DESCRIPTION
            "This object represents the Administrative State of the 
             Port."
    ::= { gps10MHzPortEntry 4 }

gps10MHzPortOperationalState OBJECT-TYPE
    SYNTAX      OperationalState 
    MAX-ACCESS  read-only
    STATUS      current
    DESCRIPTION
            "This object represents the Operational State of the 
             Port."
    ::= { gps10MHzPortEntry 5 }

gps10MHzPortSecondaryState OBJECT-TYPE
    SYNTAX      SecondaryState 
    MAX-ACCESS  read-only
    STATUS      current
    DESCRIPTION
            "This object represents the Secondary State of the 
             Port."
    ::= { gps10MHzPortEntry 6 }

gps10MHzPortSignalDirection OBJECT-TYPE
    SYNTAX      SignalDirectionType 
    MAX-ACCESS  read-write
    STATUS      current
    DESCRIPTION
            "This object allows specification of the signal type 
             (i.e. input or output)."
    ::= { gps10MHzPortEntry 7 }

gps10MHzPortSquelchControl  OBJECT-TYPE 
    SYNTAX     SquelchControl
    MAX-ACCESS read-write
    STATUS     current
    DESCRIPTION
         "This object allows to set the Squelch Control for the 10MHz port. 
          The Squelch Control is used to determine the type of squelch control 
          used to squelch the output of the TOD port. Only option supported
          is squelch-ql."
     ::= { gps10MHzPortEntry 8 }

gps10MHzPortSquelchQL OBJECT-TYPE 
    SYNTAX     SSMQualityLevel
    MAX-ACCESS read-write
    STATUS     current
    DESCRIPTION
         "This object allows to set the Squelch QL for the 10MHz port. 
          This value is used when f310MHzClockPortSquelchControl is squelch-ql.
          The Squelch QL is used to determine whether or not to squelch 
          the output of the TOD port. If the system's QL is lower 
          than the Squelch QL, the output is squelched."
     ::= { gps10MHzPortEntry 9 }

gps10MHzPortFrequencySource OBJECT-TYPE 
    SYNTAX     VariablePointer
    MAX-ACCESS read-write
    STATUS     current
    DESCRIPTION
         "This object allows to set the Frequency Source for the Port." 
     ::= { gps10MHzPortEntry 10 }

gps10MHzPortClockClass OBJECT-TYPE
    SYNTAX      Unsigned32
    MAX-ACCESS  read-only
    STATUS      deprecated
    DESCRIPTION
           "This object specify GPS port clock class."
    ::= { gps10MHzPortEntry 11 }

gps10MHzPortClockAccuracy OBJECT-TYPE
    SYNTAX      Unsigned32
    MAX-ACCESS  read-only
    STATUS      deprecated
    DESCRIPTION
           "This object specify GPS port clock accuracy."
    ::= { gps10MHzPortEntry 12 }

gps10MHzPortTimeSource OBJECT-TYPE
    SYNTAX      TimeSource
    MAX-ACCESS  read-only
    STATUS      deprecated
    DESCRIPTION
           "This object specify GPS port time source."
    ::= { gps10MHzPortEntry 13 }

gps10MHzPortAssumedQL OBJECT-TYPE 
    SYNTAX     SSMQualityLevel
    MAX-ACCESS read-write
    STATUS     current
    DESCRIPTION
         "This object allows to specify the assumed QL on the 
          GPS Port.  The Assumed QL is only meaningful if the 
          Network Clock Type (see fsp150cm-sync.mib) is option1 and the 
          port's QL Mode is disabled and the port is being used as 
          an input reference source. Under these conditions, 
          the specified QL value is assumed to be the Quality Level of the
          non-failed reference."
     ::= { gps10MHzPortEntry 14 }

gps10MHzPortAlias    OBJECT-TYPE
    SYNTAX      DisplayString (SIZE(0..64))
    MAX-ACCESS  read-write
    STATUS      current
    DESCRIPTION
         "This object allows SNMP management entities to provide an 
          alias to the gps 10MHz Port entity."
     ::= { gps10MHzPortEntry 15 }

gps10MHzPortInputSignalType  OBJECT-TYPE
    SYNTAX      ClkSignalType 
    MAX-ACCESS  read-write
    STATUS      current
    DESCRIPTION
            "This object allows specification of the input signal type 
             (i.e. 10mhz or 2048khz)."
    ::= { gps10MHzPortEntry 16 }

--
--  Ethernet Network Port Cable Length Benchmark 
--
cmEthernetNetPortClbTable  OBJECT-TYPE
    SYNTAX      SEQUENCE OF CmEthernetNetPortClbEntry
    MAX-ACCESS  not-accessible
    STATUS      current
    DESCRIPTION
            "A list of entries corresponding to Ethernet Network Port 
             Cable Length Benchmark."
    ::= { cmFacilityObjects 19 }

cmEthernetNetPortClbEntry OBJECT-TYPE
    SYNTAX      CmEthernetNetPortClbEntry 
    MAX-ACCESS  not-accessible
    STATUS      current
    DESCRIPTION
            "A conceptual row in the cmEthernetNetPortClbTable. 
             These entries represent Cable Length Benchmarks 
             on the Ethernet Network Port."
    INDEX { neIndex, shelfIndex, slotIndex, cmEthernetNetPortIndex, 
            cmEthernetNetPortClbIndex }
    ::= { cmEthernetNetPortClbTable 1 }


CmEthernetNetPortClbEntry ::= SEQUENCE {
    cmEthernetNetPortClbIndex          Integer32,
    cmEthernetNetPortClbEnabled        TruthValue,
    cmEthernetNetPortClbLength         DisplayString,
    cmEthernetNetPortClbDescr          DisplayString
}

cmEthernetNetPortClbIndex OBJECT-TYPE
    SYNTAX      Integer32 (1..5)
    MAX-ACCESS  read-only
    STATUS      current
    DESCRIPTION
            "An integer index value used to uniquely identify
             this Cable Length Benchmark Entry specification."
    ::= { cmEthernetNetPortClbEntry 1 }

cmEthernetNetPortClbEnabled OBJECT-TYPE
    SYNTAX     TruthValue
    MAX-ACCESS read-write
    STATUS     current
    DESCRIPTION
            "This enables specification of Cable Length Benchmark entry."
    ::= { cmEthernetNetPortClbEntry 2 }

cmEthernetNetPortClbLength OBJECT-TYPE
    SYNTAX  DisplayString 
    MAX-ACCESS read-write
    STATUS     current
    DESCRIPTION
            "Cable length of Cable Points Entry. The cable length is of
             the form XXX[.YY] where XX can be any integer value and YY
             allows precision of 2 decimals after the floating point. Note
             that .YY is optional."
    ::= { cmEthernetNetPortClbEntry 3 }

cmEthernetNetPortClbDescr OBJECT-TYPE
    SYNTAX     DisplayString (SIZE (0..256))
    MAX-ACCESS read-write
    STATUS     current
    DESCRIPTION
         "A textual string containing description of cable span."
    ::= { cmEthernetNetPortClbEntry 4 }


--Network Port Priority Mapping
cmNetPortPrioMapTable  OBJECT-TYPE
    SYNTAX      SEQUENCE OF CmNetPortPrioMapEntry
    MAX-ACCESS  not-accessible
    STATUS      current
    DESCRIPTION
            "A list of entries corresponding to Ethernet Network Port Priority Mappings
             in multi Class of Service (COS) mode."
    ::= { cmFacilityObjects 20 }

cmNetPortPrioMapEntry OBJECT-TYPE
    SYNTAX      CmNetPortPrioMapEntry
    MAX-ACCESS  not-accessible
    STATUS      current
    DESCRIPTION
            "A conceptual row in the cmNetPortPrioMapTable."
    INDEX { neIndex, shelfIndex, slotIndex,
            cmEthernetNetPortIndex, cmNetPortPrioMapIndex }
    ::= { cmNetPortPrioMapTable 1 }

CmNetPortPrioMapEntry ::= SEQUENCE {
    cmNetPortPrioMapIndex            Integer32,
    cmNetPortPrioMapInPriority       Integer32,
    cmNetPortPrioMapCOS              Integer32,
    cmNetPortPrioMapOuterTagPriority VlanPriority
}

cmNetPortPrioMapIndex OBJECT-TYPE
    SYNTAX      Integer32 (1..8)
    MAX-ACCESS  read-only
    STATUS      current
    DESCRIPTION
            "The integer index value corresponding to a priority value."
    ::= { cmNetPortPrioMapEntry 1 }

cmNetPortPrioMapInPriority OBJECT-TYPE
    SYNTAX      Integer32 (0..7)
    MAX-ACCESS  read-write
    STATUS      current
    DESCRIPTION
            "The integer index value corresponding to a priority value."
    ::= { cmNetPortPrioMapEntry 2 }

cmNetPortPrioMapCOS OBJECT-TYPE
    SYNTAX      Integer32 (0..7)
    MAX-ACCESS  read-write
    STATUS      current
    DESCRIPTION
            "This allows specification of the COS Priority, i.e.
             this helps in determining the appropriate COS Policer for
             the Flow."
    ::= { cmNetPortPrioMapEntry 3 }

cmNetPortPrioMapOuterTagPriority OBJECT-TYPE
    SYNTAX      VlanPriority
    MAX-ACCESS  read-write
    STATUS      current
    DESCRIPTION
            "This allows specification of the VLAN priority that
             will replace the outgoing (N2A direction) outer-tag's priority.
             Note that, each flow participates or not in outer-tag
             priority mapping, using the object 'cmFlowN2AOuterTagPrioEnabled'."
    ::= { cmNetPortPrioMapEntry 4 }


--
-- Access Port PCP encoding table 
--
cmAccPortPcpDEEncTable  OBJECT-TYPE
    SYNTAX      SEQUENCE OF CmAccPortPcpDEEncEntry 
    MAX-ACCESS  not-accessible
    STATUS      current
    DESCRIPTION
        "Ethernet Access Port PCP drop eligibility encoding table. This
         is applied to a frame that is egressing at the Access port."
    ::= { cmFacilityObjects 21 }

cmAccPortPcpDEEncEntry OBJECT-TYPE
    SYNTAX      CmAccPortPcpDEEncEntry 
    MAX-ACCESS  not-accessible
    STATUS      current
    DESCRIPTION
            "A conceptual row in the ethernetPBPcpDEEncPortTable."
    INDEX { neIndex, shelfIndex, slotIndex, cmEthernetAccPortIndex, 
            cmAccPortPcpDEEncIndex }
    ::= { cmAccPortPcpDEEncTable 1 }

CmAccPortPcpDEEncEntry ::= SEQUENCE {
  cmAccPortPcpDEEncIndex              Integer32,
  cmAccPortPcpDEEncInPriority         VlanPriority,
  cmAccPortPcpDEEncDropIneligiblePrio VlanPriority,
  cmAccPortPcpDEEncDropEligiblePrio   VlanPriority
}

cmAccPortPcpDEEncIndex OBJECT-TYPE
    SYNTAX      Integer32 (1..8)
    MAX-ACCESS  read-only
    STATUS      current
    DESCRIPTION
            "An integer index value used to uniquely identify
             a row in the PCP drop eligible encoding table."
    ::= { cmAccPortPcpDEEncEntry 1 }

cmAccPortPcpDEEncInPriority OBJECT-TYPE
    SYNTAX     VlanPriority
    MAX-ACCESS read-write
    STATUS     current
    DESCRIPTION
         "This object is the input priority that is translated to a
          drop eligibility priority or a drop ineligibility priority."
     ::= { cmAccPortPcpDEEncEntry 2 }

cmAccPortPcpDEEncDropIneligiblePrio OBJECT-TYPE
    SYNTAX     VlanPriority
    MAX-ACCESS read-write
    STATUS     current
    DESCRIPTION
         "This object is the PCP value that has a priority value with
          implicit drop ineligibility encoded into it."
     ::= { cmAccPortPcpDEEncEntry 3 }

cmAccPortPcpDEEncDropEligiblePrio OBJECT-TYPE
    SYNTAX     VlanPriority
    MAX-ACCESS read-write
    STATUS     current
    DESCRIPTION
         "This object is the PCP value that has a priority value with
          implicit drop eligibility encoded into it."
     ::= { cmAccPortPcpDEEncEntry 4 }

--
-- Access Port PCP decoding table
--

cmAccPortPcpDEDecTable  OBJECT-TYPE
    SYNTAX      SEQUENCE OF CmAccPortPcpDEDecEntry
    MAX-ACCESS  not-accessible
    STATUS      current
    DESCRIPTION
            "Ethernet Access Port PCP drop eligibility decoding table. This
             is applied to a frame that is ingressing at a port."
    ::= { cmFacilityObjects 22 }

cmAccPortPcpDEDecEntry OBJECT-TYPE
    SYNTAX      CmAccPortPcpDEDecEntry 
    MAX-ACCESS  not-accessible
    STATUS      current
    DESCRIPTION
            "A conceptual row in the ethernetPBPcpDEDecPortTable."
    INDEX { neIndex, shelfIndex, slotIndex, cmEthernetAccPortIndex, 
            cmAccPortPcpDEDecIndex }
    ::= { cmAccPortPcpDEDecTable 1 }

CmAccPortPcpDEDecEntry ::= SEQUENCE {
    cmAccPortPcpDEDecIndex        Integer32,
    cmAccPortPcpDEDecInPriority   VlanPriority,
    cmAccPortPcpDEDecOutPriority  VlanPriority,
    cmAccPortPcpDEDecDropEligible TruthValue
}


cmAccPortPcpDEDecIndex OBJECT-TYPE
    SYNTAX      Integer32 (1..8)
    MAX-ACCESS  read-only
    STATUS      current
    DESCRIPTION
            "An integer index value used to uniquely identify
             a row in the PCP drop eligible decoding table."
    ::= { cmAccPortPcpDEDecEntry 1 }

cmAccPortPcpDEDecInPriority OBJECT-TYPE
    SYNTAX     VlanPriority
    MAX-ACCESS read-write
    STATUS     current
    DESCRIPTION
         "This object is the input priority that is decoded to get
          priority and the drop eligibility of a frame."
     ::= { cmAccPortPcpDEDecEntry 2 }

cmAccPortPcpDEDecOutPriority OBJECT-TYPE
    SYNTAX     VlanPriority
    MAX-ACCESS read-write
    STATUS     current
    DESCRIPTION
         "This object is the priority value decoded from a incoming PCP value."
     ::= { cmAccPortPcpDEDecEntry 3 }

cmAccPortPcpDEDecDropEligible OBJECT-TYPE
    SYNTAX     TruthValue
    MAX-ACCESS read-write
    STATUS     current
    DESCRIPTION
         "This object is the drop eligibility decoded from a incoming
          PCP value."
     ::= { cmAccPortPcpDEDecEntry 4 }

-- 
-- Access Port PCP pair table
--

cmAccPortPcpDEPairTable  OBJECT-TYPE
    SYNTAX      SEQUENCE OF CmAccPortPcpDEPairEntry
    MAX-ACCESS  not-accessible
    STATUS      current
    DESCRIPTION
            "Ethernet Access Port PCP drop eligibility priority pair table.
             The priority pair is encoded to same drop eligibility and
             drop ineligibility priority. Depending on the PCP DE Enc/Dec
             mode there can be upto 3 pairs in the table. There will one
             pair for 7P1D, two pairs for 6P2D and three pairs for 5P3D."
    ::= { cmFacilityObjects 23 }

cmAccPortPcpDEPairEntry OBJECT-TYPE
    SYNTAX      CmAccPortPcpDEPairEntry 
    MAX-ACCESS  not-accessible
    STATUS      current
    DESCRIPTION
            "A conceptual row in the cmAccPortPcpDEPairEntry."
    INDEX { neIndex, shelfIndex, slotIndex, cmEthernetAccPortIndex, 
            cmAccPortPcpDEPairIndex }
    ::= { cmAccPortPcpDEPairTable 1 }

CmAccPortPcpDEPairEntry ::= SEQUENCE {
    cmAccPortPcpDEPairIndex          Integer32,
    cmAccPortPcpDEDropIneligiblePrio VlanPriority,
    cmAccPortPcpDEDropEligiblePrio   VlanPriority
}

cmAccPortPcpDEPairIndex OBJECT-TYPE
    SYNTAX      Integer32 (1..3)
    MAX-ACCESS  read-only
    STATUS      current
    DESCRIPTION
            "An integer index value used to uniquely identify
             a row in the PCP drop eligible priority pair table."
    ::= { cmAccPortPcpDEPairEntry 1 }

cmAccPortPcpDEDropIneligiblePrio OBJECT-TYPE
    SYNTAX     VlanPriority
    MAX-ACCESS read-write
    STATUS     current
    DESCRIPTION
         "This object is the drop ineligible priority."
     ::= { cmAccPortPcpDEPairEntry 2 }

cmAccPortPcpDEDropEligiblePrio OBJECT-TYPE
    SYNTAX     VlanPriority
    MAX-ACCESS read-write
    STATUS     current
    DESCRIPTION
         "This object is the drop eligible priority."
     ::= { cmAccPortPcpDEPairEntry 3 }

--
-- Network Port PCP encoding table 
--
cmNetPortPcpDEEncTable  OBJECT-TYPE
    SYNTAX      SEQUENCE OF CmNetPortPcpDEEncEntry 
    MAX-ACCESS  not-accessible
    STATUS      current
    DESCRIPTION
        "Ethernet Network Port PCP drop eligibility encoding table. This
         is applied to a frame that is egressing at the Network port."
    ::= { cmFacilityObjects 24 }

cmNetPortPcpDEEncEntry OBJECT-TYPE
    SYNTAX      CmNetPortPcpDEEncEntry 
    MAX-ACCESS  not-accessible
    STATUS      current
    DESCRIPTION
            "A conceptual row in the ethernetPBPcpDEEncPortTable."
    INDEX { neIndex, shelfIndex, slotIndex, cmEthernetNetPortIndex, 
            cmNetPortPcpDEEncIndex }
    ::= { cmNetPortPcpDEEncTable 1 }

CmNetPortPcpDEEncEntry ::= SEQUENCE {
  cmNetPortPcpDEEncIndex              Integer32,
  cmNetPortPcpDEEncInPriority         VlanPriority,
  cmNetPortPcpDEEncDropIneligiblePrio VlanPriority,
  cmNetPortPcpDEEncDropEligiblePrio   VlanPriority
}

cmNetPortPcpDEEncIndex OBJECT-TYPE
    SYNTAX      Integer32 (1..8)
    MAX-ACCESS  read-only
    STATUS      current
    DESCRIPTION
            "An integer index value used to uniquely identify
             a row in the PCP drop eligible encoding table."
    ::= { cmNetPortPcpDEEncEntry 1 }

cmNetPortPcpDEEncInPriority OBJECT-TYPE
    SYNTAX     VlanPriority
    MAX-ACCESS read-write
    STATUS     current
    DESCRIPTION
         "This object is the input priority that is translated to a
          drop eligibility priority or a drop ineligibility priority."
     ::= { cmNetPortPcpDEEncEntry 2 }

cmNetPortPcpDEEncDropIneligiblePrio OBJECT-TYPE
    SYNTAX     VlanPriority
    MAX-ACCESS read-write
    STATUS     current
    DESCRIPTION
         "This object is the PCP value that has a priority value with
          implicit drop ineligibility encoded into it."
     ::= { cmNetPortPcpDEEncEntry 3 }

cmNetPortPcpDEEncDropEligiblePrio OBJECT-TYPE
    SYNTAX     VlanPriority
    MAX-ACCESS read-write
    STATUS     current
    DESCRIPTION
         "This object is the PCP value that has a priority value with
          implicit drop eligibility encoded into it."
     ::= { cmNetPortPcpDEEncEntry 4 }

--
-- Network Port PCP decoding table
--

cmNetPortPcpDEDecTable  OBJECT-TYPE
    SYNTAX      SEQUENCE OF CmNetPortPcpDEDecEntry
    MAX-ACCESS  not-accessible
    STATUS      current
    DESCRIPTION
            "Ethernet Network Port PCP drop eligibility decoding table. This
             is applied to a frame that is ingressing at a port."
    ::= { cmFacilityObjects 25 }

cmNetPortPcpDEDecEntry OBJECT-TYPE
    SYNTAX      CmNetPortPcpDEDecEntry 
    MAX-ACCESS  not-accessible
    STATUS      current
    DESCRIPTION
            "A conceptual row in the ethernetPBPcpDEDecPortTable."
    INDEX { neIndex, shelfIndex, slotIndex, cmEthernetNetPortIndex, 
            cmNetPortPcpDEDecIndex }
    ::= { cmNetPortPcpDEDecTable 1 }

CmNetPortPcpDEDecEntry ::= SEQUENCE {
    cmNetPortPcpDEDecIndex        Integer32,
    cmNetPortPcpDEDecInPriority   VlanPriority,
    cmNetPortPcpDEDecOutPriority  VlanPriority,
    cmNetPortPcpDEDecDropEligible TruthValue
}


cmNetPortPcpDEDecIndex OBJECT-TYPE
    SYNTAX      Integer32 (1..8)
    MAX-ACCESS  read-only
    STATUS      current
    DESCRIPTION
            "An integer index value used to uniquely identify
             a row in the PCP drop eligible decoding table."
    ::= { cmNetPortPcpDEDecEntry 1 }

cmNetPortPcpDEDecInPriority OBJECT-TYPE
    SYNTAX     VlanPriority
    MAX-ACCESS read-write
    STATUS     current
    DESCRIPTION
         "This object is the input priority that is decoded to get
          priority and the drop eligibility of a frame."
     ::= { cmNetPortPcpDEDecEntry 2 }

cmNetPortPcpDEDecOutPriority OBJECT-TYPE
    SYNTAX     VlanPriority
    MAX-ACCESS read-write
    STATUS     current
    DESCRIPTION
         "This object is the priority value decoded from a incoming PCP value."
     ::= { cmNetPortPcpDEDecEntry 3 }

cmNetPortPcpDEDecDropEligible OBJECT-TYPE
    SYNTAX     TruthValue
    MAX-ACCESS read-write
    STATUS     current
    DESCRIPTION
         "This object is the drop eligibility decoded from a incoming
          PCP value."
     ::= { cmNetPortPcpDEDecEntry 4 }

-- 
-- Network Port PCP pair table
--

cmNetPortPcpDEPairTable  OBJECT-TYPE
    SYNTAX      SEQUENCE OF CmNetPortPcpDEPairEntry
    MAX-ACCESS  not-accessible
    STATUS      current
    DESCRIPTION
            "Ethernet Network Port PCP drop eligibility priority pair table.
             The priority pair is encoded to same drop eligibility and
             drop ineligibility priority. Depending on the PCP DE Enc/Dec
             mode there can be upto 3 pairs in the table. There will one
             pair for 7P1D, two pairs for 6P2D and three pairs for 5P3D."
    ::= { cmFacilityObjects 26 }

cmNetPortPcpDEPairEntry OBJECT-TYPE
    SYNTAX      CmNetPortPcpDEPairEntry 
    MAX-ACCESS  not-accessible
    STATUS      current
    DESCRIPTION
            "A conceptual row in the cmNetPortPcpDEPairEntry."
    INDEX { neIndex, shelfIndex, slotIndex, cmEthernetNetPortIndex, 
            cmNetPortPcpDEPairIndex }
    ::= { cmNetPortPcpDEPairTable 1 }

CmNetPortPcpDEPairEntry ::= SEQUENCE {
    cmNetPortPcpDEPairIndex          Integer32,
    cmNetPortPcpDEDropIneligiblePrio VlanPriority,
    cmNetPortPcpDEDropEligiblePrio   VlanPriority
}

cmNetPortPcpDEPairIndex OBJECT-TYPE
    SYNTAX      Integer32 (1..3)
    MAX-ACCESS  read-only
    STATUS      current
    DESCRIPTION
            "An integer index value used to uniquely identify
             a row in the PCP drop eligible priority pair table."
    ::= { cmNetPortPcpDEPairEntry 1 }

cmNetPortPcpDEDropIneligiblePrio OBJECT-TYPE
    SYNTAX     VlanPriority
    MAX-ACCESS read-write
    STATUS     current
    DESCRIPTION
         "This object is the drop ineligible priority."
     ::= { cmNetPortPcpDEPairEntry 2 }

cmNetPortPcpDEDropEligiblePrio OBJECT-TYPE
    SYNTAX     VlanPriority
    MAX-ACCESS read-write
    STATUS     current
    DESCRIPTION
         "This object is the drop eligible priority."
     ::= { cmNetPortPcpDEPairEntry 3 }

--
--  Agg Ethernet Port 
--
cmEthernetTrafficPortTable  OBJECT-TYPE
    SYNTAX      SEQUENCE OF CmEthernetTrafficPortEntry
    MAX-ACCESS  not-accessible
    STATUS      current
    DESCRIPTION
            "A list of entries corresponding to Ethernet 
             Facilities for configuration purposes."
    ::= { cmFacilityObjects 27}

cmEthernetTrafficPortEntry OBJECT-TYPE
    SYNTAX      CmEthernetTrafficPortEntry 
    MAX-ACCESS  not-accessible
    STATUS      current
    DESCRIPTION
            "A conceptual row in the cmEthernetTrafficPortTable."
    INDEX { neIndex, shelfIndex, slotIndex, cmEthernetTrafficPortIndex }
    ::= { cmEthernetTrafficPortTable 1 }

CmEthernetTrafficPortEntry ::= SEQUENCE {
    -- Port Indices 
    cmEthernetTrafficPortIndex                           Integer32,
    cmEthernetTrafficPortIfIndex                         InterfaceIndex,
    cmEthernetTrafficPortEntityIndex                     PhysicalIndex,

    -- State Management params
    cmEthernetTrafficPortAdminState                      AdminState,
    cmEthernetTrafficPortOperationalState                OperationalState,
    cmEthernetTrafficPortSecondaryState                  SecondaryState,

    -- Generic Port params
    cmEthernetTrafficPortMTU                             Integer32,

    -- Generic Ethernet Port params
    cmEthernetTrafficPortMediaType                       EthernetMediaType,
    cmEthernetTrafficPortConfigSpeed                     EthernetPortSpeed,
    cmEthernetTrafficPortNegotiatedSpeed                 EthernetPortSpeed,
    cmEthernetTrafficPortMDIXType                        CmEthernetMDIXType,  
    cmEthernetTrafficPortMDIXStatus                      CmEthernetMDIXType,
    cmEthernetTrafficPortSfpVendorName                   DisplayString,
    cmEthernetTrafficPortSfpPartNumber                   DisplayString,
    cmEthernetTrafficPortSfpSerialNumber                 DisplayString,
    cmEthernetTrafficPortSfpDateOfManufacture            DateAndTime,
    cmEthernetTrafficPortSfpConnectorValue               SfpConnectorValue,
    cmEthernetTrafficPortSfpLinkLength                   Integer32,
    cmEthernetTrafficPortSfpLaserWaveLength              Integer32,
    cmEthernetTrafficPortSfpMediaType                    SfpMediaType,
    
    -- Ethernet Loopback params
    cmEthernetTrafficPortLoopbackConfig                  CmLoopbackType,
    cmEthernetTrafficPortLoopbackStatus                  CmLoopbackType,
    cmEthernetTrafficPortLoopbackTime                    Integer32,
    cmEthernetTrafficPortLoopbackSwapSADA                CmSwapSADAType,
    cmEthernetTrafficPortOuterVlanLoopbackMask           INTEGER,
    cmEthernetTrafficPortOuterVlanLoopback1              DisplayString,
    cmEthernetTrafficPortOuterVlanLoopback2              DisplayString,
    cmEthernetTrafficPortOuterVlanLoopback3              DisplayString,

    -- Link Loss Forwarding params 
    cmEthernetTrafficPortLinkLossFwdEnabled              TruthValue,
    cmEthernetTrafficPortLinkLossFwdSignalType           CmLinkLossFwdSignalType,
    cmEthernetTrafficPortLinkLossFwdTriggerTypes         CmLinkLossFwdTriggerTypes,
    cmEthernetTrafficPortLinkLossFwdDelay                Integer32,
    cmEthernetTrafficPortLinkLossFwdActive               TruthValue,
    cmEthernetTrafficPortLinkLossFwdPartnerEnabled       TruthValue,
    cmEthernetTrafficPortLinkLossFwdLocalLinkId          Integer32,
    cmEthernetTrafficPortLinkLossFwdRemoteLinkIds        DisplayString,
    cmEthernetTrafficPortLinkLossFwdTxActionType         CmLinkLossFwdTxActionType,
    cmEthernetTrafficPortLinkLossFwdRxRLDLinkIds         DisplayString,
    -- OAM params
    cmEthernetTrafficPortOamId                           Integer32,
    cmEthernetTrafficPortOamDiscoveryState               CmOamDiscoveryState,
    cmEthernetTrafficPortOamLocalVarRtrvsEnabled         TruthValue,
    cmEthernetTrafficPortOamLocalLinkEventsEnabled       TruthValue,
    cmEthernetTrafficPortOamLocalOamLoopbacksSupported   TruthValue,
    cmEthernetTrafficPortOamLocalUnidirSupportEnabled    TruthValue,
    cmEthernetTrafficPortOamLocalMaxPDUSize              Integer32,
    cmEthernetTrafficPortOamLocalMode                    CmOamMode,
    cmEthernetTrafficPortOamRemoteMacAddress             MacAddress,
    cmEthernetTrafficPortOamRemoteVarRtrvsEnabled        TruthValue,
    cmEthernetTrafficPortOamRemoteLinkEventsEnabled      TruthValue,
    cmEthernetTrafficPortOamRemoteOamLoopbacksSupported  TruthValue,
    cmEthernetTrafficPortOamRemoteUnidirSupportEnabled   TruthValue,
    cmEthernetTrafficPortOamRemoteMaxPDUSize             Integer32,
    cmEthernetTrafficPortOamRemoteMode                   CmOamMode,
    cmEthernetTrafficPortOamEnabled                      TruthValue,
    cmEthernetTrafficPortOamAdminState                   CmOamAdminState,
    -- Ethernet Port Service params
    cmEthernetTrafficPortSvcType                         CmEthernetTrafficSvcType,

    -- Ethernet Port Traffic params
    cmEthernetTrafficPortRxPauseEnabled                  TruthValue,
    cmEthernetTrafficPortTxPauseEnabled                  TruthValue,
    cmEthernetTrafficPortAfpType                         CmAfpType,

    -- Ethernet Port Traffic params
    cmEthernetTrafficPortShapingEnabled                  TruthValue,
    cmEthernetTrafficPortShapedSpeedLo                   Unsigned32,
    cmEthernetTrafficPortShapedSpeedHi                   Unsigned32,
    cmEthernetTrafficPortQinQEtherType                   Unsigned32,

    --Ethernet Port Services params
    cmEthernetTrafficPortTagFrameControl                 AfpTagControl,
    cmEthernetTrafficPortEgressVlanTrunkingEnabled       TruthValue,
    cmEthernetTrafficPortIngressPushPVIDEnabled          TruthValue,
    cmEthernetTrafficPortEgressPopPVIDEnabled            TruthValue,
    cmEthernetTrafficPortEgressPopPriorityVidEnabled     TruthValue,
    cmEthernetTrafficPortPortVlanId                      VlanId,
    cmEthernetTrafficPortPortVlanPriority                VlanPriority,     
    cmEthernetTrafficPortPriorityVlanId                  VlanId,     
    cmEthernetTrafficPortIngressPrioMapMode              PriorityMapMode,     
    cmEthernetTrafficPortIngressCOSPriority              VlanTagType,    
    --Synchronous Port params
    cmEthernetTrafficPortSyncEEnabled                    TruthValue,
    cmEthernetTrafficPortQLModeEnabled                   TruthValue,
    cmEthernetTrafficPortExpectedQL                      SSMQualityLevel,
    cmEthernetTrafficPortAssumedQL                       SSMQualityLevel,
    cmEthernetTrafficPortReceivedQL                      SSMQualityLevel,
    cmEthernetTrafficPortTransmitQL                      SSMQualityLevel,
    cmEthernetTrafficPortPhyType                         XgePhyType,
    cmEthernetTrafficPortSfpLaserWaveLengthPicometer     Unsigned32,
    cmEthernetTrafficPortRowStatus                       RowStatus,

    cmEthernetTrafficPortSSMRemoteMacAddress             MacAddress,
    cmEthernetTrafficPortInnerVlanLoopbackMask           INTEGER,
    cmEthernetTrafficPortInnerVlanLoopback1              DisplayString,
    cmEthernetTrafficPortInnerVlanLoopback2              DisplayString,
    cmEthernetTrafficPortInnerVlanLoopback3              DisplayString,
    cmEthernetTrafficPortLaserWDMChannel                 SfpChannelIdentifier,
    cmEthernetTrafficPortLaserIsTunable                  TruthValue,
    cmEthernetTrafficPortLaserFrequency                  Unsigned32,
    cmEthernetTrafficPortDeiEnable                       TruthValue,
    cmEthernetTrafficPortPcpDEEncType                    PcpDEEncType,
    cmEthernetTrafficPortPcpDEPairsAction                PcpDEPairsAction,
    cmEthernetTrafficPortInitiateDiag                    CmEthernetDiagAction,
    cmEthernetTrafficPortDiagnosePair1Cond               CmDiagCableCondType,
    cmEthernetTrafficPortDiagnosePair2Cond               CmDiagCableCondType,
    cmEthernetTrafficPortDiagnosePair3Cond               CmDiagCableCondType,
    cmEthernetTrafficPortDiagnosePair4Cond               CmDiagCableCondType,
    cmEthernetTrafficPortDiagnoseAutoNegCond             CmDiagAutoNegCondType,
    cmEthernetTrafficPortDiagnoseLpbkCond                CmDiagLpbkCondType,
    cmEthernetTrafficPortDiagnoseEfmLpbkCond             CmDiagEfmOamLpbkCondType,
    cmEthernetTrafficPortDiagnoseResult                  DisplayString,
    cmEthernetTrafficPortDiagnoseTestStatus              CmDiagTestStatus,
    cmEthernetTrafficPortDiagnoseTestTime                DateAndTime,
    cmEthernetTrafficPortAutoDiagEnabled                 TruthValue,
    cmEthernetTrafficPortDeleteEntitiesAction            TrafficPortDeleteEntitiesAction,
    cmEthernetTrafficPortMaxMpFpNum                      Integer32,
    cmEthernetTrafficPortJdsuLoopbackEnabled             TruthValue,
    cmEthernetTrafficPortJdsuLoopbackVlanId              VlanId,
    cmEthernetTrafficPortIngressPopPriorityVidEnabled    TruthValue,

    cmEthernetTrafficPortRxDeiAction                     RxDeiAction,
    cmEthernetTrafficPortTxDeiAction                     TxDeiAction,
    cmEthernetTrafficPortRxDeiOuterTagType               DeiOuterTagType,
    cmEthernetTrafficPortTxDeiOuterTagType               DeiOuterTagType,

    -- 9.1.1 XGPRO release new columns

    cmEthernetTrafficPortMode                            CmEthernetSvcPortMode,
    cmEthernetTrafficPortServiceType                     CmEthernetSvcType,
    cmEthernetTrafficPortLoopbackSourceMacControlEnabled TruthValue,
    cmEthernetTrafficPortLoopbackDestMacControlEnabled   TruthValue,
    cmEthernetTrafficPortLoopbackSourceMacAddress        MacAddress,
    cmEthernetTrafficPortLoopbackDestMacAddress          MacAddress,
    cmEthernetTrafficPortLoopbackBlockingEnabled         TruthValue,
    cmEthernetTrafficPortMediaTypeAutoSelected           EthernetMediaType,
    cmEthernetTrafficPortLowLatencyQueuingEnabled        TruthValue,
    cmEthernetTrafficPortDiagnosticMacAddress            MacAddress,
    
    cmEthernetTrafficPortIngressSwapPriorityVIDEnabled   TruthValue,
    cmEthernetTrafficPortEgressSwapPriorityVIDEnabled    TruthValue,
    cmEthernetTrafficPortSwapPriorityVID                 VlanId,
    
    cmEthernetTrafficPortExpDEEncType                    PcpDEEncType,
    cmEthernetTrafficPortExpDEPairsAction                PcpDEPairsAction,
    cmEthernetTrafficPortJdsuLoopbackSrcIp               IpAddress,

    -- 540X Additional SyncE Attribute
    cmEthernetTrafficPortTxSsm                           ToggleValue,
    cmEthernetTrafficPortRxSsmQL                         SynceRxSsmQl,
    cmEthernetTrafficPortSyncEMode                       SynceMode,
    cmEthernetTrafficPortSyncEServiceAvailableTime       Unsigned32,
    cmEthernetTrafficPortSyncEServiceUnavailableTime     Unsigned32,
    cmEthernetTrafficPortSyncEServiceAvailablePercentage DisplayString,
    
    cmEthernetTrafficPortWfqSegmentationCOS              Integer32,
    cmEthernetTrafficPortWfqGroupCOS                     Integer32,
    cmEthernetTrafficPortWfqGroupEirLo                   Unsigned32,
    cmEthernetTrafficPortWfqGroupEirHi                   Unsigned32,

    -- Ethernet Port Traffic params
    cmEthernetTrafficPortOuterTagTpidOverride            TruthValue,
    cmEthernetTrafficPortOuterTagTpid                    Unsigned32,

    -- Ethernet Port Power Level params
    cmEthernetTrafficPortSfpTxPowerLevel                 DisplayString,
    cmEthernetTrafficPortSfpRxPowerLevel                 DisplayString,
    cmEthernetTrafficPortBwResourcePort                  VariablePointer,

    -- Ethernet Port SFP params
    cmEthernetTrafficPortSfpName                         DisplayString,
    cmEthernetTrafficPortSfpHardwareRevision             DisplayString,

    -- Ethernet Port Loopback Test Reflector params
    cmEthernetTrafficPortLoopbackTestReflectorIPv4AddressControl TruthValue,
    cmEthernetTrafficPortLoopbackTestReflectorIPv4Address        IpAddress,
    cmEthernetTrafficPortLoopbackTestReflectorIPv6AddressControl TruthValue,
    cmEthernetTrafficPortLoopbackTestReflectorIPv6Address        Ipv6Address,

    -- Ethernet Port SFP params
    cmEthernetTrafficPortSfpIdentifierValue              SfpIdentifierValue,

    -- Ethernet Port Plug params
    cmEthernetTrafficPortPlugType                        PlugType,
    cmEthernetTrafficPortPlugMode                        PlugMode,
    cmEthernetTrafficPortPlugGMetroAutoTuningMode        GMetroAutoTuningMode,
    cmEthernetTrafficPortPlugChannelType                 ChannelType,
    cmEthernetTrafficPortPlugITUCbandChannel             ITUCBandChannelIdentifier,
    cmEthernetTrafficPortPlugRelativeChannel             RelativeChannelIdentifier,
    cmEthernetTrafficPortPlugFrequency                   FrequencyIdentifier,
    cmEthernetTrafficPortPlugOutOfBandChannelStatus      OutOfBandChannelStatus,

    -- Ethernet Port Remote Plug params
    cmEthernetTrafficPortRemotePlugITUCbandChannel       ITUCBandChannelIdentifier,
    cmEthernetTrafficPortRemotePlugRelativeChannel       RelativeChannelIdentifier,
    cmEthernetTrafficPortRemotePlugFrequency             FrequencyIdentifier,

    -- Ethernet Port Remote SFP params
    cmEthernetTrafficPortRemoteSfpVendorName             DisplayString,
    cmEthernetTrafficPortRemoteSfpName                   DisplayString,
    cmEthernetTrafficPortRemoteSfpPartNumber             DisplayString,
    cmEthernetTrafficPortRemoteSfpHardwareRevision       DisplayString,
    cmEthernetTrafficPortRemoteSfpSerialNumber           DisplayString,
    cmEthernetTrafficPortRemoteSfpDateOfManufacture      DateAndTime,
    cmEthernetTrafficPortRemoteSfpLinkLength             Integer32,
    cmEthernetTrafficPortRemoteSfpLaserWaveLength        Integer32,
    cmEthernetTrafficPortRemoteSfpLaserFrequency         Unsigned32,
    cmEthernetTrafficPortRemoteSfpMediaType              SfpMediaType,
    cmEthernetTrafficPortRemoteSfpConnectorValue         SfpConnectorValue,
    cmEthernetTrafficPortRemoteSfpIdentifierValue        SfpIdentifierValue
}

-- Port Indices 
cmEthernetTrafficPortIndex OBJECT-TYPE
    SYNTAX      Integer32 (1..65535)
    MAX-ACCESS  read-only
    STATUS      current
    DESCRIPTION
            "An integer index value used to uniquely identify
             this Ethernet Port within a card.
             Note that each Ethernet Port is uniquely identified
             by the indices neIndex, shelfIndex, 
             slotIndex, cmEthernetTrafficPortIndex." 
    ::= { cmEthernetTrafficPortEntry 1 }

cmEthernetTrafficPortIfIndex OBJECT-TYPE
    SYNTAX      InterfaceIndex 
    MAX-ACCESS  read-only
    STATUS      current
    DESCRIPTION
            "This object has the same value as ifIndex for 
             Ethernet Port.  An integer index value used to 
             uniquely identify this Ethernet Port."
    ::= { cmEthernetTrafficPortEntry 2 }

cmEthernetTrafficPortEntityIndex OBJECT-TYPE
    SYNTAX      PhysicalIndex 
    MAX-ACCESS  read-only
    STATUS      current
    DESCRIPTION
           "Entity Index from ENTITY-MIB for this port."
    ::= { cmEthernetTrafficPortEntry 3 }

-- State Management params
cmEthernetTrafficPortAdminState OBJECT-TYPE
    SYNTAX      AdminState 
    MAX-ACCESS  read-write
    STATUS      current
    DESCRIPTION
            "This object represents the Administrative State of the Ethernet Port."
    ::= { cmEthernetTrafficPortEntry 4 }

cmEthernetTrafficPortOperationalState OBJECT-TYPE
    SYNTAX      OperationalState 
    MAX-ACCESS  read-only
    STATUS      current
    DESCRIPTION
            "This object represents the Operational State of the Ethernet Port."
    ::= { cmEthernetTrafficPortEntry 5 }

cmEthernetTrafficPortSecondaryState OBJECT-TYPE
    SYNTAX      SecondaryState 
    MAX-ACCESS  read-only
    STATUS      current
    DESCRIPTION
            "This object represents the Secondary State of the Ethernet Port."
    ::= { cmEthernetTrafficPortEntry 6 }

-- Generic Port params
cmEthernetTrafficPortMTU OBJECT-TYPE
    SYNTAX      Integer32 
    MAX-ACCESS  read-write
    STATUS      current
    DESCRIPTION
            "This object provides the MTU on the Ethernet Port.
             The object is made read-write for FSP150CC devices."
    ::= { cmEthernetTrafficPortEntry 7 }

cmEthernetTrafficPortMediaType OBJECT-TYPE
    SYNTAX     EthernetMediaType
    MAX-ACCESS read-write
    STATUS     current
    DESCRIPTION
            "This object represents the type of Ethernet Media on the 
             Ethernet Port.
             The media type includes,
                 copper (1)
                 fiber (2)
                 coppersfp (3)
             CM Aggregation Product doesn't support copper."
    ::= { cmEthernetTrafficPortEntry 8 }

cmEthernetTrafficPortConfigSpeed OBJECT-TYPE
    SYNTAX     EthernetPortSpeed
    MAX-ACCESS read-write
    STATUS     current
    DESCRIPTION
            "This object allows to configure the speed of the 
             Ethernet Port."
    ::= { cmEthernetTrafficPortEntry 9 }

cmEthernetTrafficPortNegotiatedSpeed OBJECT-TYPE
    SYNTAX     EthernetPortSpeed
    MAX-ACCESS read-only
    STATUS     current
    DESCRIPTION
            "This object provides the negotiated speed of the 
             Ethernet Port."
    ::= { cmEthernetTrafficPortEntry 10 }

cmEthernetTrafficPortMDIXType OBJECT-TYPE
    SYNTAX     CmEthernetMDIXType
    MAX-ACCESS read-write
    STATUS     current
    DESCRIPTION
            "This object allows management of MDIX property on  
             Ethernet Port."
    ::= { cmEthernetTrafficPortEntry 11 }

cmEthernetTrafficPortMDIXStatus OBJECT-TYPE
    SYNTAX     CmEthernetMDIXType
    MAX-ACCESS read-only
    STATUS     current
    DESCRIPTION
         "This object provides the current MDIX status of the 
          Ethernet port."
     ::= { cmEthernetTrafficPortEntry 12 }
     
cmEthernetTrafficPortSfpVendorName OBJECT-TYPE
    SYNTAX  DisplayString (SIZE (0..16)) 
    MAX-ACCESS read-only
    STATUS     current
    DESCRIPTION
            "This object provides the vendor name of the SFP. 
             This is applicable when cmEthernetTrafficPortMediaType is fiber or coppersfp."
     ::= { cmEthernetTrafficPortEntry 13 }

cmEthernetTrafficPortSfpPartNumber OBJECT-TYPE
    SYNTAX  DisplayString (SIZE (0..16)) 
    MAX-ACCESS read-only
    STATUS     current
    DESCRIPTION
            "This object provides the part number of the SFP. 
             This is applicable when cmEthernetTrafficPortMediaType is fiber or coppersfp."
     ::= { cmEthernetTrafficPortEntry 14 }

cmEthernetTrafficPortSfpSerialNumber OBJECT-TYPE
    SYNTAX  DisplayString (SIZE (0..32)) 
    MAX-ACCESS read-only
    STATUS     current
    DESCRIPTION
            "This object provides the serial number of the SFP.  
             This is shown only when cmEthernetTrafficPortMediaType is fiber."
     ::= { cmEthernetTrafficPortEntry 15 }

cmEthernetTrafficPortSfpDateOfManufacture OBJECT-TYPE
    SYNTAX     DateAndTime 
    MAX-ACCESS read-only
    STATUS     current
    DESCRIPTION
            "This object provides the date of manufacture of the SFP.
             This is applicable when cmEthernetTrafficPortMediaType is fiber or coppersfp."
     ::= { cmEthernetTrafficPortEntry 16 }

cmEthernetTrafficPortSfpConnectorValue OBJECT-TYPE
    SYNTAX     SfpConnectorValue 
    MAX-ACCESS read-only
    STATUS     current
    DESCRIPTION
            "This object provides the SFP connector value.
             This is applicable when cmEthernetTrafficPortMediaType is fiber or coppersfp."
     ::= { cmEthernetTrafficPortEntry 17 }

-- Generic Ethernet Port params
cmEthernetTrafficPortSfpLinkLength OBJECT-TYPE
    SYNTAX     Integer32
    MAX-ACCESS read-only
    STATUS     current
    DESCRIPTION
         "This object provides the SFP Link Length.
          This is applicable only when cmEthernetTrafficPortMediaType is fiber or coppersfp."
     ::= { cmEthernetTrafficPortEntry 18 }

cmEthernetTrafficPortSfpLaserWaveLength OBJECT-TYPE
    SYNTAX     Integer32
    MAX-ACCESS read-only
    STATUS     current
    DESCRIPTION
         "This object provides the SFP Laser Wave Length in nano meters.
          This is applicable only when cmEthernetTrafficPortMediaType is fiber."
     ::= { cmEthernetTrafficPortEntry 19 }
     
cmEthernetTrafficPortSfpMediaType OBJECT-TYPE
    SYNTAX     SfpMediaType
    MAX-ACCESS read-only
    STATUS     current
    DESCRIPTION
         "This object provides the SFP Media Type.
          This is applicable only when cmEthernetTrafficPortMediaType is fiber or coppersfp."
     ::= { cmEthernetTrafficPortEntry 20 }

-- Ethernet Loopback params
cmEthernetTrafficPortLoopbackConfig OBJECT-TYPE
    SYNTAX     CmLoopbackType
    MAX-ACCESS read-write
    STATUS     current
    DESCRIPTION
            "This object allows to initiate loopbacks on 
             on the Ethernet Port."
     ::= { cmEthernetTrafficPortEntry 21 }

cmEthernetTrafficPortLoopbackStatus OBJECT-TYPE
    SYNTAX     CmLoopbackType
    MAX-ACCESS read-only
    STATUS     current
    DESCRIPTION
            "This object provides status of the current loopback 
             on the Ethernet Port."
     ::= { cmEthernetTrafficPortEntry 22 }

cmEthernetTrafficPortLoopbackTime OBJECT-TYPE                   
    SYNTAX     Integer32 (2..300)
    MAX-ACCESS read-write
    STATUS     current
    DESCRIPTION
            "This object allows to specify time for timed-loopbacks on 
             on the Ethernet Port."
     ::= { cmEthernetTrafficPortEntry 23 }

cmEthernetTrafficPortLoopbackSwapSADA OBJECT-TYPE
    SYNTAX     CmSwapSADAType
    MAX-ACCESS read-write
    STATUS     current
    DESCRIPTION
            "This object allows to specify whether or not the loopbacked
             frame will have the Source Address and Destination Address
             swapped."
     ::= { cmEthernetTrafficPortEntry 24 }

cmEthernetTrafficPortOuterVlanLoopbackMask OBJECT-TYPE
    SYNTAX     INTEGER (0..16)
    MAX-ACCESS read-write
    STATUS     current
    DESCRIPTION
             "This object allows specification of the outer VLANs to be 
              looped back when port is in vlan(terminal/facility) 
              loopback configuration. Only 3 VLANs can be specified 
              for vlan loopback. The various bit positions are:
                   1         Outer VLAN 1 Loopback Enabled
                   2         Outer VLAN 2 Loopback Enabled
                   4         Outer VLAN 3 Loopback Enabled"
     ::= { cmEthernetTrafficPortEntry 25 }

cmEthernetTrafficPortOuterVlanLoopback1 OBJECT-TYPE              
    SYNTAX  DisplayString (SIZE (0..6)) 
    MAX-ACCESS read-write
    STATUS     current
    DESCRIPTION
             "This object allows specification of the outer VLAN 1 to be 
              looped back when port is in vlan(terminal/facility) 
              loopback configuration. This is valid only if the
              corresponding bit in cmEthernetTrafficPortOuterVlanLoopbackMask
              is set.  The value to be specified should be in the form 
              X-Y where X is the VLAN Id and Y is the VLAN Priority.  
              If Y is specified as a *, all Priorities (0 to 7) 
              are looped back."
     ::= { cmEthernetTrafficPortEntry 26 }

cmEthernetTrafficPortOuterVlanLoopback2 OBJECT-TYPE
    SYNTAX  DisplayString (SIZE (0..6)) 
    MAX-ACCESS read-write
    STATUS     current
    DESCRIPTION
             "This object allows specification of the outer VLAN 2 to be 
              looped back when port is in vlan(terminal/facility) 
              loopback configuration. This is valid only if the
              corresponding bit in cmEthernetTrafficPortOuterVlanLoopbackMask
              is set.  The value to be specified should be in the form 
              X-Y where X is the VLAN Id and Y is the VLAN Priority.  
              If Y is specified as a *, all Priorities (0 to 7) 
              are looped back."
     ::= { cmEthernetTrafficPortEntry 27 }

cmEthernetTrafficPortOuterVlanLoopback3 OBJECT-TYPE
    SYNTAX  DisplayString (SIZE (0..6)) 
    MAX-ACCESS read-write
    STATUS     current
    DESCRIPTION
             "This object allows specification of the outer VLAN 3 to be 
              looped back when port is in vlan(terminal/facility) 
              loopback configuration. This is valid only if the
              corresponding bit in cmEthernetTrafficPortOuterVlanLoopbackMask
              is set.  The value to be specified should be in the form 
              X-Y where X is the VLAN Id and Y is the VLAN Priority.  
              If Y is specified as a *, all Priorities (0 to 7) 
              are looped back."
     ::= { cmEthernetTrafficPortEntry 28 }

-- Link Loss Forwarding params 
cmEthernetTrafficPortLinkLossFwdEnabled OBJECT-TYPE
    SYNTAX     TruthValue
    MAX-ACCESS read-write
    STATUS     current
    DESCRIPTION
             "This object allows enabling/disabling link loss forwarding 
              on the Ethernet Port." 
     ::= { cmEthernetTrafficPortEntry 29 }

cmEthernetTrafficPortLinkLossFwdSignalType  OBJECT-TYPE
    SYNTAX     CmLinkLossFwdSignalType
    MAX-ACCESS read-write
    STATUS     current
    DESCRIPTION
             "This object allows definition of the link loss forwarding
              signalling type.  This is applicable only if 
              cmEthernetTrafficPortLinkLossFwdEnabled is enabled."
     ::= { cmEthernetTrafficPortEntry 30 }

cmEthernetTrafficPortLinkLossFwdTriggerTypes  OBJECT-TYPE
    SYNTAX     CmLinkLossFwdTriggerTypes
    MAX-ACCESS read-write
    STATUS     current
    DESCRIPTION
             "This object allows definition of the link loss forwarding
              trigger types.  This is applicable only if 
              cmEthernetTrafficPortLinkLossFwdEnabled is enabled."
     ::= { cmEthernetTrafficPortEntry 31 }

cmEthernetTrafficPortLinkLossFwdDelay OBJECT-TYPE                
    SYNTAX     Integer32
    MAX-ACCESS read-write
    STATUS     current
    DESCRIPTION
             "This object allows specification of the delay between
              detection of link loss and signalling of link loss forwarding. 
              Time specified is in seconds."
     ::= { cmEthernetTrafficPortEntry 32 }

cmEthernetTrafficPortLinkLossFwdActive OBJECT-TYPE 
    SYNTAX     TruthValue
    MAX-ACCESS read-only
    STATUS     current
    DESCRIPTION
             "This object provides the link loss forwarding status indicating
              if link loss forwarding is currently being signaled via 
              the port." 
     ::= { cmEthernetTrafficPortEntry 33 }

cmEthernetTrafficPortLinkLossFwdPartnerEnabled OBJECT-TYPE 
    SYNTAX     TruthValue
    MAX-ACCESS read-only
    STATUS     current
    DESCRIPTION
             "This object provides the indication of a link partners ability
              to support link loss forwarding via EFM, i.e. from
              received organization specific OAMPDUs." 
     ::= { cmEthernetTrafficPortEntry 34 }

cmEthernetTrafficPortLinkLossFwdLocalLinkId OBJECT-TYPE 
    SYNTAX     Integer32
    MAX-ACCESS read-write
    STATUS     current
    DESCRIPTION
             "This object allows configuration of the Local Link Id on 
              Ethernet port." 
     ::= { cmEthernetTrafficPortEntry 35 }

cmEthernetTrafficPortLinkLossFwdRemoteLinkIds OBJECT-TYPE 
    SYNTAX     DisplayString (SIZE (0..512)) 
    MAX-ACCESS read-write
    STATUS     current
    DESCRIPTION
             "This object allows enabling/disabling Remote Link Ids 
              on Ethernet port. The Ethernet port is able to distinguish 
              the remote side client ports from the Remote Link Down
              PDUs coming from remote end.
              Input format allows multiple Remote Link Ids seperated by comma (e.g. 1,2,3,10,20...).
              Number range is product-specific (for EGX8.1, max value is 554). 
              Empty string clears the configuration."
     ::= { cmEthernetTrafficPortEntry 36 }
     
cmEthernetTrafficPortLinkLossFwdTxActionType OBJECT-TYPE
    SYNTAX     CmLinkLossFwdTxActionType
    MAX-ACCESS read-write
    STATUS     current
    DESCRIPTION
         "This object allows to specify the Ethernet Port's behavior when
          link loss forwarding trigger events occur on the Port.
          This provides ability to configure per Ethernet port LLF behavior." 
     ::= { cmEthernetTrafficPortEntry 37 }

cmEthernetTrafficPortLinkLossFwdRxRLDLinkIds OBJECT-TYPE
    SYNTAX     DisplayString (SIZE (0..512))
    MAX-ACCESS read-only
    STATUS     current
    DESCRIPTION
         "This object provides the received Remote Link IDs in 
          EFM RLD messages on the Ethernet Port." 
     ::= { cmEthernetTrafficPortEntry 38 }
     
-- OAM params
cmEthernetTrafficPortOamId  OBJECT-TYPE
    SYNTAX     Integer32 
    MAX-ACCESS read-only
    STATUS     current
    DESCRIPTION
             "OAM Id.  This is unique EFM OAM sublayer port id." 
     ::= { cmEthernetTrafficPortEntry 39 }

cmEthernetTrafficPortOamDiscoveryState  OBJECT-TYPE
    SYNTAX     CmOamDiscoveryState
    MAX-ACCESS read-only
    STATUS     current
    DESCRIPTION
             "Ethernet Port's OAM discovery state." 
     ::= { cmEthernetTrafficPortEntry 40 }

cmEthernetTrafficPortOamLocalVarRtrvsEnabled  OBJECT-TYPE
    SYNTAX     TruthValue
    MAX-ACCESS read-only
    STATUS     current
    DESCRIPTION
             "This object allows specification of whether the Ethernet
              Port supports sending variable response OAMPDUs." 
     ::= { cmEthernetTrafficPortEntry 41 }

cmEthernetTrafficPortOamLocalLinkEventsEnabled  OBJECT-TYPE
    SYNTAX     TruthValue 
    MAX-ACCESS read-only
    STATUS     current
    DESCRIPTION
             "This object allows specification of whether the Ethernet
              Port supports interpreting Link Events."
     ::= { cmEthernetTrafficPortEntry 42 }

cmEthernetTrafficPortOamLocalOamLoopbacksSupported  OBJECT-TYPE
    SYNTAX     TruthValue 
    MAX-ACCESS read-write
    STATUS     current
    DESCRIPTION
             "This object allows specification of whether the Ethernet
              Port is capable of OAM remote loopback mode."
     ::= { cmEthernetTrafficPortEntry 43 }

cmEthernetTrafficPortOamLocalUnidirSupportEnabled  OBJECT-TYPE
    SYNTAX     TruthValue 
    MAX-ACCESS read-only
    STATUS     current
    DESCRIPTION
             "This object allows specification of whether the Ethernet
              Port is capable of sending OAMPDUs when the receive path 
              is non-operational."
     ::= { cmEthernetTrafficPortEntry 44 }

cmEthernetTrafficPortOamLocalMaxPDUSize  OBJECT-TYPE
    SYNTAX     Integer32
    MAX-ACCESS read-only
    STATUS     current
    DESCRIPTION
             "This object represents the largest OAMPDU, in octets, 
              supported by the Ethernet Port.  This value is
              compared to the remote Maximum PDU Size and the smaller of 
              the two is used." 
     ::= { cmEthernetTrafficPortEntry 45 }

cmEthernetTrafficPortOamLocalMode OBJECT-TYPE
    SYNTAX     CmOamMode 
    MAX-ACCESS read-write
    STATUS     current
    DESCRIPTION
             "This object allows to configure the OAM sublayer entity in
              either Active or Passive mode." 
     ::= { cmEthernetTrafficPortEntry 46 }

cmEthernetTrafficPortOamRemoteMacAddress OBJECT-TYPE
    SYNTAX     MacAddress
    MAX-ACCESS read-only
    STATUS     current
    DESCRIPTION
             "This object allows retrieval of the Remote Mac Address." 
     ::= { cmEthernetTrafficPortEntry 47 }

cmEthernetTrafficPortOamRemoteVarRtrvsEnabled OBJECT-TYPE
    SYNTAX     TruthValue
    MAX-ACCESS read-only
    STATUS     current
    DESCRIPTION
             "This object allows retrieval of whether the remote OAM 
              entity supports sending variable response OAMPDUs." 
     ::= { cmEthernetTrafficPortEntry 48 }

cmEthernetTrafficPortOamRemoteLinkEventsEnabled OBJECT-TYPE
    SYNTAX     TruthValue 
    MAX-ACCESS read-only
    STATUS     current
    DESCRIPTION
             "This object allows retrieval of whether the remote OAM 
              entity supports interpreting Link Events."
     ::= { cmEthernetTrafficPortEntry 49 }

cmEthernetTrafficPortOamRemoteOamLoopbacksSupported OBJECT-TYPE
    SYNTAX     TruthValue 
    MAX-ACCESS read-only
    STATUS     current
    DESCRIPTION
             "This object allows retrieval of whether the remote OAM 
              entity supports OAM remote loopback mode."
     ::= { cmEthernetTrafficPortEntry 50 }

cmEthernetTrafficPortOamRemoteUnidirSupportEnabled OBJECT-TYPE
    SYNTAX     TruthValue 
    MAX-ACCESS read-only
    STATUS     current
    DESCRIPTION
             "This object allows retrieval of whether the remote 
              OAM entity is capable of sending OAMPDUs when the receive path 
              is non-operational."
     ::= { cmEthernetTrafficPortEntry 51 }

cmEthernetTrafficPortOamRemoteMaxPDUSize OBJECT-TYPE
    SYNTAX     Integer32
    MAX-ACCESS read-only
    STATUS     current
    DESCRIPTION
             "This object allows retrieval of the remote OAM 
              entity maximum OAMPDU size."
     ::= { cmEthernetTrafficPortEntry 52 }

cmEthernetTrafficPortOamRemoteMode OBJECT-TYPE
    SYNTAX     CmOamMode 
    MAX-ACCESS read-only
    STATUS     current
    DESCRIPTION
             "This object allows to retrieve whether the remote OAM 
              sublayer entity is either in Active or Passive mode." 
     ::= { cmEthernetTrafficPortEntry 53 }

cmEthernetTrafficPortOamEnabled  OBJECT-TYPE
    SYNTAX     TruthValue
    MAX-ACCESS read-write 
    STATUS     current
    DESCRIPTION
             "This object allows to manage the EFM OAM on Ethernet Traffic Port."
     ::= { cmEthernetTrafficPortEntry 54 }

cmEthernetTrafficPortOamAdminState OBJECT-TYPE
    SYNTAX     CmOamAdminState
    MAX-ACCESS read-only 
    STATUS     current
    DESCRIPTION
             "This object provides the EFM OAM Admin State."
     ::= { cmEthernetTrafficPortEntry 55 }
     
-- Ethernet Port Service params
cmEthernetTrafficPortSvcType  OBJECT-TYPE 
    SYNTAX     CmEthernetTrafficSvcType 
    MAX-ACCESS read-write
    STATUS     current
    DESCRIPTION
             "This object allows specification of whether the 
              Ethernet Port is port based or vlan based." 
     ::= { cmEthernetTrafficPortEntry 56 }

-- Ethernet Port Traffic params
cmEthernetTrafficPortRxPauseEnabled OBJECT-TYPE 
    SYNTAX     TruthValue
    MAX-ACCESS read-write
    STATUS     current
    DESCRIPTION
         "This object defines the RxPause enable or disable of the port."
     ::= { cmEthernetTrafficPortEntry 57 }

cmEthernetTrafficPortTxPauseEnabled OBJECT-TYPE
    SYNTAX     TruthValue
    MAX-ACCESS read-write
    STATUS     current
    DESCRIPTION
         "This object allows enabling/disabling transmit pause frames on
          Ethernet port."
     ::= { cmEthernetTrafficPortEntry 58 }

cmEthernetTrafficPortAfpType OBJECT-TYPE
    SYNTAX     CmAfpType
    MAX-ACCESS read-write
    STATUS     current
    DESCRIPTION
         "This object allows specification of the Acceptable Frame Policy on
          Ethernet port. Users can specify whether the port supports
          only tagged frames, only untagged frames or both tagged and 
          untagged frames."
     ::= { cmEthernetTrafficPortEntry 59 }

-- Ethernet Port Traffic params
cmEthernetTrafficPortShapingEnabled OBJECT-TYPE
    SYNTAX     TruthValue
    MAX-ACCESS read-write
    STATUS     current
    DESCRIPTION
         "This object allows to manage the Ethernet Port Shaping.
          When enabled, values in cmEthernetTrafficPortShapedSpeedLo and
          cmEthernetTrafficPortShapedSpeedHi are applicable."
     ::= { cmEthernetTrafficPortEntry 60 }

cmEthernetTrafficPortShapedSpeedLo OBJECT-TYPE
    SYNTAX     Unsigned32
    MAX-ACCESS read-write
    STATUS     current
    DESCRIPTION
         "This object allows to specify the lower 32 bits of 
          the Ethernet Port Shaped speed. This value is applicable
          when cmEthernetTrafficPortShapingEnabled is enabled."
     ::= { cmEthernetTrafficPortEntry 61 }

cmEthernetTrafficPortShapedSpeedHi OBJECT-TYPE
    SYNTAX     Unsigned32
    MAX-ACCESS read-write
    STATUS     current
    DESCRIPTION
         "This object allows to specify the higher 32 bits of 
          the Port Shaped speed. This value is applicable
          when cmEthernetTrafficPortShapingEnabled is enabled."
     ::= { cmEthernetTrafficPortEntry 62 }

cmEthernetTrafficPortQinQEtherType OBJECT-TYPE
    SYNTAX     Unsigned32
    MAX-ACCESS read-write
    STATUS     current
    DESCRIPTION
         "This object allows to specify the Q-in-Q Ether Type 
          on the Port."
     ::= { cmEthernetTrafficPortEntry 63 }

--Ethernet Port Services params

cmEthernetTrafficPortTagFrameControl OBJECT-TYPE 
    SYNTAX     AfpTagControl
    MAX-ACCESS read-write
    STATUS     current
    DESCRIPTION
         "This object defines if c-tag/s-tag frame is allowed to pass through,
          available only when AFP is set to Tagged."
     ::= { cmEthernetTrafficPortEntry 64 }
     
cmEthernetTrafficPortEgressVlanTrunkingEnabled OBJECT-TYPE
    SYNTAX     TruthValue
    MAX-ACCESS read-write
    STATUS     current
    DESCRIPTION
         "This object allows to enable or disable the VLAN trunking on
          Ethernet port. Disabling VLAN trunking removes all
          VLAN tags before transmitting traffic out of the port. 
          This object is only applicable for connection-oriented, 
          evpl service type."
     ::= { cmEthernetTrafficPortEntry 65 }

cmEthernetTrafficPortIngressPushPVIDEnabled OBJECT-TYPE
    SYNTAX     TruthValue
    MAX-ACCESS read-write
    STATUS     current
    DESCRIPTION
         "This object allows to specify whether cmEthernetTrafficPortPortVlanId
          value will be PUSHed on untagged frames or not in the 
          ingress direction.  This object is only applicable 
          for connection-oriented, evpl service type."
     ::= { cmEthernetTrafficPortEntry 66 }

cmEthernetTrafficPortEgressPopPVIDEnabled OBJECT-TYPE
    SYNTAX     TruthValue
    MAX-ACCESS read-write
    STATUS     current
    DESCRIPTION
         "This object allows to specify whether cmEthernetTrafficPortPortVlanId
          value will be POPed in the 
          egress direction.  This object is only applicable 
          for connection-oriented, evpl service type."
     ::= { cmEthernetTrafficPortEntry 67 }

cmEthernetTrafficPortEgressPopPriorityVidEnabled OBJECT-TYPE 
    SYNTAX     TruthValue
    MAX-ACCESS read-write
    STATUS     current
    DESCRIPTION
         "This object defines the egress PopPriorityVid enable or disable of the port.
          If it is enabled, the outgoing packets with VID=Priority VLAN ID 
          will be swapped back to VID=0.
         
          This attribute has been deprecated and is supported only on EG-X. 
          Please use cmEthernetTrafficPortEgressSwapPriorityVIDEnabled"
     ::= { cmEthernetTrafficPortEntry 68 }

cmEthernetTrafficPortPortVlanId OBJECT-TYPE
    SYNTAX     VlanId
    MAX-ACCESS read-write
    STATUS     current
    DESCRIPTION
         "This object allows to specify the Ethernet Port VLAN Id 
          to PUSH on untagged frames in the to Network
          direction.  This object is only applicable for connection-oriented,
          evpl service type, when cmEthernetTrafficPortIngressPushPVIDEnabled 
          is set to true."
     ::= { cmEthernetTrafficPortEntry 69 }

cmEthernetTrafficPortPortVlanPriority OBJECT-TYPE
    SYNTAX     VlanPriority
    MAX-ACCESS read-write
    STATUS     current
    DESCRIPTION
         "This object allows to specify the Ethernet Port VLAN Priority 
          for the PUSHed VLAN tag (specified by cmEthernetTrafficPortPortVlanId) 
          on untagged frames in the ingress direction.  
          This object is only applicable for connection-oriented,
          evpl service type, when cmEthernetTrafficPortIngressPushPVIDEnabled 
          is set to true."
     ::= { cmEthernetTrafficPortEntry 70 }

cmEthernetTrafficPortPriorityVlanId OBJECT-TYPE 
    SYNTAX     VlanId
    MAX-ACCESS read-write
    STATUS     deprecated
    DESCRIPTION
         "This object allows to specify the Ethernet Priority VLAN Id 
          to replace the null-tagged or priority tagged frames in the 
          to ingress direction.  This object is only applicable 
          for connection-oriented, evpl service type.
          
          This attribute has been deprecated and is supported only on EG-X. 
          Please use cmEthernetTrafficPortSwapPriorityVID"
     ::= { cmEthernetTrafficPortEntry 71 }

cmEthernetTrafficPortIngressPrioMapMode OBJECT-TYPE
    SYNTAX     PriorityMapMode
    MAX-ACCESS read-write
    STATUS     current
    DESCRIPTION
         "This object allows to specify the Ethernet Port 
          Priority Mapping Mode used for classification of frames.
          This object is only applicable for connection-oriented,
          evpl service type."
     ::= { cmEthernetTrafficPortEntry 72 }

cmEthernetTrafficPortIngressCOSPriority  OBJECT-TYPE
    SYNTAX     VlanTagType
    MAX-ACCESS read-create
    STATUS     deprecated
    DESCRIPTION
         "This object is used to specify whether the EthernetTrafficPort
          uses the inner-tag or the outer-tag in determining the COS (Class of Service).
          
          This attribute has been deprecated and is not supported.  Now,
          the Priority Map Mode indicates whether it is inner or outer.
          Use priomap-8021p(4) for outer and priomap-8021p-inner(5)
          for inner." 
     ::= { cmEthernetTrafficPortEntry 73 }
     
--Synchronous Port params
cmEthernetTrafficPortSyncEEnabled OBJECT-TYPE 
    SYNTAX     TruthValue
    MAX-ACCESS read-write
    STATUS     current
    DESCRIPTION
         "This object allows to specify whether the Ethernet Port 
          can be enabled/disabled for Synchronous Ethernet. This object
          is only applicable for Synchronous Ethernet capable ports.
          When enabled, on receive side 
            -port can extract the frequency of its input signal
             and pass the recovered clock to the system clock
            -port processes the ESMC(Ethernet Synchronization Messaging
             Channel) and extracts the QL (when also QL enabled)   
            -port is eligible to be selected as a system clock reference
          When enabled, on transmit side 
            -port's transmit clock is locked to the system clock
            -port generates an ESMC to generate a QL (when also QL enabled)

          When disabled, on receive side,
            -port does not pass the recovered clock to the system clock 
            -port does not process the ESMC (if present) 
            -port is not eligible to be selected as a 
                     system clock reference
          When disabled, on transmit side 
            -port's output frequency may be synchronized to the system clock
            -port does not generate an ESMC."
     ::= { cmEthernetTrafficPortEntry 74 }

cmEthernetTrafficPortQLModeEnabled OBJECT-TYPE 
    SYNTAX     TruthValue
    MAX-ACCESS read-write
    STATUS     current
    DESCRIPTION
         "This object allows to specify whether the Ethernet Port 
          can be enabled/disabled for QL Mode. This object
          is only applicable for Synchronous Ethernet capable ports,
          when cmEthernetTrafficPortQLModeEnabled is set to true.
          When enabled, on receive side 
            -port shall PEER the SSM (Sync Status Messages) slow protocol PDUs 
             and take appropriate action 
          When enabled, on transmit side 
            -port shall periodically (once a second) transmit QL TLV 
             information PDUs
          When disabled, on receive side,
            -port shall terminate and discard any SSM slow protocol PDUs 
          When disabled, on transmit side 
            -port shall not transmit any SSM slow protocol PDUs."
     ::= { cmEthernetTrafficPortEntry 75 }

cmEthernetTrafficPortExpectedQL OBJECT-TYPE 
    SYNTAX     SSMQualityLevel
    MAX-ACCESS read-write
    STATUS     current
    DESCRIPTION
         "This object allows to specify the expected QL when the 
          Ethernet Port is enabled for QL Mode. This object
          is only applicable for Synchronous Ethernet capable ports,
          when cmEthernetTrafficPortQLModeEnabled is set to true.
          This object allows the user to set a minimum
          expected received Quality Level on the port. The valid values
          depend upon the SYNC entity Network Clock Type. A value of
          None represents that a minimum Quality Level is not expected. 
          The default value shall be None."
     ::= { cmEthernetTrafficPortEntry 76 }

cmEthernetTrafficPortAssumedQL OBJECT-TYPE 
    SYNTAX     SSMQualityLevel
    MAX-ACCESS read-write
    STATUS     current
    DESCRIPTION
         "This object allows to specify the assumed QL on the 
          Ethernet Port. This object is only applicable for 
          Synchronous Ethernet capable ports. 
          The Assumed QL is only meaningful if the Network Clock Type
          (see fsp150cm-sync.mib) is option1 and the 
          port TransmitQL Mode is disabled and the port is being used as 
          an input reference source. Under these conditions, 
          the specified QL value is assumed to be the Quality Level of the
          non-failed reference."
     ::= { cmEthernetTrafficPortEntry 77 }

cmEthernetTrafficPortReceivedQL OBJECT-TYPE 
    SYNTAX     SSMQualityLevel
    MAX-ACCESS read-only
    STATUS     current
    DESCRIPTION
         "This object provides the Received QL value for the Ethernet port. 
          If the Ethernet port TransmitQL Mode is disabled, then the received 
          QL value is not applicable.This object is only applicable for 
          Synchronous Ethernet capable ports."
     ::= { cmEthernetTrafficPortEntry 78 }

cmEthernetTrafficPortTransmitQL OBJECT-TYPE 
    SYNTAX     SSMQualityLevel
    MAX-ACCESS read-only
    STATUS     current
    DESCRIPTION
         "This object provides the Transmitted QL value for the Ethernet port. 
          If the Ethernet port TransmitQL Mode is disabled, then the received 
          QL value is not applicable. This object is only applicable for 
          Synchronous Ethernet capable ports."
     ::= { cmEthernetTrafficPortEntry 79 }

cmEthernetTrafficPortPhyType OBJECT-TYPE 
    SYNTAX     XgePhyType
    MAX-ACCESS read-write
    STATUS     current
    DESCRIPTION
         "This object is valid only to XGE card. And the value should be LAN or WAN when 
         it is XGE card."
     ::= { cmEthernetTrafficPortEntry 80 }

cmEthernetTrafficPortSfpLaserWaveLengthPicometer OBJECT-TYPE 
    SYNTAX     Unsigned32
    MAX-ACCESS read-only
    STATUS     current
    DESCRIPTION
         "This object provide laser wavelength pico value.
          For example, laser wavelength is 1510.01,
          then cmEthernetTrafficPortSfpLaserWaveLength=1510 
          and cmTrafficPortSfpLaserWaveLengthPicometer=10."
     ::= { cmEthernetTrafficPortEntry 81 }

cmEthernetTrafficPortRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of cmEthernetTrafficPortRowStatus supported are
            createAndGo(4) and destroy(6).  All mandatory attributes
            must be specified in a single SNMP SET request with
            neRowStatus value as createAndGo(4).
            Upon successful row creation, this object has a
            value of active(1).

            The cmEthernetTrafficPortRowStatus object may be modified if
            the associated instance of this object is equal to active(1)."
    ::= { cmEthernetTrafficPortEntry 82 }

cmEthernetTrafficPortSSMRemoteMacAddress OBJECT-TYPE
    SYNTAX     MacAddress
    MAX-ACCESS read-only
    STATUS     current
    DESCRIPTION
             "This object allows retrieval of the Remote Mac Address, when
              the port is peering using SSM." 
     ::= { cmEthernetTrafficPortEntry 83 }

cmEthernetTrafficPortInnerVlanLoopbackMask OBJECT-TYPE
    SYNTAX     INTEGER (0..16)
    MAX-ACCESS read-write
    STATUS     current
    DESCRIPTION
             "This object allows specification of the inner VLANs to be 
              looped back when port is in vlan(terminal/facility) 
              loopback configuration. Only 3 VLANs can be specified 
              for vlan loopback. The various bit positions are:
                   1         Inner VLAN 1 Loopback Enabled
                   2         Inner VLAN 2 Loopback Enabled
                   4         Inner VLAN 3 Loopback Enabled"
     ::= { cmEthernetTrafficPortEntry 84 }

cmEthernetTrafficPortInnerVlanLoopback1 OBJECT-TYPE              
    SYNTAX  DisplayString (SIZE (0..6)) 
    MAX-ACCESS read-write
    STATUS     current
    DESCRIPTION
             "This object allows specification of the inner VLAN 1 to be 
              looped back when port is in vlan(terminal/facility) 
              loopback configuration. This is valid only if the
              corresponding bit in cmEthernetTrafficPortInnerVlanLoopbackMask
              is set.  The value to be specified should be in the form 
              X-Y where X is the VLAN Id and Y is the VLAN Priority.  
              If Y is specified as a *, all Priorities (0 to 7) 
              are looped back."
     ::= { cmEthernetTrafficPortEntry 85 }

cmEthernetTrafficPortInnerVlanLoopback2 OBJECT-TYPE
    SYNTAX  DisplayString (SIZE (0..6)) 
    MAX-ACCESS read-write
    STATUS     current
    DESCRIPTION
             "This object allows specification of the inner VLAN 2 to be 
              looped back when port is in vlan(terminal/facility) 
              loopback configuration. This is valid only if the
              corresponding bit in cmEthernetTrafficPortInnerVlanLoopbackMask
              is set.  The value to be specified should be in the form 
              X-Y where X is the VLAN Id and Y is the VLAN Priority.  
              If Y is specified as a *, all Priorities (0 to 7) 
              are looped back."
     ::= { cmEthernetTrafficPortEntry 86 }

cmEthernetTrafficPortInnerVlanLoopback3 OBJECT-TYPE
    SYNTAX  DisplayString (SIZE (0..6)) 
    MAX-ACCESS read-write
    STATUS     current
    DESCRIPTION
             "This object allows specification of the inner VLAN 3 to be 
              looped back when port is in vlan(terminal/facility) 
              loopback configuration. This is valid only if the
              corresponding bit in cmEthernetTrafficPortInnerVlanLoopbackMask
              is set.  The value to be specified should be in the form 
              X-Y where X is the VLAN Id and Y is the VLAN Priority.  
              If Y is specified as a *, all Priorities (0 to 7) 
              are looped back."
     ::= { cmEthernetTrafficPortEntry 87 }

cmEthernetTrafficPortLaserWDMChannel OBJECT-TYPE
    SYNTAX  SfpChannelIdentifier 
    MAX-ACCESS read-write
    STATUS     current
    DESCRIPTION
             "Channel number of WDM tunable XFP setting."
     ::= { cmEthernetTrafficPortEntry 88 }

cmEthernetTrafficPortLaserIsTunable OBJECT-TYPE
    SYNTAX  TruthValue 
    MAX-ACCESS read-only
    STATUS     current
    DESCRIPTION
             "This object means this module whether tunnable."
     ::= { cmEthernetTrafficPortEntry 89 }

cmEthernetTrafficPortLaserFrequency OBJECT-TYPE
    SYNTAX  Unsigned32 
    MAX-ACCESS read-only
    STATUS     current
    DESCRIPTION
             "This object describes this module's frequency, and the step is 1GHZ."
     ::= { cmEthernetTrafficPortEntry 90 }

cmEthernetTrafficPortDeiEnable OBJECT-TYPE
    SYNTAX  TruthValue 
    MAX-ACCESS read-write
    STATUS     deprecated
    DESCRIPTION
             "This object describes whether use DEI bit in S-tag to 
              recognize Drop Eligibility Parameter for ingress S-tag packets or Set 
              DEI bit for egress S-tag Packets. 
              This object is still supported by OSA8.1.1"
     ::= { cmEthernetTrafficPortEntry 91 }

cmEthernetTrafficPortPcpDEEncType OBJECT-TYPE
    SYNTAX  PcpDEEncType 
    MAX-ACCESS read-write
    STATUS     current
    DESCRIPTION
             "This object describes the PCP encoding mode for egress packets
             and the PCP decoding mode for ingress packets on this port."
     ::= { cmEthernetTrafficPortEntry 92 }

cmEthernetTrafficPortPcpDEPairsAction OBJECT-TYPE
    SYNTAX  PcpDEPairsAction 
    MAX-ACCESS read-write
    STATUS     current
    DESCRIPTION
             "This object describes this port pcp de pairs action."
     ::= { cmEthernetTrafficPortEntry 93 }

-- EtherJack Diagnosis params
cmEthernetTrafficPortInitiateDiag  OBJECT-TYPE
    SYNTAX     CmEthernetDiagAction
    MAX-ACCESS read-write
    STATUS     current
    DESCRIPTION
            "This object allows to initiate Etherjack diagnosis on the
             Ethernet Traffic Port."
     ::= { cmEthernetTrafficPortEntry 94 }

cmEthernetTrafficPortDiagnosePair1Cond OBJECT-TYPE
    SYNTAX     CmDiagCableCondType
    MAX-ACCESS read-only
    STATUS     current
    DESCRIPTION
            "This object provides diagnosis results for the cable Pair 1
             on Ethernet Traffic Port."
     ::= { cmEthernetTrafficPortEntry 95 }

cmEthernetTrafficPortDiagnosePair2Cond OBJECT-TYPE
    SYNTAX     CmDiagCableCondType
    MAX-ACCESS read-only
    STATUS     current
    DESCRIPTION
            "This object provides diagnosis results for the cable Pair 2
             on Ethernet Traffic Port."
     ::= { cmEthernetTrafficPortEntry 96 }

cmEthernetTrafficPortDiagnosePair3Cond OBJECT-TYPE
    SYNTAX     CmDiagCableCondType
    MAX-ACCESS read-only
    STATUS     current
    DESCRIPTION
            "This object provides diagnosis results for the cable Pair 3
             on Ethernet Traffic Port."
     ::= { cmEthernetTrafficPortEntry 97 }

cmEthernetTrafficPortDiagnosePair4Cond OBJECT-TYPE
    SYNTAX     CmDiagCableCondType
    MAX-ACCESS read-only
    STATUS     current
    DESCRIPTION
            "This object provides diagnosis results for the cable Pair 4
             on Ethernet Traffic Port."
     ::= { cmEthernetTrafficPortEntry 98 }

cmEthernetTrafficPortDiagnoseAutoNegCond OBJECT-TYPE
    SYNTAX     CmDiagAutoNegCondType
    MAX-ACCESS read-only
    STATUS     current
    DESCRIPTION
            "This object provides auto negotiation results of the diagnosis
             test on Ethernet Traffic Port."
     ::= { cmEthernetTrafficPortEntry 99 }

cmEthernetTrafficPortDiagnoseLpbkCond OBJECT-TYPE
    SYNTAX     CmDiagLpbkCondType
    MAX-ACCESS read-only
    STATUS     current
    DESCRIPTION
            "This object provides port loopback results of the diagnosis
             test on Ethernet Traffic Port."
     ::= { cmEthernetTrafficPortEntry 100 }

cmEthernetTrafficPortDiagnoseEfmLpbkCond OBJECT-TYPE
    SYNTAX     CmDiagEfmOamLpbkCondType
    MAX-ACCESS read-only
    STATUS     current
    DESCRIPTION
            "This object provides remote EFM loopback results of the diagnosis
             test on Ethernet Traffic Port."
     ::= { cmEthernetTrafficPortEntry 101 }

cmEthernetTrafficPortDiagnoseResult OBJECT-TYPE
    SYNTAX  DisplayString (SIZE (0..256)) 
    MAX-ACCESS read-only
    STATUS     current
    DESCRIPTION
            "This object provides results of the diagnosis
             test in string form on Ethernet Traffic Port."
     ::= { cmEthernetTrafficPortEntry 102 }

cmEthernetTrafficPortDiagnoseTestStatus OBJECT-TYPE
    SYNTAX  CmDiagTestStatus 
    MAX-ACCESS read-only
    STATUS     current
    DESCRIPTION
            "This object provides the current status of the diagnosis
             test on Ethernet Traffic Port."
     ::= { cmEthernetTrafficPortEntry 103 }

cmEthernetTrafficPortDiagnoseTestTime OBJECT-TYPE
    SYNTAX  DateAndTime 
    MAX-ACCESS read-only
    STATUS     current
    DESCRIPTION
       "This object provides the time when diagnosis test was last executed."
     ::= { cmEthernetTrafficPortEntry 104 }

cmEthernetTrafficPortAutoDiagEnabled OBJECT-TYPE
    SYNTAX     TruthValue
    MAX-ACCESS read-write
    STATUS     current
    DESCRIPTION
         "This object allows to enable or disable the automatic 
          Cable Diagnostic tests when the cable is removed from the port."
     ::= { cmEthernetTrafficPortEntry 105 }

cmEthernetTrafficPortDeleteEntitiesAction OBJECT-TYPE
    SYNTAX     TrafficPortDeleteEntitiesAction
    MAX-ACCESS read-write
    STATUS     current
    DESCRIPTION
         "This object allows to delete esa entities relate this port and 
         Cfm entities relate this port."
     ::= { cmEthernetTrafficPortEntry 106 }

cmEthernetTrafficPortMaxMpFpNum OBJECT-TYPE
    SYNTAX     Integer32
    MAX-ACCESS read-write
    STATUS     current
    DESCRIPTION
         "This object allows to set the mpflow max fp number, and now only the ports on ethernet10x1GCard,
          ethernet1x10GCard, ethernet1x10GHighPerCard, ethernet10x1GHighPerCard support this attribute. for
          others, cann't be set and will return 0."
     ::= { cmEthernetTrafficPortEntry 107 }

cmEthernetTrafficPortJdsuLoopbackEnabled OBJECT-TYPE
    SYNTAX     TruthValue
    MAX-ACCESS read-write
    STATUS     deprecated
    DESCRIPTION
         "This object allows to enable or disable jdsu loopback on this port.

         Note: This object is deprecated."
     ::= { cmEthernetTrafficPortEntry 108 }

cmEthernetTrafficPortJdsuLoopbackVlanId OBJECT-TYPE
    SYNTAX     VlanId
    MAX-ACCESS read-only
    STATUS     deprecated
    DESCRIPTION
         "This object allows to set the jdsu loopback vlan.
         if status is jdsu-terminal-port-tailend(19) or jdsu-facility-port-tailend(21), 
         then VID is 0 means not applicable.

         Note: This object is deprecated."
     ::= { cmEthernetTrafficPortEntry 109 }

cmEthernetTrafficPortIngressPopPriorityVidEnabled OBJECT-TYPE 
    SYNTAX     TruthValue
    MAX-ACCESS read-write
    STATUS     current
    DESCRIPTION
         "This object defines the Ingress PopPriorityVid enable or disable of the port.
          If it is enabled, then incoming priority tagged 
          packet's VID is swapped to Priority VLAN ID.
          
          This attribute has been deprecated and is supported only on EG-X. 
          Please use cmEthernetTrafficPortIngressSwapPriorityVIDEnabled"
     ::= { cmEthernetTrafficPortEntry 110 }

cmEthernetTrafficPortRxDeiAction OBJECT-TYPE 
    SYNTAX     RxDeiAction
    MAX-ACCESS read-write
    STATUS     current
    DESCRIPTION
             "This object allows to specify
              the Receive DEI Action."
     ::= { cmEthernetTrafficPortEntry 111 }

cmEthernetTrafficPortTxDeiAction OBJECT-TYPE 
    SYNTAX     TxDeiAction
    MAX-ACCESS read-write
    STATUS     current
    DESCRIPTION
             "This object allows to specify
              the Transmit DEI Action."
     ::= { cmEthernetTrafficPortEntry 112 }

cmEthernetTrafficPortRxDeiOuterTagType OBJECT-TYPE 
    SYNTAX     DeiOuterTagType
    MAX-ACCESS read-write
    STATUS     current
    DESCRIPTION
             "This object allows to specify
              the Receive DEI Outer Tag Type."
     ::= { cmEthernetTrafficPortEntry 113 }

cmEthernetTrafficPortTxDeiOuterTagType OBJECT-TYPE 
    SYNTAX     DeiOuterTagType
    MAX-ACCESS read-write
    STATUS     current
    DESCRIPTION
             "This object allows to specify
              the Transmit DEI Outer Tag Type."
     ::= { cmEthernetTrafficPortEntry 114 }

-- 9.1.1 XGPRO release new columns

cmEthernetTrafficPortMode OBJECT-TYPE 
    SYNTAX     CmEthernetSvcPortMode 
    MAX-ACCESS read-write
    STATUS     current
    DESCRIPTION
             "This object allows specification of whether the 
              Ethernet Traffic Port is in a connection-oriented 
              (offering VLAN based services) mode or connection-less 
              (offering MAC based services) mode." 
     ::= { cmEthernetTrafficPortEntry 115 }

cmEthernetTrafficPortServiceType  OBJECT-TYPE 
    SYNTAX     CmEthernetSvcType 
    MAX-ACCESS read-write
    STATUS     current
    DESCRIPTION
             "This object allows specification of whether the 
              Ethernet Traffic Port provides transparent port based services,
              or multi-flow VLAN based services." 
     ::= { cmEthernetTrafficPortEntry 116 }

cmEthernetTrafficPortLoopbackSourceMacControlEnabled OBJECT-TYPE
    SYNTAX      TruthValue  
    MAX-ACCESS  read-write
    STATUS      current
    DESCRIPTION
         "This object allows to Enable/Disable the Traffic Port Source MAC 
         Address frame matching criteria for all streams. 
         Not applicable for: efm-oam-remote, efm-oam-remote-timed."
    ::= { cmEthernetTrafficPortEntry 117 }

cmEthernetTrafficPortLoopbackDestMacControlEnabled OBJECT-TYPE
    SYNTAX      TruthValue  
    MAX-ACCESS  read-write
    STATUS      current
    DESCRIPTION
         "This object allows to Enable/Disable the Traffic Port Destination MAC 
         Address frame matching criteria for all streams. 
         Not applicable for: efm-oam-remote, efm-oam-remote-timed."
    ::= { cmEthernetTrafficPortEntry 118 }

cmEthernetTrafficPortLoopbackSourceMacAddress OBJECT-TYPE
    SYNTAX      MacAddress  
    MAX-ACCESS  read-write
    STATUS      current
    DESCRIPTION
         "This object allows to set Traffic Port Source MAC Address for frame 
          matching when Traffic Port Source MAC Control is enabled."
    ::= { cmEthernetTrafficPortEntry 119 }

cmEthernetTrafficPortLoopbackDestMacAddress OBJECT-TYPE
    SYNTAX      MacAddress  
    MAX-ACCESS  read-write
    STATUS      current
    DESCRIPTION
         "This object allows to set Traffic Port Destination MAC Address for frame 
          matching when Traffic Port Destination MAC Control is enabled."
    ::= { cmEthernetTrafficPortEntry 120 }

cmEthernetTrafficPortLoopbackBlockingEnabled OBJECT-TYPE
    SYNTAX      TruthValue  
    MAX-ACCESS  read-write
    STATUS      current
    DESCRIPTION
        "This object allows frame blocking when loopback is active.
         - True: Blocks frames in the non-loopback direction 
           that match the PORT or VLAN received in the 
           non-loopback direction. Discards  frames 
           in the loopback direction that match 
           the PORT or VLAN, but do not match 
           the MAC address criteria,
         - False: No blocking of frames."
    ::= { cmEthernetTrafficPortEntry 121 }

cmEthernetTrafficPortMediaTypeAutoSelected OBJECT-TYPE
    SYNTAX     EthernetMediaType
    MAX-ACCESS read-only
    STATUS     current
    DESCRIPTION
            "This object provides the auto selected Ethernet Media of the
             Ethernet Traffic Port."
    ::= { cmEthernetTrafficPortEntry 122 }

cmEthernetTrafficPortLowLatencyQueuingEnabled OBJECT-TYPE
    SYNTAX     TruthValue
    MAX-ACCESS read-write
    STATUS     current
    DESCRIPTION
            "This object allows to Enable/Disable the Low Latency Queuing on
             the Ethernet Traffic Port."
    ::= { cmEthernetTrafficPortEntry 123 }

cmEthernetTrafficPortDiagnosticMacAddress OBJECT-TYPE
    SYNTAX      MacAddress  
    MAX-ACCESS  read-only
    STATUS      current
    DESCRIPTION
         "This object describes the diagnose mac address for SAT, ECPA, JDSU, Loopback with Override SA etc."
    ::= { cmEthernetTrafficPortEntry 124 }

cmEthernetTrafficPortIngressSwapPriorityVIDEnabled OBJECT-TYPE 
    SYNTAX     TruthValue
    MAX-ACCESS read-write
    STATUS     current
    DESCRIPTION
         "This object defines the Ingress Swap Priority Vid enable or disable of the port.
          If it is enabled, then incoming priority tagged 
          packet's VID is swapped to Priority VLAN ID."
     ::= { cmEthernetTrafficPortEntry 125 }

cmEthernetTrafficPortEgressSwapPriorityVIDEnabled OBJECT-TYPE 
    SYNTAX     TruthValue
    MAX-ACCESS read-write
    STATUS     current
    DESCRIPTION
         "This object defines the egress Swap Priority Vid enable or disable of the port.
          If it is enabled, the outgoing packets with VID=Priority VLAN ID 
          will be swapped back to VID=0."
     ::= { cmEthernetTrafficPortEntry 126 }

cmEthernetTrafficPortSwapPriorityVID OBJECT-TYPE 
    SYNTAX     VlanId
    MAX-ACCESS read-write
    STATUS     current
    DESCRIPTION
         "This object allows to specify the Ethernet Priority VLAN Id 
          to replace the null-tagged or priority tagged frames in the 
          to ingress direction.  This object is only applicable 
          for connection-oriented, evpl service type."
     ::= { cmEthernetTrafficPortEntry 127 }

cmEthernetTrafficPortExpDEEncType OBJECT-TYPE
    SYNTAX      PcpDEEncType
    MAX-ACCESS  read-write
    STATUS      current
    DESCRIPTION
        "This is a port level control that specifies the mode of drop
         eligibility encoding in exp bits of the VLAN tag."
    ::= { cmEthernetTrafficPortEntry 128 }

cmEthernetTrafficPortExpDEPairsAction OBJECT-TYPE
    SYNTAX      PcpDEPairsAction
    MAX-ACCESS  read-write
    STATUS      current
    DESCRIPTION
        "This object allows the SNMP user to manage the Priority 
         Code Point (PCP) Drop Eligibility Pairs.  When the
         cmEthernetTrafficPortExpDEEncType is of type 7p1d, 6p2d, 5p3d,
         the cmEthernetTrafficPortExpDEPairTable can be used to specify 
         alternate pairs of priorities to specify drop eligibility/
         ineligibility."
    ::= { cmEthernetTrafficPortEntry 129 }

cmEthernetTrafficPortJdsuLoopbackSrcIp OBJECT-TYPE
    SYNTAX      IpAddress  
    MAX-ACCESS  read-only
    STATUS      current
    DESCRIPTION
         "This object is applicable when there is jdsu l3 loopback."
    ::= { cmEthernetTrafficPortEntry 130 }

cmEthernetTrafficPortTxSsm OBJECT-TYPE
    SYNTAX      ToggleValue  
    MAX-ACCESS  read-write
    STATUS      current
    DESCRIPTION
         "This object allows to manage (enable/disable) TX SMM on OSA540X ethernet port."
    ::= { cmEthernetTrafficPortEntry 131 }

cmEthernetTrafficPortRxSsmQL OBJECT-TYPE
    SYNTAX      SynceRxSsmQl  
    MAX-ACCESS  read-write
    STATUS      current
    DESCRIPTION
         "This object allows to manage how RX quality level is utilized on OSA540X ethernet port."
    ::= { cmEthernetTrafficPortEntry 132 }

cmEthernetTrafficPortSyncEMode OBJECT-TYPE
    SYNTAX      SynceMode  
    MAX-ACCESS  read-write
    STATUS      current
    DESCRIPTION
         "This object allows to manage SyncE mode (master or slave) on OSA540X ethernet port."
    ::= { cmEthernetTrafficPortEntry 133 }

cmEthernetTrafficPortSyncEServiceAvailableTime OBJECT-TYPE
    SYNTAX      Unsigned32  
    MAX-ACCESS  read-only
    STATUS      current
    DESCRIPTION
         "This object allows to manage service available time (seconds) for SYNCE."
    ::= { cmEthernetTrafficPortEntry 134 }

cmEthernetTrafficPortSyncEServiceUnavailableTime OBJECT-TYPE
    SYNTAX      Unsigned32  
    MAX-ACCESS  read-only
    STATUS      current
    DESCRIPTION
         "This object allows to manage service unavailable time (seconds) for SYNCE."
    ::= { cmEthernetTrafficPortEntry 135 }

cmEthernetTrafficPortSyncEServiceAvailablePercentage OBJECT-TYPE
    SYNTAX      DisplayString  
    MAX-ACCESS  read-only
    STATUS      current
    DESCRIPTION
         "This object allows to manage service available in percentage [XXX.YY%] for SYNCE."
    ::= { cmEthernetTrafficPortEntry 136 }


cmEthernetTrafficPortWfqSegmentationCOS OBJECT-TYPE
    SYNTAX      Integer32  
    MAX-ACCESS  read-write
    STATUS      current
    DESCRIPTION
         "This object is used to specify the wfq segmentation cos value."
    ::= { cmEthernetTrafficPortEntry 137 }

cmEthernetTrafficPortWfqGroupCOS OBJECT-TYPE
    SYNTAX      Integer32  
    MAX-ACCESS  read-write
    STATUS      current
    DESCRIPTION
         "This object is used to specify the wfq group cos value."
    ::= { cmEthernetTrafficPortEntry 138 }

cmEthernetTrafficPortWfqGroupEirLo OBJECT-TYPE
    SYNTAX      Unsigned32  
    MAX-ACCESS  read-write
    STATUS      current
    DESCRIPTION
         "This object is used to specify the wfq group eir low 32 bits value."
    ::= { cmEthernetTrafficPortEntry 139 }

cmEthernetTrafficPortWfqGroupEirHi OBJECT-TYPE
    SYNTAX      Unsigned32  
    MAX-ACCESS  read-write
    STATUS      current
    DESCRIPTION
         "This object is used to specify the wfq group eir high 32 bits value."
    ::= { cmEthernetTrafficPortEntry 140 }

cmEthernetTrafficPortOuterTagTpidOverride OBJECT-TYPE
    SYNTAX      TruthValue  
    MAX-ACCESS  read-write
    STATUS      current
    DESCRIPTION
         "This object allows enabling/disabling of Outer Tag TPID override.
          When enabled, values in Outer Tag TPID is applicable on egress
          Ethernet Traffic Port."
    ::= { cmEthernetTrafficPortEntry 141 }

cmEthernetTrafficPortOuterTagTpid OBJECT-TYPE
    SYNTAX     Unsigned32
    MAX-ACCESS read-write
    STATUS     current
    DESCRIPTION
         "This object allows to specify the egress Outer Tag TPID 
          on the Ethernet Traffic Port."
     ::= { cmEthernetTrafficPortEntry 142 }

cmEthernetTrafficPortSfpTxPowerLevel OBJECT-TYPE
    SYNTAX     DisplayString
    MAX-ACCESS read-only
    STATUS     current
    DESCRIPTION
         "This object provides the SFP TX power level in dBm.
          The format would be [+/-]XX.YYYY. 
          Note: the sign [+/-] and the decimal point (.YYYY) are optional."
     ::= { cmEthernetTrafficPortEntry 143 }

cmEthernetTrafficPortSfpRxPowerLevel OBJECT-TYPE
    SYNTAX     DisplayString
    MAX-ACCESS read-only
    STATUS     current
    DESCRIPTION
         "This object provides the SFP TX power level in dBm.
          The format would be [+/-]XX.YYYY. 
          Note: the sign [+/-] and the decimal point (.YYYY) are optional."
     ::= { cmEthernetTrafficPortEntry 144 }

cmEthernetTrafficPortBwResourcePort OBJECT-TYPE
    SYNTAX     VariablePointer
    MAX-ACCESS read-write
    STATUS     current
    DESCRIPTION
         "Specifies a port whose bandwidth resources will be used.
          This object is applicable only for VM Server ports."
     ::= { cmEthernetTrafficPortEntry 145 }

-- Ethernet Port SFP params
cmEthernetTrafficPortSfpName OBJECT-TYPE
    SYNTAX  DisplayString (SIZE (0..32))
    MAX-ACCESS read-only
    STATUS     current
    DESCRIPTION
         "This object provides the official name of the SFP."
     ::= { cmEthernetTrafficPortEntry 146 }

cmEthernetTrafficPortSfpHardwareRevision OBJECT-TYPE
    SYNTAX  DisplayString (SIZE (0..16)) 
    MAX-ACCESS read-only
    STATUS     current
    DESCRIPTION
         "This object provides the hardware revision of the SFP."
     ::= { cmEthernetTrafficPortEntry 147 }

cmEthernetTrafficPortLoopbackTestReflectorIPv4AddressControl OBJECT-TYPE
    SYNTAX      TruthValue
    MAX-ACCESS  read-write
    STATUS      current
    DESCRIPTION
         "Control that enables/disables Test Reflector IPv4 Address
          to be used for Test Reflector IP Interface."
    ::= { cmEthernetTrafficPortEntry 148 }

cmEthernetTrafficPortLoopbackTestReflectorIPv4Address OBJECT-TYPE
    SYNTAX      IpAddress
    MAX-ACCESS  read-write
    STATUS      current
    DESCRIPTION
         "This is the Test Reflector Interface IPv4 address."
    ::= { cmEthernetTrafficPortEntry 149 }

cmEthernetTrafficPortLoopbackTestReflectorIPv6AddressControl OBJECT-TYPE
    SYNTAX      TruthValue
    MAX-ACCESS  read-write
    STATUS      current
    DESCRIPTION
         "Control that enables/disables Test Reflector IPv6 Address
          to be used for Test Reflector IP Interface."
    ::= { cmEthernetTrafficPortEntry 150 }

cmEthernetTrafficPortLoopbackTestReflectorIPv6Address OBJECT-TYPE
    SYNTAX      Ipv6Address
    MAX-ACCESS  read-write
    STATUS      current
    DESCRIPTION
         "This is the Test Reflector Interface IPv6 address."
    ::= { cmEthernetTrafficPortEntry 151 }

cmEthernetTrafficPortSfpIdentifierValue OBJECT-TYPE
    SYNTAX     SfpIdentifierValue
    MAX-ACCESS read-only
    STATUS     current
    DESCRIPTION
         "This object provides the SFP identifier value."
     ::= { cmEthernetTrafficPortEntry 152 }

-- Ethernet Port Plug params
cmEthernetTrafficPortPlugType OBJECT-TYPE
    SYNTAX     PlugType
    MAX-ACCESS read-write
    STATUS     current
    DESCRIPTION
         "This specifies the port's plug type."
     ::= { cmEthernetTrafficPortEntry 153 }

cmEthernetTrafficPortPlugMode OBJECT-TYPE
    SYNTAX     PlugMode
    MAX-ACCESS read-write
    STATUS     current
    DESCRIPTION
         "This specifies if the plug is acting as head-end or tail-end."
     ::= { cmEthernetTrafficPortEntry 154 }

cmEthernetTrafficPortPlugGMetroAutoTuningMode OBJECT-TYPE
    SYNTAX     GMetroAutoTuningMode
    MAX-ACCESS read-write
    STATUS     current
    DESCRIPTION
         "This is tuning mode for G.Metro plug."
     ::= { cmEthernetTrafficPortEntry 155 }

cmEthernetTrafficPortPlugChannelType OBJECT-TYPE
    SYNTAX     ChannelType
    MAX-ACCESS read-write
    STATUS     current
    DESCRIPTION
         "This specifies plug's type channel configuration."
     ::= { cmEthernetTrafficPortEntry 156 }

cmEthernetTrafficPortPlugITUCbandChannel OBJECT-TYPE
    SYNTAX     ITUCBandChannelIdentifier
    MAX-ACCESS read-write
    STATUS     current
    DESCRIPTION
         "If Channel Type is ITU-CBAND, this is
          the local plug's ITU C-band channel."
     ::= { cmEthernetTrafficPortEntry 157 }

cmEthernetTrafficPortPlugRelativeChannel OBJECT-TYPE
    SYNTAX     RelativeChannelIdentifier
    MAX-ACCESS read-write
    STATUS     current
    DESCRIPTION
         "If Channel Type is RELATIVE-CHANNEL-NUMBER, this is
          the local plug's relative channel."
     ::= { cmEthernetTrafficPortEntry 158 }

cmEthernetTrafficPortPlugFrequency OBJECT-TYPE
    SYNTAX     FrequencyIdentifier
    MAX-ACCESS read-write
    STATUS     current
    DESCRIPTION
         "If Channel Type is FREQUENCY, this is the local plug's frequency."
     ::= { cmEthernetTrafficPortEntry 159 }

cmEthernetTrafficPortPlugOutOfBandChannelStatus OBJECT-TYPE
    SYNTAX     OutOfBandChannelStatus
    MAX-ACCESS read-only
    STATUS     current
    DESCRIPTION
         "Status of the out of band channel between the local and remote plug."
     ::= { cmEthernetTrafficPortEntry 160 }

-- Ethernet Port Remote Plug params
cmEthernetTrafficPortRemotePlugITUCbandChannel OBJECT-TYPE
    SYNTAX     ITUCBandChannelIdentifier
    MAX-ACCESS read-write
    STATUS     current
    DESCRIPTION
         "If Channel Type is ITU-CBAND, this is the remote plug's
          ITU C-band channel."
     ::= { cmEthernetTrafficPortEntry 161 }

cmEthernetTrafficPortRemotePlugRelativeChannel OBJECT-TYPE
    SYNTAX     RelativeChannelIdentifier
    MAX-ACCESS read-write
    STATUS     current
    DESCRIPTION
         "If Channel Type is RELATIVE-CHANNEL-NUMBER, this is
          the remote plug's relative channel."
     ::= { cmEthernetTrafficPortEntry 162 }

cmEthernetTrafficPortRemotePlugFrequency OBJECT-TYPE
    SYNTAX     FrequencyIdentifier
    MAX-ACCESS read-write
    STATUS     current
    DESCRIPTION
         "If Channel Type is FREQUENCY, this is the remote plug's frequency."
     ::= { cmEthernetTrafficPortEntry 163 }

-- Ethernet Port Remote SFP params
cmEthernetTrafficPortRemoteSfpVendorName OBJECT-TYPE
    SYNTAX  DisplayString (SIZE (0..16)) 
    MAX-ACCESS read-only
    STATUS     current
    DESCRIPTION
         "This object provides the vendor name of the Remote SFP."
     ::= { cmEthernetTrafficPortEntry 164 }

cmEthernetTrafficPortRemoteSfpName OBJECT-TYPE
    SYNTAX  DisplayString (SIZE (0..32)) 
    MAX-ACCESS read-only
    STATUS     current
    DESCRIPTION
         "This object provides the official name of the Remote SFP."
     ::= { cmEthernetTrafficPortEntry 165 }

cmEthernetTrafficPortRemoteSfpPartNumber OBJECT-TYPE
    SYNTAX  DisplayString (SIZE (0..16)) 
    MAX-ACCESS read-only
    STATUS     current
    DESCRIPTION
         "This object provides the part number of the Remote SFP."
     ::= { cmEthernetTrafficPortEntry 166 }

cmEthernetTrafficPortRemoteSfpHardwareRevision OBJECT-TYPE
    SYNTAX  DisplayString (SIZE (0..16)) 
    MAX-ACCESS read-only
    STATUS     current
    DESCRIPTION
         "This object provides the hardware revision of the Remote SFP."
     ::= { cmEthernetTrafficPortEntry 167 }

cmEthernetTrafficPortRemoteSfpSerialNumber OBJECT-TYPE
    SYNTAX  DisplayString (SIZE (0..32)) 
    MAX-ACCESS read-only
    STATUS     current
    DESCRIPTION
         "This object provides the serial number of the Remote SFP."
     ::= { cmEthernetTrafficPortEntry 168 }

cmEthernetTrafficPortRemoteSfpDateOfManufacture OBJECT-TYPE
    SYNTAX     DateAndTime 
    MAX-ACCESS read-only
    STATUS     current
    DESCRIPTION
         "This object provides the date of manufacture of the Remote SFP."
     ::= { cmEthernetTrafficPortEntry 169 }

cmEthernetTrafficPortRemoteSfpLinkLength OBJECT-TYPE
    SYNTAX     Integer32
    MAX-ACCESS read-only
    STATUS     current
    DESCRIPTION
         "This object provides Link Length of the Remote SFP."
     ::= { cmEthernetTrafficPortEntry 170 }

cmEthernetTrafficPortRemoteSfpLaserWaveLength OBJECT-TYPE
    SYNTAX     Integer32
    MAX-ACCESS read-only
    STATUS     current
    DESCRIPTION
         "This object provides Laser Wave Length in nano meters of
          the Remote SFP."
     ::= { cmEthernetTrafficPortEntry 171 }

cmEthernetTrafficPortRemoteSfpLaserFrequency OBJECT-TYPE
    SYNTAX  Unsigned32 
    MAX-ACCESS read-only
    STATUS     current
    DESCRIPTION
         "This object provides frequency of the Remote SFP, the step is 1GHZ."
     ::= { cmEthernetTrafficPortEntry 172 }

cmEthernetTrafficPortRemoteSfpMediaType OBJECT-TYPE
    SYNTAX     SfpMediaType
    MAX-ACCESS read-only
    STATUS     current
    DESCRIPTION
         "This object provides Media Type of the Remote SFP."
     ::= { cmEthernetTrafficPortEntry 173 }

cmEthernetTrafficPortRemoteSfpConnectorValue OBJECT-TYPE
    SYNTAX     SfpConnectorValue 
    MAX-ACCESS read-only
    STATUS     current
    DESCRIPTION
         "This object provides Connector Type of the Remote SFP."
     ::= { cmEthernetTrafficPortEntry 174 }

cmEthernetTrafficPortRemoteSfpIdentifierValue OBJECT-TYPE
    SYNTAX     SfpIdentifierValue
    MAX-ACCESS read-only
    STATUS     current
    DESCRIPTION
         "This object provides the Remote SFP identifier value."
     ::= { cmEthernetTrafficPortEntry 175 }

--
--  Agg Flow Table
--
cmElineFlowTable  OBJECT-TYPE
    SYNTAX      SEQUENCE OF CmElineFlowEntry
    MAX-ACCESS  not-accessible
    STATUS      current
    DESCRIPTION
            "A list of entries corresponding to Flows 
             for configuration purposes."
    ::= { cmFacilityObjects 28 }

cmElineFlowEntry OBJECT-TYPE
    SYNTAX      CmElineFlowEntry 
    MAX-ACCESS  not-accessible
    STATUS      current
    DESCRIPTION
            "A conceptual row in the cmElineFlowTable. These entries represent
             an Flow."
    INDEX { neIndex, cmElineFlowIndex }
    ::= { cmElineFlowTable 1 }

CmElineFlowEntry ::= SEQUENCE {
    -- Flow Index/Id
    cmElineFlowIndex                           Integer32,
    cmElineFlowCircuitName                     DisplayString,

    -- State Management params
    cmElineFlowAdminState                      AdminState,
    cmElineFlowOperationalState                OperationalState,
    cmElineFlowSecondaryState                  SecondaryState,
    
    -- flow attributes
    cmElineFlowFP1                             VariablePointer,
    cmElineFlowFP2                             VariablePointer,
  
    --SNMP row creation 
    cmElineFlowStorageType                     StorageType,
    cmElineFlowRowStatus                       RowStatus
}

cmElineFlowIndex OBJECT-TYPE
    SYNTAX      Integer32 (1..65535)
    MAX-ACCESS  read-create
    STATUS      current
    DESCRIPTION
            "The integer index value corresponding to an Flow." 
    ::= { cmElineFlowEntry 1 }

cmElineFlowCircuitName    OBJECT-TYPE
    SYNTAX      DisplayString (SIZE(0..256))
    MAX-ACCESS  read-create
    STATUS      current
    DESCRIPTION
         "This object allows SNMP management entities to provide a
          circuit identifier with the Flow."
     ::= { cmElineFlowEntry 2 }

-- State Management params
cmElineFlowAdminState OBJECT-TYPE
    SYNTAX      AdminState 
    MAX-ACCESS  read-write
    STATUS      current
    DESCRIPTION
            "This object represents the Administrative State of the Flow." 
    ::= { cmElineFlowEntry 3 }

cmElineFlowOperationalState OBJECT-TYPE
    SYNTAX      OperationalState 
    MAX-ACCESS  read-only
    STATUS      current
    DESCRIPTION
            "This object represents the Operational State of the Flow." 
    ::= { cmElineFlowEntry 4 }

cmElineFlowSecondaryState OBJECT-TYPE
    SYNTAX      SecondaryState 
    MAX-ACCESS  read-only
    STATUS      current
    DESCRIPTION
            "This object represents the Secondary State of the Flow." 
    ::= { cmElineFlowEntry 5 }

cmElineFlowFP1    OBJECT-TYPE
    SYNTAX      VariablePointer
    MAX-ACCESS  read-create
    STATUS      current
    DESCRIPTION
         "This object allows SNMP management entities to provide a
          flowpoint with the Flow."
     ::= { cmElineFlowEntry 6 }

cmElineFlowFP2    OBJECT-TYPE
    SYNTAX      VariablePointer
    MAX-ACCESS  read-create
    STATUS      current
    DESCRIPTION
         "This object allows SNMP management entities to provide another
          flowpoint with the Flow."
     ::= { cmElineFlowEntry 7 }

cmElineFlowStorageType OBJECT-TYPE
    SYNTAX     StorageType
    MAX-ACCESS read-create
    STATUS     current
    DESCRIPTION
            "The type of storage configured for this entry."
    ::= { cmElineFlowEntry 8 }

cmElineFlowRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmElineFlowRowStatus supported are
            createAndGo(4) and destroy(6).  All mandatory attributes
            must be specified in a single SNMP SET request with
            cmElineFlowRowStatus value as createAndGo(4).
            Upon successful row creation, this object has a
            value of active(1).

            The cmElineFlowRowStatus object may be modified if
            the associated instance of this object is equal to active(1)."
    ::= { cmElineFlowEntry 9 }

--
--  Agg FlowPoint
--
cmFlowPointTable  OBJECT-TYPE
    SYNTAX      SEQUENCE OF CmFlowPointEntry
    MAX-ACCESS  not-accessible
    STATUS      current
    DESCRIPTION
            "A list of entries corresponding to FlowPoint
             for configuration purposes."
    ::= { cmFacilityObjects 29 }

cmFlowPointEntry OBJECT-TYPE
    SYNTAX      CmFlowPointEntry 
    MAX-ACCESS  not-accessible
    STATUS      current
    DESCRIPTION
            "A conceptual row in the cmFlowPointTable. These entries represent
             an FlowPoint.
             If the flowpoint attached to a lag, the slotIndex should 
             be 255(255 is used to identify the flowpoint belongs to lag), 
             and the cmEthernetTrafficPortIndex should be the f3LagIndex."
    INDEX { neIndex, shelfIndex, slotIndex, cmEthernetTrafficPortIndex, cmFlowPointIndex }
    ::= { cmFlowPointTable 1 }

CmFlowPointEntry ::= SEQUENCE {
    -- FlowPoint Index/Id
    cmFlowPointIndex                           Integer32,
    cmFlowPointCircuitName                     DisplayString,

    -- State Management params
    cmFlowPointAdminState                      AdminState,
    cmFlowPointOperationalState                OperationalState,
    cmFlowPointSecondaryState                  SecondaryState,
    
    cmFlowPointAssociatedFlowId                VariablePointer,

    cmFlowPointIngressMultiCOS                 TruthValue,
    cmFlowPointIngressCOS                      Integer32,
    --flowpoint membership
    cmFlowPointIngressVlanMemberList           DisplayString, 
    cmFlowPointVlanMemberAction                FlowVlanActionType, 
    cmFlowPointVlanMemberActionVlan            DisplayString, 
    cmFlowPointIngressUntaggedFrameEnabled     TruthValue,

    --flowpoint tag management
    cmFlowPointCTagControl                     FlowTagControl,
    cmFlowPointCTagVlanId                      VlanId,
    cmFlowPointCTagVlanPriority                VlanPriority,

    cmFlowPointSTagControl                     FlowTagControl,
    cmFlowPointSTagVlanId                      VlanId,
    cmFlowPointSTagVlanPriority                VlanPriority,
        
    cmFlowPointEgressOuterTagPrioMapEnabled    TruthValue,
    cmFlowPointColorMarkingSupported           TruthValue,
    cmFlowPointAssociatedAclProfile            VariablePointer,
    cmFlowPointSESFramesLossThresholdRatio     Integer32,
    cmFlowPointStorageType                     StorageType,
    cmFlowPointRowStatus                       RowStatus,
    cmFlowPointDefaultMemberEnabled            TruthValue,
    cmFlowPointMcastRateLimitEnabled           TruthValue,
    cmFlowPointMcastRateLimitSpeedLo           Unsigned32,
    cmFlowPointMcastRateLimitSpeedHi           Unsigned32,
    cmFlowPointBcastRateLimitEnabled           TruthValue,
    cmFlowPointBcastRateLimitSpeedLo           Unsigned32,
    cmFlowPointBcastRateLimitSpeedHi           Unsigned32,
    cmFlowPointSplitHorizonGroupOID            VariablePointer,
    cmFlowPointLoopAvoidance                   VariablePointer,
    cmFlowPointHierarchicalCosEnabled          TruthValue,
    cmFlowPointWfqQid                          Integer32,
    cmFlowPointWfqOutPriority                  Integer32,
    cmFlowPointMaximumBWLo                     Unsigned32,
    cmFlowPointMaximumBWHi                     Unsigned32,
    cmFlowPointGuaranteedBWLo                  Unsigned32,
    cmFlowPointGuaranteedBWHi                  Unsigned32,

    cmFlowPointRefPrioMapProfile               VariablePointer,
    cmFlowPointMcastAndBcastRateLimitEnabled   TruthValue,
    cmFlowPointMcastAndBcastRateLimitSpeedLo   Unsigned32,
    cmFlowPointMcastAndBcastRateLimitSpeedHi   Unsigned32,
    
    -- new 9.1.1 xgpro release columns
    
    cmFlowPointEgressShapingType               ShapingType,
    cmFlowPointEgressInnerTagPrioMapEnabled    TruthValue,
    cmFlowPointAutoBandwidthConfigEnabled      TruthValue,
    cmFlowPointAutoCIRPercentage               Integer32,
    cmFlowPointFrameFwdEnabled                 TruthValue,
    cmFlowPointUsePortPrioMapProfile           TruthValue,
    cmFlowPointRefEoMplsPwObject               VariablePointer,
    cmFlowPointElmiEvcIdentifier               DisplayString,
    cmFlowPointRefElpObject                    VariablePointer,
    cmFlowPointEfEnabled                       TruthValue,
    cmFlowPointEfIdentificationType            EfIdentificationType,
    cmFlowPointEfRateThresholdLo               Unsigned32,
    cmFlowPointEfRateThresholdHi               Unsigned32,
    cmFlowPointAclNoMatchDisposition           AclNoMatchDispositionType,
    cmFlowPointEfIdentificationFields          EfIdentificationFieldType,
    cmFlowPointWfqSegmentationCOS              Integer32,
    cmFlowPointWfqGroupCOS                     Integer32,
    cmFlowPointWfqGroupEirLo                   Unsigned32,
    cmFlowPointWfqGroupEirHi                   Unsigned32
}

cmFlowPointIndex OBJECT-TYPE
    SYNTAX      Integer32 (1..65535)
    MAX-ACCESS  read-create
    STATUS      current
    DESCRIPTION
            "The integer index value corresponding to an FlowPoint." 
    ::= { cmFlowPointEntry 1 }

cmFlowPointCircuitName    OBJECT-TYPE
    SYNTAX      DisplayString (SIZE(0..256))
    MAX-ACCESS  read-create
    STATUS      current
    DESCRIPTION
         "This object allows SNMP management entities to provide a
          circuit identifier with the FlowPoint."
     ::= { cmFlowPointEntry 2 }

-- State Management params
cmFlowPointAdminState OBJECT-TYPE
    SYNTAX      AdminState 
    MAX-ACCESS  read-write
    STATUS      current
    DESCRIPTION
            "This object represents the Administrative State of the FlowPoint." 
    ::= { cmFlowPointEntry 3 }

cmFlowPointOperationalState OBJECT-TYPE
    SYNTAX      OperationalState 
    MAX-ACCESS  read-only
    STATUS      current
    DESCRIPTION
            "This object represents the Operational State of the FlowPoint." 
    ::= { cmFlowPointEntry 4 }

cmFlowPointSecondaryState OBJECT-TYPE
    SYNTAX      SecondaryState 
    MAX-ACCESS  read-only
    STATUS      current
    DESCRIPTION
            "This object represents the Secondary State of the FlowPoint." 
    ::= { cmFlowPointEntry 5 }

cmFlowPointAssociatedFlowId OBJECT-TYPE
    SYNTAX      VariablePointer
    MAX-ACCESS  read-only
    STATUS      current
    DESCRIPTION
            "This object provides the association of an Flow with an FlowPoint." 
    ::= { cmFlowPointEntry 6 }

cmFlowPointIngressMultiCOS OBJECT-TYPE
    SYNTAX     TruthValue
    MAX-ACCESS read-create
    STATUS     current
    DESCRIPTION
         "This object allows specification of ingress multiple COS (Class of Service) FlowPoint." 
     ::= { cmFlowPointEntry 7 }

cmFlowPointIngressCOS OBJECT-TYPE
    SYNTAX     Integer32
    MAX-ACCESS read-create
    STATUS     current
    DESCRIPTION
         "This object allows specification of ingress COS (Class of Service) FlowPoint." 
     ::= { cmFlowPointEntry 8 }
     
cmFlowPointIngressVlanMemberList OBJECT-TYPE
    SYNTAX     DisplayString (SIZE (0..512))
    MAX-ACCESS read-create
    STATUS     current
    DESCRIPTION
         "It allows specification of VLAN members of the FlowPoint.
          VLAN members are comma separated, of the form X-Y where X is the
          VLAN Id and Y is the VLAN Priority.  VLAN members can be of
          the form X-* or X (vlan X with all priorities), 
          *-Y (all vlans with priority Y), and X1:X2 
          (range of vlans from X1 to X2, all priorities). Members 
          with specific VLAN Id and specific VLAN Priority are not supported.
          Once the flowpoint is created, this attribute can only be updated
          using cmFlowPointVlanMemberAction and cmFlowPointVlanMemberActionVlan objects."
     ::= { cmFlowPointEntry 9 }

cmFlowPointVlanMemberAction OBJECT-TYPE
    SYNTAX     FlowVlanActionType 
    MAX-ACCESS read-write
    STATUS     current
    DESCRIPTION
         "This object allows to add or remove the VLAN members specified by
          cmFlowPointVlanMemberActionVlan object.  SNMP manager must first
          configure the VLAN member to be added/removed in the object
          cmFlowPointVlanMemberActionVlan and then should specify
          cmFlowPointVlanMemberAction on whether to add/remove the specified
          VLAN member."
     ::= { cmFlowPointEntry 10 }

cmFlowPointVlanMemberActionVlan OBJECT-TYPE
    SYNTAX     DisplayString (SIZE (0..16))
    MAX-ACCESS read-create
    STATUS     current
    DESCRIPTION
         "This object allows adding/removing VLAN members
          to a flowpoint.
          VLAN member is of the form X-Y where X is the
          VLAN Id and Y is the VLAN Priority.  VLAN members can be of
          the form X-* (vlan X with all priorities), 
          *-Y (all vlans with priority Y), and X1:X2 
          (range of vlans from X1 to X2, all priorities).  
          Members with specific VLAN Id and 
          specific VLAN Priority are not supported.
          In order to add/remove VLAN member to a flow, user must
          specify this object with appropriate VLAN and then invoke
          cmFlowPointVlanMemberAction."
     ::= { cmFlowPointEntry 11 }
     
cmFlowPointIngressUntaggedFrameEnabled OBJECT-TYPE
    SYNTAX     TruthValue 
    MAX-ACCESS read-create
    STATUS     current
    DESCRIPTION
         "This object allows to specify whether or not the flowpoint
          supports untagged frame."
     ::= { cmFlowPointEntry 12 }

--flowpoint tag management
cmFlowPointCTagControl  OBJECT-TYPE
    SYNTAX     FlowTagControl
    MAX-ACCESS read-create
    STATUS     current
    DESCRIPTION
         "This object allows specification of the tag management 
          operation on the C-TAG.  Supported types are 'push', 'pushvid',
          'swaptag', 'swapvid' and 'none'. If the type is 'push', 
          the VLAN Id (cmFlowPointCTagVlanId) and priority
          (cmFlowPointCTagVlanPriority) are pushed onto the frame;
          if the type is 'pushvid', only the VLAN Id (12 bits) is pushed,
          the Priority is copied from incoming tag's priority;
          if the type is 'swaptag', both VLAN Id and Priority (15 bits) 
          are swapped with the specified cmFlowPointCTagVlanId and 
          cmFlowPointCTagVlanPriority;
          if the type is 'swapvid', only the VLAN Id (12 bits) are 
          swapped with the specified cmFlowPointCTagVlanId; 
          if the type is 'none', no C-TAG management is performed."
     ::= { cmFlowPointEntry 13 }

cmFlowPointCTagVlanId  OBJECT-TYPE
    SYNTAX     VlanId
    MAX-ACCESS read-create
    STATUS     current
    DESCRIPTION
         "This object allows specification of the VLAN Id to
          be pushed or swapped, based on the value of cmFlowPointIngressCTagControl.
          It is applicable for 'push', 'swaptag', 'swapvid' and 'pushvid'
          control types."
     ::= { cmFlowPointEntry 14 }

cmFlowPointCTagVlanPriority  OBJECT-TYPE
    SYNTAX     VlanPriority
    MAX-ACCESS read-create
    STATUS     current
    DESCRIPTION
         "This object allows specification of the VLAN Priority to
          be pushed or swapped, based on the value of cmFlowPointIngressCTagControl.
          It is applicable for 'push' and 'swaptag' control types."
     ::= { cmFlowPointEntry 15 }

cmFlowPointSTagControl  OBJECT-TYPE
    SYNTAX     FlowTagControl
    MAX-ACCESS read-create
    STATUS     current
    DESCRIPTION
         "This object allows specification of the tag management 
          operation on the S-TAG.  Supported types are 'push', 'pushvid',
          'swaptag', 'swapvid' and 'none'. If the type is 'push', 
          the VLAN Id (cmFlowPointSTagVlanId) and priority
          (cmFlowPointSTagVlanPriority) are pushed onto the frame;
          if the type is 'pushvid', only the VLAN Id (12 bits) is pushed,
          the Priority is copied from incoming tag's priority;
          if the type is 'swaptag', both VLAN Id and Priority (15 bits) 
          are swapped with the specified cmFlowPointSTagVlanId and 
          cmFlowPointSTagVlanPriority;
          if the type is 'swapvid', only the VLAN Id (12 bits) are 
          swapped with the specified cmFlowPointSTagVlanId; 
          if the type is 'none', no S-TAG management is performed."
     ::= { cmFlowPointEntry 16 }

cmFlowPointSTagVlanId  OBJECT-TYPE
    SYNTAX     VlanId
    MAX-ACCESS read-create
    STATUS     current
    DESCRIPTION
         "This object allows specification of the VLAN Id to
          be pushed or swapped, based on the value of cmFlowPointIngressSTagControl.
          It is applicable for 'push', 'swaptag', 'swapvid' and 'pushvid'
          control types."
     ::= { cmFlowPointEntry 17 }

cmFlowPointSTagVlanPriority  OBJECT-TYPE
    SYNTAX     VlanPriority
    MAX-ACCESS read-create
    STATUS     current
    DESCRIPTION
         "This object allows specification of the VLAN Priority to
          be pushed or swapped, based on the value of cmFlowPointIngressSTagControl.
          It is applicable for 'push' and 'swaptag' control types."
     ::= { cmFlowPointEntry 18 }

cmFlowPointEgressOuterTagPrioMapEnabled  OBJECT-TYPE
    SYNTAX     TruthValue
    MAX-ACCESS read-create
    STATUS     current
    DESCRIPTION
         "This object defines whether to use the Egress Prio Mapping to swap the priority of outer tag.
         When Enabled,it indicates that the operation specified in the EgressPrioMapTable would be 
         applied to Flow for specified COS.
         When Disabled,the EgressPrioMapTable operations are ignored for specified Flow COS."
     ::= { cmFlowPointEntry 19 }

cmFlowPointColorMarkingSupported  OBJECT-TYPE
    SYNTAX     TruthValue
    MAX-ACCESS read-create
    STATUS     current
    DESCRIPTION
         "This object defines the egress color marking. If set to Enabled, the DEI bit of S-tag pushed 
          will be remarked according the meter result. If set to Disabled, the DEI bit is forced to 0."
     ::= { cmFlowPointEntry 20 }

cmFlowPointAssociatedAclProfile OBJECT-TYPE
    SYNTAX      VariablePointer
    MAX-ACCESS  read-create
    STATUS      current
    DESCRIPTION
            "This object provides the association of an Flow with an ACL profile." 
    ::= { cmFlowPointEntry 21 }

cmFlowPointSESFramesLossThresholdRatio OBJECT-TYPE 
    SYNTAX     Integer32 (0..100)
    MAX-ACCESS read-write
    STATUS     current
    DESCRIPTION
         "This object is used to specify the frame-loss ratio 
          per flow that starts counting Severely Errored Seconds (SES) 
          on the flowpoint.
          This functionality is applicable if the flowpoint is monitored
          using the Y.1731 ESA functionality." 
     ::= { cmFlowPointEntry 22 }

cmFlowPointStorageType OBJECT-TYPE
    SYNTAX     StorageType
    MAX-ACCESS read-create
    STATUS     current
    DESCRIPTION
            "The type of storage configured for this entry."
    ::= { cmFlowPointEntry 23 }

cmFlowPointRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmFlowPointRowStatus supported are
            createAndGo(4) and destroy(6).  All mandatory attributes
            must be specified in a single SNMP SET request with
            cmFlowPointRowStatus value as createAndGo(4).
            Upon successful row creation, this object has a
            value of active(1).

            The cmFlowPointRowStatus object may be modified if
            the associated instance of this object is equal to active(1)."
    ::= { cmFlowPointEntry 24 }
    
cmFlowPointDefaultMemberEnabled OBJECT-TYPE
    SYNTAX      TruthValue
    MAX-ACCESS  read-write
    STATUS      current
    DESCRIPTION
            "defaultMemberEnabled with enabled means that on this FP, 
            the membership is all the tag packets without match any 
            other membership associated to the port. Untagged means 
            untagged flow. Default only care tagged flow." 
    ::= { cmFlowPointEntry 25 }

cmFlowPointMcastRateLimitEnabled OBJECT-TYPE
    SYNTAX      TruthValue
    MAX-ACCESS  read-write
    STATUS      current
    DESCRIPTION
            "Whether multicast packets need be limited per FP." 
    ::= { cmFlowPointEntry 26 }

cmFlowPointMcastRateLimitSpeedLo OBJECT-TYPE
    SYNTAX      Unsigned32
    MAX-ACCESS  read-write
    STATUS      current
    DESCRIPTION
            "The rate limiting for multicast packets per FP
             When cmFlowPointMcastRateLimitEnabled and the value is 0, 
             it means all multicast frame are dropped.

             This objects only represents low 32 bits." 
    ::= { cmFlowPointEntry 27 }

cmFlowPointMcastRateLimitSpeedHi OBJECT-TYPE
    SYNTAX      Unsigned32
    MAX-ACCESS  read-write
    STATUS      current
    DESCRIPTION
            "The rate limiting for multicast packets per FP
             When cmFlowPointMcastRateLimitEnabled and the value is 0, 
             it means all multicast frame are dropped.

             This objects only represents high 32 bits." 
    ::= { cmFlowPointEntry 28 }

cmFlowPointBcastRateLimitEnabled OBJECT-TYPE
    SYNTAX      TruthValue
    MAX-ACCESS  read-write
    STATUS      current
    DESCRIPTION
            "Whether broadcast packets need be limited per FP." 
    ::= { cmFlowPointEntry 29 }

cmFlowPointBcastRateLimitSpeedLo OBJECT-TYPE
    SYNTAX      Unsigned32
    MAX-ACCESS  read-write
    STATUS      current
    DESCRIPTION
            "The rate limiting for broadcast packets per FP
             When cmFlowPointBcastRateLimitEnabled and the value is 0, 
             it means all multicast frame are dropped.

             This objects only represents low 32 bits." 
    ::= { cmFlowPointEntry 30 }

cmFlowPointBcastRateLimitSpeedHi OBJECT-TYPE
    SYNTAX      Unsigned32
    MAX-ACCESS  read-write
    STATUS      current
    DESCRIPTION
            "The rate limiting for broadcast packets per FP
             When cmFlowPointBcastRateLimitEnabled and the value is 0, 
             it means all multicast frame are dropped.

             This objects only represents high 32 bits." 
    ::= { cmFlowPointEntry 31 }

cmFlowPointSplitHorizonGroupOID OBJECT-TYPE
    SYNTAX      VariablePointer
    MAX-ACCESS  read-write
    STATUS      current
    DESCRIPTION
            "Specifies the Split-Horizon Group EID. If there is no SHG, the value is none." 
    ::= { cmFlowPointEntry 32 }

cmFlowPointLoopAvoidance OBJECT-TYPE
    SYNTAX      VariablePointer
    MAX-ACCESS  read-write
    STATUS      current
    DESCRIPTION
            "EID of this associated Loop Avoidance protocol entity.
             A value of NONE indicates there is no loop avoidance protocol.
             Currently ERP EID is filled when ELAN service is created." 
    ::= { cmFlowPointEntry 33 }

cmFlowPointHierarchicalCosEnabled OBJECT-TYPE
    SYNTAX      TruthValue
    MAX-ACCESS  read-write
    STATUS      current
    DESCRIPTION
            "Enable or Disable Hierarchical COS shaping (flow shaping)." 
    ::= { cmFlowPointEntry 34 }

cmFlowPointWfqQid  OBJECT-TYPE
    SYNTAX      Integer32 (0..7)
    MAX-ACCESS  read-write
    STATUS      current
    DESCRIPTION
            "This attribute description the WFQ Qid." 
    ::= { cmFlowPointEntry 35 }

cmFlowPointWfqOutPriority  OBJECT-TYPE
    SYNTAX      Integer32 (0..7)
    MAX-ACCESS  read-write
    STATUS      current
    DESCRIPTION
            "This attribute description the WFQ out priority." 
    ::= { cmFlowPointEntry 36 }

cmFlowPointMaximumBWLo  OBJECT-TYPE
    SYNTAX      Unsigned32
    MAX-ACCESS  read-write
    STATUS      current
    DESCRIPTION
            "This attribute description the flow point maximum bandwidth.

             This objects only represents low 32 bits." 
    ::= { cmFlowPointEntry 37 }

cmFlowPointMaximumBWHi  OBJECT-TYPE
    SYNTAX      Unsigned32
    MAX-ACCESS  read-write
    STATUS      current
    DESCRIPTION
            "This attribute description the flow point maximum bandwidth.

             This objects only represents high 32 bits." 
    ::= { cmFlowPointEntry 38 }

cmFlowPointGuaranteedBWLo  OBJECT-TYPE
    SYNTAX      Unsigned32
    MAX-ACCESS  read-write
    STATUS      current
    DESCRIPTION
            "This attribute description the flow point guaranteed bandwidth.

             This objects only represents low 32 bits." 
    ::= { cmFlowPointEntry 39 }

cmFlowPointGuaranteedBWHi  OBJECT-TYPE
    SYNTAX      Unsigned32
    MAX-ACCESS  read-write
    STATUS      current
    DESCRIPTION
            "This attribute description the flow point guaranteed bandwidth.

             This objects only represents high 32 bits." 
    ::= { cmFlowPointEntry 40 }

cmFlowPointRefPrioMapProfile OBJECT-TYPE
    SYNTAX      VariablePointer  
    MAX-ACCESS  read-write
    STATUS      current
    DESCRIPTION
         "This object allows to set priority map profile."
    ::= { cmFlowPointEntry 41 }

cmFlowPointMcastAndBcastRateLimitEnabled OBJECT-TYPE
    SYNTAX      TruthValue
    MAX-ACCESS  read-write
    STATUS      current
    DESCRIPTION
            "Whether multicast packets and broadcast packets need be limited per FP." 
    ::= { cmFlowPointEntry 42 }

cmFlowPointMcastAndBcastRateLimitSpeedLo OBJECT-TYPE
    SYNTAX      Unsigned32
    MAX-ACCESS  read-write
    STATUS      current
    DESCRIPTION
            "The rate limiting for multicast packets and broadcast packets per FP
             When cmFlowPointMcastAndBcastRateLimitEnabled and the value is 0, 
             it means all multicast frame are dropped.

             This objects only represents low 32 bits." 
    ::= { cmFlowPointEntry 43 }

cmFlowPointMcastAndBcastRateLimitSpeedHi OBJECT-TYPE
    SYNTAX      Unsigned32
    MAX-ACCESS  read-write
    STATUS      current
    DESCRIPTION
            "The rate limiting for multicast packets and broadcast packets per FP
             When cmFlowPointMcastAndBcastRateLimitEnabled and the value is 0, 
             it means all multicast frame are dropped.

             This objects only represents high 32 bits." 
    ::= { cmFlowPointEntry 44 }

cmFlowPointEgressShapingType OBJECT-TYPE
    SYNTAX     ShapingType
    MAX-ACCESS read-write
    STATUS     current
    DESCRIPTION
       "This object allows specification of Shaping Type for Flow Point.
        For 8.1.1 release, only flow-based Shaping Type is supported." 
    ::= { cmFlowPointEntry 45 }

cmFlowPointEgressInnerTagPrioMapEnabled OBJECT-TYPE
    SYNTAX     TruthValue
    MAX-ACCESS read-create
    STATUS     current
    DESCRIPTION
       "This object defines whether to use the Egress Prio
        Mapping to swap the priority of inner tag. When Enabled,
        it indicates that the operation specified in the 
        EgressPrioMapTable would be applied to Flow for specified COS.
        When Disabled, the EgressPrioMapTable operations are ignored
        for specified Flow COS."
    ::= { cmFlowPointEntry 46 }

cmFlowPointAutoBandwidthConfigEnabled OBJECT-TYPE
    SYNTAX      TruthValue
    MAX-ACCESS  read-create
    STATUS      current
    DESCRIPTION
       "This object specifies the shaper bandwidth is automatically adjusted 
        by the system. For a single COS Flow Point, the shaper EIR bandwidth is 
        set to the maximum port bandwidth; the shaper CIR is set to the available 
        port bandwidth multiplied by the value of the cmFlowPointAutoCIRPercentage
        object. For a Hierarchical-COS Flow Point, the cmFlowPointMaximumBWLo and
        cmFlowPointMaximumBWHi are set to the maximum port bandwidth; 
        the cmFlowPointGuaranteedBWLo and cmFlowPointGuaranteedBWHi are set to 
        the available port bandwidth multiplied by the value of the 
        cmFlowPointAutoCIRPercentage object. The value of this object must be FALSE 
        when cmFlowPointIngressMultiCOSEnabled is TRUE and 
        cmFlowPointHierarchicalCOSEnabled is FALSE." 
    ::= { cmFlowPointEntry 47 }
    
cmFlowPointAutoCIRPercentage OBJECT-TYPE
    SYNTAX      Integer32 (0..100)
    MAX-ACCESS  read-create
    STATUS      current
    DESCRIPTION
       "This object specifies the percentage of available shaper CIR to be assigned 
        to this Flow Point when cmFlowPointAutoBandwidthConfigEnabled is TRUE." 
    ::= { cmFlowPointEntry 48 }

cmFlowPointFrameFwdEnabled OBJECT-TYPE
    SYNTAX      TruthValue
    MAX-ACCESS  read-create
    STATUS      current
    DESCRIPTION
       "When enabled Flow Point will forward frames it receives. When disabled, 
        the Flow Point will not forward frames it receives." 
    ::= { cmFlowPointEntry 49 }

cmFlowPointUsePortPrioMapProfile OBJECT-TYPE
    SYNTAX      TruthValue  
    MAX-ACCESS  read-write
    STATUS      current
    DESCRIPTION
         "This indicates whether the flow point is using, if true, the port's 
         Priority Mapping Profile or, if false, is using its own
         Priority Mapping Profile."
    ::= { cmFlowPointEntry 50 }

cmFlowPointRefEoMplsPwObject OBJECT-TYPE
    SYNTAX      VariablePointer  
    MAX-ACCESS  read-create
    STATUS      current
    DESCRIPTION
         "This object specifies EoMpls Pw object OID."
    ::= { cmFlowPointEntry 51 }

cmFlowPointElmiEvcIdentifier OBJECT-TYPE
    SYNTAX      DisplayString  
    MAX-ACCESS  read-create
    STATUS      current
    DESCRIPTION
         "This object specifies FlowPoint Evc Identifier 
          required for E-LMI feature."
    ::= { cmFlowPointEntry 52 }

cmFlowPointRefElpObject OBJECT-TYPE
    SYNTAX      VariablePointer  
    MAX-ACCESS  read-create
    STATUS      current
    DESCRIPTION
         "This object specifies ELP object OID."
    ::= { cmFlowPointEntry 53 }

cmFlowPointEfEnabled OBJECT-TYPE
    SYNTAX      TruthValue
    MAX-ACCESS  read-create
    STATUS      current
    DESCRIPTION
       "When enabled FlowPoint is configured to monitor elephant(large) flows. When disabled, elephant flow management
        is not supported on the FlowPoint." 
    ::= { cmFlowPointEntry 54 }

cmFlowPointEfIdentificationType OBJECT-TYPE
    SYNTAX     EfIdentificationType
    MAX-ACCESS read-write
    STATUS     current
    DESCRIPTION
       "The Elephant Flows are identified per flowpoint. This object specifies the type of Elephant Flow
        identification based on specific fields in the L2-L4 headers. The five-tuple identification includes the
        Source MAC Address, Destination MAC Address, Source IP Address, Destination IP Address and IP Protocol.
        The seven-tuple identification includes the five-tuple fields as well as Source Port and Destination Port. 
        For Source and Destination ports, the supported protocols are TCP, UDP and SCTP."
    ::= { cmFlowPointEntry 55 }

cmFlowPointEfRateThresholdLo OBJECT-TYPE
    SYNTAX      Unsigned32
    MAX-ACCESS  read-write
    STATUS      current
    DESCRIPTION
            "This object specifies the threshold for the rate to declare a flow
             as an Elephant Flow. If cmFlowPointEfEnabled is enabled and this
             is set to 0, it is same as cmFlowPointEfEnabled control being disabled.

             This object only represents lower-order 32 bits." 
    ::= { cmFlowPointEntry 56 }

cmFlowPointEfRateThresholdHi OBJECT-TYPE
    SYNTAX      Unsigned32
    MAX-ACCESS  read-write
    STATUS      current
    DESCRIPTION
            "This object specifies the threshold for the rate to declare a flow
             as an Elephant Flow. If cmFlowPointEfEnabled is enabled and this
             is set to 0, it is same as cmFlowPointEfEnabled control being disabled.

             This object only represents higher-order 32 bits." 
    ::= { cmFlowPointEntry 57 }

cmFlowPointAclNoMatchDisposition OBJECT-TYPE
    SYNTAX     AclNoMatchDispositionType
    MAX-ACCESS read-write
    STATUS     current
    DESCRIPTION
            "This attribute allows specify ACL no match disposition type"
    ::= { cmFlowPointEntry 58 }

cmFlowPointEfIdentificationFields OBJECT-TYPE
    SYNTAX     EfIdentificationFieldType
    MAX-ACCESS read-write
    STATUS     current
    DESCRIPTION
       "The Elephant Flows are identified per flowpoint. This object specifies the type of Elephant Flow
        identification based on specific fields in the L2-L4 headers. The identification includes the
        Source MAC Address, Destination MAC Address, Source IP Address, Destination IP Address, IP Protocol,
        Source Port and Destination Port. 
        For Source and Destination ports, the supported protocols are TCP, UDP and SCTP."
    ::= { cmFlowPointEntry 59 }

cmFlowPointWfqSegmentationCOS OBJECT-TYPE
    SYNTAX      Integer32
    MAX-ACCESS  read-write
    STATUS      current
    DESCRIPTION
           "This object is used to specify wfq segmentation COS value."
    ::= { cmFlowPointEntry 60 }

cmFlowPointWfqGroupCOS OBJECT-TYPE
    SYNTAX      Integer32
    MAX-ACCESS  read-write
    STATUS      current
    DESCRIPTION
           "This object is used to specify wfq group COS value."
    ::= { cmFlowPointEntry 61 }

cmFlowPointWfqGroupEirLo OBJECT-TYPE
    SYNTAX      Unsigned32
    MAX-ACCESS  read-write
    STATUS      current
    DESCRIPTION
           "This object is used to specify wfq group EIR low 32 bits value."
    ::= { cmFlowPointEntry 62 }

cmFlowPointWfqGroupEirHi OBJECT-TYPE
    SYNTAX      Unsigned32
    MAX-ACCESS  read-write
    STATUS      current
    DESCRIPTION
           "This object is used to specify wfq group EIR high 32 bits value."
    ::= { cmFlowPointEntry 63 }

--
--  Agg OAM FlowPoint
--
cmOAMFlowPointTable  OBJECT-TYPE
    SYNTAX      SEQUENCE OF CmOAMFlowPointEntry
    MAX-ACCESS  not-accessible
    STATUS      current
    DESCRIPTION
            "A list of entries corresponding to OAMFlowPoint
             for configuration purposes."
    ::= { cmFacilityObjects 30 }

cmOAMFlowPointEntry OBJECT-TYPE
    SYNTAX      CmOAMFlowPointEntry 
    MAX-ACCESS  not-accessible
    STATUS      current
    DESCRIPTION
            "A conceptual row in the cmOAMFlowPointTable. These entries represent
             an FlowPoint.
             If the oam flowpoint attached to a lag, the slotIndex should 
             be 255(255 is used to identify the oam flowpoint belongs to lag), 
             and the cmEthernetTrafficPortIndex should be the f3LagIndex."
    INDEX { neIndex, shelfIndex, slotIndex, cmEthernetTrafficPortIndex, cmOAMFlowPointIndex }
    ::= { cmOAMFlowPointTable 1 }
                    
--OAM FlowPoint 

CmOAMFlowPointEntry ::= SEQUENCE {
    -- FlowPoint Index/Id
    cmOAMFlowPointIndex                           Integer32,
    cmOAMFlowPointCircuitName                     DisplayString,

    -- State Management params
    cmOAMFlowPointAdminState                      AdminState,
    cmOAMFlowPointOperationalState                OperationalState,
    cmOAMFlowPointSecondaryState                  SecondaryState,
    
    --OAM flowpoint membership
    cmOAMFlowPointIngressVlanMemberList           DisplayString, 
    cmOAMFlowPointVlanMemberAction                FlowVlanActionType, 
    cmOAMFlowPointVlanMemberActionVlan            DisplayString, 
    cmOAMFlowPointIngressUntaggedFrameSupported   TruthValue,
    cmOAMFlowPointSESFramesLossThresholdRatio     Integer32,
    cmOAMFlowPointStorageType                     StorageType,
    cmOAMFlowPointRowStatus                       RowStatus
}

cmOAMFlowPointIndex OBJECT-TYPE
    SYNTAX      Integer32 (1..65535)
    MAX-ACCESS  read-create
    STATUS      current
    DESCRIPTION
            "The integer index value corresponding to an OAMFlowPoint." 
    ::= { cmOAMFlowPointEntry 1 }

cmOAMFlowPointCircuitName    OBJECT-TYPE
    SYNTAX      DisplayString (SIZE(0..64))
    MAX-ACCESS  read-create
    STATUS      current
    DESCRIPTION
         "This object allows SNMP management entities to provide a
          circuit identifier with the OAMFlowPoint."
     ::= { cmOAMFlowPointEntry 2 }

-- State Management params
cmOAMFlowPointAdminState OBJECT-TYPE
    SYNTAX      AdminState 
    MAX-ACCESS  read-write
    STATUS      current
    DESCRIPTION
            "This object represents the Administrative State of the OAMFlowPoint." 
    ::= { cmOAMFlowPointEntry 3 }

cmOAMFlowPointOperationalState OBJECT-TYPE
    SYNTAX      OperationalState 
    MAX-ACCESS  read-only
    STATUS      current
    DESCRIPTION
            "This object represents the Operational State of the OAMFlowPoint." 
    ::= { cmOAMFlowPointEntry 4 }

cmOAMFlowPointSecondaryState OBJECT-TYPE
    SYNTAX      SecondaryState 
    MAX-ACCESS  read-only
    STATUS      current
    DESCRIPTION
            "This object represents the Secondary State of the OAMFlowPoint." 
    ::= { cmOAMFlowPointEntry 5 }

    
cmOAMFlowPointIngressVlanMemberList OBJECT-TYPE
    SYNTAX     DisplayString (SIZE (0..512))
    MAX-ACCESS read-create
    STATUS     current
    DESCRIPTION
         "It allows specification of VLAN members of the OAMFlowPoint.
          VLAN members are comma separated, of the form X-Y where X is the
          VLAN Id and Y is the VLAN Priority.  VLAN members can be of
          the form X-* or X (vlan X with all priorities), 
          *-Y (all vlans with priority Y), and X1:X2 (range of vlans from X1 to X2, all priorities). 
          Members with specific VLAN Id and specific VLAN Priority are not supported.
          Once the flowpoint is created, this attribute can only be updated
          using cmOAMFlowPointVlanMemberAction and cmOAMFlowPointVlanMemberActionVlan objects."
     ::= { cmOAMFlowPointEntry 6 }    
  
cmOAMFlowPointVlanMemberAction OBJECT-TYPE
    SYNTAX     FlowVlanActionType 
    MAX-ACCESS read-write
    STATUS     current
    DESCRIPTION
         "This object allows to add or remove the VLAN members specified by
          cmOAMFlowPointVlanMemberActionVlan object.  SNMP manager must first
          configure the VLAN member to be added/removed in the object
          cmOAMFlowPointVlanMemberActionVlan and then should specify
          cmOAMFlowPointVlanMemberAction on whether to add/remove the specified
          VLAN member."
     ::= { cmOAMFlowPointEntry 7 }

cmOAMFlowPointVlanMemberActionVlan OBJECT-TYPE
    SYNTAX     DisplayString (SIZE (0..16))
    MAX-ACCESS read-create
    STATUS     current
    DESCRIPTION
         "This object allows adding/removing VLAN members
         to a oam flowpoint.
           VLAN member is of the form X-Y where X is the
           VLAN Id and Y is the VLAN Priority.  VLAN members can be of
           the form X-* (vlan X with all priorities), 
           *-Y (all vlans with priority Y), and X1:X2 
           (range of vlans from X1 to X2, all priorities).  
           Members with specific VLAN Id and 
           specific VLAN Priority are not supported.
           In order to add/remove VLAN member to a flow, user must
           specify this object with appropriate VLAN and then invoke
           cmOAMFlowPointVlanMemberAction."
     ::= { cmOAMFlowPointEntry 8 }
     
cmOAMFlowPointIngressUntaggedFrameSupported OBJECT-TYPE
    SYNTAX     TruthValue 
    MAX-ACCESS read-create
    STATUS     current
    DESCRIPTION
         "This object allows to specify whether or not the OAMFlowPoint
          supports untagged frame."
     ::= { cmOAMFlowPointEntry 9 }

cmOAMFlowPointSESFramesLossThresholdRatio OBJECT-TYPE 
    SYNTAX     Integer32 (1..100)
    MAX-ACCESS read-write
    STATUS     current
    DESCRIPTION
         "This object is used to specify the frame-loss ratio 
          per flow that starts counting Severely Errored Seconds (SES) 
          on the oam flowpoint.
          This functionality is applicable if the oam flowpoint is monitored
          using the Y.1731 ESA functionality." 
     ::= { cmOAMFlowPointEntry 10 }
     
cmOAMFlowPointStorageType OBJECT-TYPE
    SYNTAX     StorageType
    MAX-ACCESS read-create
    STATUS     current
    DESCRIPTION
            "The type of storage configured for this entry."
    ::= { cmOAMFlowPointEntry 11 }

cmOAMFlowPointRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmOAMFlowPointRowStatus supported are
            createAndGo(4) and destroy(6).  All mandatory attributes
            must be specified in a single SNMP SET request with
            cmOAMFlowPointRowStatus value as createAndGo(4).
            Upon successful row creation, this object has a
            value of active(1).

            The cmOAMFlowPointRowStatus object may be modified if
            the associated instance of this object is equal to active(1)."
    ::= { cmOAMFlowPointEntry 12 }

--
--Agg Ingress Map Table
--
cmIngressPrioMapTable  OBJECT-TYPE
    SYNTAX      SEQUENCE OF CmIngressPrioMapEntry
    MAX-ACCESS  not-accessible
    STATUS      current
    DESCRIPTION
            "A list of entries corresponding to Ingress Priority Mapping 
             for configuration purposes."
    ::= { cmFacilityObjects 31 }

cmIngressPrioMapEntry OBJECT-TYPE
    SYNTAX      CmIngressPrioMapEntry 
    MAX-ACCESS  not-accessible
    STATUS      current
    DESCRIPTION
            "A conceptual row in the cmIngressPrioMapTable."
    INDEX { neIndex, shelfIndex, slotIndex, cmEthernetTrafficPortIndex, cmIngressPrioMapIndex }
    ::= { cmIngressPrioMapTable 1 }

CmIngressPrioMapEntry ::= SEQUENCE {
    -- Flow Index/Id
    cmIngressPrioMapIndex                        Integer32,
    cmIngressPrioMapInPriority                   Integer32,
    cmIngressPrioMapCOS                          Integer32
}

cmIngressPrioMapIndex OBJECT-TYPE
    SYNTAX      Integer32 (1..64)
    MAX-ACCESS  read-only
    STATUS      current
    DESCRIPTION
            "The integer index value corresponding to a priority value
             based on the cmEthernetTrafficPortPrioMapMode.
             In case of TOS and 8021P, valid indices are 1 to 8,
             in case of DSCP, valid indices are 1 to 64."
    ::= { cmIngressPrioMapEntry 1 }

cmIngressPrioMapInPriority OBJECT-TYPE
    SYNTAX      Integer32 (0..63)
    MAX-ACCESS  read-write
    STATUS      current
    DESCRIPTION
            "The integer index value corresponding to a priority value
             based on the cmEthernetTrafficPortIngressPrioMapMode.
             In case of TOS and 8021P, valid indices are 0 to 7,
             in case of DSCP, valid indices are 0 to 63."
    ::= { cmIngressPrioMapEntry 2 }
    
cmIngressPrioMapCOS OBJECT-TYPE
    SYNTAX      Integer32 (0..7)
    MAX-ACCESS  read-write
    STATUS      current
    DESCRIPTION
            "This allows specification of the COS Priority, i.e.
             this helps in determining the appropriate COS Policer for
             the Flow."
    ::= { cmIngressPrioMapEntry 3 }


--
--Agg Egress Map Table
--
cmEgressPrioMapTable  OBJECT-TYPE
    SYNTAX      SEQUENCE OF CmEgressPrioMapEntry
    MAX-ACCESS  not-accessible
    STATUS      current
    DESCRIPTION
            "A list of entries corresponding to Egress Priority Mapping 
             for configuration purposes."
    ::= { cmFacilityObjects 32 }

cmEgressPrioMapEntry OBJECT-TYPE
    SYNTAX      CmEgressPrioMapEntry 
    MAX-ACCESS  not-accessible
    STATUS      current
    DESCRIPTION
            "A conceptual row in the cmEgressPrioMapTable."
    INDEX { neIndex, shelfIndex, slotIndex, cmEthernetTrafficPortIndex, cmEgressCOSIndex  }
    ::= { cmEgressPrioMapTable 1 }

CmEgressPrioMapEntry ::= SEQUENCE {
    -- Flow Index/Id
    cmEgressCOSIndex                     Integer32,
    cmEgressCOS                          Integer32,
    cmEgressOuterTagCtrl                 PrioMapControlType,
    cmEgressOuterTagPriority             VlanPriority
}

cmEgressCOSIndex OBJECT-TYPE
    SYNTAX      Integer32 (1..8)
    MAX-ACCESS  read-only
    STATUS      current
    DESCRIPTION
            "The integer index used to uniquely identify
               this Egress Priority Map Entry "
    ::= { cmEgressPrioMapEntry 1 }

cmEgressCOS OBJECT-TYPE
    SYNTAX      Integer32 (0..7)
    MAX-ACCESS  read-write
    STATUS      current
    DESCRIPTION
            "This allows specification of the COS Priority, i.e.
             this helps in determining the appropriate COS Policer for
             the Flow."
    ::= { cmEgressPrioMapEntry 2 }

cmEgressOuterTagCtrl OBJECT-TYPE
    SYNTAX      PrioMapControlType
    MAX-ACCESS  read-write
    STATUS      current
    DESCRIPTION
            "This object defines the behavior of the Priority portion of the frame transmit out. 
             If NONE is selected, the outgoing priority bits are left unchanged. 
             If SWAP is selected, the priority bits are changed by the value specified 
             in the Outer-Tag Priority parameter."
    ::= { cmEgressPrioMapEntry 3 }

cmEgressOuterTagPriority OBJECT-TYPE
    SYNTAX      VlanPriority
    MAX-ACCESS  read-write
    STATUS      current
    DESCRIPTION
            "This object defines the new priority bits to be used, 
             it is available only if Outer-Tag PRIOCTL is set to SWAP."
    ::= { cmEgressPrioMapEntry 4 }
    
--
--  Port Control Protocol Disposition V3 profile Table
--
cmPortCpdProfileTable  OBJECT-TYPE
    SYNTAX      SEQUENCE OF CmPortCpdProfileEntry
    MAX-ACCESS  not-accessible
    STATUS      current
    DESCRIPTION
            "A list of entries corresponding to System 
             Control Protocol Disposition V3 profile."
    ::= { cmFacilityObjects 33 }

cmPortCpdProfileEntry OBJECT-TYPE
    SYNTAX      CmPortCpdProfileEntry 
    MAX-ACCESS  not-accessible
    STATUS      current
    DESCRIPTION
            "A conceptual row in the cmPortCpdProfileTable. 
             These entries represent a Control Protocol Disposition 
             of a port filtering criteria of the System."
    INDEX { cmPortCpdProfileIndex }
    ::= { cmPortCpdProfileTable 1 }


CmPortCpdProfileEntry ::= SEQUENCE {
    -- Index
    cmPortCpdProfileIndex                 Integer32,
    cmPortCpdProfileName                  DisplayString,
    -- Filtering Criteria
    cmPortCpdProfileCiscoGroupDispType    CmControlProtocolDispType,
    cmPortCpdProfileIslDispType           CmControlProtocolDispType,
    cmPortCpdProfilePagpDispType          CmControlProtocolDispType,
    cmPortCpdProfileUdldDispType          CmControlProtocolDispType,
    cmPortCpdProfileCdpDispType           CmControlProtocolDispType,
    cmPortCpdProfileVtpDispType           CmControlProtocolDispType,
    cmPortCpdProfileDtpDispType           CmControlProtocolDispType,
    cmPortCpdProfilePvstpPlusDispType     CmControlProtocolDispType,
    cmPortCpdProfileUplinkFastDispType    CmControlProtocolDispType,
    cmPortCpdProfileVlanBridgeDispType    CmControlProtocolDispType,
    cmPortCpdProfileL2PTDispType          CmControlProtocolDispType,
    cmPortCpdProfileBridgeGroupDispType   CmControlProtocolDispType,
    cmPortCpdProfileBPDUDispType          CmControlProtocolDispType,
    cmPortCpdProfilePauseDispType         CmControlProtocolDispType,
    cmPortCpdProfileLACPDispType          CmControlProtocolDispType,
    cmPortCpdProfileLACPMarkerDispType    CmControlProtocolDispType,
    cmPortCpdProfileEfmOamDispType        CmControlProtocolDispType,
    cmPortCpdProfileSSMDispType           CmControlProtocolDispType,
    cmPortCpdProfilePortAuthenDispType    CmControlProtocolDispType,
    cmPortCpdProfileBridgeReservedDispType    CmControlProtocolDispType,
    cmPortCpdProfileLANBridgesDispType    CmControlProtocolDispType,
    cmPortCpdProfileGARPGroupDispType     CmControlProtocolDispType,
    cmPortCpdProfileGMRPDispType          CmControlProtocolDispType,
    cmPortCpdProfileGVRPDispType          CmControlProtocolDispType,
    cmPortCpdProfileGARPDispType          CmControlProtocolDispType,
    cmPortCpdProfileLldpDispType          CmControlProtocolDispType,
    cmPortCpdProfileStorageType           StorageType,
    cmPortCpdProfileRowStatus             RowStatus,
    cmPortCpdProfileMac00DispType         CmControlProtocolDispType,
    cmPortCpdProfileMac01DispType         CmControlProtocolDispType,
    cmPortCpdProfileMac02DispType         CmControlProtocolDispType,
    cmPortCpdProfileMac03DispType         CmControlProtocolDispType,
    cmPortCpdProfileMac04DispType         CmControlProtocolDispType,
    cmPortCpdProfileMac05DispType         CmControlProtocolDispType,
    cmPortCpdProfileMac06DispType         CmControlProtocolDispType,
    cmPortCpdProfileMac07DispType         CmControlProtocolDispType,
    cmPortCpdProfileMac08DispType         CmControlProtocolDispType,
    cmPortCpdProfileMac09DispType         CmControlProtocolDispType,
    cmPortCpdProfileMac0ADispType         CmControlProtocolDispType,
    cmPortCpdProfileMac0BDispType         CmControlProtocolDispType,
    cmPortCpdProfileMac0CDispType         CmControlProtocolDispType,
    cmPortCpdProfileMac0DDispType         CmControlProtocolDispType,
    cmPortCpdProfileMac0EDispType         CmControlProtocolDispType,
    cmPortCpdProfileMac0FDispType         CmControlProtocolDispType,
    cmPortCpdProfileNearestLLDPDispType   CmControlProtocolDispType,
    cmPortCpdProfileNonTpmrLLDPDispType   CmControlProtocolDispType,
    cmPortCpdProfileCustomerLLDPDispType  CmControlProtocolDispType,
    cmPortCpdProfileELMIDispType          CmControlProtocolDispType
}

cmPortCpdProfileIndex OBJECT-TYPE
    SYNTAX      Integer32 (1..65535)
    MAX-ACCESS  read-only
    STATUS      current
    DESCRIPTION
        "Unique Index value to access the CPD profile row."
    ::= { cmPortCpdProfileEntry 1 }
    
cmPortCpdProfileName OBJECT-TYPE
    SYNTAX   DisplayString (SIZE (0..64))
    MAX-ACCESS read-write
    STATUS   current
    DESCRIPTION
       "This object describes the alias of the cpd V3 profile entry."
    ::= { cmPortCpdProfileEntry 2 }

cmPortCpdProfileCiscoGroupDispType OBJECT-TYPE
    SYNTAX      CmControlProtocolDispType 
    MAX-ACCESS  read-write
    STATUS      deprecated
    DESCRIPTION
        "Deprecated - each Cisco protocol has its own disposition.
         Control Protocol Disposition for Cisco Group.  This includes
         ISL, PAGP, UDLD, CDP, VTP, DTP, PSVTP+, UplinkFast, VLAN Bridge,
         L2PT.  Note that a specific protocol filter overrides the
         group setting."
    ::= { cmPortCpdProfileEntry 3 }

cmPortCpdProfileIslDispType OBJECT-TYPE
    SYNTAX      CmControlProtocolDispType 
    MAX-ACCESS  read-write
    STATUS      current
    DESCRIPTION
        "Control Protocol Disposition for ISL (Inter Switch Link).
         MAC Address (01:00:0C:00:00:00)."
    ::= { cmPortCpdProfileEntry 4 }

cmPortCpdProfilePagpDispType OBJECT-TYPE
    SYNTAX      CmControlProtocolDispType 
    MAX-ACCESS  read-write
    STATUS      current
    DESCRIPTION
        "Control Protocol Disposition for PAGP (Port Aggregation Protocol).
         MAC Address (01:00:0C:CC:CC:CC), Ethertype(0x104)."
    ::= { cmPortCpdProfileEntry 5 }

cmPortCpdProfileUdldDispType OBJECT-TYPE
    SYNTAX      CmControlProtocolDispType 
    MAX-ACCESS  read-write
    STATUS      current
    DESCRIPTION
        "Control Protocol Disposition for UDLD (Unidirectional Link Detection).
         MAC Address (01:00:0C:CC:CC:CC), Ethertype(0x111)."
    ::= { cmPortCpdProfileEntry 6 }

cmPortCpdProfileCdpDispType OBJECT-TYPE
    SYNTAX      CmControlProtocolDispType 
    MAX-ACCESS  read-write
    STATUS      current
    DESCRIPTION
        "Control Protocol Disposition for CDP (Cisco Discovery Protocol).
         MAC Address (01:00:0C:CC:CC:CC), Ethertype(0x2000)."
    ::= { cmPortCpdProfileEntry 7 }

cmPortCpdProfileVtpDispType OBJECT-TYPE
    SYNTAX      CmControlProtocolDispType 
    MAX-ACCESS  read-write
    STATUS      current
    DESCRIPTION
        "Control Protocol Disposition for VTP (VLAN Trunking Protocol).
         MAC Address (01:00:0C:CC:CC:CC), Ethertype(0x2003)."
    ::= { cmPortCpdProfileEntry 8 }

cmPortCpdProfileDtpDispType OBJECT-TYPE
    SYNTAX      CmControlProtocolDispType 
    MAX-ACCESS  read-write
    STATUS      current
    DESCRIPTION
        "Control Protocol Disposition for DTP (Dynamic Trunking).
         MAC Address (01:00:0C:CC:CC:CC), Ethertype(0x2004)."
    ::= { cmPortCpdProfileEntry 9 }

cmPortCpdProfilePvstpPlusDispType OBJECT-TYPE
    SYNTAX      CmControlProtocolDispType 
    MAX-ACCESS  read-write
    STATUS      current
    DESCRIPTION
        "Control Protocol Disposition for Spanning Tree PVSTP+.
         MAC Address (01:00:0C:CC:CC:CC), Ethertype(0x10B)."
    ::= { cmPortCpdProfileEntry 10 }

cmPortCpdProfileUplinkFastDispType OBJECT-TYPE
    SYNTAX      CmControlProtocolDispType 
    MAX-ACCESS  read-write
    STATUS      current
    DESCRIPTION
        "Control Protocol Disposition for STP UplinkFast.
         MAC Address (01:00:0C:CD:CD:CD), Ethertype(0x200A)."
    ::= { cmPortCpdProfileEntry 11 }

cmPortCpdProfileVlanBridgeDispType OBJECT-TYPE
    SYNTAX      CmControlProtocolDispType 
    MAX-ACCESS  read-write
    STATUS      current
    DESCRIPTION
        "Control Protocol Disposition for VLAN Bridge.
         MAC Address (01:00:0C:CD:CD:CE), Ethertype(0x10C)."
    ::= { cmPortCpdProfileEntry 12 }

cmPortCpdProfileL2PTDispType OBJECT-TYPE
    SYNTAX      CmControlProtocolDispType 
    MAX-ACCESS  read-write
    STATUS      current
    DESCRIPTION
        "Control Protocol Disposition for Layer 2 Protocol Tunnelling(L2PT).
         MAC Address (01:00:0C:CD:CD:D0)."
    ::= { cmPortCpdProfileEntry 13 }

cmPortCpdProfileBridgeGroupDispType OBJECT-TYPE
    SYNTAX      CmControlProtocolDispType 
    MAX-ACCESS  read-write
    STATUS      deprecated
    DESCRIPTION
        "Deprecated - individual dispositions available for each MAC.
         Bridge Group Control Protocol Disposition Type.  This
         includes BPDU, PAUSE (IEEE 802.3x Flow Control), 
         LACP (Link Aggregation), LACP Marker (Marker), 
         EFM OAM (IEEE 802.3 ah) and IEEE 802.1x Port Authentication, 
         besides reserved MAC addresses from 
         01:80:C2:00:00:04 thru 01:80:C2:00:00:0F."
    ::= { cmPortCpdProfileEntry 14 }

cmPortCpdProfileBPDUDispType OBJECT-TYPE
    SYNTAX      CmControlProtocolDispType 
    MAX-ACCESS  read-write
    STATUS      current
    DESCRIPTION
        "Control Protocol Disposition for IEEE Spanning Tree(STP),
         MSTP (Multiple Spanning Tree) and RSTP (Rapid Reconfiguration of
         Spanning Tree). MAC Address (01:80:C2:00:00:00)."
    ::= { cmPortCpdProfileEntry 15 }

cmPortCpdProfilePauseDispType OBJECT-TYPE
    SYNTAX      CmControlProtocolDispType 
    MAX-ACCESS  read-write
    STATUS      current
    DESCRIPTION
        "Control Protocol Disposition for IEEE 802.3x Flow Control 
         (PAUSE frames)."
    ::= { cmPortCpdProfileEntry 16 }

cmPortCpdProfileLACPDispType OBJECT-TYPE
    SYNTAX      CmControlProtocolDispType 
    MAX-ACCESS  read-write
    STATUS      current
    DESCRIPTION
        "Control Protocol Disposition for 802.3ad Link Aggregation
         Protocol.
         MAC Address (01:80:C2:00:00:03), Ethertype (0x8809), Subtype(01)."
    ::= { cmPortCpdProfileEntry 17 }

cmPortCpdProfileLACPMarkerDispType OBJECT-TYPE
    SYNTAX      CmControlProtocolDispType 
    MAX-ACCESS  read-write
    STATUS      current
    DESCRIPTION
        "Control Protocol Disposition for IEEE 802.3ad Marker Protocol.
         MAC Address (01:80:C2:00:00:03), Ethertype (0x8809), Subtype(02)."
    ::= { cmPortCpdProfileEntry 18 }

cmPortCpdProfileEfmOamDispType OBJECT-TYPE
    SYNTAX      CmControlProtocolDispType 
    MAX-ACCESS  read-write
    STATUS      current
    DESCRIPTION
        "Control Protocol Disposition for IEEE 802.3ah EFM OAM.
         MAC Address (01:80:C2:00:00:03), Ethertype (0x8809), Subtype(03)."
    ::= { cmPortCpdProfileEntry 19 }

cmPortCpdProfileSSMDispType OBJECT-TYPE
    SYNTAX      CmControlProtocolDispType 
    MAX-ACCESS  read-write
    STATUS      current
    DESCRIPTION
        "Control Protocol Disposition for Sync Status Messages.
         MAC Address (01:80:C2:00:00:02), Ethertype (0x19A7), Subtype(0A)."
    ::= { cmPortCpdProfileEntry 20 }

cmPortCpdProfilePortAuthenDispType OBJECT-TYPE
    SYNTAX      CmControlProtocolDispType 
    MAX-ACCESS  read-write
    STATUS      current
    DESCRIPTION
        "Control Protocol Disposition for IEEE 802.1x Protocol.
         MAC Address (01:80:C2:00:00:03), Ethertype (0x888E)."
    ::= { cmPortCpdProfileEntry 21 }

cmPortCpdProfileBridgeReservedDispType OBJECT-TYPE
    SYNTAX      CmControlProtocolDispType 
    MAX-ACCESS  read-write
    STATUS      deprecated
    DESCRIPTION
        "Deprecated - individual dispositions available for each MAC.
         Control Protocol Disposition for Range of MAC Addresses
         from 01:80:C2:00:00:04 to 01:80:C2:00:00:0F."
    ::= { cmPortCpdProfileEntry 22 }
    
cmPortCpdProfileLANBridgesDispType OBJECT-TYPE
    SYNTAX      CmControlProtocolDispType 
    MAX-ACCESS  read-write
    STATUS      current
    DESCRIPTION
        "Control Protocol Disposition for IEEE 802.1d LAN Bridge Managment.
         MAC Address (01:80:C2:00:00:10)."
    ::= { cmPortCpdProfileEntry 23 }

cmPortCpdProfileGARPGroupDispType OBJECT-TYPE
    SYNTAX      CmControlProtocolDispType 
    MAX-ACCESS  read-write
    STATUS      deprecated
    DESCRIPTION
        "Deprecated - each GARP Group protocol has its own disposition.
         Group Disposition type which includes GMRP, GVRP and
         MAC Address from range 01:80:C2:00:00:22 to 01:80:C2:00:00:2F."
    ::= { cmPortCpdProfileEntry 24 }

cmPortCpdProfileGMRPDispType OBJECT-TYPE
    SYNTAX      CmControlProtocolDispType 
    MAX-ACCESS  read-write
    STATUS      current
    DESCRIPTION
        "Control Protocol Disposition for GARP Multicast Registration
         Protocol. MAC Address (01:80:C2:00:00:20)."
    ::= { cmPortCpdProfileEntry 25 }

cmPortCpdProfileGVRPDispType OBJECT-TYPE
    SYNTAX      CmControlProtocolDispType 
    MAX-ACCESS  read-write
    STATUS      current
    DESCRIPTION
        "Control Protocol Disposition for GARP VLAN Registration
         Protocol. MAC Address (01:80:C2:00:00:22)."
    ::= { cmPortCpdProfileEntry 26 }

cmPortCpdProfileGARPDispType OBJECT-TYPE 
    SYNTAX      CmControlProtocolDispType 
    MAX-ACCESS  read-write     
    STATUS      current     
    DESCRIPTION     
        "Group Disposition type which includes GMRP, GVRP and
         MAC Address from range 01:80:C2:00:00:20 to 01:80:C2:00:00:2F."
    ::= { cmPortCpdProfileEntry 27 }     

cmPortCpdProfileLldpDispType OBJECT-TYPE 
    SYNTAX      CmControlProtocolDispType 
    MAX-ACCESS  read-write     
    STATUS      deprecated     
    DESCRIPTION     
        "Deprecated - each LLDP MAC protocol has its own disposition.
         Control Protocol Disposition for LLDP."
    ::= { cmPortCpdProfileEntry 28 }

cmPortCpdProfileStorageType OBJECT-TYPE
    SYNTAX     StorageType
    MAX-ACCESS read-create
    STATUS     current
    DESCRIPTION
            "The type of storage configured for this entry."
    ::= { cmPortCpdProfileEntry 29 }
    
cmPortCpdProfileRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmCpdProfileRowStatus supported are
            createAndGo(4) and destroy(6).  All mandatory attributes
            must be specified in a single SNMP SET request with
            cmCpdProfileRowStatus value as createAndGo(4).
            Upon successful row creation, this object has a
            value of active(1).

            The cmCpdProfileRowStatus object may be modified if
            the associated instance of this object is equal to active(1)."
    ::= { cmPortCpdProfileEntry 30 }

cmPortCpdProfileMac00DispType OBJECT-TYPE
    SYNTAX      CmControlProtocolDispType 
    MAX-ACCESS  read-write
    STATUS      current
    DESCRIPTION
        "MAC Address 01:80:C2:00:00:00 Disposition type."
    ::= { cmPortCpdProfileEntry 31 }

cmPortCpdProfileMac01DispType OBJECT-TYPE
    SYNTAX      CmControlProtocolDispType 
    MAX-ACCESS  read-write
    STATUS      current
    DESCRIPTION
        "MAC Address 01:80:C2:00:00:01 Disposition type."
    ::= { cmPortCpdProfileEntry 32 }

cmPortCpdProfileMac02DispType OBJECT-TYPE
    SYNTAX      CmControlProtocolDispType 
    MAX-ACCESS  read-write
    STATUS      current
    DESCRIPTION
        "MAC Address 01:80:C2:00:00:02 Disposition type."
    ::= { cmPortCpdProfileEntry 33 }

cmPortCpdProfileMac03DispType OBJECT-TYPE
    SYNTAX      CmControlProtocolDispType 
    MAX-ACCESS  read-write
    STATUS      current
    DESCRIPTION
        "MAC Address 01:80:C2:00:00:03 Disposition type."
    ::= { cmPortCpdProfileEntry 34 }

cmPortCpdProfileMac04DispType OBJECT-TYPE
    SYNTAX      CmControlProtocolDispType 
    MAX-ACCESS  read-write
    STATUS      current
    DESCRIPTION
        "MAC Address 01:80:C2:00:00:04 Disposition type."
    ::= { cmPortCpdProfileEntry 35 }

cmPortCpdProfileMac05DispType OBJECT-TYPE
    SYNTAX      CmControlProtocolDispType 
    MAX-ACCESS  read-write
    STATUS      current
    DESCRIPTION
        "MAC Address 01:80:C2:00:00:05 Disposition type."
    ::= { cmPortCpdProfileEntry 36 }

cmPortCpdProfileMac06DispType OBJECT-TYPE
    SYNTAX      CmControlProtocolDispType 
    MAX-ACCESS  read-write
    STATUS      current
    DESCRIPTION
        "MAC Address 01:80:C2:00:00:06 Disposition type."
    ::= { cmPortCpdProfileEntry 37 }

cmPortCpdProfileMac07DispType OBJECT-TYPE
    SYNTAX      CmControlProtocolDispType 
    MAX-ACCESS  read-write
    STATUS      current
    DESCRIPTION
        "MAC Address 01:80:C2:00:00:07 Disposition type."
    ::= { cmPortCpdProfileEntry 38 }

cmPortCpdProfileMac08DispType OBJECT-TYPE
    SYNTAX      CmControlProtocolDispType 
    MAX-ACCESS  read-write
    STATUS      current
    DESCRIPTION
        "MAC Address 01:80:C2:00:00:08 Disposition type."
    ::= { cmPortCpdProfileEntry 39 }

cmPortCpdProfileMac09DispType OBJECT-TYPE
    SYNTAX      CmControlProtocolDispType 
    MAX-ACCESS  read-write
    STATUS      current
    DESCRIPTION
        "MAC Address 01:80:C2:00:00:09 Disposition type."
    ::= { cmPortCpdProfileEntry 40 }

cmPortCpdProfileMac0ADispType OBJECT-TYPE
    SYNTAX      CmControlProtocolDispType 
    MAX-ACCESS  read-write
    STATUS      current
    DESCRIPTION
        "MAC Address 01:80:C2:00:00:0A Disposition type."
    ::= { cmPortCpdProfileEntry 41 }

cmPortCpdProfileMac0BDispType OBJECT-TYPE
    SYNTAX      CmControlProtocolDispType 
    MAX-ACCESS  read-write
    STATUS      current
    DESCRIPTION
        "MAC Address 01:80:C2:00:00:0B Disposition type."
    ::= { cmPortCpdProfileEntry 42 }

cmPortCpdProfileMac0CDispType OBJECT-TYPE
    SYNTAX      CmControlProtocolDispType 
    MAX-ACCESS  read-write
    STATUS      current
    DESCRIPTION
        "MAC Address 01:80:C2:00:00:0C Disposition type."
    ::= { cmPortCpdProfileEntry 43 }

cmPortCpdProfileMac0DDispType OBJECT-TYPE
    SYNTAX      CmControlProtocolDispType 
    MAX-ACCESS  read-write
    STATUS      current
    DESCRIPTION
        "MAC Address 01:80:C2:00:00:0D Disposition type."
    ::= { cmPortCpdProfileEntry 44 }

cmPortCpdProfileMac0EDispType OBJECT-TYPE
    SYNTAX      CmControlProtocolDispType 
    MAX-ACCESS  read-write
    STATUS      current
    DESCRIPTION
        "MAC Address 01:80:C2:00:00:0E Disposition type."
    ::= { cmPortCpdProfileEntry 45 }

cmPortCpdProfileMac0FDispType OBJECT-TYPE
    SYNTAX      CmControlProtocolDispType 
    MAX-ACCESS  read-write
    STATUS      current
    DESCRIPTION
        "MAC Address 01:80:C2:00:00:0F Disposition type."
    ::= { cmPortCpdProfileEntry 46 }

cmPortCpdProfileNearestLLDPDispType OBJECT-TYPE
    SYNTAX      CmControlProtocolDispType 
    MAX-ACCESS  read-write
    STATUS      current
    DESCRIPTION
        "The nearest lldp Disposition type."
    ::= { cmPortCpdProfileEntry 47 }

cmPortCpdProfileNonTpmrLLDPDispType OBJECT-TYPE
    SYNTAX      CmControlProtocolDispType 
    MAX-ACCESS  read-write
    STATUS      current
    DESCRIPTION
        "The non tp mr lldp Disposition type."
    ::= { cmPortCpdProfileEntry 48 }

cmPortCpdProfileCustomerLLDPDispType OBJECT-TYPE
    SYNTAX      CmControlProtocolDispType 
    MAX-ACCESS  read-write
    STATUS      current
    DESCRIPTION
        "The customer lldp Disposition type."
    ::= { cmPortCpdProfileEntry 49 }

cmPortCpdProfileELMIDispType OBJECT-TYPE
    SYNTAX      CmControlProtocolDispType 
    MAX-ACCESS  read-write
    STATUS      current
    DESCRIPTION
        "The ELMI Disposition type."
    ::= { cmPortCpdProfileEntry 50 }


--
--  Flow Point Control Protocol Disposition profile Table
--
cmFlowPointCpdProfileTable  OBJECT-TYPE
    SYNTAX      SEQUENCE OF CmFlowPointCpdProfileEntry
    MAX-ACCESS  not-accessible
    STATUS      current
    DESCRIPTION
            "A list of entries corresponding to System 
             Control Protocol Disposition V3 profile."
    ::= { cmFacilityObjects 34 }

cmFlowPointCpdProfileEntry OBJECT-TYPE
    SYNTAX      CmFlowPointCpdProfileEntry 
    MAX-ACCESS  not-accessible
    STATUS      current
    DESCRIPTION
            "A conceptual row in the cmFlowPointCpdProfileTable. 
             These entries represent a Control Protocol Disposition 
             of a flow point filtering criteria of the System."
    INDEX { cmFlowPointCpdProfileIndex }
    ::= { cmFlowPointCpdProfileTable 1 }


CmFlowPointCpdProfileEntry ::= SEQUENCE {
    -- Index
    cmFlowPointCpdProfileIndex                 Integer32,
    cmFlowPointCpdProfileName                  DisplayString,
    -- Filtering Criteria
    cmFlowPointCpdProfileCiscoGroupDispType    CmControlProtocolDispType,
    cmFlowPointCpdProfileIslDispType           CmControlProtocolDispType,
    cmFlowPointCpdProfilePagpDispType          CmControlProtocolDispType,
    cmFlowPointCpdProfileUdldDispType          CmControlProtocolDispType,
    cmFlowPointCpdProfileCdpDispType           CmControlProtocolDispType,
    cmFlowPointCpdProfileVtpDispType           CmControlProtocolDispType,
    cmFlowPointCpdProfileDtpDispType           CmControlProtocolDispType,
    cmFlowPointCpdProfilePvstpPlusDispType     CmControlProtocolDispType,
    cmFlowPointCpdProfileUplinkFastDispType    CmControlProtocolDispType,
    cmFlowPointCpdProfileVlanBridgeDispType    CmControlProtocolDispType,
    cmFlowPointCpdProfileL2PTDispType          CmControlProtocolDispType,
    cmFlowPointCpdProfileBridgeGroupDispType   CmControlProtocolDispType,
    cmFlowPointCpdProfileBPDUDispType          CmControlProtocolDispType,
    cmFlowPointCpdProfilePauseDispType         CmControlProtocolDispType,
    cmFlowPointCpdProfileLACPDispType          CmControlProtocolDispType,
    cmFlowPointCpdProfileLACPMarkerDispType    CmControlProtocolDispType,
    cmFlowPointCpdProfileEfmOamDispType        CmControlProtocolDispType,
    cmFlowPointCpdProfileSSMDispType           CmControlProtocolDispType,
    cmFlowPointCpdProfilePortAuthenDispType    CmControlProtocolDispType,
    cmFlowPointCpdProfileBridgeReservedDispType    CmControlProtocolDispType,
    cmFlowPointCpdProfileLANBridgesDispType    CmControlProtocolDispType,
    cmFlowPointCpdProfileGARPGroupDispType     CmControlProtocolDispType,
    cmFlowPointCpdProfileGMRPDispType          CmControlProtocolDispType,
    cmFlowPointCpdProfileGVRPDispType          CmControlProtocolDispType,
    cmFlowPointCpdProfileGARPDispType          CmControlProtocolDispType,
    cmFlowPointCpdProfileLldpDispType          CmControlProtocolDispType,
    cmFlowPointCpdProfileStorageType           StorageType,
    cmFlowPointCpdProfileRowStatus             RowStatus,
    cmFlowPointCpdProfileMac00DispType         CmControlProtocolDispType,
    cmFlowPointCpdProfileMac01DispType         CmControlProtocolDispType,
    cmFlowPointCpdProfileMac02DispType         CmControlProtocolDispType,
    cmFlowPointCpdProfileMac03DispType         CmControlProtocolDispType,
    cmFlowPointCpdProfileMac04DispType         CmControlProtocolDispType,
    cmFlowPointCpdProfileMac05DispType         CmControlProtocolDispType,
    cmFlowPointCpdProfileMac06DispType         CmControlProtocolDispType,
    cmFlowPointCpdProfileMac07DispType         CmControlProtocolDispType,
    cmFlowPointCpdProfileMac08DispType         CmControlProtocolDispType,
    cmFlowPointCpdProfileMac09DispType         CmControlProtocolDispType,
    cmFlowPointCpdProfileMac0ADispType         CmControlProtocolDispType,
    cmFlowPointCpdProfileMac0BDispType         CmControlProtocolDispType,
    cmFlowPointCpdProfileMac0CDispType         CmControlProtocolDispType,
    cmFlowPointCpdProfileMac0DDispType         CmControlProtocolDispType,
    cmFlowPointCpdProfileMac0EDispType         CmControlProtocolDispType,
    cmFlowPointCpdProfileMac0FDispType         CmControlProtocolDispType,
    cmFlowPointCpdProfileNearestLLDPDispType   CmControlProtocolDispType,
    cmFlowPointCpdProfileNonTpmrLLDPDispType   CmControlProtocolDispType,
    cmFlowPointCpdProfileCustomerLLDPDispType  CmControlProtocolDispType,
    cmFlowPointCpdProfileELMIDispType          CmControlProtocolDispType
}

cmFlowPointCpdProfileIndex OBJECT-TYPE
    SYNTAX      Integer32 (1..65535)
    MAX-ACCESS  read-only
    STATUS      current
    DESCRIPTION
        "Unique Index value to access the CPD profile row."
    ::= { cmFlowPointCpdProfileEntry 1 }
    
cmFlowPointCpdProfileName OBJECT-TYPE
    SYNTAX   DisplayString (SIZE (0..64))
    MAX-ACCESS read-write
    STATUS   current
    DESCRIPTION
       "This object describes the alias of the cpd V3 profile entry."
    ::= { cmFlowPointCpdProfileEntry 2 }
cmFlowPointCpdProfileCiscoGroupDispType OBJECT-TYPE
    SYNTAX      CmControlProtocolDispType 
    MAX-ACCESS  read-write
    STATUS      deprecated
    DESCRIPTION
        "Deprecated - each Cisco protocol has its own disposition.
         Control Protocol Disposition for Cisco Group.  This includes
         ISL, PAGP, UDLD, CDP, VTP, DTP, PSVTP+, UplinkFast, VLAN Bridge,
         L2PT.  Note that a specific protocol filter overrides the
         group setting."
    ::= { cmFlowPointCpdProfileEntry 3 }

cmFlowPointCpdProfileIslDispType OBJECT-TYPE
    SYNTAX      CmControlProtocolDispType 
    MAX-ACCESS  read-write
    STATUS      current
    DESCRIPTION
        "Control Protocol Disposition for ISL (Inter Switch Link).
         MAC Address (01:00:0C:00:00:00)."
    ::= { cmFlowPointCpdProfileEntry 4 }

cmFlowPointCpdProfilePagpDispType OBJECT-TYPE
    SYNTAX      CmControlProtocolDispType 
    MAX-ACCESS  read-write
    STATUS      current
    DESCRIPTION
        "Control Protocol Disposition for PAGP (Port Aggregation Protocol).
         MAC Address (01:00:0C:CC:CC:CC), Ethertype(0x104)."
    ::= { cmFlowPointCpdProfileEntry 5 }

cmFlowPointCpdProfileUdldDispType OBJECT-TYPE
    SYNTAX      CmControlProtocolDispType 
    MAX-ACCESS  read-write
    STATUS      current
    DESCRIPTION
        "Control Protocol Disposition for UDLD (Unidirectional Link Detection).
         MAC Address (01:00:0C:CC:CC:CC), Ethertype(0x111)."
    ::= { cmFlowPointCpdProfileEntry 6 }

cmFlowPointCpdProfileCdpDispType OBJECT-TYPE
    SYNTAX      CmControlProtocolDispType 
    MAX-ACCESS  read-write
    STATUS      current
    DESCRIPTION
        "Control Protocol Disposition for CDP (Cisco Discovery Protocol).
         MAC Address (01:00:0C:CC:CC:CC), Ethertype(0x2000)."
    ::= { cmFlowPointCpdProfileEntry 7 }

cmFlowPointCpdProfileVtpDispType OBJECT-TYPE
    SYNTAX      CmControlProtocolDispType 
    MAX-ACCESS  read-write
    STATUS      current
    DESCRIPTION
        "Control Protocol Disposition for VTP (VLAN Trunking Protocol).
         MAC Address (01:00:0C:CC:CC:CC), Ethertype(0x2003)."
    ::= { cmFlowPointCpdProfileEntry 8 }

cmFlowPointCpdProfileDtpDispType OBJECT-TYPE
    SYNTAX      CmControlProtocolDispType 
    MAX-ACCESS  read-write
    STATUS      current
    DESCRIPTION
        "Control Protocol Disposition for DTP (Dynamic Trunking).
         MAC Address (01:00:0C:CC:CC:CC), Ethertype(0x2004)."
    ::= { cmFlowPointCpdProfileEntry 9 }

cmFlowPointCpdProfilePvstpPlusDispType OBJECT-TYPE
    SYNTAX      CmControlProtocolDispType 
    MAX-ACCESS  read-write
    STATUS      current
    DESCRIPTION
        "Control Protocol Disposition for Spanning Tree PVSTP+.
         MAC Address (01:00:0C:CC:CC:CC), Ethertype(0x10B)."
    ::= { cmFlowPointCpdProfileEntry 10 }

cmFlowPointCpdProfileUplinkFastDispType OBJECT-TYPE
    SYNTAX      CmControlProtocolDispType 
    MAX-ACCESS  read-write
    STATUS      current
    DESCRIPTION
        "Control Protocol Disposition for STP UplinkFast.
         MAC Address (01:00:0C:CD:CD:CD), Ethertype(0x200A)."
    ::= { cmFlowPointCpdProfileEntry 11 }

cmFlowPointCpdProfileVlanBridgeDispType OBJECT-TYPE
    SYNTAX      CmControlProtocolDispType 
    MAX-ACCESS  read-write
    STATUS      current
    DESCRIPTION
        "Control Protocol Disposition for VLAN Bridge.
         MAC Address (01:00:0C:CD:CD:CE), Ethertype(0x10C)."
    ::= { cmFlowPointCpdProfileEntry 12 }

cmFlowPointCpdProfileL2PTDispType OBJECT-TYPE
    SYNTAX      CmControlProtocolDispType 
    MAX-ACCESS  read-write
    STATUS      current
    DESCRIPTION
        "Control Protocol Disposition for Layer 2 Protocol Tunnelling(L2PT).
         MAC Address (01:00:0C:CD:CD:D0)."
    ::= { cmFlowPointCpdProfileEntry 13 }

cmFlowPointCpdProfileBridgeGroupDispType OBJECT-TYPE
    SYNTAX      CmControlProtocolDispType 
    MAX-ACCESS  read-write
    STATUS      deprecated
    DESCRIPTION
        "Deprecated - individual dispositions available for each MAC.
         Bridge Group Control Protocol Disposition Type.  This
         includes BPDU, PAUSE (IEEE 802.3x Flow Control), 
         LACP (Link Aggregation), LACP Marker (Marker), 
         EFM OAM (IEEE 802.3 ah) and IEEE 802.1x Port Authentication, 
         besides reserved MAC addresses from 
         01:80:C2:00:00:04 thru 01:80:C2:00:00:0F."
    ::= { cmFlowPointCpdProfileEntry 14 }

cmFlowPointCpdProfileBPDUDispType OBJECT-TYPE
    SYNTAX      CmControlProtocolDispType 
    MAX-ACCESS  read-write
    STATUS      current
    DESCRIPTION
        "Control Protocol Disposition for IEEE Spanning Tree(STP),
         MSTP (Multiple Spanning Tree) and RSTP (Rapid Reconfiguration of
         Spanning Tree). MAC Address (01:80:C2:00:00:00)."
    ::= { cmFlowPointCpdProfileEntry 15 }

cmFlowPointCpdProfilePauseDispType OBJECT-TYPE
    SYNTAX      CmControlProtocolDispType 
    MAX-ACCESS  read-write
    STATUS      current
    DESCRIPTION
        "Control Protocol Disposition for IEEE 802.3x Flow Control 
         (PAUSE frames)."
    ::= { cmFlowPointCpdProfileEntry 16 }

cmFlowPointCpdProfileLACPDispType OBJECT-TYPE
    SYNTAX      CmControlProtocolDispType 
    MAX-ACCESS  read-write
    STATUS      current
    DESCRIPTION
        "Control Protocol Disposition for 802.3ad Link Aggregation
         Protocol.
         MAC Address (01:80:C2:00:00:03), Ethertype (0x8809), Subtype(01)."
    ::= { cmFlowPointCpdProfileEntry 17 }

cmFlowPointCpdProfileLACPMarkerDispType OBJECT-TYPE
    SYNTAX      CmControlProtocolDispType 
    MAX-ACCESS  read-write
    STATUS      current
    DESCRIPTION
        "Control Protocol Disposition for IEEE 802.3ad Marker Protocol.
         MAC Address (01:80:C2:00:00:03), Ethertype (0x8809), Subtype(02)."
    ::= { cmFlowPointCpdProfileEntry 18 }

cmFlowPointCpdProfileEfmOamDispType OBJECT-TYPE
    SYNTAX      CmControlProtocolDispType 
    MAX-ACCESS  read-write
    STATUS      current
    DESCRIPTION
        "Control Protocol Disposition for IEEE 802.3ah EFM OAM.
         MAC Address (01:80:C2:00:00:03), Ethertype (0x8809), Subtype(03)."
    ::= { cmFlowPointCpdProfileEntry 19 }

cmFlowPointCpdProfileSSMDispType OBJECT-TYPE
    SYNTAX      CmControlProtocolDispType 
    MAX-ACCESS  read-write
    STATUS      current
    DESCRIPTION
        "Control Protocol Disposition for Sync Status Messages.
         MAC Address (01:80:C2:00:00:02), Ethertype (0x19A7), Subtype(0A)."
    ::= { cmFlowPointCpdProfileEntry 20 }

cmFlowPointCpdProfilePortAuthenDispType OBJECT-TYPE
    SYNTAX      CmControlProtocolDispType 
    MAX-ACCESS  read-write
    STATUS      current
    DESCRIPTION
        "Control Protocol Disposition for IEEE 802.1x Protocol.
         MAC Address (01:80:C2:00:00:03), Ethertype (0x888E)."
    ::= { cmFlowPointCpdProfileEntry 21 }

cmFlowPointCpdProfileBridgeReservedDispType OBJECT-TYPE
    SYNTAX      CmControlProtocolDispType 
    MAX-ACCESS  read-write
    STATUS      deprecated
    DESCRIPTION
        "Deprecated - individual dispositions available for each MAC.
         Control Protocol Disposition for Range of MAC Addresses
         from 01:80:C2:00:00:04 to 01:80:C2:00:00:0F."
    ::= { cmFlowPointCpdProfileEntry 22 }
    
cmFlowPointCpdProfileLANBridgesDispType OBJECT-TYPE
    SYNTAX      CmControlProtocolDispType 
    MAX-ACCESS  read-write
    STATUS      current
    DESCRIPTION
        "Control Protocol Disposition for IEEE 802.1d LAN Bridge Managment.
         MAC Address (01:80:C2:00:00:10)."
    ::= { cmFlowPointCpdProfileEntry 23 }

cmFlowPointCpdProfileGARPGroupDispType OBJECT-TYPE
    SYNTAX      CmControlProtocolDispType 
    MAX-ACCESS  read-write
    STATUS      deprecated
    DESCRIPTION
        "Deprecated - each GARP Group protocol has its own disposition.
         Group Disposition type which includes GMRP, GVRP and
         MAC Address from range 01:80:C2:00:00:22 to 01:80:C2:00:00:2F."
    ::= { cmFlowPointCpdProfileEntry 24 }

cmFlowPointCpdProfileGMRPDispType OBJECT-TYPE
    SYNTAX      CmControlProtocolDispType 
    MAX-ACCESS  read-write
    STATUS      current
    DESCRIPTION
        "Control Protocol Disposition for GARP Multicast Registration
         Protocol. MAC Address (01:80:C2:00:00:20)."
    ::= { cmFlowPointCpdProfileEntry 25 }

cmFlowPointCpdProfileGVRPDispType OBJECT-TYPE
    SYNTAX      CmControlProtocolDispType 
    MAX-ACCESS  read-write
    STATUS      current
    DESCRIPTION
        "Control Protocol Disposition for GARP VLAN Registration
         Protocol. MAC Address (01:80:C2:00:00:22)."
    ::= { cmFlowPointCpdProfileEntry 26 }

cmFlowPointCpdProfileGARPDispType OBJECT-TYPE 
    SYNTAX      CmControlProtocolDispType 
    MAX-ACCESS  read-write     
    STATUS      current     
    DESCRIPTION     
        "Group Disposition type which includes GMRP, GVRP and
         MAC Address from range 01:80:C2:00:00:20 to 01:80:C2:00:00:2F."
    ::= { cmFlowPointCpdProfileEntry 27 }     

cmFlowPointCpdProfileLldpDispType OBJECT-TYPE 
    SYNTAX      CmControlProtocolDispType 
    MAX-ACCESS  read-write     
    STATUS      deprecated     
    DESCRIPTION     
        "Deprecated - each LLDP MAC protocol has its own disposition.
         Control Protocol Disposition for LLDP."
    ::= { cmFlowPointCpdProfileEntry 28 }

cmFlowPointCpdProfileStorageType OBJECT-TYPE
    SYNTAX     StorageType
    MAX-ACCESS read-create
    STATUS     current
    DESCRIPTION
            "The type of storage configured for this entry."
    ::= { cmFlowPointCpdProfileEntry 29 }
    
cmFlowPointCpdProfileRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmCpdProfileRowStatus supported are
            createAndGo(4) and destroy(6).  All mandatory attributes
            must be specified in a single SNMP SET request with
            cmCpdProfileRowStatus value as createAndGo(4).
            Upon successful row creation, this object has a
            value of active(1).

            The cmCpdProfileRowStatus object may be modified if
            the associated instance of this object is equal to active(1)."
    ::= { cmFlowPointCpdProfileEntry 30 }

cmFlowPointCpdProfileMac00DispType OBJECT-TYPE
    SYNTAX      CmControlProtocolDispType 
    MAX-ACCESS  read-write
    STATUS      current
    DESCRIPTION
        "MAC Address 01:80:C2:00:00:00 Disposition type."
    ::= { cmFlowPointCpdProfileEntry 31 }

cmFlowPointCpdProfileMac01DispType OBJECT-TYPE
    SYNTAX      CmControlProtocolDispType 
    MAX-ACCESS  read-write
    STATUS      current
    DESCRIPTION
        "MAC Address 01:80:C2:00:00:01 Disposition type."
    ::= { cmFlowPointCpdProfileEntry 32 }

cmFlowPointCpdProfileMac02DispType OBJECT-TYPE
    SYNTAX      CmControlProtocolDispType 
    MAX-ACCESS  read-write
    STATUS      current
    DESCRIPTION
        "MAC Address 01:80:C2:00:00:02 Disposition type."
    ::= { cmFlowPointCpdProfileEntry 33 }

cmFlowPointCpdProfileMac03DispType OBJECT-TYPE
    SYNTAX      CmControlProtocolDispType 
    MAX-ACCESS  read-write
    STATUS      current
    DESCRIPTION
        "MAC Address 01:80:C2:00:00:03 Disposition type."
    ::= { cmFlowPointCpdProfileEntry 34 }

cmFlowPointCpdProfileMac04DispType OBJECT-TYPE
    SYNTAX      CmControlProtocolDispType 
    MAX-ACCESS  read-write
    STATUS      current
    DESCRIPTION
        "MAC Address 01:80:C2:00:00:04 Disposition type."
    ::= { cmFlowPointCpdProfileEntry 35 }

cmFlowPointCpdProfileMac05DispType OBJECT-TYPE
    SYNTAX      CmControlProtocolDispType 
    MAX-ACCESS  read-write
    STATUS      current
    DESCRIPTION
        "MAC Address 01:80:C2:00:00:05 Disposition type."
    ::= { cmFlowPointCpdProfileEntry 36 }

cmFlowPointCpdProfileMac06DispType OBJECT-TYPE
    SYNTAX      CmControlProtocolDispType 
    MAX-ACCESS  read-write
    STATUS      current
    DESCRIPTION
        "MAC Address 01:80:C2:00:00:06 Disposition type."
    ::= { cmFlowPointCpdProfileEntry 37 }

cmFlowPointCpdProfileMac07DispType OBJECT-TYPE
    SYNTAX      CmControlProtocolDispType 
    MAX-ACCESS  read-write
    STATUS      current
    DESCRIPTION
        "MAC Address 01:80:C2:00:00:07 Disposition type."
    ::= { cmFlowPointCpdProfileEntry 38 }

cmFlowPointCpdProfileMac08DispType OBJECT-TYPE
    SYNTAX      CmControlProtocolDispType 
    MAX-ACCESS  read-write
    STATUS      current
    DESCRIPTION
        "MAC Address 01:80:C2:00:00:08 Disposition type."
    ::= { cmFlowPointCpdProfileEntry 39 }

cmFlowPointCpdProfileMac09DispType OBJECT-TYPE
    SYNTAX      CmControlProtocolDispType 
    MAX-ACCESS  read-write
    STATUS      current
    DESCRIPTION
        "MAC Address 01:80:C2:00:00:09 Disposition type."
    ::= { cmFlowPointCpdProfileEntry 40 }

cmFlowPointCpdProfileMac0ADispType OBJECT-TYPE
    SYNTAX      CmControlProtocolDispType 
    MAX-ACCESS  read-write
    STATUS      current
    DESCRIPTION
        "MAC Address 01:80:C2:00:00:0A Disposition type."
    ::= { cmFlowPointCpdProfileEntry 41 }

cmFlowPointCpdProfileMac0BDispType OBJECT-TYPE
    SYNTAX      CmControlProtocolDispType 
    MAX-ACCESS  read-write
    STATUS      current
    DESCRIPTION
        "MAC Address 01:80:C2:00:00:0B Disposition type."
    ::= { cmFlowPointCpdProfileEntry 42 }

cmFlowPointCpdProfileMac0CDispType OBJECT-TYPE
    SYNTAX      CmControlProtocolDispType 
    MAX-ACCESS  read-write
    STATUS      current
    DESCRIPTION
        "MAC Address 01:80:C2:00:00:0C Disposition type."
    ::= { cmFlowPointCpdProfileEntry 43 }

cmFlowPointCpdProfileMac0DDispType OBJECT-TYPE
    SYNTAX      CmControlProtocolDispType 
    MAX-ACCESS  read-write
    STATUS      current
    DESCRIPTION
        "MAC Address 01:80:C2:00:00:0D Disposition type."
    ::= { cmFlowPointCpdProfileEntry 44 }

cmFlowPointCpdProfileMac0EDispType OBJECT-TYPE
    SYNTAX      CmControlProtocolDispType 
    MAX-ACCESS  read-write
    STATUS      current
    DESCRIPTION
        "MAC Address 01:80:C2:00:00:0E Disposition type."
    ::= { cmFlowPointCpdProfileEntry 45 }

cmFlowPointCpdProfileMac0FDispType OBJECT-TYPE
    SYNTAX      CmControlProtocolDispType 
    MAX-ACCESS  read-write
    STATUS      current
    DESCRIPTION
        "MAC Address 01:80:C2:00:00:0F Disposition type."
    ::= { cmFlowPointCpdProfileEntry 46 }

cmFlowPointCpdProfileNearestLLDPDispType OBJECT-TYPE
    SYNTAX      CmControlProtocolDispType 
    MAX-ACCESS  read-write
    STATUS      current
    DESCRIPTION
        "The nearest lldp Disposition type."
    ::= { cmFlowPointCpdProfileEntry 47 }

cmFlowPointCpdProfileNonTpmrLLDPDispType OBJECT-TYPE
    SYNTAX      CmControlProtocolDispType 
    MAX-ACCESS  read-write
    STATUS      current
    DESCRIPTION
        "The non tp mr lldp Disposition type."
    ::= { cmFlowPointCpdProfileEntry 48 }

cmFlowPointCpdProfileCustomerLLDPDispType OBJECT-TYPE
    SYNTAX      CmControlProtocolDispType 
    MAX-ACCESS  read-write
    STATUS      current
    DESCRIPTION
        "The customer lldp Disposition type."
    ::= { cmFlowPointCpdProfileEntry 49 }

cmFlowPointCpdProfileELMIDispType OBJECT-TYPE
    SYNTAX      CmControlProtocolDispType 
    MAX-ACCESS  read-write
    STATUS      current
    DESCRIPTION
        "The ELMI Disposition type."
    ::= { cmFlowPointCpdProfileEntry 50 }

--
--  Ethernet Agg Port CPD Table
--
cmEthernetTrafficPortCpdTable OBJECT-TYPE
    SYNTAX      SEQUENCE OF CmEthernetTrafficPortCpdEntry
    MAX-ACCESS  not-accessible
    STATUS      current
    DESCRIPTION
            "A list of entries corresponding to Ethernet Port 
             CPD for configuration purposes."
    ::= { cmFacilityObjects 35 }

cmEthernetTrafficPortCpdEntry OBJECT-TYPE
    SYNTAX      CmEthernetTrafficPortCpdEntry 
    MAX-ACCESS  not-accessible
    STATUS      current
    DESCRIPTION
            "A conceptual row in the cmEthernetTrafficPortCpdTable."
    INDEX { neIndex, shelfIndex, slotIndex, cmEthernetTrafficPortIndex, cmEthernetTrafficPortCpdIndex }
    ::= { cmEthernetTrafficPortCpdTable 1 }

CmEthernetTrafficPortCpdEntry ::= SEQUENCE {
    -- Port Indices 
    cmEthernetTrafficPortCpdIndex                  Integer32,
    cmEthernetTrafficPortAssociatedCpdProfile VariablePointer
}

cmEthernetTrafficPortCpdIndex OBJECT-TYPE
    SYNTAX      Integer32 (1..65535)
    MAX-ACCESS  read-only
    STATUS      current
    DESCRIPTION
         "An arbitrary integer index value used to uniquely identify this CPD Service Entry."
    ::= { cmEthernetTrafficPortCpdEntry 1 }

cmEthernetTrafficPortAssociatedCpdProfile OBJECT-TYPE
    SYNTAX      VariablePointer
    MAX-ACCESS  read-write
    STATUS      current
    DESCRIPTION
         "An integer index value used to apply cmCpdProfile configure, corresponding to cmCpdProfileIndex." 
    ::= { cmEthernetTrafficPortCpdEntry 2 }

--
--  Ethernet Flow Point CPD Table
--
cmEthernetFlowPointCpdTable OBJECT-TYPE
    SYNTAX      SEQUENCE OF CmEthernetFlowPointCpdEntry
    MAX-ACCESS  not-accessible
    STATUS      current
    DESCRIPTION
            "A list of entries corresponding to Ethernet Flow Point 
             CPD for configuration purposes."
    ::= { cmFacilityObjects 36 }

cmEthernetFlowPointCpdEntry OBJECT-TYPE
    SYNTAX      CmEthernetFlowPointCpdEntry 
    MAX-ACCESS  not-accessible
    STATUS      current
    DESCRIPTION
            "A conceptual row in the cmEthernetFlowPointCpdTable."
    INDEX { neIndex, shelfIndex, slotIndex, cmEthernetTrafficPortIndex, cmFlowPointIndex, cmEthernetFlowPointCpdIndex }
    ::= { cmEthernetFlowPointCpdTable 1 }

CmEthernetFlowPointCpdEntry ::= SEQUENCE {
    -- Port Indices 
    cmEthernetFlowPointCpdIndex                  Integer32,
    cmEthernetFlowPointAssociatedCpdProfile      VariablePointer
}

cmEthernetFlowPointCpdIndex OBJECT-TYPE
    SYNTAX      Integer32 (1..65535)
    MAX-ACCESS  read-only
    STATUS      current
    DESCRIPTION
         "An arbitrary integer index value used to uniquely identify this CPD Service Entry."
    ::= { cmEthernetFlowPointCpdEntry 1 }

cmEthernetFlowPointAssociatedCpdProfile OBJECT-TYPE
    SYNTAX      VariablePointer
    MAX-ACCESS  read-write
    STATUS      current
    DESCRIPTION
         "An integer index value used to apply cmCpdProfile configure, corresponding to cmCpdProfileIndex." 
    ::= { cmEthernetFlowPointCpdEntry 2 }


-- Traffic ACL Profile Table
cmTrafficAclProfileTable OBJECT-TYPE
    SYNTAX     SEQUENCE OF CmTrafficAclProfileEntry
    MAX-ACCESS not-accessible
    STATUS     current
    DESCRIPTION
            "A list of entries corresponding to the Traffic Profile Rules Entry. 
             It provides upto 4000 Traffic ACL Rules to be configured."
    ::= { cmFacilityObjects 37 }

cmTrafficAclProfileEntry OBJECT-TYPE
    SYNTAX     CmTrafficAclProfileEntry
    MAX-ACCESS not-accessible
    STATUS     current
    DESCRIPTION
            "An entry containing information applicable to a system ACL Profile that can be configured."
    INDEX { cmTrafficAclProfileIndex }
    ::= { cmTrafficAclProfileTable 1 }

CmTrafficAclProfileEntry ::= SEQUENCE {
    cmTrafficAclProfileIndex            Integer32,
    cmTrafficAclProfileName             DisplayString,
    cmTrafficAclProfileStorageType      StorageType,
    cmTrafficAclProfileRowStatus        RowStatus
    }

cmTrafficAclProfileIndex OBJECT-TYPE
    SYNTAX      Integer32 (1..65535)
    MAX-ACCESS  read-create
    STATUS      current
    DESCRIPTION
            "An arbitrary integer index value used to uniquely identify
             Traffic ACL profile entry."
    ::= { cmTrafficAclProfileEntry 1 }
    
cmTrafficAclProfileName OBJECT-TYPE
    SYNTAX   DisplayString (SIZE (0..64))
    MAX-ACCESS read-write
    STATUS   current
    DESCRIPTION
       "This object describes the alias of the Acl profile entry."
    ::= { cmTrafficAclProfileEntry 2 }

cmTrafficAclProfileStorageType OBJECT-TYPE
    SYNTAX     StorageType
    MAX-ACCESS read-create
    STATUS     current
    DESCRIPTION
            "The type of storage configured for this entry."
    ::= { cmTrafficAclProfileEntry 3 }
    
cmTrafficAclProfileRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmTrafficAclProfileRowStatus supported are
            createAndGo(4) and destroy(6).  All mandatory attributes
            must be specified in a single SNMP SET request with
            cmTrafficAclProfileRowStatus value as createAndGo(4).
            Upon successful row creation, this object has a
            value of active(1).

            The cmTrafficAclProfileRowStatus object may be modified if
            the associated instance of this object is equal to active(1)."
    ::= { cmTrafficAclProfileEntry 4 }

-- Traffic ACL Rules Table
cmTrafficAclRulesTable OBJECT-TYPE
    SYNTAX     SEQUENCE OF CmTrafficAclRulesEntry
    MAX-ACCESS not-accessible
    STATUS     current
    DESCRIPTION
            "A list of entries corresponding to the Traffic ACL Rules Entry."
    ::= { cmFacilityObjects 38 }

cmTrafficAclRulesEntry OBJECT-TYPE
    SYNTAX     CmTrafficAclRulesEntry
    MAX-ACCESS not-accessible
    STATUS     current
    DESCRIPTION
            "An entry containing information applicable to a system ACL Rules that can be configured."
    INDEX { cmTrafficAclProfileIndex, cmTrafficAclRulesIndex }
    ::= { cmTrafficAclRulesTable 1 }

CmTrafficAclRulesEntry ::= SEQUENCE {
    cmTrafficAclRulesIndex              Integer32,
    cmTrafficAclFilterAction            CmTrafficAclFilterActionType,
    cmTrafficAclFilterType              CmTrafficAclFilterType,
    cmTrafficAclEnabled                 TruthValue,
    cmTrafficAclSrcMacAddr              MacAddress,
    cmTrafficAclSrcMacAddrEnabled       TruthValue,
    cmTrafficAclDstMacAddr              MacAddress,
    cmTrafficAclDstMacAddrEnabled       TruthValue,
    cmTrafficAclSrcIpFilterEnabled      TruthValue,
    cmTrafficAclDstIpFilterEnabled      TruthValue,
    cmTrafficAclSrcIpV4Addr             IpAddress,
    cmTrafficAclSrcIpV4AddrMask         IpAddress,
    cmTrafficAclDstIpV4Addr             IpAddress,
    cmTrafficAclDstIpV4AddrMask         IpAddress,
    cmTrafficAclSrcIpV6Addr             Ipv6Address,
    cmTrafficAclSrcIpV6AddrMask         Ipv6Address,
    cmTrafficAclDstIpV6Addr             Ipv6Address,
    cmTrafficAclDstIpV6AddrMask         Ipv6Address,
    cmTrafficAclTcpUdpSrcPortNum        Integer32,
    cmTrafficAclTcpUdpSrcPortMask       Integer32,
    cmTrafficAclTcpUdpSrcPortEnabled    TruthValue,
    cmTrafficAclTcpUdpDstPortNum        Integer32,
    cmTrafficAclTcpUdpDstPortMask       Integer32,
    cmTrafficAclTcpUdpDstPortEnabled    TruthValue,
    cmTrafficAclIpQosType               CmTrafficACLPriorityType,
    cmTrafficAclIpQosValue              Integer32,
    cmTrafficAclIpQosTypeEnabled        TruthValue,
    cmTrafficAclVlanId                  VlanId,
    cmTrafficAclVlanIdEnabled           TruthValue,
    cmTrafficAclVlanPriority            Integer32,
    cmTrafficAclVlanPriorityEnabled     TruthValue,
    cmTrafficAclProtocolType            CmTrafficAclProtocolType,
    cmTrafficAclProtocolTypeEnabled     TruthValue,
    cmTrafficAclStorageType             StorageType,
    cmTrafficAclRowStatus               RowStatus
}

cmTrafficAclRulesIndex OBJECT-TYPE
    SYNTAX      Integer32 (1..65535)
    MAX-ACCESS  read-create
    STATUS      current
    DESCRIPTION
            "An arbitrary integer index value used to uniquely identify
             Traffic ACL profile entry. The manager may not assume any
             particular semantics or meaning to this index, except that
             it identifies a logical row in the table."
    ::= { cmTrafficAclRulesEntry 1 }
    
cmTrafficAclFilterAction OBJECT-TYPE
    SYNTAX   CmTrafficAclFilterActionType 
    MAX-ACCESS read-write
    STATUS   current
    DESCRIPTION
       "Currently,  'permit' and 'deny' are supported."
    ::= { cmTrafficAclRulesEntry 2 }

cmTrafficAclFilterType OBJECT-TYPE
    SYNTAX   CmTrafficAclFilterType 
    MAX-ACCESS read-write
    STATUS   current
    DESCRIPTION
       "This object describes the Acl filter type."
    ::= { cmTrafficAclRulesEntry 3 }
cmTrafficAclEnabled OBJECT-TYPE
    SYNTAX   TruthValue 
    MAX-ACCESS read-write
    STATUS   current
    DESCRIPTION
       "This object enables/disables the Acl entity."
    ::= { cmTrafficAclRulesEntry 4 }

cmTrafficAclSrcMacAddr OBJECT-TYPE
    SYNTAX   MacAddress 
    MAX-ACCESS read-write
    STATUS   current
    DESCRIPTION
       "The source mac address of Acl entry."
    ::= { cmTrafficAclRulesEntry 5 }

cmTrafficAclSrcMacAddrEnabled OBJECT-TYPE
    SYNTAX   TruthValue 
    MAX-ACCESS read-write
    STATUS   current
    DESCRIPTION
       "This object enables/disables source MAC address of Acl entry."
    ::= { cmTrafficAclRulesEntry 6 }

cmTrafficAclDstMacAddr OBJECT-TYPE
    SYNTAX   MacAddress 
    MAX-ACCESS read-write
    STATUS   current
    DESCRIPTION
       "The destination MAC address of Acl entry."
    ::= { cmTrafficAclRulesEntry 7 }

cmTrafficAclDstMacAddrEnabled OBJECT-TYPE
    SYNTAX   TruthValue 
    MAX-ACCESS read-write
    STATUS   current
    DESCRIPTION
       "This object enables/disables destination MAC address  of Acl entry."
    ::= { cmTrafficAclRulesEntry 8 }

cmTrafficAclSrcIpFilterEnabled OBJECT-TYPE
    SYNTAX   TruthValue 
    MAX-ACCESS read-write
    STATUS   current
    DESCRIPTION
       "This object enable/disable Source IPV4 or IPV6 address filter criteria."
    ::= { cmTrafficAclRulesEntry 9 }

cmTrafficAclDstIpFilterEnabled OBJECT-TYPE
    SYNTAX   TruthValue 
    MAX-ACCESS read-write
    STATUS   current
    DESCRIPTION
       "This object enable/disable Destination IPV4 or IPV6 address filter criteria."
    ::= { cmTrafficAclRulesEntry 10 }

cmTrafficAclSrcIpV4Addr OBJECT-TYPE
    SYNTAX   IpAddress 
    MAX-ACCESS read-write
    STATUS   current
    DESCRIPTION
       "The source IP address of Acl entry."
    ::= { cmTrafficAclRulesEntry 11 }

cmTrafficAclSrcIpV4AddrMask OBJECT-TYPE
    SYNTAX   IpAddress 
    MAX-ACCESS read-write
    STATUS   current
    DESCRIPTION
       "The source IP mask of Acl entry."
    ::= { cmTrafficAclRulesEntry 12 }

cmTrafficAclDstIpV4Addr OBJECT-TYPE
    SYNTAX   IpAddress 
    MAX-ACCESS read-write
    STATUS   current
    DESCRIPTION
       "The destination IP address of Acl entry."
    ::= { cmTrafficAclRulesEntry 13 }

cmTrafficAclDstIpV4AddrMask OBJECT-TYPE
    SYNTAX   IpAddress 
    MAX-ACCESS read-write
    STATUS   current
    DESCRIPTION
       "The destination IP mask of Acl entry."
    ::= { cmTrafficAclRulesEntry 14 }

cmTrafficAclSrcIpV6Addr OBJECT-TYPE
    SYNTAX   Ipv6Address 
    MAX-ACCESS read-write
    STATUS   current
    DESCRIPTION
       "The source IPV6 address of Acl entry."
    ::= { cmTrafficAclRulesEntry 15 }

cmTrafficAclSrcIpV6AddrMask OBJECT-TYPE
    SYNTAX   Ipv6Address 
    MAX-ACCESS read-write
    STATUS   current
    DESCRIPTION
       "The source IPV6 mask of Acl entry."
    ::= { cmTrafficAclRulesEntry 16 }

cmTrafficAclDstIpV6Addr OBJECT-TYPE
    SYNTAX   Ipv6Address 
    MAX-ACCESS read-write
    STATUS   current
    DESCRIPTION
       "The destination IPV6 address of Acl entry."
    ::= { cmTrafficAclRulesEntry 17 }

cmTrafficAclDstIpV6AddrMask OBJECT-TYPE
    SYNTAX   Ipv6Address 
    MAX-ACCESS read-write
    STATUS   current
    DESCRIPTION
       "The destination IPV6 mask of Acl entry."
    ::= { cmTrafficAclRulesEntry 18 }

cmTrafficAclTcpUdpSrcPortNum OBJECT-TYPE
    SYNTAX   Integer32 (0..65535)
    MAX-ACCESS read-write
    STATUS   current
    DESCRIPTION
       "This object describes TCP/UDP minimum source port number of Acl entry."
    ::= { cmTrafficAclRulesEntry 19 }

cmTrafficAclTcpUdpSrcPortMask OBJECT-TYPE
    SYNTAX   Integer32 (0..65535)
    MAX-ACCESS read-write
    STATUS   current
    DESCRIPTION
       "This object describes TCP/UDP maximum source port number of Acl entry."
    ::= { cmTrafficAclRulesEntry 20 }

cmTrafficAclTcpUdpSrcPortEnabled OBJECT-TYPE
    SYNTAX   TruthValue
    MAX-ACCESS read-write
    STATUS   current
    DESCRIPTION
       "This object enables/disables TCP/UDP source port of Acl entry."
    ::= { cmTrafficAclRulesEntry 21 }

cmTrafficAclTcpUdpDstPortNum OBJECT-TYPE
    SYNTAX   Integer32 (0..65535)
    MAX-ACCESS read-write
    STATUS   current
    DESCRIPTION
       "This object describes TCP/UDP minimum destination port number of Acl entry."
    ::= { cmTrafficAclRulesEntry 22 }

cmTrafficAclTcpUdpDstPortMask OBJECT-TYPE
    SYNTAX   Integer32 (0..65535)
    MAX-ACCESS read-write
    STATUS   current
    DESCRIPTION
       "This object describes TCP/UDP maximum destination port number of Acl entry."
    ::= { cmTrafficAclRulesEntry 23 }

cmTrafficAclTcpUdpDstPortEnabled OBJECT-TYPE
    SYNTAX   TruthValue
    MAX-ACCESS read-write
    STATUS   current
    DESCRIPTION
       "This object enables/disables TCP/UDP destination port of Acl entry."
    ::= { cmTrafficAclRulesEntry 24 }

cmTrafficAclIpQosType OBJECT-TYPE
    SYNTAX   CmTrafficACLPriorityType
    MAX-ACCESS read-write
    STATUS   current
    DESCRIPTION
       "This object describes QosType Acl entry."
    ::= { cmTrafficAclRulesEntry 25 }

cmTrafficAclIpQosValue OBJECT-TYPE
    SYNTAX   Integer32
    MAX-ACCESS read-write
    STATUS   current
    DESCRIPTION
       "This object describes QOS value of Acl entry."
    ::= { cmTrafficAclRulesEntry 26 }

cmTrafficAclIpQosTypeEnabled OBJECT-TYPE
    SYNTAX   TruthValue
    MAX-ACCESS read-write
    STATUS   current
    DESCRIPTION
       "This object enables/disables qos type of acl entry."
    ::= { cmTrafficAclRulesEntry 27 }

cmTrafficAclVlanId OBJECT-TYPE
    SYNTAX   VlanId
    MAX-ACCESS read-write
    STATUS   current
    DESCRIPTION
       "This object describes the vlan Id of Acl entry."
    ::= { cmTrafficAclRulesEntry 28 }

cmTrafficAclVlanIdEnabled OBJECT-TYPE
    SYNTAX   TruthValue
    MAX-ACCESS read-write
    STATUS   current
    DESCRIPTION
       "This object enables/disables Vlan Id of Acl entry."
    ::= { cmTrafficAclRulesEntry 29 }

cmTrafficAclVlanPriority OBJECT-TYPE
    SYNTAX   Integer32 (0..7)
    MAX-ACCESS read-write
    STATUS   current
    DESCRIPTION
       "This object describes the Vlan Priority of Acl entry."
    ::= { cmTrafficAclRulesEntry 30 }

cmTrafficAclVlanPriorityEnabled OBJECT-TYPE
    SYNTAX   TruthValue
    MAX-ACCESS read-write
    STATUS   current
    DESCRIPTION
       "This object enables/disables Vlan Priority of Acl entry."
    ::= { cmTrafficAclRulesEntry 31 }

cmTrafficAclProtocolType OBJECT-TYPE
    SYNTAX   CmTrafficAclProtocolType
    MAX-ACCESS read-write
    STATUS   current
    DESCRIPTION
       "This object describes protocol type of Acl entry."
    ::= { cmTrafficAclRulesEntry 32 }
    
cmTrafficAclProtocolTypeEnabled OBJECT-TYPE
    SYNTAX   TruthValue
    MAX-ACCESS read-write
    STATUS   current
    DESCRIPTION
       "This object enables/disables protocol type of Acl entry."
    ::= { cmTrafficAclRulesEntry 33 }    

cmTrafficAclStorageType OBJECT-TYPE
    SYNTAX     StorageType
    MAX-ACCESS read-create
    STATUS     current
    DESCRIPTION
            "The type of storage configured for this entry."
    ::= { cmTrafficAclRulesEntry 34 }

cmTrafficAclRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmTrafficAclRowStatus supported are
            createAndGo(4) and destroy(6).  All mandatory attributes
            must be specified in a single SNMP SET request with
            cmTrafficAclRowStatus value as createAndGo(4).
            Upon successful row creation, this object has a
            value of active(1).

            The cmTrafficAclRowStatus object may be modified if
            the associated instance of this object is equal to active(1)."
    ::= { cmTrafficAclRulesEntry 35 }

--Qos Policer V2 Profile
cmQosPolicerProfileTable  OBJECT-TYPE
    SYNTAX      SEQUENCE OF CmQosPolicerProfileEntry
    MAX-ACCESS  not-accessible
    STATUS      current
    DESCRIPTION
        "A list of entries corresponding to Quality of Service 
         Policer for configuration purposes."
    ::= { cmFacilityObjects 39 }

cmQosPolicerProfileEntry OBJECT-TYPE
    SYNTAX      CmQosPolicerProfileEntry 
    MAX-ACCESS  not-accessible
    STATUS      current
    DESCRIPTION
         "A conceptual row in the cmQosPolicerProfileTable. 
          These entries represent a Quality of Service Policer."
    INDEX { cmQosPolicerProfileIndex }
    ::= { cmQosPolicerProfileTable 1 }

CmQosPolicerProfileEntry ::= SEQUENCE {
    cmQosPolicerProfileIndex            Integer32,
    cmQosPolicerProfileName             DisplayString,

    cmQosPolicerProfileCIRLo            Unsigned32,
    cmQosPolicerProfileCIRHi            Unsigned32,
    cmQosPolicerProfileEIRLo            Unsigned32,
    cmQosPolicerProfileEIRHi            Unsigned32,
    cmQosPolicerProfileCBS              Integer32,
    cmQosPolicerProfileEBS              Integer32,
    cmQosPolicerProfileColorMode        PolicerColorMode,
    cmQosPolicerProfileCouplingFlag     TruthValue,
    cmQosPolicerProfileStorageType      StorageType,
    cmQosPolicerProfileRowStatus        RowStatus 
}

cmQosPolicerProfileIndex OBJECT-TYPE
    SYNTAX      Integer32 (1..65535)
    MAX-ACCESS  read-create
    STATUS      current
    DESCRIPTION
            "This object defines the Policer profile ID. Up to 1000 profiles can be specified per system." 
    ::= { cmQosPolicerProfileEntry 1 }

cmQosPolicerProfileName OBJECT-TYPE
    SYNTAX      DisplayString (SIZE (0..64)) 
    MAX-ACCESS  read-create
    STATUS      current
    DESCRIPTION
            "This object defines the alias for this profile"
    ::= { cmQosPolicerProfileEntry 2 }

cmQosPolicerProfileCIRLo OBJECT-TYPE
    SYNTAX     Unsigned32
    MAX-ACCESS read-create
    STATUS     current
    DESCRIPTION
         "This object allows specification of the Commited Information
          Rate(CIR) on Policer Profile.  This represents the lower 32 bits of the
          CIR."
     ::= { cmQosPolicerProfileEntry 3 }

cmQosPolicerProfileCIRHi OBJECT-TYPE
    SYNTAX     Unsigned32
    MAX-ACCESS read-create
    STATUS     current
    DESCRIPTION
         "This object allows specification of the Commited Information
          Rate(CIR) on Policer Profile.  This represents the upper 32 bits of the
          CIR."
     ::= { cmQosPolicerProfileEntry 4 }

cmQosPolicerProfileEIRLo OBJECT-TYPE
    SYNTAX     Unsigned32
    MAX-ACCESS read-create
    STATUS     current
    DESCRIPTION
         "This object allows specification of the Excess Information
          Rate(EIR) on the Policer Profile.  This represents the lower 32 bits
          of the EIR."
     ::= { cmQosPolicerProfileEntry 5 }

cmQosPolicerProfileEIRHi OBJECT-TYPE
    SYNTAX     Unsigned32
    MAX-ACCESS read-create
    STATUS     current
    DESCRIPTION
         "This object allows specification of the Excess Information
          Rate(EIR) on the Policer Profile.  This represents the upper 32 bits
          of the EIR."
     ::= { cmQosPolicerProfileEntry 6 }

cmQosPolicerProfileCBS OBJECT-TYPE
    SYNTAX     Integer32
    MAX-ACCESS read-create
    STATUS     current
    DESCRIPTION
         "This object allows specification of the Commited Burst Size
          (CBS) on Policer Profile."
     ::= { cmQosPolicerProfileEntry 7 }

cmQosPolicerProfileEBS OBJECT-TYPE
    SYNTAX     Integer32
    MAX-ACCESS read-create
    STATUS     current
    DESCRIPTION
         "This object allows specification of the Excess Burst Size
          (EBS) on the Policer Profile."
     ::= { cmQosPolicerProfileEntry 8 }

cmQosPolicerProfileColorMode OBJECT-TYPE
    SYNTAX      PolicerColorMode 
    MAX-ACCESS  read-create
    STATUS      current
    DESCRIPTION
          "This object allows specification of Policer Color Mode as
           'color-aware' or 'color-blind'."
    ::= { cmQosPolicerProfileEntry 9 }

cmQosPolicerProfileCouplingFlag OBJECT-TYPE
    SYNTAX      TruthValue
    MAX-ACCESS  read-create
    STATUS      current
    DESCRIPTION
       "This object allows specification of Policer Coupling Flag.
        When coupling is enabled, tokens that would normally be 
        added to the C-bucket are passed to the E-bucket only once the CIR
        bucket has reached its CBS level. Therefore under this condition
        the E-bucket is being filled at the rate of CIR + EIR. 
        Normally the long term average of frames declared yellow, which is 
        bounded by the EIR. Coupling is a function to allow the 
        long term average of frames declared yellow to be bounded by 
        CIR + EIR. This allows a higher volume of yellow frames 
        to be delivered/received if the arrival of green marked frames 
        is low.  Tokens from the E-bucket do NOT get passed to the 
        C-bucket once the EBS level has been reached.
        Enabling coupling in combination with a provisioned EIR of 0 
        allows for a single rate three color marking (srTCM) algorithm 
        to be established.  In this situation the E-bucket is filled at the 
        CIR rate in the case the C-bucket is filled to its CBS level."
    ::= { cmQosPolicerProfileEntry 10 }

cmQosPolicerProfileStorageType OBJECT-TYPE
    SYNTAX     StorageType
    MAX-ACCESS read-create
    STATUS     current
    DESCRIPTION
            "The type of storage configured for this entry."
    ::= { cmQosPolicerProfileEntry 11 }

cmQosPolicerProfileRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmQosPolicerProfileRowStatus supported are
            createAndGo(4) and destroy(6).  All mandatory attributes
            must be specified in a single SNMP SET request with
            cmQosPolicerProfileRowStatus value as createAndGo(4).
            Upon successful row creation, this object has a
            value of active(1).

            The cmQosPolicerProfileRowStatus object may be modified if
            the associated instance of this object is equal to active(1)."
    ::= { cmQosPolicerProfileEntry 12 }

--Qos Queue Profile
cmQosQueueProfileTable  OBJECT-TYPE
    SYNTAX      SEQUENCE OF CmQosQueueProfileEntry
    MAX-ACCESS  not-accessible
    STATUS      current
    DESCRIPTION
        "A list of entries corresponding to Quality of Service 
         Queue for configuration purposes."
    ::= { cmFacilityObjects 40 }

cmQosQueueProfileEntry OBJECT-TYPE
    SYNTAX      CmQosQueueProfileEntry 
    MAX-ACCESS  not-accessible
    STATUS      current
    DESCRIPTION
         "A conceptual row in the cmQosQueueProfileTable. 
          These entries represent a Quality of Service Queue."
    INDEX { cmQosQueueProfileIndex }
    ::= { cmQosQueueProfileTable 1 }

CmQosQueueProfileEntry ::= SEQUENCE {
    cmQosQueueProfileIndex            Integer32,
    cmQosQueueProfileName            DisplayString,

    cmQosQueueProfileBufferSize       Integer32,
    cmQosQueueProfileREDEnabled       TruthValue,
    cmQosQueueProfileStorageType      StorageType,
    cmQosQueueProfileRowStatus        RowStatus 
}

cmQosQueueProfileIndex OBJECT-TYPE
    SYNTAX      Integer32 (1..64)
    MAX-ACCESS  read-create
    STATUS      current
    DESCRIPTION
            "This object defines the Queue profile ID. Up to 64 profiles can be specified per system." 
    ::= { cmQosQueueProfileEntry 1 }

cmQosQueueProfileName OBJECT-TYPE
    SYNTAX      DisplayString (SIZE (0..64)) 
    MAX-ACCESS  read-create
    STATUS      current
    DESCRIPTION
            "This object defines the alias for this profile"
    ::= { cmQosQueueProfileEntry 2 }

cmQosQueueProfileBufferSize OBJECT-TYPE
    SYNTAX     Integer32
    MAX-ACCESS read-create
    STATUS     current
    DESCRIPTION
         "This object defines the buffer size of the selected queues."
     ::= { cmQosQueueProfileEntry 3 }

cmQosQueueProfileREDEnabled OBJECT-TYPE
    SYNTAX     TruthValue
    MAX-ACCESS read-create
    STATUS     current
    DESCRIPTION
         "This object defines whether the WRED is enabled as congestion algorithm or not.
          If disabled, then the following RED parameters (cmQueueProfileWREDDp0MinTh, 
          cmQueueProfileWREDDp0MaxTh and cmQueueProfileWREDDp0MaxProb) must not be specified."
     ::= { cmQosQueueProfileEntry 4 }

cmQosQueueProfileStorageType OBJECT-TYPE
    SYNTAX     StorageType
    MAX-ACCESS read-create
    STATUS     current
    DESCRIPTION
            "The type of storage configured for this entry."
    ::= { cmQosQueueProfileEntry 5 }

cmQosQueueProfileRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmQosQueueProfileRowStatus supported are
            createAndGo(4) and destroy(6).  All mandatory attributes
            must be specified in a single SNMP SET request with
            cmQosQueueProfileRowStatus value as createAndGo(4).
            Upon successful row creation, this object has a
            value of active(1).

            The cmQosQueueProfileRowStatus object may be modified if
            the associated instance of this object is equal to active(1)."
    ::= { cmQosQueueProfileEntry 6 }    

--FlowPoint Policer
cmQosPolicerV2Table  OBJECT-TYPE
    SYNTAX      SEQUENCE OF CmQosPolicerV2Entry
    MAX-ACCESS  not-accessible
    STATUS      current
    DESCRIPTION
        "A list of entries corresponding to Quality of Service 
         Policer for configuration purposes."
    ::= { cmFacilityObjects 41 }

cmQosPolicerV2Entry OBJECT-TYPE
    SYNTAX      CmQosPolicerV2Entry 
    MAX-ACCESS  not-accessible
    STATUS      current
    DESCRIPTION
         "A conceptual row in the cmQosPolicerV2Table. 
          These entries represent a Quality of Service Policer."
    INDEX { neIndex, shelfIndex, slotIndex, cmEthernetTrafficPortIndex, 
            cmFlowPointIndex, cmQosPolicerV2Index }
    ::= { cmQosPolicerV2Table 1 }

CmQosPolicerV2Entry ::= SEQUENCE {
    cmQosPolicerV2Index         Integer32,

    -- State Management params
    cmQosPolicerV2AdminState          AdminState,
    cmQosPolicerV2OperationalState    OperationalState,
    cmQosPolicerV2SecondaryState      SecondaryState,
    cmQosPolicerV2ColorMarkingEnabled TruthValue,
    cmQosPolicerV2AssociatedProfile   VariablePointer,
    cmQosPolicerV2StorageType         StorageType,
    cmQosPolicerV2RowStatus           RowStatus,
    cmQosPolicerV2PolicingEnabled     TruthValue
}

cmQosPolicerV2Index OBJECT-TYPE
    SYNTAX      Integer32 (1..8)
    MAX-ACCESS  read-create
    STATUS      current
    DESCRIPTION
            "The Policer Index that represents the COS level. Index 1
             represents COS 0; Index 2 represents COS 1 and so on." 
    ::= { cmQosPolicerV2Entry 1 }

-- State Management params
cmQosPolicerV2AdminState OBJECT-TYPE
    SYNTAX      AdminState 
    MAX-ACCESS  read-write
    STATUS      current
    DESCRIPTION
            "This object represents the Administrative State of 
             the QOS Policer." 
    ::= { cmQosPolicerV2Entry 2 }

cmQosPolicerV2OperationalState OBJECT-TYPE
    SYNTAX      OperationalState 
    MAX-ACCESS  read-only
    STATUS      current
    DESCRIPTION
            "This object represents the Operational State of the QOS Policer." 
    ::= { cmQosPolicerV2Entry 3 }

cmQosPolicerV2SecondaryState OBJECT-TYPE
    SYNTAX      SecondaryState 
    MAX-ACCESS  read-only
    STATUS      current
    DESCRIPTION
            "This object represents the Secondary State of the QOS Policer." 
    ::= { cmQosPolicerV2Entry 4 }

cmQosPolicerV2ColorMarkingEnabled OBJECT-TYPE
    SYNTAX      TruthValue 
    MAX-ACCESS  read-only
    STATUS      current
    DESCRIPTION
            "This object indicates the colorMarking state of the QOS Policer." 
    ::= { cmQosPolicerV2Entry 5 }
    
cmQosPolicerV2AssociatedProfile OBJECT-TYPE
    SYNTAX     VariablePointer
    MAX-ACCESS read-create
    STATUS     current
    DESCRIPTION
         "This object define the queue profile ID to be used,
          it is associated with the cmQosPolicerProfileIndex."
     ::= { cmQosPolicerV2Entry 6 }

cmQosPolicerV2StorageType OBJECT-TYPE
    SYNTAX     StorageType
    MAX-ACCESS read-create
    STATUS     current
    DESCRIPTION
            "The type of storage configured for this entry."
    ::= { cmQosPolicerV2Entry 7 }

cmQosPolicerV2RowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmQosPolicerV2RowStatus supported are
            createAndGo(4) and destroy(6).  All mandatory attributes
            must be specified in a single SNMP SET request with
            cmQosPolicerV2RowStatus value as createAndGo(4).
            Upon successful row creation, this object has a
            value of active(1).

            The cmQosPolicerV2RowStatus object may be modified if
            the associated instance of this object is equal to active(1)."
    ::= { cmQosPolicerV2Entry 8 }

cmQosPolicerV2PolicingEnabled OBJECT-TYPE
    SYNTAX      TruthValue 
    MAX-ACCESS  read-write
    STATUS      current
    DESCRIPTION
            "Whether enable or disable the functionality of policing for this COS." 
    ::= { cmQosPolicerV2Entry 9 }

--FlowPoint Queue
cmQosShaperV2Table  OBJECT-TYPE
    SYNTAX      SEQUENCE OF CmQosShaperV2Entry
    MAX-ACCESS  not-accessible
    STATUS      current
    DESCRIPTION
        "A list of entries corresponding to Quality of Service 
         ShaperV2 for configuration purposes."
    ::= { cmFacilityObjects 42 }

cmQosShaperV2Entry OBJECT-TYPE
    SYNTAX      CmQosShaperV2Entry 
    MAX-ACCESS  not-accessible
    STATUS      current
    DESCRIPTION
         "A conceptual row in the cmQosShaperV2Table. 
          These entries represent a Quality of Service Shaper."
    INDEX { neIndex, shelfIndex, slotIndex, cmEthernetTrafficPortIndex, 
            cmFlowPointIndex, cmQosShaperV2Index }
    ::= { cmQosShaperV2Table 1 }

CmQosShaperV2Entry ::= SEQUENCE {
    cmQosShaperV2Index         Integer32,

    -- State Management params
    cmQosShaperV2AdminState         AdminState,
    cmQosShaperV2OperationalState   OperationalState,
    cmQosShaperV2SecondaryState     SecondaryState,
    
    cmQosShaperV2AssociatedQueueProfile  VariablePointer,
    --cmQosShaperV2BufferSize      Integer32,
    cmQosShaperV2CIRLo           Unsigned32,
    cmQosShaperV2CIRHi           Unsigned32,
    cmQosShaperV2EIRLo           Unsigned32,
    cmQosShaperV2EIRHi           Unsigned32,
--    cmQosShaperV2REDEnabled      TruthValue,
    cmQosShaperV2IngressAverageFrameSize Integer32,
    cmQosShaperV2StorageType     StorageType,
    cmQosShaperV2RowStatus       RowStatus,
    cmQosShaperV2AdditionalCIRLo Unsigned32,
    cmQosShaperV2AdditionalCIRHi Unsigned32,
    cmQosShaperV2WFQWeight       Integer32,
    cmQosShaperV2ActualCIR       Counter64,
    cmQosShaperV2ActualEIR       Counter64,
    cmQosShaperV2LowLatencyControl  TruthValue
}

cmQosShaperV2Index OBJECT-TYPE
    SYNTAX      Integer32 (1..8)
    MAX-ACCESS  read-create
    STATUS      current
    DESCRIPTION
            "The ShaperV2 Index that represents the COS level. Index 1
             represents COS 0; Index 2 represents COS 1 and so on." 
    ::= { cmQosShaperV2Entry 1 }

-- State Management params
cmQosShaperV2AdminState OBJECT-TYPE
    SYNTAX      AdminState 
    MAX-ACCESS  read-write
    STATUS      current
    DESCRIPTION
            "This object represents the Administrative State of 
             the QOS Shaper." 
    ::= { cmQosShaperV2Entry 2 }

cmQosShaperV2OperationalState OBJECT-TYPE
    SYNTAX      OperationalState 
    MAX-ACCESS  read-only
    STATUS      current
    DESCRIPTION
            "This object represents the Operational State of the QOS ShaperV2." 
    ::= { cmQosShaperV2Entry 3 }

cmQosShaperV2SecondaryState OBJECT-TYPE
    SYNTAX      SecondaryState 
    MAX-ACCESS  read-only
    STATUS      current
    DESCRIPTION
            "This object represents the Secondary State of the QOS QosShaperV2." 
    ::= { cmQosShaperV2Entry 4 }

cmQosShaperV2AssociatedQueueProfile OBJECT-TYPE
    SYNTAX     VariablePointer
    MAX-ACCESS read-create
    STATUS     current
    DESCRIPTION
         "This object defines the queue profile ID to be used,
          it is associated with the cmQosQueueProfileIndex."
     ::= { cmQosShaperV2Entry 5 }

--cmQosShaperV2BufferSize OBJECT-TYPE
--    SYNTAX     Integer32
--    MAX-ACCESS read-create
--    STATUS     current
--    DESCRIPTION
--         "This object defines the buffer size of ShaperV2."
--     ::= { cmQosShaperV2Entry 6 }

cmQosShaperV2CIRLo OBJECT-TYPE
    SYNTAX     Unsigned32 
    MAX-ACCESS read-write
    STATUS     current
    DESCRIPTION
         "This object specifies the Lower 32 bits of CIR."
     ::= { cmQosShaperV2Entry 6 }
     
cmQosShaperV2CIRHi OBJECT-TYPE
    SYNTAX     Unsigned32 
    MAX-ACCESS read-write
    STATUS     current
    DESCRIPTION
         "This object specifies the Higher 32 bits of CIR."
     ::= { cmQosShaperV2Entry 7 }

cmQosShaperV2EIRLo OBJECT-TYPE
    SYNTAX     Unsigned32 
    MAX-ACCESS read-write
    STATUS     current
    DESCRIPTION
         "This object specifies the Lower 32 bits of EIR."
     ::= { cmQosShaperV2Entry 8 }
     
cmQosShaperV2EIRHi OBJECT-TYPE
    SYNTAX     Unsigned32 
    MAX-ACCESS read-write
    STATUS     current
    DESCRIPTION
         "This object specifies the Higher 32 bits of EIR."
     ::= { cmQosShaperV2Entry 9 }

cmQosShaperV2IngressAverageFrameSize  OBJECT-TYPE
    SYNTAX     Integer32 (64..9600)
    MAX-ACCESS read-create
    STATUS     current
    DESCRIPTION
         "This object defines the average frame size for accounting for Meter/Shaping."
     ::= { cmQosShaperV2Entry 10 }

--cmQosShaperV2REDEnabled OBJECT-TYPE
--    SYNTAX     TruthValue 
--    MAX-ACCESS read-create
--    STATUS     current
--    DESCRIPTION
--         "This object specifies RED of ShaperV2."
--     ::= { cmQosShaperV2Entry 11 }
     
cmQosShaperV2StorageType OBJECT-TYPE
    SYNTAX     StorageType
    MAX-ACCESS read-create
    STATUS     current
    DESCRIPTION
            "The type of storage configured for this entry."
    ::= { cmQosShaperV2Entry 11 }

cmQosShaperV2RowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmQosShaperV2RowStatus supported are
            createAndGo(4) and destroy(6).  All mandatory attributes
            must be specified in a single SNMP SET request with
            cmQosShaperV2RowStatus value as createAndGo(4).
            Upon successful row creation, this object has a
            value of active(1).

            The cmQosShaperV2RowStatus object may be modified if
            the associated instance of this object is equal to active(1)."
    ::= { cmQosShaperV2Entry 12 }

cmQosShaperV2AdditionalCIRLo OBJECT-TYPE
    SYNTAX     Unsigned32 
    MAX-ACCESS read-write
    STATUS     current
    DESCRIPTION
         "This object specifies the Lower 32 bits of additional CIR."
     ::= { cmQosShaperV2Entry 13 }
     
cmQosShaperV2AdditionalCIRHi OBJECT-TYPE
    SYNTAX     Unsigned32 
    MAX-ACCESS read-write
    STATUS     current
    DESCRIPTION
         "This object specifies the Higher 32 bits of additional CIR."
     ::= { cmQosShaperV2Entry 14 }

cmQosShaperV2WFQWeight OBJECT-TYPE
    SYNTAX     Integer32 (1..64) 
    MAX-ACCESS read-write
    STATUS     current
    DESCRIPTION
         "Weight of queue to be scheduled by WFQ mechanism."
     ::= { cmQosShaperV2Entry 15 }

cmQosShaperV2ActualCIR OBJECT-TYPE
    SYNTAX     Counter64 
    MAX-ACCESS read-only
    STATUS     current
    DESCRIPTION
         "This object specifies the actual CIR."
     ::= { cmQosShaperV2Entry 16 }

cmQosShaperV2ActualEIR OBJECT-TYPE
    SYNTAX     Counter64 
    MAX-ACCESS read-only
    STATUS     current
    DESCRIPTION
         "This object specifies the actual EIR."
     ::= { cmQosShaperV2Entry 17 }
     
cmQosShaperV2LowLatencyControl OBJECT-TYPE
    SYNTAX     TruthValue 
    MAX-ACCESS read-write
    STATUS     current
    DESCRIPTION
         "This object specifies low latency control whether enabled."
     ::= { cmQosShaperV2Entry 18 }

--Lag Shaper
cmTrafficPortQosShaperTable  OBJECT-TYPE
    SYNTAX      SEQUENCE OF CmTrafficPortQosShaperEntry
    MAX-ACCESS  not-accessible
    STATUS      current
    DESCRIPTION
        "A list of entries corresponding to Quality of Service 
         Shaper for configuration purposes."
    ::= { cmFacilityObjects 43 }

cmTrafficPortQosShaperEntry OBJECT-TYPE
    SYNTAX      CmTrafficPortQosShaperEntry 
    MAX-ACCESS  not-accessible
    STATUS      current
    DESCRIPTION
         "A conceptual row in the cmTrafficPortQosShaperTable. 
          These entries represent a Quality of Service Shaper."
    INDEX { neIndex, shelfIndex, slotIndex, cmEthernetTrafficPortIndex, cmTrafficPortQosShaperIndex }
    ::= { cmTrafficPortQosShaperTable 1 }

CmTrafficPortQosShaperEntry ::= SEQUENCE {
    cmTrafficPortQosShaperIndex                   Integer32,

    -- State Management params
    cmTrafficPortQosShaperAdminState              AdminState,
    cmTrafficPortQosShaperOperationalState        OperationalState,
    cmTrafficPortQosShaperSecondaryState          SecondaryState,
    
    cmTrafficPortQosShaperAssociatedQueueProfile  VariablePointer,
    cmTrafficPortQosShaperBufferSize              Integer32,
    cmTrafficPortQosShaperCIRLo                   Unsigned32,
    cmTrafficPortQosShaperCIRHi                   Unsigned32,
    cmTrafficPortQosShaperEIRLo                   Unsigned32,
    cmTrafficPortQosShaperEIRHi                   Unsigned32,
    --cmTrafficPortQosShaperREDEnabled      TruthValue,
    cmTrafficPortQosShaperStorageType             StorageType,
    cmTrafficPortQosShaperRowStatus               RowStatus,
    cmTrafficPortQosShaperIngressAverageFrameSize Integer32,
    cmTrafficPortQosShaperAdditionalCIRLo         Unsigned32,
    cmTrafficPortQosShaperAdditionalCIRHi         Unsigned32,
    cmTrafficPortQosShaperWfqWeight               Integer32
}

cmTrafficPortQosShaperIndex OBJECT-TYPE
    SYNTAX      Integer32 (1..8)
    MAX-ACCESS  read-create
    STATUS      current
    DESCRIPTION
            "The ShaperV2 Index that represents the COS level. Index 1
             represents COS 0; Index 2 represents COS 1 and so on." 
    ::= { cmTrafficPortQosShaperEntry 1 }

-- State Management params
cmTrafficPortQosShaperAdminState OBJECT-TYPE
    SYNTAX      AdminState 
    MAX-ACCESS  read-write
    STATUS      current
    DESCRIPTION
            "This object represents the Administrative State of 
             the QOS Shaper." 
    ::= { cmTrafficPortQosShaperEntry 2 }

cmTrafficPortQosShaperOperationalState OBJECT-TYPE
    SYNTAX      OperationalState 
    MAX-ACCESS  read-only
    STATUS      current
    DESCRIPTION
            "This object represents the Operational State of the QOS ShaperV2." 
    ::= { cmTrafficPortQosShaperEntry 3 }

cmTrafficPortQosShaperSecondaryState OBJECT-TYPE
    SYNTAX      SecondaryState 
    MAX-ACCESS  read-only
    STATUS      current
    DESCRIPTION
            "This object represents the Secondary State of the QOS LagQosShaper." 
    ::= { cmTrafficPortQosShaperEntry 4 }

cmTrafficPortQosShaperAssociatedQueueProfile OBJECT-TYPE
    SYNTAX     VariablePointer
    MAX-ACCESS read-create
    STATUS     current
    DESCRIPTION
         "This object defines the queue profile ID to be used,
          it is associated with the cmQosQueueProfileIndex."
     ::= { cmTrafficPortQosShaperEntry 5 }

cmTrafficPortQosShaperBufferSize OBJECT-TYPE
    SYNTAX     Integer32
    MAX-ACCESS read-create
    STATUS     current
    DESCRIPTION
         "This object defines the buffer size of Shaper."
     ::= { cmTrafficPortQosShaperEntry 6 }

cmTrafficPortQosShaperCIRLo OBJECT-TYPE
    SYNTAX     Unsigned32 
    MAX-ACCESS read-create
    STATUS     current
    DESCRIPTION
         "This object specifies the Lower 32 bits of CIR."
     ::= { cmTrafficPortQosShaperEntry 7 }
     
cmTrafficPortQosShaperCIRHi OBJECT-TYPE
    SYNTAX     Unsigned32 
    MAX-ACCESS read-create
    STATUS     current
    DESCRIPTION
         "This object specifies the Higher 32 bits of CIR."
     ::= { cmTrafficPortQosShaperEntry 8 }

cmTrafficPortQosShaperEIRLo OBJECT-TYPE
    SYNTAX     Unsigned32 
    MAX-ACCESS read-create
    STATUS     current
    DESCRIPTION
         "This object specifies the Lower 32 bits of EIR."
     ::= { cmTrafficPortQosShaperEntry 9 }
     
cmTrafficPortQosShaperEIRHi OBJECT-TYPE
    SYNTAX     Unsigned32 
    MAX-ACCESS read-create
    STATUS     current
    DESCRIPTION
         "This object specifies the Higher 32 bits of EIR."
     ::= { cmTrafficPortQosShaperEntry 10 }

--cmTrafficPortQosShaperREDEnabled OBJECT-TYPE
--    SYNTAX     TruthValue 
--    MAX-ACCESS read-create
--    STATUS     current
--    DESCRIPTION
--         "This object specifies RED of Port Shaper."
--     ::= { cmTrafficPortQosShaperEntry 11 }

cmTrafficPortQosShaperStorageType OBJECT-TYPE
    SYNTAX     StorageType
    MAX-ACCESS read-create
    STATUS     current
    DESCRIPTION
            "The type of storage configured for this entry."
    ::= { cmTrafficPortQosShaperEntry 11 }

cmTrafficPortQosShaperRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmTrafficPortQosShaperRowStatus supported are
            createAndGo(4) and destroy(6).  All mandatory attributes
            must be specified in a single SNMP SET request with
            cmTrafficPortQosShaperRowStatus value as createAndGo(4).
            Upon successful row creation, this object has a
            value of active(1).

            The cmTrafficPortQosShaperRowStatus object may be modified if
            the associated instance of this object is equal to active(1)."
    ::= { cmTrafficPortQosShaperEntry 12 }

cmTrafficPortQosShaperIngressAverageFrameSize  OBJECT-TYPE
    SYNTAX     Integer32 (64..9600)
    MAX-ACCESS read-create
    STATUS     current
    DESCRIPTION
         "This object defines the average frame size for accounting for Meter/Shaping."
     ::= { cmTrafficPortQosShaperEntry 13 }

cmTrafficPortQosShaperAdditionalCIRLo OBJECT-TYPE
    SYNTAX     Unsigned32 
    MAX-ACCESS read-create
    STATUS     current
    DESCRIPTION
         "This object specifies the Lower 32 bits of additional CIR."
     ::= { cmTrafficPortQosShaperEntry 14 }
     
cmTrafficPortQosShaperAdditionalCIRHi OBJECT-TYPE
    SYNTAX     Unsigned32 
    MAX-ACCESS read-create
    STATUS     current
    DESCRIPTION
         "This object specifies the Higher 32 bits of additional CIR."
     ::= { cmTrafficPortQosShaperEntry 15 }

cmTrafficPortQosShaperWfqWeight OBJECT-TYPE
    SYNTAX     Integer32
    MAX-ACCESS read-write
    STATUS     current
    DESCRIPTION
         "This object specifies the wfq weight value of the QoS shaper."
     ::= { cmTrafficPortQosShaperEntry 16 }

cmTrafficAclRscAllocation OBJECT-TYPE
    SYNTAX     CmAclConfiguration
    MAX-ACCESS read-write
    STATUS     current
    DESCRIPTION
        "This object is defined to set traffic acl resource allocation.

         Supported actions are:
         all-bk-l2(1)  - all bank allocated to l2. 
         all-bk-l2-ipv4(2)  - all bank allocated to l2/ipv4. 
         two-bk-l2-ipv4(3)  - two thirds allocated to l2/ipv4, the left belongs to ipv6.
         one-bk-l2-ipv4(4)  - one thirds allocated to l2/ipv4, the left belongs to ipv6.
         none-bk-l2-ipv4(5) - all bank allocated to ipv6. "
    ::= { cmFacilityObjects 44 }

--
--  Ethernet Network Port Quality of Service Shaper 
--
f3NetPortQosShaperTable  OBJECT-TYPE
    SYNTAX      SEQUENCE OF F3NetPortQosShaperEntry
    MAX-ACCESS  not-accessible
    STATUS      current
    DESCRIPTION
            "A list of entries corresponding to Ethernet Network Port 
             Quality of Service Shaper for configuration purposes.
             These shapers can be managed when the Network Port is
             in evpl mode and are relevant for traffic in the
             access to network direction."
    ::= { cmFacilityObjects 45 }

f3NetPortQosShaperEntry OBJECT-TYPE
    SYNTAX      F3NetPortQosShaperEntry
    MAX-ACCESS  not-accessible
    STATUS      current
    DESCRIPTION
            "A conceptual row in the f3NetPortQosShaperTable. 
             These entries represent a Quality of Service Shaper."
    INDEX { neIndex, shelfIndex, slotIndex, cmEthernetNetPortIndex, 
            f3NetPortQosShaperIndex }
    ::= { f3NetPortQosShaperTable 1 }

F3NetPortQosShaperEntry ::= SEQUENCE {
    -- QOS Shaper Index/Id
    f3NetPortQosShaperIndex               Integer32,
    f3NetPortQosShaperDirection           TrafficDirection,

    -- State Management params
    f3NetPortQosShaperAdminState          AdminState,
    f3NetPortQosShaperOperationalState    OperationalState,
    f3NetPortQosShaperSecondaryState      SecondaryState,

    -- QOS Shaper Properties
    f3NetPortQosShaperCIRLo               Unsigned32,
    f3NetPortQosShaperCIRHi               Unsigned32,
    f3NetPortQosShaperEIRLo               Unsigned32,
    f3NetPortQosShaperEIRHi               Unsigned32,
    f3NetPortQosShaperCBS                 Unsigned32,
    f3NetPortQosShaperEBS                 Unsigned32,
    f3NetPortQosShaperBufferSize          Unsigned32,
    f3NetPortQosShaperCOS                 Integer32,
    f3NetPortQosShaperSoamCIRLo           Unsigned32,
    f3NetPortQosShaperSoamCIRHi           Unsigned32,
    f3NetPortQosShaperSoamEIRLo           Unsigned32,
    f3NetPortQosShaperSoamEIRHi           Unsigned32,

    --wred threshold
    f3NetPortQosShaperWredGreenMinQueueThreshold       Unsigned32,
    f3NetPortQosShaperWredGreenMaxQueueThreshold       Unsigned32,
    f3NetPortQosShaperWredGreenDropProbability         Unsigned32,
    f3NetPortQosShaperWredYellowMinQueueThreshold      Unsigned32,
    f3NetPortQosShaperWredYellowMaxQueueThreshold      Unsigned32,
    f3NetPortQosShaperWredYellowDropProbability        Unsigned32,
    f3NetPortQosShaperAvgFrameSizeBeforeFragment       Integer32,
    f3NetPortQosShaperWfqWeight                        Integer32
}

f3NetPortQosShaperIndex OBJECT-TYPE
    SYNTAX      Integer32 (1..8)
    MAX-ACCESS  read-create
    STATUS      current
    DESCRIPTION
            "The unique integer index value corresponding to a 
             Quality of Service Shaper."
    ::= { f3NetPortQosShaperEntry 1 }

f3NetPortQosShaperDirection OBJECT-TYPE
    SYNTAX      TrafficDirection 
    MAX-ACCESS  read-only
    STATUS      current
    DESCRIPTION
            "The direction of the Quality of Service Shaper."
    ::= { f3NetPortQosShaperEntry 2 }

-- State Management params
f3NetPortQosShaperAdminState OBJECT-TYPE
    SYNTAX      AdminState 
    MAX-ACCESS  read-write
    STATUS      current
    DESCRIPTION
            "This object represents the Administrative State of 
             the QOS Shaper." 
    ::= { f3NetPortQosShaperEntry 3 }

f3NetPortQosShaperOperationalState OBJECT-TYPE
    SYNTAX      OperationalState 
    MAX-ACCESS  read-only
    STATUS      current
    DESCRIPTION
            "This object represents the Operational State of the QOS Shaper." 
    ::= { f3NetPortQosShaperEntry 4 }

f3NetPortQosShaperSecondaryState OBJECT-TYPE
    SYNTAX      SecondaryState 
    MAX-ACCESS  read-only
    STATUS      current
    DESCRIPTION
            "This object represents the Secondary State of the QOS Shaper." 
    ::= { f3NetPortQosShaperEntry 5 }

f3NetPortQosShaperCIRLo OBJECT-TYPE
    SYNTAX     Unsigned32
    MAX-ACCESS read-create
    STATUS     current
    DESCRIPTION
         "This object represents the Commited Information
          Rate(CIR) (Lower 32 bits)of a Shaper."
     ::= { f3NetPortQosShaperEntry 6 }

f3NetPortQosShaperCIRHi OBJECT-TYPE
    SYNTAX     Unsigned32
    MAX-ACCESS read-create
    STATUS     current
    DESCRIPTION
         "This object represents the Commited Information
          Rate(CIR) (Higher 32 bits) of a Shaper."
     ::= { f3NetPortQosShaperEntry 7 }

f3NetPortQosShaperEIRLo OBJECT-TYPE
    SYNTAX     Unsigned32
    MAX-ACCESS read-create
    STATUS     current
    DESCRIPTION
         "This object represents the Excess Information
          Rate(EIR) (Higher 32 bits) on the Shaper."
     ::= { f3NetPortQosShaperEntry 8 }

f3NetPortQosShaperEIRHi OBJECT-TYPE
    SYNTAX     Unsigned32
    MAX-ACCESS read-create
    STATUS     current
    DESCRIPTION
         "This object represents the Excess Information
          Rate(EIR) (Higher 32 bits) on the Shaper."
     ::= { f3NetPortQosShaperEntry 9 }

f3NetPortQosShaperCBS OBJECT-TYPE
    SYNTAX     Unsigned32
    MAX-ACCESS read-create
    STATUS     current
    DESCRIPTION
         "This object represents the Commited Burst Size (CBS) of the Shaper."
     ::= { f3NetPortQosShaperEntry 10 }

f3NetPortQosShaperEBS OBJECT-TYPE
    SYNTAX     Unsigned32
    MAX-ACCESS read-create
    STATUS     current
    DESCRIPTION
         "This object represents the Excess Burst Size (EBS) of the Shaper."
     ::= { f3NetPortQosShaperEntry 11 }

f3NetPortQosShaperBufferSize OBJECT-TYPE
    SYNTAX     Unsigned32
    MAX-ACCESS read-create
    STATUS     current
    DESCRIPTION
         "This object represents the Buffer Size of the Shaper."
     ::= { f3NetPortQosShaperEntry 12 }

f3NetPortQosShaperCOS OBJECT-TYPE
    SYNTAX     Integer32 (0..7)
    MAX-ACCESS read-only
    STATUS     current
    DESCRIPTION
            "This object provides the COS (Class of Service)
             value for the QOS Shaper."
    ::= { f3NetPortQosShaperEntry 13 }

f3NetPortQosShaperSoamCIRLo OBJECT-TYPE
    SYNTAX     Unsigned32
    MAX-ACCESS read-create
    STATUS     current
    DESCRIPTION
         "This object represents the Soam Commited Information
          Rate(SOAM-CIR) (Lower 32 bits)of a Shaper."
     ::= { f3NetPortQosShaperEntry 14 }

f3NetPortQosShaperSoamCIRHi OBJECT-TYPE
    SYNTAX     Unsigned32
    MAX-ACCESS read-create
    STATUS     current
    DESCRIPTION
         "This object represents the Soam Commited Information
          Rate(SOAM-CIR) (Higher 32 bits) of a Shaper."
     ::= { f3NetPortQosShaperEntry 15 }

f3NetPortQosShaperSoamEIRLo OBJECT-TYPE
    SYNTAX     Unsigned32
    MAX-ACCESS read-create
    STATUS     current
    DESCRIPTION
         "This object represents the Soam Excess Information
          Rate(SOAM-EIR) (Higher 32 bits) on the Shaper."
     ::= { f3NetPortQosShaperEntry 16 }

f3NetPortQosShaperSoamEIRHi OBJECT-TYPE
    SYNTAX     Unsigned32
    MAX-ACCESS read-create
    STATUS     current
    DESCRIPTION
         "This object represents the Soam Excess Information
          Rate(SOAM-EIR) (Higher 32 bits) on the Shaper."
     ::= { f3NetPortQosShaperEntry 17 }

f3NetPortQosShaperWredGreenMinQueueThreshold OBJECT-TYPE
    SYNTAX     Unsigned32
    MAX-ACCESS read-create
    STATUS     current
    DESCRIPTION
         "This object represents the Wred green packet min queue threshold value."
     ::= { f3NetPortQosShaperEntry 18 }

f3NetPortQosShaperWredGreenMaxQueueThreshold OBJECT-TYPE
    SYNTAX     Unsigned32
    MAX-ACCESS read-create
    STATUS     current
    DESCRIPTION
         "This object represents the Wred green packet max queue threshold value."
     ::= { f3NetPortQosShaperEntry 19 }

f3NetPortQosShaperWredGreenDropProbability OBJECT-TYPE
    SYNTAX     Unsigned32
    MAX-ACCESS read-create
    STATUS     current
    DESCRIPTION
         "This object represents the Wred green packet drop probability."
     ::= { f3NetPortQosShaperEntry 20 }

f3NetPortQosShaperWredYellowMinQueueThreshold OBJECT-TYPE
    SYNTAX     Unsigned32
    MAX-ACCESS read-create
    STATUS     current
    DESCRIPTION
         "This object represents the Wred yellow packet min queue threshold value."
     ::= { f3NetPortQosShaperEntry 21 }

f3NetPortQosShaperWredYellowMaxQueueThreshold OBJECT-TYPE
    SYNTAX     Unsigned32
    MAX-ACCESS read-create
    STATUS     current
    DESCRIPTION
         "This object represents the Wred yellow packet max queue threshold value."
     ::= { f3NetPortQosShaperEntry 22 }

f3NetPortQosShaperWredYellowDropProbability OBJECT-TYPE
    SYNTAX     Unsigned32
    MAX-ACCESS read-create
    STATUS     current
    DESCRIPTION
         "This object represents the Wred yellow packet drop probability."
     ::= { f3NetPortQosShaperEntry 23 }

f3NetPortQosShaperAvgFrameSizeBeforeFragment OBJECT-TYPE
    SYNTAX     Integer32
    MAX-ACCESS read-write
    STATUS     current
    DESCRIPTION
         "This object specifies the average frame size before fragmentation."
     ::= { f3NetPortQosShaperEntry 24 }

f3NetPortQosShaperWfqWeight OBJECT-TYPE
    SYNTAX     Integer32
    MAX-ACCESS read-write
    STATUS     current
    DESCRIPTION
         "This object specifies the wfq weight value."
     ::= { f3NetPortQosShaperEntry 25 }

-- 
-- ge dcn port table
--
f3Usb3GDCNPortTable   OBJECT-TYPE
    SYNTAX      SEQUENCE OF F3Usb3GDCNPortEntry
    MAX-ACCESS  not-accessible
    STATUS      current
    DESCRIPTION
            "3G DCN Port table.
             The table contains parameters of 3G USB modem."
    ::= { cmFacilityObjects 46 }

f3Usb3GDCNPortEntry OBJECT-TYPE
    SYNTAX      F3Usb3GDCNPortEntry 
    MAX-ACCESS  not-accessible
    STATUS      current
    DESCRIPTION
            "A conceptual row in the f3Usb3GDCNPortTable."
    INDEX { neIndex, shelfIndex, slotIndex, f3UsbHostIndex }
    ::= { f3Usb3GDCNPortTable 1 }

F3Usb3GDCNPortEntry ::= SEQUENCE {
    f3Usb3GDCNPortIndex                Integer32,
    f3Usb3GDCNPortIfIndex              InterfaceIndex,
    f3Usb3GDCNPortEntityIndex          PhysicalIndex,
    f3Usb3GDCNPortAdminState           AdminState,
    f3Usb3GDCNPortOperationalState     OperationalState,
    f3Usb3GDCNPortSecondaryState       SecondaryState,
    f3Usb3GDCNPortVendorName           DisplayString,
    f3Usb3GDCNPortModel                DisplayString,
    f3Usb3GDCNPortFSN                  DisplayString,
    f3Usb3GDCNPortIMEI                 DisplayString,
    f3Usb3GDCNPortHardwareVersion      DisplayString,
    f3Usb3GDCNPortFirmwareVersion      DisplayString,
    f3Usb3GDCNPortSIMStatus            F3Usb3GSimCardState,
    f3Usb3GDCNPortPINLeftChances       Integer32,
    f3Usb3GDCNPortPUKLeftChances       Integer32,
    f3Usb3GDCNPortConnectionStatus     F3Usb3GNetworkConnectionState,
    f3Usb3GDCNPortRSSI                 F3Usb3GRecvSignalStrengthInd,
    f3Usb3GDCNPortSpeed                Integer32,
    f3Usb3GDCNPortMTU                  Integer32,
    f3Usb3GDCNPortProviderName         DisplayString,
    f3Usb3GDCNPortDNS1                 IpAddress,
    f3Usb3GDCNPortDNS2                 IpAddress,
    f3Usb3GDCNPortAPN                  DisplayString,
    f3Usb3GDCNPortUserName             DisplayString,
    f3Usb3GDCNPortPassword             DisplayString,
    f3Usb3GDCNPortDailNumber           DisplayString,
    f3Usb3GDCNPortRedialTimer          Integer32,
    f3Usb3GDCNPortCurrentPinCode       DisplayString,
    f3Usb3GDCNPortNewPinCode           DisplayString,
    f3Usb3GDCNPortConfirmPinCode       DisplayString,
    f3Usb3GDCNPortCurrentPukCode       DisplayString,
    f3Usb3GDCNPINCodeAction            F3Usb3GDCNPINCodeActionType,
    f3Usb3GDCNPortStorageType          StorageType,
    f3Usb3GDCNPortRowStatus            RowStatus,
    f3Usb3GDCNPortIMSI                 DisplayString,
    f3Usb3GDCNPortPINStatus            G3AuthStatus,
    f3UsbDCNPortMobileNetworkType      UsbDCNMobileNetworkType,
    f3Usb3GDCNMuxOperationalMode       UsbOperationalMode,
    f3Usb3GDCNPortIpAddress            IpAddress,
    f3Usb3GDCNPortNetMask              IpAddress
}


f3Usb3GDCNPortIndex OBJECT-TYPE
    SYNTAX      Integer32
    MAX-ACCESS  read-only
    STATUS      current
    DESCRIPTION
            "An integer index value used to uniquely identify
             this Ethernet Access Port within a card.
             Note that each Ethernet Access Port is uniquely identified
             by the indices neIndex, shelfIndex, 
             slotIndex, f3Usb3GDCNPortIndex"
    ::= { f3Usb3GDCNPortEntry 1 }

f3Usb3GDCNPortIfIndex OBJECT-TYPE
    SYNTAX     InterfaceIndex
    MAX-ACCESS read-only
    STATUS     current
    DESCRIPTION
         "This object has the same value as ifIndex for 
             G3 DCN Port.  An integer index value used to 
             uniquely identify this G3 DCN Port."
     ::= { f3Usb3GDCNPortEntry 2 }

f3Usb3GDCNPortEntityIndex OBJECT-TYPE
    SYNTAX     PhysicalIndex
    MAX-ACCESS read-only
    STATUS     current
    DESCRIPTION
         "Entity Index from ENTITY-MIB for this port."
     ::= { f3Usb3GDCNPortEntry 3 }

f3Usb3GDCNPortAdminState OBJECT-TYPE
    SYNTAX     AdminState
    MAX-ACCESS read-write
    STATUS     current
    DESCRIPTION
         "This object represents the Administrative State of the G3 DCN Port."
     ::= { f3Usb3GDCNPortEntry 4 }

f3Usb3GDCNPortOperationalState OBJECT-TYPE
    SYNTAX     OperationalState
    MAX-ACCESS read-only
    STATUS     current
    DESCRIPTION
         "This object represents the Operational State of the G3 DCN Port."
     ::= { f3Usb3GDCNPortEntry 5 }

f3Usb3GDCNPortSecondaryState OBJECT-TYPE
    SYNTAX     SecondaryState
    MAX-ACCESS read-only
    STATUS     current
    DESCRIPTION
         "This object represents the Secondary State of the G3 DCN Port."
     ::= { f3Usb3GDCNPortEntry 6 }

f3Usb3GDCNPortVendorName OBJECT-TYPE
    SYNTAX     DisplayString
    MAX-ACCESS read-only
    STATUS     current
    DESCRIPTION
         "This object provides the Vendor Name of the G3 DCN Port."
     ::= { f3Usb3GDCNPortEntry 7 }

f3Usb3GDCNPortModel OBJECT-TYPE
    SYNTAX     DisplayString
    MAX-ACCESS read-only
    STATUS     current
    DESCRIPTION
         "This object provides the Model of the G3 DCN Port."
     ::= { f3Usb3GDCNPortEntry 8 }

f3Usb3GDCNPortFSN OBJECT-TYPE
    SYNTAX     DisplayString
    MAX-ACCESS read-only
    STATUS     current
    DESCRIPTION
         "This object provides the Factory Serial Number of the G3 DCN Port."
     ::= { f3Usb3GDCNPortEntry 9 }

f3Usb3GDCNPortIMEI OBJECT-TYPE
    SYNTAX     DisplayString
    MAX-ACCESS read-only
    STATUS     current
    DESCRIPTION
         "This object provides the International Mobile Equipment Identity of the G3 DCN Port."
     ::= { f3Usb3GDCNPortEntry 10 }

f3Usb3GDCNPortHardwareVersion OBJECT-TYPE
    SYNTAX     DisplayString
    MAX-ACCESS read-only
    STATUS     current
    DESCRIPTION
         "This object provides the Hardware Version of the G3 DCN Port."
     ::= { f3Usb3GDCNPortEntry 11 }

f3Usb3GDCNPortFirmwareVersion OBJECT-TYPE
    SYNTAX     DisplayString
    MAX-ACCESS read-only
    STATUS     current
    DESCRIPTION
         "This object provides the Firmware Version of the G3 DCN Port.."
     ::= { f3Usb3GDCNPortEntry 12 }

f3Usb3GDCNPortSIMStatus OBJECT-TYPE
    SYNTAX     F3Usb3GSimCardState
    MAX-ACCESS read-only
    STATUS     current
    DESCRIPTION
         "This object provides the SIM card Status of the G3 DCN Port."
     ::= { f3Usb3GDCNPortEntry 13 }

f3Usb3GDCNPortPINLeftChances OBJECT-TYPE
    SYNTAX     Integer32
    MAX-ACCESS read-only
    STATUS     current
    DESCRIPTION
         "This object provides the Left Chances for PIN input of the G3 DCN Port."
     ::= { f3Usb3GDCNPortEntry 14 }

f3Usb3GDCNPortPUKLeftChances OBJECT-TYPE
    SYNTAX     Integer32
    MAX-ACCESS read-only
    STATUS     current
    DESCRIPTION
         "This object provides the Left Chances for PUK input of the G3 DCN Port."
     ::= { f3Usb3GDCNPortEntry 15 }

f3Usb3GDCNPortConnectionStatus OBJECT-TYPE
    SYNTAX     F3Usb3GNetworkConnectionState
    MAX-ACCESS read-only
    STATUS     current
    DESCRIPTION
         "This object provides the Wirless Connection Status of the G3 DCN Port."
     ::= { f3Usb3GDCNPortEntry 16 }

f3Usb3GDCNPortRSSI OBJECT-TYPE
    SYNTAX     F3Usb3GRecvSignalStrengthInd
    MAX-ACCESS read-only
    STATUS     current
    DESCRIPTION
         "This object provides the Received Signal Strength Indication of the G3 DCN Port."
     ::= { f3Usb3GDCNPortEntry 17 }

f3Usb3GDCNPortSpeed OBJECT-TYPE
    SYNTAX     Integer32
    MAX-ACCESS read-only
    STATUS     current
    DESCRIPTION
         "This object provides the Connection Speed of the G3 DCN Port."
     ::= { f3Usb3GDCNPortEntry 18 }

f3Usb3GDCNPortMTU OBJECT-TYPE
    SYNTAX     Integer32
    MAX-ACCESS read-only
    STATUS     current
    DESCRIPTION
         "This object provides the MTU of the G3 DCN Port."
     ::= { f3Usb3GDCNPortEntry 19 }

f3Usb3GDCNPortProviderName OBJECT-TYPE
    SYNTAX     DisplayString
    MAX-ACCESS read-only
    STATUS     current
    DESCRIPTION
         "This object provides the Wireless Service Provider Name of the G3 DCN Port."
     ::= { f3Usb3GDCNPortEntry 20 }

f3Usb3GDCNPortDNS1 OBJECT-TYPE
    SYNTAX      IpAddress 
    MAX-ACCESS  read-only
    STATUS      current
    DESCRIPTION
            "This first DNS of the interface." 
    ::= { f3Usb3GDCNPortEntry 21 }

f3Usb3GDCNPortDNS2 OBJECT-TYPE
    SYNTAX      IpAddress 
    MAX-ACCESS  read-only
    STATUS      current
    DESCRIPTION
            "This second DNS of the interface." 
    ::= { f3Usb3GDCNPortEntry 22 }

f3Usb3GDCNPortAPN OBJECT-TYPE
    SYNTAX     DisplayString (SIZE (0..64))
    MAX-ACCESS read-write
    STATUS     current
    DESCRIPTION
         "This object allows configure the Access Point Name of the G3 DCN Port."
     ::= { f3Usb3GDCNPortEntry 23 }

f3Usb3GDCNPortUserName OBJECT-TYPE
    SYNTAX     DisplayString (SIZE (0..32))
    MAX-ACCESS read-write
    STATUS     current
    DESCRIPTION
         "This object allows configure the User Name of the G3 DCN Port."
     ::= { f3Usb3GDCNPortEntry 24 }

f3Usb3GDCNPortPassword OBJECT-TYPE
    SYNTAX     DisplayString (SIZE (0..32))
    MAX-ACCESS read-write
    STATUS     current
    DESCRIPTION
         "This object allows configure the Password of the G3 DCN Port."
     ::= { f3Usb3GDCNPortEntry 25 }

f3Usb3GDCNPortDailNumber OBJECT-TYPE
    SYNTAX     DisplayString (SIZE (0..32))
    MAX-ACCESS read-write
    STATUS     current
    DESCRIPTION
         "This object allows configure the Dail Number of the G3 DCN Port."
     ::= { f3Usb3GDCNPortEntry 26 }

f3Usb3GDCNPortRedialTimer OBJECT-TYPE
    SYNTAX     Integer32
    MAX-ACCESS read-write
    STATUS     current
    DESCRIPTION
         "This object allows configure the Retail Timer of the G3 DCN Port."
     ::= { f3Usb3GDCNPortEntry 27 }

f3Usb3GDCNPortCurrentPinCode OBJECT-TYPE
    SYNTAX     DisplayString (SIZE (0..64))
    MAX-ACCESS read-create
    STATUS     current
    DESCRIPTION
         "This object is the Current Pin Code."
     ::= { f3Usb3GDCNPortEntry 28 }

f3Usb3GDCNPortNewPinCode OBJECT-TYPE
    SYNTAX     DisplayString (SIZE (0..64))
    MAX-ACCESS read-create
    STATUS     current
    DESCRIPTION
         "This object is the New Pin code."
     ::= { f3Usb3GDCNPortEntry 29 }

f3Usb3GDCNPortConfirmPinCode OBJECT-TYPE
    SYNTAX     DisplayString (SIZE (0..64))
    MAX-ACCESS read-create
    STATUS     current
    DESCRIPTION
         "This object is the Confirm Pin Code."
     ::= { f3Usb3GDCNPortEntry 30 }

f3Usb3GDCNPortCurrentPukCode OBJECT-TYPE
    SYNTAX     DisplayString (SIZE (0..64))
    MAX-ACCESS read-create
    STATUS     current
    DESCRIPTION
         "This object is the Current Puk Code."
     ::= { f3Usb3GDCNPortEntry 31 }

f3Usb3GDCNPINCodeAction OBJECT-TYPE
    SYNTAX     F3Usb3GDCNPINCodeActionType
    MAX-ACCESS read-create
    STATUS     current
    DESCRIPTION
         "This Action is for PIN code operation."
     ::= { f3Usb3GDCNPortEntry 32 }

f3Usb3GDCNPortStorageType OBJECT-TYPE
    SYNTAX     StorageType
    MAX-ACCESS read-create
    STATUS     current
    DESCRIPTION
            "The type of storage configured for this entry."
    ::= { f3Usb3GDCNPortEntry 33 }

f3Usb3GDCNPortRowStatus OBJECT-TYPE
    SYNTAX      RowStatus
    MAX-ACCESS  read-write
    STATUS      current
    DESCRIPTION
            "The status of this row.
             The f3Usb3GDCNPortRowStatus object may be modified if
             the associated instance of this object is equal to active(1),
             notInService(2), or notReady(3)."
    ::= { f3Usb3GDCNPortEntry 34 }

f3Usb3GDCNPortIMSI OBJECT-TYPE
    SYNTAX     DisplayString
    MAX-ACCESS read-only
    STATUS     current
    DESCRIPTION
         "This object provides the International Mobile Subscriber Identity of the G3 DCN Port."
     ::= { f3Usb3GDCNPortEntry 35 }

f3Usb3GDCNPortPINStatus OBJECT-TYPE
    SYNTAX     G3AuthStatus
    MAX-ACCESS read-only
    STATUS     current
    DESCRIPTION
         "This status of PIN/PUK"
     ::= { f3Usb3GDCNPortEntry 36 }

f3UsbDCNPortMobileNetworkType OBJECT-TYPE
    SYNTAX     UsbDCNMobileNetworkType
    MAX-ACCESS read-only
    STATUS     current
    DESCRIPTION
         "This object describe the mobile network type."
     ::= { f3Usb3GDCNPortEntry 37 }

f3Usb3GDCNMuxOperationalMode OBJECT-TYPE
    SYNTAX     UsbOperationalMode
    MAX-ACCESS read-write
    STATUS     current
    DESCRIPTION
         "This object describe the USB operatioan mode."
     ::= { f3Usb3GDCNPortEntry 38 }

f3Usb3GDCNPortIpAddress OBJECT-TYPE
    SYNTAX      IpAddress
    MAX-ACCESS  read-only
    STATUS      current
    DESCRIPTION
            "The IP address of this port." 
    ::= { f3Usb3GDCNPortEntry 39 }

f3Usb3GDCNPortNetMask OBJECT-TYPE
    SYNTAX      IpAddress
    MAX-ACCESS  read-only
    STATUS      current
    DESCRIPTION
            "The IP subnet mask of this port." 
    ::= { f3Usb3GDCNPortEntry 40 } 

--
-- For tdm tables
--


--
--  OCn/STM Table
--
ocnStmTable  OBJECT-TYPE
    SYNTAX      SEQUENCE OF OcnStmEntry
    MAX-ACCESS  not-accessible
    STATUS      current
    DESCRIPTION
            "A list of entries corresponding to OCn/STM interface."
    ::= { cmFacilityObjects 47 }

ocnStmEntry  OBJECT-TYPE
    SYNTAX      OcnStmEntry
    MAX-ACCESS  not-accessible
    STATUS      current
    DESCRIPTION
            "A conceptual row in the ocnStmTable."
    INDEX { neIndex, shelfIndex, slotIndex, ocnStmIndex }
    ::= { ocnStmTable 1 }

OcnStmEntry ::= SEQUENCE {
    ocnStmIndex                        Integer32,
    ocnStmIfIndex                      InterfaceIndex,
    ocnStmEntityIndex                  PhysicalIndex,
    ocnStmAdminState                   AdminState,
    ocnStmOperationalState             OperationalState,
    ocnStmSecondaryState               SecondaryState,
    ocnStmSfpVendorName                DisplayString,
    ocnStmSfpPartNumber                DisplayString,
    ocnStmSfpSerialNumber              DisplayString,
    ocnStmSfpDateOfManufacture         DateAndTime,
    ocnStmSfpConnectorValue            SfpConnectorValue,
    ocnStmSfpLinkLength                Integer32,
    ocnStmSfpLaserWaveLength           Integer32,
    ocnStmSfpLaserWaveLengthPicometer  Unsigned32,
    ocnStmSfpMediaType                 SfpMediaType,
    ocnStmMultiplexingStructures       MultiplexingStructure,
    ocnStmEoTDMMode                    EoTDMMode,
    ocnStmLoopbackConfig               CmLoopbackType,
    ocnStmLoopbackStatus               CmLoopbackType,
    ocnStmLoopbackTime                 Integer32,
    ocnStmInsertingAIS                 TruthValue,
    ocnStmBerExcThreshold              BitErrRate,
    ocnStmBerDegThreshold              BitErrRate,
    ocnStmRxTrailTrace                 DisplayString,
    ocnStmTxTrailTrace                 DisplayString,
    ocnStmExpectedTrailTrace           DisplayString,
    ocnStmTrailTraceFormat             TrailTraceFormat,
    ocnStmQLModeEnabled                TruthValue,
    ocnStmExpectedQL                   SSMQualityLevel,
    ocnStmAssumedQL                    SSMQualityLevel,
    ocnStmReceivedQL                   SSMQualityLevel,
    ocnStmTransmitQL                   SSMQualityLevel,
    ocnStmPortType                     OCNSTMPortType,
    ocnStmFreqSourceType               TDMFrequencySourceType,
    ocnStmHighOrderPathType            TDMPathType,
    ocnStmSfpName                      DisplayString,
    ocnStmSfpHardwareRevision          DisplayString
}

ocnStmIndex OBJECT-TYPE
    SYNTAX      Integer32
    MAX-ACCESS  not-accessible 
    STATUS      current
    DESCRIPTION
            "Unique index value associated with the OCn/STM interface."
    ::= { ocnStmEntry 1 }

ocnStmIfIndex OBJECT-TYPE
    SYNTAX      InterfaceIndex
    MAX-ACCESS  read-only
    STATUS      current
    DESCRIPTION
            "This object has the same value as ifIndex for OCn/STM interface.
             An integer index value used to uniquely identify
             this OCn/STM interface."
    ::= { ocnStmEntry 2 }

ocnStmEntityIndex OBJECT-TYPE
    SYNTAX      PhysicalIndex 
    MAX-ACCESS  read-only
    STATUS      current
    DESCRIPTION
           "Entity Index from ENTITY-MIB for this OCn/STM interface."
    ::= { ocnStmEntry 3 }

ocnStmAdminState OBJECT-TYPE
    SYNTAX      AdminState 
    MAX-ACCESS  read-write
    STATUS      current
    DESCRIPTION
            "This object represents the Administrative State of the OCn/STM interface."
    ::= { ocnStmEntry 4 }

ocnStmOperationalState OBJECT-TYPE
    SYNTAX      OperationalState 
    MAX-ACCESS  read-only
    STATUS      current
    DESCRIPTION
            "This object represents the Operational State of the OCn/STM interface."
    ::= { ocnStmEntry 5 }

ocnStmSecondaryState OBJECT-TYPE
    SYNTAX      SecondaryState 
    MAX-ACCESS  read-only
    STATUS      current
    DESCRIPTION
            "This object represents the Secondary State of the OCn/STM interface."
    ::= { ocnStmEntry 6 }

ocnStmSfpVendorName OBJECT-TYPE
    SYNTAX  DisplayString (SIZE (0..16))
    MAX-ACCESS read-only
    STATUS     current
    DESCRIPTION
            "This object provides the vendor name of the SFP."
     ::= { ocnStmEntry 7 }

ocnStmSfpPartNumber OBJECT-TYPE
    SYNTAX  DisplayString (SIZE (0..16))
    MAX-ACCESS read-only
    STATUS     current
    DESCRIPTION
            "This object provides the part number of the SFP."
     ::= { ocnStmEntry 8 }

ocnStmSfpSerialNumber OBJECT-TYPE
    SYNTAX  DisplayString (SIZE (0..32)) 
    MAX-ACCESS read-only
    STATUS     current
    DESCRIPTION
            "This object provides the serial number of the SFP."
     ::= { ocnStmEntry 9 }

ocnStmSfpDateOfManufacture OBJECT-TYPE
    SYNTAX     DateAndTime 
    MAX-ACCESS read-only
    STATUS     current
    DESCRIPTION
            "This object provides the date of manufacture of the SFP."
     ::= { ocnStmEntry 10 }

ocnStmSfpConnectorValue OBJECT-TYPE
    SYNTAX     SfpConnectorValue 
    MAX-ACCESS read-only
    STATUS     current
    DESCRIPTION
            "This object provides the SFP connector value."
     ::= { ocnStmEntry 11 }

ocnStmSfpLinkLength OBJECT-TYPE
    SYNTAX     Integer32
    MAX-ACCESS read-only
    STATUS     current
    DESCRIPTION
         "This object provides the SFP Link Length."
     ::= { ocnStmEntry 12 }

ocnStmSfpLaserWaveLength OBJECT-TYPE
    SYNTAX     Integer32
    MAX-ACCESS read-only
    STATUS     current
    DESCRIPTION
         "This object provides the SFP Laser Wave Length in nano meters."
     ::= { ocnStmEntry 13 }

ocnStmSfpLaserWaveLengthPicometer OBJECT-TYPE 
    SYNTAX     Unsigned32
    MAX-ACCESS read-only
    STATUS     current
    DESCRIPTION
         "This object provide laser wavelength pico value. 
          For example, laser wavelength is 1510.01,
          then ocnStmSfpLaserWaveLength=1510 
          and ocnStmSfpLaserWaveLengthPicometer=10."
     ::= { ocnStmEntry 14 }

ocnStmSfpMediaType OBJECT-TYPE
    SYNTAX     SfpMediaType
    MAX-ACCESS read-only
    STATUS     current
    DESCRIPTION
         "This object provides the SFP Media Type."
     ::= { ocnStmEntry 15 }

ocnStmMultiplexingStructures OBJECT-TYPE
    SYNTAX     MultiplexingStructure 
    MAX-ACCESS read-write
    STATUS     current
    DESCRIPTION
            "This object provides the TDM Multiplexing Structure base on OCn/STM interface."
     ::= { ocnStmEntry 16 }

ocnStmEoTDMMode OBJECT-TYPE
    SYNTAX     EoTDMMode 
    MAX-ACCESS read-write
    STATUS     current
    DESCRIPTION
            "This object provides the TDM Mode base on OCn/STM interface. 
            EoPDH means VCG container is PDH; EoTDM means VCG container is VC of SDH/SONET"
     ::= { ocnStmEntry 17 }

ocnStmLoopbackConfig OBJECT-TYPE
    SYNTAX     CmLoopbackType
    MAX-ACCESS read-write
    STATUS     current
    DESCRIPTION
            "This object allows to initiate loopbacks on 
             on the OCn/STM interface."
     ::= { ocnStmEntry 18 }

ocnStmLoopbackStatus OBJECT-TYPE
    SYNTAX     CmLoopbackType
    MAX-ACCESS read-only
    STATUS     current
    DESCRIPTION
            "This object provides status of the current loopback 
             on the OCn/STM interface."
     ::= { ocnStmEntry 19 }

ocnStmLoopbackTime OBJECT-TYPE
    SYNTAX     Integer32 (2..300)
    MAX-ACCESS read-write
    STATUS     current
    DESCRIPTION
            "This object allows to specify time for timed-loopbacks on 
             on the OCn/STM interface."
     ::= { ocnStmEntry 20 }

ocnStmInsertingAIS OBJECT-TYPE
    SYNTAX     TruthValue
    MAX-ACCESS read-write
    STATUS     current
    DESCRIPTION
            "This object allows to insert AIS-L out from OCn/STM interface 
            when it is in maintenance state."
     ::= { ocnStmEntry 21 }

ocnStmBerExcThreshold OBJECT-TYPE
    SYNTAX     BitErrRate
    MAX-ACCESS read-write
    STATUS     current
    DESCRIPTION
            "This object provide the threshold of B2EXC."
     ::= { ocnStmEntry 22 }

ocnStmBerDegThreshold OBJECT-TYPE
    SYNTAX     BitErrRate
    MAX-ACCESS read-write
    STATUS     current
    DESCRIPTION
            "This object provides the threshold of B2DEG."
     ::= { ocnStmEntry 23 }

ocnStmRxTrailTrace OBJECT-TYPE
    SYNTAX     DisplayString (SIZE (0..128))
    MAX-ACCESS read-only
    STATUS     current
    DESCRIPTION
            "This object provides the recevied J0 on the OCn/STM interface."
     ::= { ocnStmEntry 24 }

ocnStmTxTrailTrace OBJECT-TYPE
    SYNTAX     DisplayString (SIZE (0..128))
    MAX-ACCESS read-write
    STATUS     current
    DESCRIPTION
            "This object provides the transmit J0 on the OCn/STM interface."
     ::= { ocnStmEntry 25 }

ocnStmExpectedTrailTrace OBJECT-TYPE
    SYNTAX     DisplayString (SIZE (0..128))
    MAX-ACCESS read-write
    STATUS     current
    DESCRIPTION
            "This object provides the expected J0 on the OCn/STM interface."
     ::= { ocnStmEntry 26 }

ocnStmTrailTraceFormat OBJECT-TYPE
    SYNTAX     TrailTraceFormat
    MAX-ACCESS read-write
    STATUS     current
    DESCRIPTION
            "This object provides the J0 length mode on the OCn/STM interface."
     ::= { ocnStmEntry 27 }

ocnStmQLModeEnabled OBJECT-TYPE 
    SYNTAX     TruthValue
    MAX-ACCESS read-write
    STATUS     current
    DESCRIPTION
         "This object allows to specify whether the OCn/STM interface 
          can be enabled/disabled for QL Mode. This object
          is only applicable for Synchronous OCn/STM interface,
          when ocnStmQLModeEnabled is set to true.
          When enabled, on receive side 
            -port shall PEER the SSM (Sync Status Messages) slow protocol PDUs 
             and take appropriate action 
          When enabled, on transmit side 
            -port shall periodically (once a second) transmit QL TLV 
             information PDUs
          When disabled, on receive side,
            -port shall terminate and discard any SSM slow protocol PDUs 
          When disabled, on transmit side 
            -port shall not transmit any SSM slow protocol PDUs."
     ::= { ocnStmEntry 28 }

ocnStmExpectedQL OBJECT-TYPE 
    SYNTAX     SSMQualityLevel
    MAX-ACCESS read-write
    STATUS     current
    DESCRIPTION
         "This object allows to specify the expected QL when the 
          OCn/STM interface is enabled for QL Mode. This object
          is only applicable for Synchronous OCn/STM interface,
          when ocnStmQLModeEnabled is set to true.
          This object allows the user to set a minimum
          expected received Quality Level on the port. The valid values
          depend upon the SYNC entity Network Clock Type. A value of
          None represents that a minimum Quality Level is not expected. 
          The default value shall be None."
     ::= { ocnStmEntry 29 }

ocnStmAssumedQL OBJECT-TYPE 
    SYNTAX     SSMQualityLevel
    MAX-ACCESS read-write
    STATUS     current
    DESCRIPTION
         "This object allows to specify the assumed QL on the 
          OCn/STM interface. This object is only applicable for 
          Synchronous OCn/STM interface. 
          The Assumed QL is only meaningful if the Network Clock Type
          (see fsp150cm-sync.mib) is option1 and the 
          port TransmitQL Mode is disabled and the port is being used as 
          an input reference source. Under these conditions, 
          the specified QL value is assumed to be the Quality Level of the
          non-failed reference."
     ::= { ocnStmEntry 30 }

ocnStmReceivedQL OBJECT-TYPE 
    SYNTAX     SSMQualityLevel
    MAX-ACCESS read-only
    STATUS     current
    DESCRIPTION
         "This object provides the Received QL value for the OCn/STM interface. 
          If the OCn/STM interface TransmitQL Mode is disabled, then the received 
          QL value is not applicable.This object is only applicable for 
          Synchronous OCn/STM interface."
     ::= { ocnStmEntry 31 }

ocnStmTransmitQL OBJECT-TYPE 
    SYNTAX     SSMQualityLevel
    MAX-ACCESS read-only
    STATUS     current
    DESCRIPTION
         "This object provides the Transmitted QL value for the OCn/STM interface. 
          If the OCn/STM interface TransmitQL Mode is disabled, then the received 
          QL value is not applicable. This object is only applicable for 
          Synchronous OCn/STM interface."
     ::= { ocnStmEntry 32 }

ocnStmPortType OBJECT-TYPE 
    SYNTAX     OCNSTMPortType  
    MAX-ACCESS read-only
    STATUS     current
    DESCRIPTION
         "This object represents the OCN/STM Port Type.
          Determines whether the OCN/STM port operates in OC or STM mode."
     ::= { ocnStmEntry 33 }

ocnStmFreqSourceType OBJECT-TYPE 
    SYNTAX     TDMFrequencySourceType  
    MAX-ACCESS read-write
    STATUS     current
    DESCRIPTION
         "This object represents the TDM Frequency source of OCN/STM port."
     ::= { ocnStmEntry 34 }
 
ocnStmHighOrderPathType OBJECT-TYPE 
    SYNTAX     TDMPathType
    MAX-ACCESS read-write
    STATUS     current
    DESCRIPTION
         "This object provides the High Order Path Type of the OCn/STM interface."
     ::= { ocnStmEntry 35 }

ocnStmSfpName OBJECT-TYPE
    SYNTAX  DisplayString (SIZE (0..32))
    MAX-ACCESS read-only
    STATUS     current
    DESCRIPTION
            "This object provides the official name of the SFP."
     ::= { ocnStmEntry 36 }

ocnStmSfpHardwareRevision OBJECT-TYPE
    SYNTAX  DisplayString (SIZE (0..16))
    MAX-ACCESS read-only
    STATUS     current
    DESCRIPTION
            "This object provides the hardware revision of the SFP."
     ::= { ocnStmEntry 37 }


--
--  OCn Path Table
--
stsVcPathTable  OBJECT-TYPE
    SYNTAX      SEQUENCE OF StsVcPathEntry
    MAX-ACCESS  not-accessible
    STATUS      current
    DESCRIPTION
            "A list of entries corresponding to OCn Path."
    ::= { cmFacilityObjects 48 }

stsVcPathEntry  OBJECT-TYPE
    SYNTAX      StsVcPathEntry
    MAX-ACCESS  not-accessible
    STATUS      current
    DESCRIPTION
            "A conceptual row in the stsVcPathTable."
    INDEX { neIndex, shelfIndex, slotIndex, ocnStmIndex,
            stsVcPathParentIfIndex, stsVcPathIndex }
    ::= { stsVcPathTable 1 }

StsVcPathEntry ::= SEQUENCE {
    stsVcPathParentIfIndex           InterfaceIndex,
    stsVcPathIndex                   Unsigned32,
    stsVcPathIfIndex                 InterfaceIndex,
    stsVcPathAdminState              AdminState,
    stsVcPathOperationalState        OperationalState,
    stsVcPathSecondaryState          SecondaryState,
    stsVcPathLoopbackConfig          CmLoopbackType,
    stsVcPathLoopbackStatus          CmLoopbackType,
    stsVcPathLoopbackTime            Integer32,
    stsVcPathInsertingAIS            TruthValue,
    stsVcPathBerExcThreshold         BitErrRate,
    stsVcPathBerDegThreshold         BitErrRate,
    stsVcPathTrailTraceFormat        TrailTraceFormat,
    stsVcPathRxTrailTrace            DisplayString,
    stsVcPathTxTrailTrace            DisplayString,
    stsVcPathExpectedTrailTrace      DisplayString,
    stsVcPathRxSignalLabel           Unsigned32,
    stsVcPathTxSignalLabel           Unsigned32,
    stsVcPathExpectedSignalLabel     Unsigned32,
    stsVcPathRowStatus               RowStatus,
    stsVcPathLowOrderPathType        TDMPathType
}

stsVcPathParentIfIndex OBJECT-TYPE
    SYNTAX      InterfaceIndex
    MAX-ACCESS  not-accessible
    STATUS      current
    DESCRIPTION
            "This object is its parent's ifindex. Based on the Multiplexing hierarchy,
             this object points to the container's interface index."
    ::= { stsVcPathEntry 1 }

stsVcPathIndex OBJECT-TYPE
    SYNTAX      Unsigned32
    MAX-ACCESS  not-accessible
    STATUS      current
    DESCRIPTION
            "This object is his index."
    ::= { stsVcPathEntry 2 }

stsVcPathIfIndex OBJECT-TYPE
    SYNTAX      InterfaceIndex
    MAX-ACCESS  read-only
    STATUS      current
    DESCRIPTION
            "This object has the same value as ifIndex for OCn Path.
             An integer index value used to uniquely identify
             this OCn Path interface."
    ::= { stsVcPathEntry 3 }

stsVcPathAdminState OBJECT-TYPE
    SYNTAX      AdminState 
    MAX-ACCESS  read-write
    STATUS      current
    DESCRIPTION
            "This object represents the Administrative State of the OCn Path."
    ::= { stsVcPathEntry 4 }

stsVcPathOperationalState OBJECT-TYPE
    SYNTAX      OperationalState 
    MAX-ACCESS  read-only
    STATUS      current
    DESCRIPTION
            "This object represents the Operational State of the OCn Path."
    ::= { stsVcPathEntry 5 }

stsVcPathSecondaryState OBJECT-TYPE
    SYNTAX      SecondaryState 
    MAX-ACCESS  read-only
    STATUS      current
    DESCRIPTION
            "This object represents the Secondary State of the OCn Path."
    ::= { stsVcPathEntry 6 }

stsVcPathLoopbackConfig OBJECT-TYPE
    SYNTAX     CmLoopbackType
    MAX-ACCESS read-write
    STATUS     current
    DESCRIPTION
            "This object allows to initiate loopbacks on 
             on the OCn Path."
     ::= { stsVcPathEntry 7 }

stsVcPathLoopbackStatus OBJECT-TYPE
    SYNTAX     CmLoopbackType
    MAX-ACCESS read-only
    STATUS     current
    DESCRIPTION
            "This object provides status of the current loopback 
             on the OCn Path."
     ::= { stsVcPathEntry 8 }

stsVcPathLoopbackTime OBJECT-TYPE
    SYNTAX     Integer32 (2..300)
    MAX-ACCESS read-write
    STATUS     current
    DESCRIPTION
            "This object allows to specify time for timed-loopbacks on 
             on the OCn Path."
     ::= { stsVcPathEntry 9 }

stsVcPathInsertingAIS OBJECT-TYPE
    SYNTAX     TruthValue
    MAX-ACCESS read-write
    STATUS     current
    DESCRIPTION
            "This object allows to insert AIS-P out from OCn Path 
            when it is in maintenance state."
     ::= { stsVcPathEntry 10 }

stsVcPathBerExcThreshold OBJECT-TYPE
    SYNTAX     BitErrRate
    MAX-ACCESS read-write
    STATUS     current
    DESCRIPTION
            "This object provide the threshold of B3EXC."
     ::= { stsVcPathEntry 11 }

stsVcPathBerDegThreshold OBJECT-TYPE
    SYNTAX     BitErrRate
    MAX-ACCESS read-write
    STATUS     current
    DESCRIPTION
            "This object provides the threshold of B3DEG."
     ::= { stsVcPathEntry 12 }

stsVcPathTrailTraceFormat OBJECT-TYPE
    SYNTAX     TrailTraceFormat
    MAX-ACCESS read-write
    STATUS     current
    DESCRIPTION
            "This object provides the J1 length mode on the OCn Path."
     ::= { stsVcPathEntry 13 }

stsVcPathRxTrailTrace OBJECT-TYPE
    SYNTAX     DisplayString (SIZE (0..128))
    MAX-ACCESS read-only
    STATUS     current
    DESCRIPTION
            "This object provides the recevied J1 on the OCn Path."
     ::= { stsVcPathEntry 14 }

stsVcPathTxTrailTrace OBJECT-TYPE
    SYNTAX     DisplayString (SIZE (0..128))
    MAX-ACCESS read-write
    STATUS     current
    DESCRIPTION
            "This object provides the transmit J1 on the OCn Path."
     ::= { stsVcPathEntry 15 }

stsVcPathExpectedTrailTrace OBJECT-TYPE
    SYNTAX     DisplayString (SIZE (0..128))
    MAX-ACCESS read-write
    STATUS     current
    DESCRIPTION
            "This object provides the expected J1 on the OCn Path."
     ::= { stsVcPathEntry 16 }

stsVcPathRxSignalLabel OBJECT-TYPE
    SYNTAX     Unsigned32 (0..255)
    MAX-ACCESS read-only
    STATUS     current
    DESCRIPTION
            "This object provides the recevied C2 on the OCn Path."
     ::= { stsVcPathEntry 17 }

stsVcPathTxSignalLabel OBJECT-TYPE
    SYNTAX     Unsigned32 (0..255)
    MAX-ACCESS read-write
    STATUS     current
    DESCRIPTION
            "This object provides the transmit C2 on the OCn Path."
     ::= { stsVcPathEntry 18 }

stsVcPathExpectedSignalLabel OBJECT-TYPE
    SYNTAX     Unsigned32 (0..255)
    MAX-ACCESS read-write
    STATUS     current
    DESCRIPTION
            "This object provides the expected C2 on the OCn Path."
     ::= { stsVcPathEntry 19 }

stsVcPathRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of stsVcPathRowStatus supported are
            createAndGo(4) and destroy(6).  All mandatory attributes
            must be specified in a single SNMP SET request with
            stsVcPathRowStatus value as createAndGo(4).
            Upon successful row creation, this object has a
            value of active(1).

            The stsVcPathRowStatus object may be modified if
            the associated instance of this object is equal to active(1)."
    ::= { stsVcPathEntry 20 }

stsVcPathLowOrderPathType OBJECT-TYPE 
    SYNTAX     TDMPathType
    MAX-ACCESS read-write
    STATUS     current
    DESCRIPTION
         "This object provides the low Order Path Type of the sts vc interface."
     ::= { stsVcPathEntry 21 }


--
--  VT/VC Table
--
vtVcPathTable  OBJECT-TYPE
    SYNTAX      SEQUENCE OF VtVcPathEntry
    MAX-ACCESS  not-accessible
    STATUS      current
    DESCRIPTION
            "A list of entries corresponding to VT1.5/VC12. These represent the
             lower order path (LOP) entities."
    ::= { cmFacilityObjects 49 }

vtVcPathEntry  OBJECT-TYPE
    SYNTAX      VtVcPathEntry
    MAX-ACCESS  not-accessible
    STATUS      current
    DESCRIPTION
            "A conceptual row in the vtVcPathTable."
    INDEX { neIndex, shelfIndex, slotIndex, ocnStmIndex, 
            vtVcPathParentIfIndex, vtVcPathIndex }
    ::= { vtVcPathTable 1 }

VtVcPathEntry ::= SEQUENCE {
    vtVcPathParentIfIndex           InterfaceIndex,
    vtVcPathIndex                   Unsigned32,
    vtVcPathIfIndex                 InterfaceIndex,
    vtVcPathAdminState              AdminState,
    vtVcPathOperationalState        OperationalState,
    vtVcPathSecondaryState          SecondaryState,
    vtVcPathLoopbackConfig          CmLoopbackType,
    vtVcPathLoopbackStatus          CmLoopbackType,
    vtVcPathLoopbackTime            Integer32,
    vtVcPathInsertingAIS            TruthValue,
    vtVcPathBerExcThreshold         BitErrRate,
    vtVcPathBerDegThreshold         BitErrRate,
    vtVcPathTrailTraceFormat        TrailTraceFormat,
    vtVcPathRxTrailTrace            DisplayString,
    vtVcPathTxTrailTrace            DisplayString,
    vtVcPathExpectedTrailTrace      DisplayString,
    vtVcPathRxSignalLabel           Unsigned32,
    vtVcPathTxSignalLabel           Unsigned32,
    vtVcPathExpectedSignalLabel     Unsigned32,
    vtVcPathRowStatus               RowStatus
}

vtVcPathParentIfIndex OBJECT-TYPE
    SYNTAX      InterfaceIndex
    MAX-ACCESS  not-accessible
    STATUS      current
    DESCRIPTION
            "This object is its parent's ifindex."
    ::= { vtVcPathEntry 1 }

vtVcPathIndex OBJECT-TYPE
    SYNTAX      Unsigned32
    MAX-ACCESS  not-accessible
    STATUS      current
    DESCRIPTION
            "This object represents the unique number of the Path within the
             parent container represented by vtvcPathParentIfIndex."
    ::= { vtVcPathEntry 2 }

vtVcPathIfIndex OBJECT-TYPE
    SYNTAX      InterfaceIndex
    MAX-ACCESS  read-only
    STATUS      current
    DESCRIPTION
            "This object has the same value as ifIndex for OCn VT1.5/VC12.
             An integer index value used to uniquely identify
             this OCn VT1.5/VC12 interface."
    ::= { vtVcPathEntry 3 }

vtVcPathAdminState OBJECT-TYPE
    SYNTAX      AdminState 
    MAX-ACCESS  read-write
    STATUS      current
    DESCRIPTION
            "This object represents the Administrative State of the OCn VT1.5/VC12."
    ::= { vtVcPathEntry 4 }

vtVcPathOperationalState OBJECT-TYPE
    SYNTAX      OperationalState 
    MAX-ACCESS  read-only
    STATUS      current
    DESCRIPTION
            "This object represents the Operational State of the OCn VT1.5/VC12."
    ::= { vtVcPathEntry 5 }

vtVcPathSecondaryState OBJECT-TYPE
    SYNTAX      SecondaryState 
    MAX-ACCESS  read-only
    STATUS      current
    DESCRIPTION
            "This object represents the Secondary State of the OCn VT1.5/VC12."
    ::= { vtVcPathEntry 6 }

vtVcPathLoopbackConfig OBJECT-TYPE
    SYNTAX     CmLoopbackType
    MAX-ACCESS read-write
    STATUS     current
    DESCRIPTION
            "This object allows to initiate loopbacks on 
             on the OCn VT1.5/VC12."
     ::= { vtVcPathEntry 7 }

vtVcPathLoopbackStatus OBJECT-TYPE
    SYNTAX     CmLoopbackType
    MAX-ACCESS read-only
    STATUS     current
    DESCRIPTION
            "This object provides status of the current loopback 
             on the OCn VT1.5/VC12."
     ::= { vtVcPathEntry 8 }

vtVcPathLoopbackTime OBJECT-TYPE
    SYNTAX     Integer32 (2..300)
    MAX-ACCESS read-write
    STATUS     current
    DESCRIPTION
            "This object allows to specify time for timed-loopbacks on 
             on the OCn VT1.5/VC12."
     ::= { vtVcPathEntry 9 }

vtVcPathInsertingAIS OBJECT-TYPE
    SYNTAX     TruthValue
    MAX-ACCESS read-write
    STATUS     current
    DESCRIPTION
            "This object allows to insert AIS-P out from OCn VT1.5/VC12 
            when it is in maintenance state."
     ::= { vtVcPathEntry 10 }

vtVcPathBerExcThreshold OBJECT-TYPE
    SYNTAX     BitErrRate
    MAX-ACCESS read-write
    STATUS     current
    DESCRIPTION
            "This object provide the threshold of BEREXC."
     ::= { vtVcPathEntry 11 }

vtVcPathBerDegThreshold OBJECT-TYPE
    SYNTAX     BitErrRate
    MAX-ACCESS read-write
    STATUS     current
    DESCRIPTION
            "This object provides the threshold of BERDEG."
     ::= { vtVcPathEntry 12 }

vtVcPathTrailTraceFormat OBJECT-TYPE
    SYNTAX     TrailTraceFormat
    MAX-ACCESS read-only
    STATUS     current
    DESCRIPTION
            "This object provides the J2 length mode on the OCn VT1.5/VC12."
     ::= { vtVcPathEntry 13 }

vtVcPathRxTrailTrace OBJECT-TYPE
    SYNTAX     DisplayString (SIZE (0..128))
    MAX-ACCESS read-only
    STATUS     current
    DESCRIPTION
            "This object provides the recevied J2 on the OCn VT1.5/VC12."
     ::= { vtVcPathEntry 14 }

vtVcPathTxTrailTrace OBJECT-TYPE
    SYNTAX     DisplayString (SIZE (0..128))
    MAX-ACCESS read-write
    STATUS     current
    DESCRIPTION
            "This object provides the transmit J2 on the OCn VT1.5/VC12."
     ::= { vtVcPathEntry 15 }

vtVcPathExpectedTrailTrace OBJECT-TYPE
    SYNTAX     DisplayString (SIZE (0..128))
    MAX-ACCESS read-write
    STATUS     current
    DESCRIPTION
            "This object provides the expected J2 on the OCn VT1.5/VC12."
     ::= { vtVcPathEntry 16 }

vtVcPathRxSignalLabel OBJECT-TYPE
    SYNTAX     Unsigned32 (0..7)
    MAX-ACCESS read-only
    STATUS     current
    DESCRIPTION
            "This object provides the recevied V5 byte(b5-b7) on the OCn VT1.5/VC12."
     ::= { vtVcPathEntry 17 }

vtVcPathTxSignalLabel OBJECT-TYPE
    SYNTAX     Unsigned32 (0..7)
    MAX-ACCESS read-write
    STATUS     current
    DESCRIPTION
            "This object provides the transmit V5 byte(b5-b7) on the OCn VT1.5/VC12."
     ::= { vtVcPathEntry 18 }

vtVcPathExpectedSignalLabel OBJECT-TYPE
    SYNTAX     Unsigned32 (0..7)
    MAX-ACCESS read-write
    STATUS     current
    DESCRIPTION
            "This object provides the expected V5 byte(b5-b7) on the OCn VT1.5/VC12."
     ::= { vtVcPathEntry 19 }

vtVcPathRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of vtVcPathRowStatus supported are
            createAndGo(4) and destroy(6).  All mandatory attributes
            must be specified in a single SNMP SET request with
            vtVcPathRowStatus value as createAndGo(4).
            Upon successful row creation, this object has a
            value of active(1).

            The vtVcPathRowStatus object may be modified if
            the associated instance of this object is equal to active(1)."
    ::= { vtVcPathEntry 20 }

--
--  OCn E1T1 Table
--
e1t1Table  OBJECT-TYPE
    SYNTAX      SEQUENCE OF E1T1Entry
    MAX-ACCESS  not-accessible
    STATUS      current
    DESCRIPTION
            "A list of entries corresponding to E1/T1."
    ::= { cmFacilityObjects 50 }

e1t1Entry  OBJECT-TYPE
    SYNTAX      E1T1Entry
    MAX-ACCESS  not-accessible
    STATUS      current
    DESCRIPTION
            "A conceptual row in the e1t1Table."
    INDEX { neIndex, shelfIndex, slotIndex,
            e1t1ParentIfIndex, e1t1Index }
    ::= { e1t1Table 1 }

E1T1Entry ::= SEQUENCE {
    e1t1ParentIfIndex           InterfaceIndex,
    e1t1Index                   Unsigned32,
    e1t1IfIndex                 InterfaceIndex,
    e1t1EntityIndex             PhysicalIndex,
    e1t1AdminState              AdminState,
    e1t1OperationalState        OperationalState,
    e1t1SecondaryState          SecondaryState,
    e1t1LoopbackConfig          CmLoopbackType,
    e1t1LoopbackStatus          CmLoopbackType,
    e1t1LoopbackTime            Integer32,
    e1t1RemoteLoopbackRequest   TruthValue,
    e1t1InsertingAIS            TruthValue,
    e1t1RowStatus               RowStatus,
    e1t1LineType                E1T1LineType,
    e1t1LineCode                E1T1LineCode,
    e1t1FrameFormat             E1T1FrameFormat,
    e1t1LineBuildOut            LineBuildOut,
    e1t1TimingDomain            VariablePointer,
    e1t1RcvSensitivity          E1T1RcvSensitivity,
    e1t1IdlePatternProfile      VariablePointer,
    e1t1LoopbackProfile         VariablePointer,
    e1t1RelatedContainerId      VariablePointer,
    e1t1PatternLpbkControl      TruthValue
}

e1t1ParentIfIndex OBJECT-TYPE
    SYNTAX      InterfaceIndex
    MAX-ACCESS  not-accessible
    STATUS      current
    DESCRIPTION
            "This object represents the parent (container) object's interface index.
             In the case when parent of E1T1Entry does not have a InterfaceIndex 
             then the e1t1ParentIfIndex shall have the value of 2147483647,
             e.g. if parent of E1T1Entry is a card represented in pseudoWireE1T1CardTable."
    ::= { e1t1Entry 1 }

e1t1Index OBJECT-TYPE
    SYNTAX      Unsigned32
    MAX-ACCESS  not-accessible
    STATUS      current
    DESCRIPTION
            "Index value used to uniquely identify
             this E1/T1 interface, within the parent container specified by
             e1t1ParentIfIndex."
    ::= { e1t1Entry 2 }

e1t1IfIndex OBJECT-TYPE
    SYNTAX      InterfaceIndex
    MAX-ACCESS  read-only
    STATUS      current
    DESCRIPTION
            "This object has the same value as ifIndex for E1/T1.
             An integer index value used to uniquely identify
             this E1/T1 interface."
    ::= { e1t1Entry 3 }

e1t1EntityIndex OBJECT-TYPE
    SYNTAX      PhysicalIndex 
    MAX-ACCESS  read-only
    STATUS      current
    DESCRIPTION
           "Entity Index from ENTITY-MIB for this port."
    ::= { e1t1Entry 4 }

e1t1AdminState OBJECT-TYPE
    SYNTAX      AdminState 
    MAX-ACCESS  read-write
    STATUS      current
    DESCRIPTION
            "This object represents the Administrative State of the E1/T1."
    ::= { e1t1Entry 5 }

e1t1OperationalState OBJECT-TYPE
    SYNTAX      OperationalState 
    MAX-ACCESS  read-only
    STATUS      current
    DESCRIPTION
            "This object represents the Operational State of the E1/T1."
    ::= { e1t1Entry 6 }

e1t1SecondaryState OBJECT-TYPE
    SYNTAX      SecondaryState 
    MAX-ACCESS  read-only
    STATUS      current
    DESCRIPTION
            "This object represents the Secondary State of the E1/T1."
    ::= { e1t1Entry 7 }

e1t1LoopbackConfig OBJECT-TYPE
    SYNTAX     CmLoopbackType
    MAX-ACCESS read-write
    STATUS     current
    DESCRIPTION
            "This object allows to initiate loopbacks on 
             on the E1/T1."
     ::= { e1t1Entry 8 }

e1t1LoopbackStatus OBJECT-TYPE
    SYNTAX     CmLoopbackType
    MAX-ACCESS read-only
    STATUS     current
    DESCRIPTION
            "This object provides status of the current loopback 
             on the E1/T1."
     ::= { e1t1Entry 9 }

e1t1LoopbackTime OBJECT-TYPE
    SYNTAX     Integer32 (2..300)
    MAX-ACCESS read-write
    STATUS     current
    DESCRIPTION
            "This object allows to specify time for timed-loopbacks on 
             on the E1/T1."
     ::= { e1t1Entry 10 }

e1t1RemoteLoopbackRequest OBJECT-TYPE
    SYNTAX     TruthValue
    MAX-ACCESS read-write
    STATUS     current
    DESCRIPTION
            "This object allows to specify to repond the remote loopback request or not."
     ::= { e1t1Entry 11 }

e1t1InsertingAIS OBJECT-TYPE
    SYNTAX     TruthValue
    MAX-ACCESS read-write
    STATUS     current
    DESCRIPTION
            "This object allows to insert AIS out from E1/T1 
            when it is in maintenance state."
     ::= { e1t1Entry 12 }

e1t1RowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of e1t1RowStatus supported are
            createAndGo(4) and destroy(6).  All mandatory attributes
            must be specified in a single SNMP SET request with
            e1t1RowStatus value as createAndGo(4).
            Upon successful row creation, this object has a
            value of active(1).

            The e1t1RowStatus object may be modified if
            the associated instance of this object is equal to active(1)."
    ::= { e1t1Entry 13 }

e1t1LineType OBJECT-TYPE
    SYNTAX      E1T1LineType
    MAX-ACCESS  read-only
    STATUS      current
    DESCRIPTION
            "This object represents the E1/T1 Line Type.
             Determines whether the E1/T1 interface operates in T1 or E1 mode."
    ::= { e1t1Entry 14 }

e1t1LineCode OBJECT-TYPE
    SYNTAX      E1T1LineCode
    MAX-ACCESS  read-write
    STATUS      current
    DESCRIPTION
            "This object represents the E1/T1 Port Line Code.
             When the port is configured for a Line Type of T1, 
             the valid values are t1-b8zs and t1-ami and the default value
             is t1-b8zs. When the port is configured for a Line Type of E1, 
             the valid values are e1-hdb3 and e1-ami and the default value 
             is e1-hdb3."
    ::= { e1t1Entry 15 }

e1t1FrameFormat OBJECT-TYPE
    SYNTAX      E1T1FrameFormat
    MAX-ACCESS  read-write
    STATUS      current
    DESCRIPTION
            "This object represents the E1/T1 Port Frame Format.
             When the port is configured for a Line Type of T1, the
             valid values are t1-sf, t1-esf and t1-unframed and the default 
             value is t1-unframed.
             When the port is configured for a Line Type of E1, the
             valid values are e1-unframed, e1-crc4, and e1-dualFrame 
             and the default value is e1-crc4. 

             R5.4CC supports only t1-unframed for T1 Line type."
    ::= { e1t1Entry 16 }

e1t1LineBuildOut OBJECT-TYPE
    SYNTAX      LineBuildOut
    MAX-ACCESS  read-write
    STATUS      current
    DESCRIPTION
            "This object represents Line Build Out on E1/T1 port."

    ::= { e1t1Entry 17 }

e1t1TimingDomain OBJECT-TYPE
    SYNTAX      VariablePointer
    MAX-ACCESS  read-write
    STATUS      current
    DESCRIPTION
         "This object represents Timing Domain that the E1/T1 interface uses as 
          timing source.  The Timing Domain is a Synchronization Entity 
          represented by an object in the f3SyncTable"
    ::= { e1t1Entry 18 }

e1t1RcvSensitivity OBJECT-TYPE
    SYNTAX      E1T1RcvSensitivity
    MAX-ACCESS  read-write
    STATUS      current
    DESCRIPTION
         "This object allows configuring the reciever sensitivity based on expected
          signal strength"
    ::= { e1t1Entry 19 }

e1t1IdlePatternProfile OBJECT-TYPE
    SYNTAX      VariablePointer
    MAX-ACCESS  read-write
    STATUS      current
    DESCRIPTION
         "This object allows selecting Idle Pattern Profile for the E1/T1 interface.
          Idle Patter Profile is represented by an object in the 
          f3Pwe3IdlePatternProfileTable"
    ::= { e1t1Entry 20 }

e1t1LoopbackProfile OBJECT-TYPE
    SYNTAX      VariablePointer
    MAX-ACCESS  read-write
    STATUS      current
    DESCRIPTION
         "This object allows selecting Loopback Profile for the E1/T1 interface.
          Loopback Profile is represented by an object in the 
          f3Pwe3LoopbackProfileTable"
    ::= { e1t1Entry 21 }

e1t1RelatedContainerId OBJECT-TYPE
    SYNTAX      VariablePointer
    MAX-ACCESS  read-only
    STATUS      current
    DESCRIPTION
         "This object describes the related container VCG."
    ::= { e1t1Entry 22 }

e1t1PatternLpbkControl OBJECT-TYPE
    SYNTAX      TruthValue
    MAX-ACCESS  read-write
    STATUS      current
    DESCRIPTION
         "This object allows to enable or disable Pattern Loopback on
          a E1 port." 
    ::= { e1t1Entry 23 }    

--
--  OCn E3T3 Table
--
E3T3Type ::= TEXTUAL-CONVENTION
    STATUS       current
    DESCRIPTION
        "Describes the type of the E3/T3."
    SYNTAX       INTEGER {
                   none (0),
                   e3 (1),
                   t3 (2)
                 }

PortState ::= TEXTUAL-CONVENTION
    STATUS       current
    DESCRIPTION
        "Port states for the eight 16xbits card ports."
    SYNTAX       BITS {
                   port1(0),
                   port2(1),
                   port3(2),
                   port4(3),
                   port5(4),
                   port6(5),
                   port7(6),
                   port8(7)
                 }

e3t3Table  OBJECT-TYPE
    SYNTAX      SEQUENCE OF E3T3Entry
    MAX-ACCESS  not-accessible
    STATUS      current
    DESCRIPTION
            "A list of entries corresponding to E3/T3."
    ::= { cmFacilityObjects 51 }

e3t3Entry  OBJECT-TYPE
    SYNTAX      E3T3Entry
    MAX-ACCESS  not-accessible
    STATUS      current
    DESCRIPTION
            "A conceptual row in the e3t3Table."
    INDEX { neIndex, shelfIndex, slotIndex, 
            e3t3ParentIfIndex, e3t3Index }
    ::= { e3t3Table 1 }

E3T3Entry ::= SEQUENCE {
    e3t3ParentIfIndex           InterfaceIndex,
    e3t3Index                   Unsigned32,
    e3t3IfIndex                 InterfaceIndex,
    e3t3EntityIndex             PhysicalIndex,
    e3t3AdminState              AdminState,
    e3t3OperationalState        OperationalState,
    e3t3SecondaryState          SecondaryState,
    e3t3LoopbackConfig          CmLoopbackType,
    e3t3LoopbackStatus          CmLoopbackType,
    e3t3LoopbackTime            Integer32,
    e3t3RemoteLoopbackRequest   TruthValue,
    e3t3InsertingAIS            TruthValue,
    e3t3CBitEnable              TruthValue,
    e3t3T3Channelized           TruthValue,
    e3t3RowStatus               RowStatus,
    e3t3FrameFormat             E3T3FrameFormat,
    e3t3RelatedContainerId      VariablePointer
}

e3t3ParentIfIndex OBJECT-TYPE
    SYNTAX      InterfaceIndex
    MAX-ACCESS  not-accessible
    STATUS      current
    DESCRIPTION
            "This object is its parent's ifindex."
    ::= { e3t3Entry 1 }

e3t3Index OBJECT-TYPE
    SYNTAX      Unsigned32
    MAX-ACCESS  not-accessible
    STATUS      current
    DESCRIPTION
            "This object is his index."
    ::= { e3t3Entry 2 }

e3t3IfIndex OBJECT-TYPE
    SYNTAX      InterfaceIndex
    MAX-ACCESS  read-only
    STATUS      current
    DESCRIPTION
            "This object has the same value as ifIndex for E3/T3.
             An integer index value used to uniquely identify
             this E3/T3 interface."
    ::= { e3t3Entry 3 }

e3t3EntityIndex OBJECT-TYPE
    SYNTAX      PhysicalIndex 
    MAX-ACCESS  read-only
    STATUS      current
    DESCRIPTION
           "Entity Index from ENTITY-MIB for this port."
    ::= { e3t3Entry 4 }

e3t3AdminState OBJECT-TYPE
    SYNTAX      AdminState 
    MAX-ACCESS  read-write
    STATUS      current
    DESCRIPTION
            "This object represents the Administrative State of the E3/T3."
    ::= { e3t3Entry 5 }

e3t3OperationalState OBJECT-TYPE
    SYNTAX      OperationalState 
    MAX-ACCESS  read-only
    STATUS      current
    DESCRIPTION
            "This object represents the Operational State of the E3/T3."
    ::= { e3t3Entry 6 }

e3t3SecondaryState OBJECT-TYPE
    SYNTAX      SecondaryState 
    MAX-ACCESS  read-only
    STATUS      current
    DESCRIPTION
            "This object represents the Secondary State of the E3/T3."
    ::= { e3t3Entry 7 }

e3t3LoopbackConfig OBJECT-TYPE
    SYNTAX     CmLoopbackType
    MAX-ACCESS read-write
    STATUS     current
    DESCRIPTION
            "This object allows to initiate loopbacks on 
             on the E3/T3."
     ::= { e3t3Entry 8 }

e3t3LoopbackStatus OBJECT-TYPE
    SYNTAX     CmLoopbackType
    MAX-ACCESS read-only
    STATUS     current
    DESCRIPTION
            "This object provides status of the current loopback 
             on the E3/T3."
     ::= { e3t3Entry 9 }

e3t3LoopbackTime OBJECT-TYPE
    SYNTAX     Integer32 (2..300)
    MAX-ACCESS read-write
    STATUS     current
    DESCRIPTION
            "This object allows to specify time for timed-loopbacks on 
             on the E3/T3."
     ::= { e3t3Entry 10 }

e3t3RemoteLoopbackRequest OBJECT-TYPE
    SYNTAX     TruthValue
    MAX-ACCESS read-write
    STATUS     current
    DESCRIPTION
            "This object allows to specify to repond the remote loopback request or not."
     ::= { e3t3Entry 11 }

e3t3InsertingAIS OBJECT-TYPE
    SYNTAX     TruthValue
    MAX-ACCESS read-write
    STATUS     current
    DESCRIPTION
            "This object allows to insert AIS out from E3/T3 
            when it is in maintenance state."
     ::= { e3t3Entry 12 }

e3t3CBitEnable OBJECT-TYPE
    SYNTAX     TruthValue
    MAX-ACCESS read-write
    STATUS     current
    DESCRIPTION
            "The object provides whether C-Bit Parity is enabled/disabled."
     ::= { e3t3Entry 13 }

e3t3T3Channelized OBJECT-TYPE
    SYNTAX     TruthValue
    MAX-ACCESS read-write
    STATUS     current
    DESCRIPTION
            "The object provides whether the T3 tunnel is channlized with T1."
     ::= { e3t3Entry 14 }

e3t3RowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of e3t3RowStatus supported are
            createAndGo(4) and destroy(6).  All mandatory attributes
            must be specified in a single SNMP SET request with
            e3t3RowStatus value as createAndGo(4).
            Upon successful row creation, this object has a
            value of active(1).

            The e3t3RowStatus object may be modified if
            the associated instance of this object is equal to active(1)."
    ::= { e3t3Entry 15 }

e3t3FrameFormat OBJECT-TYPE
    SYNTAX     E3T3FrameFormat
    MAX-ACCESS read-write
    STATUS     current
    DESCRIPTION
            "This object represents the Frame Format of the E3/T3."
     ::= { e3t3Entry 16 }

e3t3RelatedContainerId OBJECT-TYPE
    SYNTAX      VariablePointer
    MAX-ACCESS  read-only
    STATUS      current
    DESCRIPTION
         "This object describe the related contained VCG."
    ::= { e3t3Entry 17 }

--
-- traffic port extense Table
--
cmEthernetTrafficPortExtTable OBJECT-TYPE
    SYNTAX      SEQUENCE OF CmEthernetTrafficPortExtEntry
    MAX-ACCESS  not-accessible
    STATUS      current
    DESCRIPTION
            "A list of entries corresponding to Ethernet 
            Facilities for configuration purposes."
    ::= { cmFacilityObjects 52 }

cmEthernetTrafficPortExtEntry OBJECT-TYPE
    SYNTAX      CmEthernetTrafficPortExtEntry
    MAX-ACCESS  not-accessible
    STATUS      current
    DESCRIPTION
            "A conceptual row in the cmEthernetTrafficPortExtTable."
    AUGMENTS { cmEthernetTrafficPortEntry }
    ::= { cmEthernetTrafficPortExtTable 1 }

CmEthernetTrafficPortExtEntry ::= SEQUENCE {
    cmEthernetTrafficPortTDMEncapsulation       GFPEncapsulationType,
    cmEthernetTrafficPortRelatedVCG             VariablePointer,
    
    -- new 9.1.1 xgpro release columns
    
    cmEthernetTrafficPortMcastRateLimitEnabled           TruthValue,
    cmEthernetTrafficPortMcastRateLimitSpeedLo           Unsigned32,
    cmEthernetTrafficPortMcastRateLimitSpeedHi           Unsigned32,
    cmEthernetTrafficPortBcastRateLimitEnabled           TruthValue,
    cmEthernetTrafficPortBcastRateLimitSpeedLo           Unsigned32,
    cmEthernetTrafficPortBcastRateLimitSpeedHi           Unsigned32,
    cmEthernetTrafficPortCombinedRateLimitEnabled        TruthValue,
    cmEthernetTrafficPortCombinedRateLimitSpeedLo        Unsigned32,
    cmEthernetTrafficPortCombinedRateLimitSpeedHi        Unsigned32,
    cmEthernetTrafficPortRefPrioMapProfile               VariablePointer
    
}

cmEthernetTrafficPortTDMEncapsulation OBJECT-TYPE 
    SYNTAX     GFPEncapsulationType
    MAX-ACCESS read-write
    STATUS     current
    DESCRIPTION
         "This object describes the GFP Encapsulation type of the traffic port."
     ::= { cmEthernetTrafficPortExtEntry 1 }

cmEthernetTrafficPortRelatedVCG OBJECT-TYPE 
    SYNTAX     VariablePointer
    MAX-ACCESS read-only
    STATUS     current
    DESCRIPTION
         "This object describes the related VCG of the traffic port."
     ::= { cmEthernetTrafficPortExtEntry 2 }

cmEthernetTrafficPortMcastRateLimitEnabled OBJECT-TYPE
    SYNTAX      TruthValue
    MAX-ACCESS  read-write
    STATUS      current
    DESCRIPTION
            "Whether multicast packets need be limited on this port." 
    ::= { cmEthernetTrafficPortExtEntry 3 }

cmEthernetTrafficPortMcastRateLimitSpeedLo OBJECT-TYPE
    SYNTAX      Unsigned32
    MAX-ACCESS  read-write
    STATUS      current
    DESCRIPTION
            "The rate limiting for multicast packets per port
             When cmEthernetTrafficPortMcastRateLimitEnabled and the value is 0, 
             it means all multicast frame are dropped.

             This objects only represents low 32 bits." 
    ::= { cmEthernetTrafficPortExtEntry 4 }

cmEthernetTrafficPortMcastRateLimitSpeedHi OBJECT-TYPE
    SYNTAX      Unsigned32
    MAX-ACCESS  read-write
    STATUS      current
    DESCRIPTION
            "The rate limiting for multicast packets per port
             When cmEthernetTrafficPortMcastRateLimitEnabled and the value is 0, 
             it means all multicast frame are dropped.

             This objects only represents high 32 bits." 
    ::= { cmEthernetTrafficPortExtEntry 5 }

cmEthernetTrafficPortBcastRateLimitEnabled OBJECT-TYPE
    SYNTAX      TruthValue
    MAX-ACCESS  read-write
    STATUS      current
    DESCRIPTION
            "Whether broadcast packets need be limited per port." 
    ::= { cmEthernetTrafficPortExtEntry 6 }

cmEthernetTrafficPortBcastRateLimitSpeedLo OBJECT-TYPE
    SYNTAX      Unsigned32
    MAX-ACCESS  read-write
    STATUS      current
    DESCRIPTION
            "The rate limiting for broadcast packets per port
             When cmEthernetTrafficPortBcastRateLimitEnabled and the value is 0, 
             it means all multicast frame are dropped.

             This objects only represents low 32 bits." 
    ::= { cmEthernetTrafficPortExtEntry 7 }

cmEthernetTrafficPortBcastRateLimitSpeedHi OBJECT-TYPE
    SYNTAX      Unsigned32
    MAX-ACCESS  read-write
    STATUS      current
    DESCRIPTION
            "The rate limiting for broadcast packets per port
             When cmEthernetTrafficPortBcastRateLimitEnabled and the value is 0, 
             it means all multicast frame are dropped.

             This objects only represents high 32 bits." 
    ::= { cmEthernetTrafficPortExtEntry 8 }

cmEthernetTrafficPortCombinedRateLimitEnabled OBJECT-TYPE
    SYNTAX      TruthValue
    MAX-ACCESS  read-write
    STATUS      current
    DESCRIPTION
            "Whether multicast and broadcast packets need be limited per port." 
    ::= { cmEthernetTrafficPortExtEntry 9 }

cmEthernetTrafficPortCombinedRateLimitSpeedLo OBJECT-TYPE
    SYNTAX      Unsigned32
    MAX-ACCESS  read-write
    STATUS      current
    DESCRIPTION
            "The rate limiting for multicast and broadcast packets per port.
             This objects only represents low 32 bits." 
    ::= { cmEthernetTrafficPortExtEntry 10 }

cmEthernetTrafficPortCombinedRateLimitSpeedHi OBJECT-TYPE
    SYNTAX      Unsigned32
    MAX-ACCESS  read-write
    STATUS      current
    DESCRIPTION
            "The rate limiting for multicast and broadcast packets per port.
             This objects only represents high 32 bits." 
    ::= { cmEthernetTrafficPortExtEntry 11 }

cmEthernetTrafficPortRefPrioMapProfile OBJECT-TYPE
    SYNTAX      VariablePointer
    MAX-ACCESS  read-write
    STATUS      current
    DESCRIPTION
            "This object allows to set priority map profile." 
    ::= { cmEthernetTrafficPortExtEntry 12 }

--
--  Pulse Per Second Port 
--
f3PulsePerSecondPortTable OBJECT-TYPE
    SYNTAX      SEQUENCE OF F3PulsePerSecondPortEntry 
    MAX-ACCESS  not-accessible
    STATUS      current
    DESCRIPTION
            "A list of entries corresponding to Pulse Per Second 
             Port Facilities."
    ::= { cmFacilityObjects 53 }

f3PulsePerSecondPortEntry OBJECT-TYPE
    SYNTAX      F3PulsePerSecondPortEntry 
    MAX-ACCESS  not-accessible
    STATUS      current
    DESCRIPTION
            "A conceptual row in the f3PulsePerSecondPortTable."
    INDEX { neIndex, shelfIndex, slotIndex, f3PulsePerSecondPortIndex }
    ::= { f3PulsePerSecondPortTable 1 }

F3PulsePerSecondPortEntry ::= SEQUENCE {
    -- Port Indices 
    f3PulsePerSecondPortIndex                  Integer32,
    f3PulsePerSecondPortIfIndex                InterfaceIndex,
    f3PulsePerSecondPortEntityIndex            PhysicalIndex,

    -- State Management params
    f3PulsePerSecondPortAdminState             AdminState,
    f3PulsePerSecondPortOperationalState       OperationalState,
    f3PulsePerSecondPortSecondaryState         SecondaryState,

    -- port specific params
    f3PulsePerSecondPortSquelchControl         SquelchControl,
    f3PulsePerSecondPortSquelchQL              SSMQualityLevel,

    f3PulsePerSecondPortTODSource              VariablePointer,
    f3PulsePerSecondPortDirection              SignalDirectionType,
    f3PulsePerSecondPortInputRate              PPSInputRate,
    f3PulsePerSecondPortDelayCompensation      Integer32,
    f3PulsePerSecondPortClockClass             Unsigned32,
    f3PulsePerSecondPortClockAccuracy          Unsigned32,
    f3PulsePerSecondPortTimeSource             TimeSource,
    f3PulsePerSecondPortPhyInterfaceType       PPSPhyInterfaceType,

    f3PulsePerSecondPortOutputDelay            Unsigned32,
    f3PulsePerSecondPortWidth                  Unsigned32,
    f3PulsePerSecondPortPolarity               PpsPolarity,
    f3PulsePerSecondPortImpedance              PpsPortImpedanceMode,
    f3PulsePerSecondPortAlias                  DisplayString,  
    f3PulsePerSecondPortAssumedClockClass      Unsigned32
}
    
f3PulsePerSecondPortIndex OBJECT-TYPE
    SYNTAX      Integer32 (1..65535)
    MAX-ACCESS  not-accessible
    STATUS      current
    DESCRIPTION
         "An integer index value used to uniquely identify
          this Pulse Per Second Port within the card." 
    ::= { f3PulsePerSecondPortEntry 1 }

f3PulsePerSecondPortIfIndex OBJECT-TYPE
    SYNTAX      InterfaceIndex
    MAX-ACCESS  read-only
    STATUS      current
    DESCRIPTION
         "This object has the same value as ifIndex for 
          Pulse Per Second Port.  An integer index value used to 
          uniquely identify this Pulse Per Second Port."
    ::= { f3PulsePerSecondPortEntry 2 }

f3PulsePerSecondPortEntityIndex OBJECT-TYPE
    SYNTAX      PhysicalIndex 
    MAX-ACCESS  read-only
    STATUS      current
    DESCRIPTION
           "Entity Index from ENTITY-MIB for this port."
    ::= { f3PulsePerSecondPortEntry 3 }

-- State Management params
f3PulsePerSecondPortAdminState OBJECT-TYPE
    SYNTAX      AdminState 
    MAX-ACCESS  read-write
    STATUS      current
    DESCRIPTION
            "This object represents the Administrative State of the Pulse Per Second 
             Port."
    ::= { f3PulsePerSecondPortEntry 4 }

f3PulsePerSecondPortOperationalState OBJECT-TYPE
    SYNTAX      OperationalState 
    MAX-ACCESS  read-only
    STATUS      current
    DESCRIPTION
            "This object represents the Operational State of the Pulse Per Second 
             Port."
    ::= { f3PulsePerSecondPortEntry 5 }

f3PulsePerSecondPortSecondaryState OBJECT-TYPE
    SYNTAX      SecondaryState 
    MAX-ACCESS  read-only
    STATUS      current
    DESCRIPTION
            "This object represents the Secondary State of the Pulse Per Second 
             Port."
    ::= { f3PulsePerSecondPortEntry 6 }

f3PulsePerSecondPortSquelchControl  OBJECT-TYPE 
    SYNTAX     SquelchControl
    MAX-ACCESS read-write
    STATUS     current
    DESCRIPTION
         "This object allows to set the Squelch Control for the Pulse Per Second port. 
          The Squelch Control is used to determine the type of squelch control 
          used to squelch the output of the TOD port."
     ::= { f3PulsePerSecondPortEntry 7 }

f3PulsePerSecondPortSquelchQL OBJECT-TYPE 
    SYNTAX     SSMQualityLevel
    MAX-ACCESS read-write
    STATUS     current
    DESCRIPTION
         "This object allows to set the Squelch QL for the Pulse Per Second port. 
          This value is used when f3PulsePerSecondPortSquelchControl is squelch-ql.
          The Squelch QL is used to determine whether or not to squelch 
          the output of the TOD port. If the system's QL is lower 
          than the Squelch QL, the output is squelched."
     ::= { f3PulsePerSecondPortEntry 8 }

f3PulsePerSecondPortTODSource OBJECT-TYPE 
    SYNTAX     VariablePointer
    MAX-ACCESS read-write
    STATUS     current
    DESCRIPTION
         "This object allows to set the Pulse Per Second Source for the Port." 
     ::= { f3PulsePerSecondPortEntry 9 }

f3PulsePerSecondPortDirection OBJECT-TYPE
    SYNTAX      SignalDirectionType 
    MAX-ACCESS  read-write
    STATUS      current
    DESCRIPTION
            "This object allows specification of the signal type 
             (i.e. input or output)."
    ::= { f3PulsePerSecondPortEntry 10 }

f3PulsePerSecondPortInputRate OBJECT-TYPE
    SYNTAX      PPSInputRate 
    MAX-ACCESS  read-write
    STATUS      current
    DESCRIPTION
            "This object allows specification of the PPS Input Rate." 
    ::= { f3PulsePerSecondPortEntry 11 }

f3PulsePerSecondPortDelayCompensation OBJECT-TYPE
    SYNTAX      Integer32 (-5000000..5000000)
    MAX-ACCESS  read-write
    STATUS      current
    DESCRIPTION
            "This object allows specification of the PPS external Delay
             Compensation in nanoseconds in 8 nanoseconds steps.
             For input port, that is with input Signal Direction, the
             valid values are -5000000 to 5000000.
             Whereas for output port, the valid values are 0 to 90.
             Values which are not multiple of 8 will be automatically
             rounded up to the next multiple of 8." 
    ::= { f3PulsePerSecondPortEntry 12 }

f3PulsePerSecondPortClockClass OBJECT-TYPE
    SYNTAX      Unsigned32
    MAX-ACCESS  read-only
    STATUS      deprecated
    DESCRIPTION
           "This object specify PPS port clock class."
    ::= { f3PulsePerSecondPortEntry 13 }

f3PulsePerSecondPortClockAccuracy OBJECT-TYPE
    SYNTAX      Unsigned32
    MAX-ACCESS  read-only
    STATUS      deprecated
    DESCRIPTION
           "This object specify PPS port clock accuracy."
    ::= { f3PulsePerSecondPortEntry 14 }

f3PulsePerSecondPortTimeSource OBJECT-TYPE
    SYNTAX      TimeSource
    MAX-ACCESS  read-only
    STATUS      deprecated
    DESCRIPTION
           "This object specify PPS port time source."
    ::= { f3PulsePerSecondPortEntry 15 }

f3PulsePerSecondPortPhyInterfaceType OBJECT-TYPE
    SYNTAX      PPSPhyInterfaceType
    MAX-ACCESS  read-write
    STATUS      current
    DESCRIPTION
           "This object specify PPS physical interface type."
    ::= { f3PulsePerSecondPortEntry 16 }

f3PulsePerSecondPortOutputDelay OBJECT-TYPE
    SYNTAX      Unsigned32 (0..999999999)
    MAX-ACCESS  read-write
    STATUS      current
    DESCRIPTION
         "This object allows specification of the PPS Output Delay
          in nanoseconds. The valid values are 0 to 999999999 in 
          10 nanoseconds steps. Values which are not multiple of 10 will
          be automatically rounded up to the next multiple of 10." 
    ::= { f3PulsePerSecondPortEntry 17 }

f3PulsePerSecondPortWidth OBJECT-TYPE
    SYNTAX      Unsigned32 (0..250000)
    MAX-ACCESS  read-write
    STATUS      current
    DESCRIPTION
         "This object allows specification of the Width of the PPS 
          signal on the PPS Port. The valid values are 0 to 250000 in 
          1 microsecond unit." 
    ::= { f3PulsePerSecondPortEntry 18 }

f3PulsePerSecondPortPolarity OBJECT-TYPE
    SYNTAX      PpsPolarity
    MAX-ACCESS  read-write
    STATUS      current
    DESCRIPTION
         "This object allows specification of the Polarity of the PPS 
          signal on the PPS Port." 
    ::= { f3PulsePerSecondPortEntry 19 }

f3PulsePerSecondPortImpedance OBJECT-TYPE 
    SYNTAX     PpsPortImpedanceMode
    MAX-ACCESS read-write
    STATUS     current
    DESCRIPTION
         "This object allows specification of the impedance mode for 
          an input PPS port.
          It is only an indication and cannot be set for an output PPS Port."
     ::= { f3PulsePerSecondPortEntry 20 }

f3PulsePerSecondPortAlias OBJECT-TYPE
    SYNTAX         DisplayString (SIZE(0..64))
    MAX-ACCESS     read-create
    STATUS         current
    DESCRIPTION    "This object allows SNMP management entities to provide an
        alias to the PPS port."
    ::= { f3PulsePerSecondPortEntry 21 }

f3PulsePerSecondPortAssumedClockClass OBJECT-TYPE 
    SYNTAX     Unsigned32 (0..255)
    MAX-ACCESS read-write
    STATUS     current
    DESCRIPTION
         "This object allows specification of the Assumed Clock Class for 
          an input PPS port.
          It is only an indication and cannot be set for an output PPS Port."
     ::= { f3PulsePerSecondPortEntry 22 }


--
--  Time Of Day Port 
--
f3TimeOfDayPortTable OBJECT-TYPE
    SYNTAX      SEQUENCE OF F3TimeOfDayPortEntry 
    MAX-ACCESS  not-accessible
    STATUS      current
    DESCRIPTION
            "A list of entries corresponding to Time Of Day 
             Port Facilities."
    ::= { cmFacilityObjects 55 }

f3TimeOfDayPortEntry OBJECT-TYPE
    SYNTAX      F3TimeOfDayPortEntry 
    MAX-ACCESS  not-accessible
    STATUS      current
    DESCRIPTION
            "A conceptual row in the f3TimeOfDayPortTable."
    INDEX { neIndex, shelfIndex, slotIndex, f3TimeOfDayPortIndex }
    ::= { f3TimeOfDayPortTable 1 }

F3TimeOfDayPortEntry ::= SEQUENCE {
    -- Port Indices 
    f3TimeOfDayPortIndex                  Integer32,
    f3TimeOfDayPortIfIndex                InterfaceIndex,
    f3TimeOfDayPortEntityIndex            PhysicalIndex,

    -- State Management params
    f3TimeOfDayPortAdminState             AdminState,
    f3TimeOfDayPortOperationalState       OperationalState,
    f3TimeOfDayPortSecondaryState         SecondaryState,

    -- port specific params
    f3TimeOfDayPortSquelchControl         SquelchControl,
    f3TimeOfDayPortSquelchQL              SSMQualityLevel,

    f3TimeOfDayPortTODSource              VariablePointer,
    f3TimeOfDayPortOutputFormat       TODOutputFormat,
    f3TimeOfDayPortSignalDirection        SignalDirectionType,
    f3TimeOfDayPortInputRate          PPSInputRate,
    f3TimeOfDayPortDelayCompensation      Integer32,
    f3TimeOfDayPortAlias                  DisplayString,
    f3TimeOfDayPortAssumedClockClass      Unsigned32
}
    
f3TimeOfDayPortIndex OBJECT-TYPE
    SYNTAX      Integer32 (1..65535)
    MAX-ACCESS  not-accessible
    STATUS      current
    DESCRIPTION
         "An integer index value used to uniquely identify
          this Time Of Day Port within the card." 
    ::= { f3TimeOfDayPortEntry 1 }

f3TimeOfDayPortIfIndex OBJECT-TYPE
    SYNTAX      InterfaceIndex
    MAX-ACCESS  read-only
    STATUS      current
    DESCRIPTION
         "This object has the same value as ifIndex for 
          Time Of Day Port.  An integer index value used to 
          uniquely identify this Time Of Day Port."
    ::= { f3TimeOfDayPortEntry 2 }

f3TimeOfDayPortEntityIndex OBJECT-TYPE
    SYNTAX      PhysicalIndex 
    MAX-ACCESS  read-only
    STATUS      current
    DESCRIPTION
           "Entity Index from ENTITY-MIB for this port."
    ::= { f3TimeOfDayPortEntry 3 }

-- State Management params
f3TimeOfDayPortAdminState OBJECT-TYPE
    SYNTAX      AdminState 
    MAX-ACCESS  read-write
    STATUS      current
    DESCRIPTION
            "This object represents the Administrative State of the Time Of Day 
             Port."
    ::= { f3TimeOfDayPortEntry 4 }

f3TimeOfDayPortOperationalState OBJECT-TYPE
    SYNTAX      OperationalState 
    MAX-ACCESS  read-only
    STATUS      current
    DESCRIPTION
            "This object represents the Operational State of the Time Of Day 
             Port."
    ::= { f3TimeOfDayPortEntry 5 }

f3TimeOfDayPortSecondaryState OBJECT-TYPE
    SYNTAX      SecondaryState 
    MAX-ACCESS  read-only
    STATUS      current
    DESCRIPTION
            "This object represents the Secondary State of the Time Of Day 
             Port."
    ::= { f3TimeOfDayPortEntry 6 }

f3TimeOfDayPortSquelchControl  OBJECT-TYPE 
    SYNTAX     SquelchControl
    MAX-ACCESS read-write
    STATUS     current
    DESCRIPTION
         "This object allows to set the Squelch Control for the Time Of Day port. 
          The Squelch Control is used to determine the type of squelch control 
          used to squelch the output of the TOD port."
     ::= { f3TimeOfDayPortEntry 7 }

f3TimeOfDayPortSquelchQL OBJECT-TYPE 
    SYNTAX     SSMQualityLevel
    MAX-ACCESS read-write
    STATUS     current
    DESCRIPTION
         "This object allows to set the Squelch QL for the Time Of Day port. 
          This value is used when f3TimeOfDayPortSquelchControl is squelch-ql.
          The Squelch QL is used to determine whether or not to squelch 
          the output of the TOD port. If the system's QL is lower 
          than the Squelch QL, the output is squelched."
     ::= { f3TimeOfDayPortEntry 8 }

f3TimeOfDayPortTODSource OBJECT-TYPE 
    SYNTAX     VariablePointer
    MAX-ACCESS read-write
    STATUS     current
    DESCRIPTION
         "This object allows to set the Time Of Day Source for the Port." 
     ::= { f3TimeOfDayPortEntry 9 }

f3TimeOfDayPortOutputFormat  OBJECT-TYPE 
    SYNTAX     TODOutputFormat
    MAX-ACCESS read-write
    STATUS     current
    DESCRIPTION
         "This object allows to set the Output Format for the Time Of Day port. 
          The Output Format is used to determine the type of output format 
          of the TOD port."
     ::= { f3TimeOfDayPortEntry 10 }

f3TimeOfDayPortSignalDirection  OBJECT-TYPE 
    SYNTAX     SignalDirectionType
    MAX-ACCESS read-write
    STATUS     current
    DESCRIPTION
         "This object allows specification of the signal direction type 
             (i.e. input or output)."
     ::= { f3TimeOfDayPortEntry 11 }

f3TimeOfDayPortInputRate  OBJECT-TYPE 
    SYNTAX     PPSInputRate
    MAX-ACCESS read-write
    STATUS     current
    DESCRIPTION
         "This object allows specification of the Time Of Day Input Rate."
     ::= { f3TimeOfDayPortEntry 12 }

f3TimeOfDayPortDelayCompensation  OBJECT-TYPE 
    SYNTAX     Integer32 (-5000000..5000000)
    MAX-ACCESS read-write
    STATUS     current
    DESCRIPTION
         "This object allows specification of the TOD external Delay
             Compensation in nanoseconds. For input port, that is with 
             input Signal Direction, the valid values are -5000000 to 5000000
             in 8 nanoseconds steps. Values which are not multiple of 8 will
             be automatically rounded up to the next multiple of 8."
     ::= { f3TimeOfDayPortEntry 13 }

f3TimeOfDayPortAlias OBJECT-TYPE
    SYNTAX         DisplayString (SIZE(0..64))
    MAX-ACCESS     read-create
    STATUS         current
    DESCRIPTION    "This object allows SNMP management entities to provide an
        alias to the Time Of Day port."
    ::= { f3TimeOfDayPortEntry 14 }


f3TimeOfDayPortAssumedClockClass OBJECT-TYPE 
    SYNTAX     Unsigned32 (0..255)
    MAX-ACCESS read-write
    STATUS     current
    DESCRIPTION
         "This object allows specification of the Assumed Clock Class for 
          an input TOD port.
          It is only an indication and cannot be set for an output TOD Port."
     ::= { f3TimeOfDayPortEntry 15 }

--
-- network port extense Table
--
cmEthernetNetPortExtTable OBJECT-TYPE
    SYNTAX      SEQUENCE OF CmEthernetNetPortExtEntry
    MAX-ACCESS  not-accessible
    STATUS      current
    DESCRIPTION
            "A list of entries corresponding to Ethernet Network Port 
            Facilities for configuration purposes."
    ::= { cmFacilityObjects 56 }

cmEthernetNetPortExtEntry OBJECT-TYPE
    SYNTAX      CmEthernetNetPortExtEntry
    MAX-ACCESS  not-accessible
    STATUS      current
    DESCRIPTION
            "A conceptual row in the cmEthernetNetPortExtTable."
    AUGMENTS { cmEthernetNetPortEntry }
    ::= { cmEthernetNetPortExtTable 1 }

CmEthernetNetPortExtEntry ::= SEQUENCE {
    cmEthernetNetPortTDMEncapsulation          GFPEncapsulationType,
    cmEthernetNetPortAssociatedTdmEntity       VariablePointer,    
    cmEthernetNetPortInsertingAIS              TruthValue
}

cmEthernetNetPortTDMEncapsulation OBJECT-TYPE 
    SYNTAX     GFPEncapsulationType
    MAX-ACCESS read-write
    STATUS     current
    DESCRIPTION
         "This object describes the GFP Encapsulation type of the TDM network port."
     ::= { cmEthernetNetPortExtEntry 1 }

cmEthernetNetPortAssociatedTdmEntity OBJECT-TYPE 
    SYNTAX     VariablePointer
    MAX-ACCESS read-write
    STATUS     current
    DESCRIPTION
         "This object describes the associated working path of TDM network port."
     ::= { cmEthernetNetPortExtEntry 2 }

cmEthernetNetPortInsertingAIS OBJECT-TYPE
    SYNTAX      TruthValue  
    MAX-ACCESS  read-write
    STATUS      current
    DESCRIPTION
        "This object allows to insert AIS out from TDM network port 
          when it is in maintenance state."
    ::= { cmEthernetNetPortExtEntry 3 }

--
--  GPS Receiver Port  
--
f3GPSReceiverPortTable OBJECT-TYPE
    SYNTAX      SEQUENCE OF F3GPSReceiverPortEntry 
    MAX-ACCESS  not-accessible
    STATUS      current
    DESCRIPTION
            "A list of entries corresponding to the GPS Receiver Port 
             Facilities."
    ::= { cmFacilityObjects 57 }

f3GPSReceiverPortEntry OBJECT-TYPE
    SYNTAX      F3GPSReceiverPortEntry 
    MAX-ACCESS  not-accessible
    STATUS      current
    DESCRIPTION
            "A conceptual row in the f3GPSReceiverPortTable."
    INDEX { neIndex, shelfIndex, slotIndex, f3GPSReceiverPortIndex }
    ::= { f3GPSReceiverPortTable 1 }

F3GPSReceiverPortEntry ::= SEQUENCE {
    -- Port Indices 
    f3GPSReceiverPortIndex                  Integer32,
    f3GPSReceiverPortIfIndex                InterfaceIndex,
    f3GPSReceiverPortEntityIndex            PhysicalIndex,

    -- State Management params
    f3GPSReceiverPortAdminState             AdminState,
    f3GPSReceiverPortOperationalState       OperationalState,
    f3GPSReceiverPortSecondaryState         SecondaryState,

    -- port specific params
    f3GPSReceiverPortPPSGenCondition        PPSGenCondition,
    f3GPSReceiverPortAntennaCableLength     Unsigned32,
    f3GPSReceiverPortAntennaStatus          GPSAntennaStatus,
    f3GPSReceiverPortSatellitesUsableFlag   TruthValue,
    f3GPSReceiverPortNumTrackingSatellites  Unsigned32,
    f3GPSReceiverPortSelfSurveyProgress     Unsigned32,
    f3GPSReceiverPortPPSGeneratedFlag       TruthValue,

    f3GPSReceiverPortGnssSystem             ConstellationType,
    f3GPSReceiverPortInstallationType       InstallationType,
    f3GPSReceiverPortGnssTOD                DateAndTime,
    f3GPSReceiverPortGnssSystemsBitMap      ConstellationTypesBitMap,
    f3GPSReceiverPortAlias                  DisplayString,
    f3GPSReceiverPortAntennaDelayValue      Integer32,
    f3GPSReceiverPortAntennaDelayType       DelayOption,
    f3GPSReceiverPortCNOMask            Unsigned32,
    f3GPSReceiverPortElevationMask          Unsigned32,
    f3GPSReceiverPortCoordinateLatitude     DisplayString,
    f3GPSReceiverPortCoordinateLongitude    DisplayString,
    f3GPSReceiverPortCoordinateAltitude     Unsigned32,
    f3GPSReceiverPortFirmwareUpgradePercent Integer32,
    f3GPSReceiverPortPDOPMask               Unsigned32,
    f3GPSReceiverPortSelfSurveyPeriod       Unsigned32,
    f3GPSReceiverPortSatMin1Threshold       Unsigned32,
    f3GPSReceiverPortSatMin2Threshold       Unsigned32,
    f3GPSReceiverPortPDOP                   Unsigned32,
    f3GPSReceiverPortSelfSurveyControl      ToggleValue,
    f3GPSReceiverPortCoordinateStringAltitude     DisplayString,
    f3GPSReceiverPortLocationMode                 LocationMode,
    f3GPSReceiverPortTimeAdvanceMode              TimeAdvanceMode,
    f3GPSReceiverPortTimeAdvanceValue             Integer32,
    f3GPSReceiverPortForcedAntennaConnected       ToggleValue,
    f3GPSReceiverPortServiceAvailableTime         Unsigned32,
    f3GPSReceiverPortServiceUnavailableTime       Unsigned32,
    f3GPSReceiverPortServiceAvailablePercentage   DisplayString,
    f3GPSReceiverPortAGC                          Integer32,
    f3GPSReceiverPortSelfSurveyPositionAccuracy   Unsigned32,
    f3GPSReceiverPortHorizontalAccuracy           Unsigned32,
    f3GPSReceiverPortVerticalAccuracy             Unsigned32,
    f3GPSReceiverPortTDOP                         Unsigned32,
    f3GPSReceiverPortHDOP                         Unsigned32,
    f3GPSReceiverPortVDOP                         Unsigned32,
    f3GPSReceiverPortFailureSuspendTime           Unsigned32,
    f3GPSReceiverPortSpoofingPpsThreshold         Unsigned32,
    f3GPSReceiverPortSpoofingPpsDifference        Unsigned32,
    f3GPSReceiverPortSpoofingLocationThreshold    Unsigned32,
    f3GPSReceiverPortSpoofingLocationDifference   Unsigned32,
    f3GPSReceiverPortGnssDynamicModel             DynamicModelType
}
    
f3GPSReceiverPortIndex OBJECT-TYPE
    SYNTAX      Integer32 (1..65535)
    MAX-ACCESS  not-accessible
    STATUS      current
    DESCRIPTION
         "An integer index value used to uniquely identify
          this GPS Receiver Port within the card." 
    ::= { f3GPSReceiverPortEntry 1 }

f3GPSReceiverPortIfIndex OBJECT-TYPE
    SYNTAX      InterfaceIndex
    MAX-ACCESS  read-only
    STATUS      current
    DESCRIPTION
         "This object has the same value as ifIndex for 
          Time Of Day Port.  An integer index value used to 
          uniquely identify this GPS Receiver Port."
    ::= { f3GPSReceiverPortEntry 2 }

f3GPSReceiverPortEntityIndex OBJECT-TYPE
    SYNTAX      PhysicalIndex 
    MAX-ACCESS  read-only
    STATUS      current
    DESCRIPTION
           "Entity Index from ENTITY-MIB for this port."
    ::= { f3GPSReceiverPortEntry 3 }

-- State Management params
f3GPSReceiverPortAdminState OBJECT-TYPE
    SYNTAX      AdminState 
    MAX-ACCESS  read-write
    STATUS      current
    DESCRIPTION
            "This object represents the Administrative State of the GPS
             Receiver Port." 
    ::= { f3GPSReceiverPortEntry 4 }

f3GPSReceiverPortOperationalState OBJECT-TYPE
    SYNTAX      OperationalState 
    MAX-ACCESS  read-only
    STATUS      current
    DESCRIPTION
            "This object represents the Operational State of the GPS 
             Receiver Port."
    ::= { f3GPSReceiverPortEntry 5 }

f3GPSReceiverPortSecondaryState OBJECT-TYPE
    SYNTAX      SecondaryState 
    MAX-ACCESS  read-only
    STATUS      current
    DESCRIPTION
            "This object represents the Secondary State of the GPS 
             Receiver Port."
    ::= { f3GPSReceiverPortEntry 6 }

f3GPSReceiverPortPPSGenCondition OBJECT-TYPE
    SYNTAX      PPSGenCondition 
    MAX-ACCESS  read-write
    STATUS      current
    DESCRIPTION
            "This object allows for configuration of the PPS generation
             condition.  PPS is generated when at least one satellite
             is tracked or when at least three satellites are tracked."
    ::= { f3GPSReceiverPortEntry 7 }

f3GPSReceiverPortAntennaCableLength OBJECT-TYPE
    SYNTAX      Unsigned32 
    MAX-ACCESS  read-write
    STATUS      deprecated
    DESCRIPTION
            "This object allows for configuration of the GPS
             Antenna cable length in meters.
         This object is deprecated and replaced by 
         f3GPSReceiverPortAntennaDelayValue." 
    ::= { f3GPSReceiverPortEntry 8 }

f3GPSReceiverPortAntennaStatus OBJECT-TYPE
    SYNTAX      GPSAntennaStatus 
    MAX-ACCESS  read-only
    STATUS      current
    DESCRIPTION
            "This object provides the GPS Receiver Port Antenna status." 
    ::= { f3GPSReceiverPortEntry 9 }

f3GPSReceiverPortSatellitesUsableFlag OBJECT-TYPE
    SYNTAX      TruthValue 
    MAX-ACCESS  read-only
    STATUS      current
    DESCRIPTION
            "This object provides information on whether the satellites are
             usable.  It is set to TRUE, when ephemeris and health data for
             at least one satellite is available."
    ::= { f3GPSReceiverPortEntry 10 }

f3GPSReceiverPortNumTrackingSatellites OBJECT-TYPE
    SYNTAX      Unsigned32 
    MAX-ACCESS  read-only
    STATUS      current
    DESCRIPTION
            "This object provides information on the number of tracking 
             satellites." 
    ::= { f3GPSReceiverPortEntry 11 }

f3GPSReceiverPortSelfSurveyProgress OBJECT-TYPE
    SYNTAX      Unsigned32
    MAX-ACCESS  read-only
    STATUS      current
    DESCRIPTION
            "This object provides information on the percentage of
             fixes collected so far." 
    ::= { f3GPSReceiverPortEntry 12 }

f3GPSReceiverPortPPSGeneratedFlag OBJECT-TYPE 
    SYNTAX     TruthValue
    MAX-ACCESS read-only
    STATUS     current
    DESCRIPTION
         "This object indicates whether there are enough usable satellites
          to provide accurate PPS output."
     ::= { f3GPSReceiverPortEntry 13 }


f3GPSReceiverPortGnssSystem OBJECT-TYPE 
    SYNTAX     ConstellationType
    MAX-ACCESS read-write
    STATUS     deprecated
    DESCRIPTION
            "This object configure Constellation Type of the GPS
             Antenna." 
     ::= { f3GPSReceiverPortEntry 14 }

f3GPSReceiverPortInstallationType OBJECT-TYPE 
    SYNTAX     InstallationType
    MAX-ACCESS read-write
    STATUS     current
    DESCRIPTION
            "This object configure Installation Type of the GPS
             Antenna." 
     ::= { f3GPSReceiverPortEntry 15 }

f3GPSReceiverPortGnssTOD OBJECT-TYPE 
    SYNTAX     DateAndTime
    MAX-ACCESS read-only
    STATUS     current
    DESCRIPTION
            "This object provides the last time was executed."
     ::= { f3GPSReceiverPortEntry 16 }

f3GPSReceiverPortGnssSystemsBitMap OBJECT-TYPE  
    SYNTAX     ConstellationTypesBitMap 
    MAX-ACCESS read-write 
    STATUS     current 
    DESCRIPTION 
        "This object configures GNSS constellation types supported by a GNSS Receiver Port"
     ::= { f3GPSReceiverPortEntry 17 }

f3GPSReceiverPortAlias OBJECT-TYPE 
    SYNTAX     DisplayString (SIZE(0..64))
    MAX-ACCESS read-create
    STATUS     current
    DESCRIPTION
            "This object provides an alias to the GPS port"
     ::= { f3GPSReceiverPortEntry 18 }

f3GPSReceiverPortAntennaDelayValue OBJECT-TYPE 
    SYNTAX     Integer32 
    MAX-ACCESS read-write
    STATUS     current
    DESCRIPTION
            "This object configures GNSS antenna cable delay used by the GNSS 
        Receiver Port, in units determined by 
        f3GPSReceiverPortAntennaDelayType object."
     ::= { f3GPSReceiverPortEntry 19 }

f3GPSReceiverPortAntennaDelayType OBJECT-TYPE 
    SYNTAX     DelayOption 
    MAX-ACCESS read-write
    STATUS     current
    DESCRIPTION
            "This object configures GNSS antenna cable delay type (units)"
     ::= { f3GPSReceiverPortEntry 20 }

f3GPSReceiverPortCNOMask OBJECT-TYPE 
    SYNTAX     Unsigned32 (0..55)
    MAX-ACCESS read-write
    STATUS     current
    DESCRIPTION
            "This object configures the C/No mask in dB-Hz units, used by the
        GNSS Receiver Port."
     ::= { f3GPSReceiverPortEntry 21 }

f3GPSReceiverPortElevationMask OBJECT-TYPE 
    SYNTAX     Unsigned32 (0..90) 
    MAX-ACCESS read-write
    STATUS     current
    DESCRIPTION
            "This object configures the elevation mask in degrees, used by the
        GNSS Receiver Port."
     ::= { f3GPSReceiverPortEntry 22 }

f3GPSReceiverPortCoordinateLatitude OBJECT-TYPE 
    SYNTAX     DisplayString (SIZE(0..15))
    MAX-ACCESS read-write
    STATUS     current
    DESCRIPTION
            "This object provides the GNSS Receiver Port coordinate latitude in 
        the following format: N|Sddd:mm:ss.sss (d=degrees, m=minutes, s=seconds)
        e.g. N37:22:44.123."
     ::= { f3GPSReceiverPortEntry 23 }

f3GPSReceiverPortCoordinateLongitude OBJECT-TYPE 
    SYNTAX     DisplayString (SIZE(0..15))
    MAX-ACCESS read-write
    STATUS     current
    DESCRIPTION
            "This object provides the GNSS Receiver Port coordinate longitude in 
        the following format: E|Wddd:mm:ss.sss (d=degrees, m=minutes, s=seconds)
        e.g. E157:53:33.456."
     ::= { f3GPSReceiverPortEntry 24 }

f3GPSReceiverPortCoordinateAltitude OBJECT-TYPE 
    SYNTAX     Unsigned32 (0..99999) 
    MAX-ACCESS read-only
    STATUS     current
    DESCRIPTION
            "This object provides the GNSS Receiver Port coordinate altitude in meters."
     ::= { f3GPSReceiverPortEntry 25 }

f3GPSReceiverPortFirmwareUpgradePercent OBJECT-TYPE 
    SYNTAX     Integer32
    MAX-ACCESS read-only
    STATUS     current
    DESCRIPTION
            "This object describes the firmware upgrade percent value.
            Note: value 255 means NA."
     ::= { f3GPSReceiverPortEntry 26 }

f3GPSReceiverPortPDOPMask OBJECT-TYPE 
    SYNTAX     Unsigned32 (200..1200) 
    MAX-ACCESS read-write
    STATUS     current
    DESCRIPTION
        "This object configures PDOP Mask used by the GNSS Receiver.
         The mask value is expressed in hundredth of the PDOP definition
         value and it is rounded to the nearest multiple of hundreds.
         For instance, a value of 200 means that GNSS Receiver stops
         collecting data when f3GPSReceiverPortPDOP value exceeds 200."
     ::= { f3GPSReceiverPortEntry 27 }

f3GPSReceiverPortSelfSurveyPeriod OBJECT-TYPE 
    SYNTAX     Unsigned32 (1..500000) 
    MAX-ACCESS read-write
    STATUS     current
    DESCRIPTION
        "This object configures the Self Survey Period used by the GNSS Receiver."
     ::= { f3GPSReceiverPortEntry 28 }

f3GPSReceiverPortSatMin1Threshold OBJECT-TYPE 
    SYNTAX     Unsigned32 (1..32) 
    MAX-ACCESS read-write
    STATUS     current
    DESCRIPTION
        "This object configures the first threshold for the minimum of satellites
         used by the GNSS Receiver. SatMin1 must be stricly greater than SatMin2."
     ::= { f3GPSReceiverPortEntry 29 }

f3GPSReceiverPortSatMin2Threshold OBJECT-TYPE 
    SYNTAX     Unsigned32 (1..32) 
    MAX-ACCESS read-write
    STATUS     current
    DESCRIPTION
        "This object configures the second threshold for the minimum of satellites
         used by the GNSS Receiver. SatMin1 must be stricly greater than SatMin2."
     ::= { f3GPSReceiverPortEntry 30 }

f3GPSReceiverPortPDOP OBJECT-TYPE 
    SYNTAX     Unsigned32 (0..4095)
    MAX-ACCESS read-only
    STATUS     current
    DESCRIPTION
        "This object provides the dimensionless PDOP value calculated by the GNSS 
         Receiver while GNSS Receiver Survey Pogress is not complete yet.
         The value is expressed in hundredth of the PDOP definition. For instance, a 
         value of 153 means that PDOP calculated by GNSS Receiver is 1.53. 
         When the value cannot be evaluated by the GNSS Receiver or when Survey Progress
         is complete, the value is shown with the maximum range value 4095."
     ::= { f3GPSReceiverPortEntry 31 }

f3GPSReceiverPortSelfSurveyControl OBJECT-TYPE 
    SYNTAX     ToggleValue
    MAX-ACCESS read-write
    STATUS     current
    DESCRIPTION
        "This object allows to enable or disable the automatic location control. 
         When it is enabled, the location of the equipment is evaluated by GNSS Receiver. 
         When it is disabled the position is given by Coordinate Lattitude, Coordinate 
         Longitude, and Altitude."
     ::= { f3GPSReceiverPortEntry 32 }

f3GPSReceiverPortCoordinateStringAltitude OBJECT-TYPE 
    SYNTAX     DisplayString
    MAX-ACCESS read-write
    STATUS     current
    DESCRIPTION
            "When Self Survey Control is disabled, this object configures the
             GNSS Receiver Port altitude in meters.
             The altitude is of the form [+/-]XXXXX[.Y] where XXXXX can be any 
             between -400 and 10000 value and Y allows precision of 1 decimal 
             after the floating point. Note that the sign and .Y are optional.
             When Self Survey Control is enabled, this object is not configurable
             and displays the GNSS Receiver Port altitude in meters."
     ::= { f3GPSReceiverPortEntry 33 }

f3GPSReceiverPortLocationMode OBJECT-TYPE
    SYNTAX      LocationMode  
    MAX-ACCESS  read-write
    STATUS      current
    DESCRIPTION
         "This object allows to manage location mode for the GNSS receiver on OSA540X."
    ::= { f3GPSReceiverPortEntry 34 }
    
f3GPSReceiverPortTimeAdvanceMode OBJECT-TYPE
    SYNTAX      TimeAdvanceMode  
    MAX-ACCESS  read-write
    STATUS      current
    DESCRIPTION
         "This object allows to manage time advance mode for the GNSS on OSA540X."
    ::= { f3GPSReceiverPortEntry 35 }
    
f3GPSReceiverPortTimeAdvanceValue OBJECT-TYPE
    SYNTAX      Integer32 (1..200)  
    MAX-ACCESS  read-write
    STATUS      current
    DESCRIPTION
         "This object allows to configure time advance value (ns) for the GNSS on OSA540X."
    ::= { f3GPSReceiverPortEntry 36 }
    
f3GPSReceiverPortForcedAntennaConnected OBJECT-TYPE
    SYNTAX      ToggleValue  
    MAX-ACCESS  read-write
    STATUS      current
    DESCRIPTION
         "This object allows to manage the antenna connected mode on OSA540X."
    ::= { f3GPSReceiverPortEntry 37 }
    
f3GPSReceiverPortServiceAvailableTime OBJECT-TYPE
    SYNTAX      Unsigned32  
    MAX-ACCESS  read-only
    STATUS      current
    DESCRIPTION
         "This object allows to manage service available time (seconds) for GNSS."
    ::= { f3GPSReceiverPortEntry 38 }
    
f3GPSReceiverPortServiceUnavailableTime OBJECT-TYPE
    SYNTAX      Unsigned32  
    MAX-ACCESS  read-only
    STATUS      current
    DESCRIPTION
         "This object allows to manage service unavailable time (seconds) for GNSS."
    ::= { f3GPSReceiverPortEntry 39 }
    
f3GPSReceiverPortServiceAvailablePercentage OBJECT-TYPE
    SYNTAX      DisplayString  
    MAX-ACCESS  read-only
    STATUS      current
    DESCRIPTION
         "This object allows to manage service available in percentage [XXX.YY%] for GNSS."
    ::= { f3GPSReceiverPortEntry 40 }
    
f3GPSReceiverPortAGC OBJECT-TYPE
    SYNTAX      Integer32  
    MAX-ACCESS  read-only
    STATUS      current
    DESCRIPTION
         "This object represents the Automatic Gain Control (AGC) level for the GNSS receiver."
    ::= { f3GPSReceiverPortEntry 41 }


f3GPSReceiverPortSelfSurveyPositionAccuracy OBJECT-TYPE
    SYNTAX      Unsigned32  
    MAX-ACCESS  read-write
    STATUS      current
    DESCRIPTION
         "This object configures the Self Survey Position accuracy threshold (in millimeters) used by the GNSS Receiver."
    ::= { f3GPSReceiverPortEntry 42 }

f3GPSReceiverPortHorizontalAccuracy OBJECT-TYPE
    SYNTAX      Unsigned32  
    MAX-ACCESS  read-only
    STATUS      current
    DESCRIPTION
         "This object represents the horizontal accuracy (in millimeters) of the position fix determined by the GNSS receiver."
    ::= { f3GPSReceiverPortEntry 43 }

f3GPSReceiverPortVerticalAccuracy OBJECT-TYPE
    SYNTAX      Unsigned32  
    MAX-ACCESS  read-only
    STATUS      current
    DESCRIPTION
         "This object represents the vertical accuracy (in millimeters) of the position fix determined by the GNSS receiver."
    ::= { f3GPSReceiverPortEntry 44 }

f3GPSReceiverPortTDOP OBJECT-TYPE
    SYNTAX      Unsigned32 (0..4095)
    MAX-ACCESS  read-only
    STATUS      current
    DESCRIPTION
        "This object provides the dimensionless TDOP value calculated by the GNSS Receiver.
         The value is expressed in hundredth of the TDOP definition. For instance, a 
         value of 153 means that TDOP calculated by GNSS Receiver is 1.53. 
         When the value cannot be evaluated by the GNSS Receiver, the value is shown with the minimum range value 0."
    ::= { f3GPSReceiverPortEntry 45 }

f3GPSReceiverPortHDOP OBJECT-TYPE
    SYNTAX      Unsigned32 (0..4095)
    MAX-ACCESS  read-only
    STATUS      current
    DESCRIPTION
        "This object provides the dimensionless HDOP value calculated by the GNSS 
         Receiver while GNSS Receiver Survey Pogress is not complete yet or the receiver is in navigation mode.
         The value is expressed in hundredth of the HDOP definition. For instance, a 
         value of 153 means that HDOP calculated by GNSS Receiver is 1.53. 
         When the value cannot be evaluated by the GNSS Receiver or when Survey Progress
         is complete, the value is shown with the minimum range value 0."
    ::= { f3GPSReceiverPortEntry 46 }

f3GPSReceiverPortVDOP OBJECT-TYPE
    SYNTAX      Unsigned32 (0..4095)
    MAX-ACCESS  read-only
    STATUS      current
    DESCRIPTION
        "This object provides the dimensionless VDOP value calculated by the GNSS 
         Receiver while GNSS Receiver Survey Pogress is not complete yet or the receiver is in navigation mode.
         The value is expressed in hundredth of the VDOP definition. For instance, a 
         value of 153 means that VDOP calculated by GNSS Receiver is 1.53. 
         When the value cannot be evaluated by the GNSS Receiver or when Survey Progress
         is complete, the value is shown with the minimum range value 0."
    ::= { f3GPSReceiverPortEntry 47 }
    
f3GPSReceiverPortFailureSuspendTime OBJECT-TYPE
    SYNTAX      Unsigned32 (3..3600)  
    MAX-ACCESS  read-write
    STATUS      current
    DESCRIPTION
         "This object represents the Failure Suspend Time for the GNSS receiver."
    ::= { f3GPSReceiverPortEntry 48 }

f3GPSReceiverPortSpoofingPpsThreshold OBJECT-TYPE
    SYNTAX      Unsigned32 (0..1000)
    MAX-ACCESS  read-write
    STATUS      current
    DESCRIPTION
        "This object defines the threshold  (in nanoseconds ) for generating PPS spoofing alarm in 5405."
    ::= { f3GPSReceiverPortEntry 49 }

f3GPSReceiverPortSpoofingPpsDifference OBJECT-TYPE
    SYNTAX      Unsigned32
    MAX-ACCESS  read-only
    STATUS      current
    DESCRIPTION
        "This object provides the calculated PPS difference (in nanoseconds ) provided by default and secondary GNSS receivers in 5405."
    ::= { f3GPSReceiverPortEntry 50 }
    
f3GPSReceiverPortSpoofingLocationThreshold OBJECT-TYPE
    SYNTAX      Unsigned32 (0..500)
    MAX-ACCESS  read-write
    STATUS      current
    DESCRIPTION
        "This object defines the threshold (in meters) for generating Location spoofing alarm in 5405."
    ::= { f3GPSReceiverPortEntry 51 }   
    
f3GPSReceiverPortSpoofingLocationDifference OBJECT-TYPE
    SYNTAX      Unsigned32
    MAX-ACCESS  read-only
    STATUS      current
    DESCRIPTION
        "This object provides the calculated Location difference (in meters) based on position information provided by default and secondary GNSS receivers in 5405."
    ::= { f3GPSReceiverPortEntry 52 }

f3GPSReceiverPortGnssDynamicModel OBJECT-TYPE
    SYNTAX      DynamicModelType
    MAX-ACCESS  read-write
    STATUS      current
    DESCRIPTION
        "This object defines the dynamic model of GNSS. For example, whether the GNSS receiver is stationary, automotive etc. "
    ::= { f3GPSReceiverPortEntry 53 }
    
cmPethPsePortExtTable  OBJECT-TYPE
    SYNTAX      SEQUENCE OF CmPethPsePortExtEntry
    MAX-ACCESS  not-accessible
    STATUS      current
    DESCRIPTION
            "A list of entries corresponding to PsePortExtEntry."
    ::= { cmFacilityObjects 58 }

cmPethPsePortExtEntry OBJECT-TYPE
    SYNTAX      CmPethPsePortExtEntry 
    MAX-ACCESS  not-accessible
    STATUS      current
    DESCRIPTION
            "A conceptual row in the cmPethPsePortExtEntry."
    INDEX { cmPethPsePortExtGroupIndex, cmPethPsePortExtIndex }
    ::= { cmPethPsePortExtTable 1 }

CmPethPsePortExtEntry ::= SEQUENCE {
    cmPethPsePortExtGroupIndex        Integer32,
    cmPethPsePortExtIndex             Integer32,
    cmPethPsePortExtAssociatedPort    VariablePointer,
    pethPsePortExtPowerConsumption    Unsigned32,
    pethPsePortExtAvailablePowerLevel PsePowerLevel
}

cmPethPsePortExtGroupIndex OBJECT-TYPE
    SYNTAX      Integer32
    MAX-ACCESS  not-accessible
    STATUS      current
    DESCRIPTION
            "This object has the same value with the group index in pethPsePortTalbe."
    ::= { cmPethPsePortExtEntry 1 }

cmPethPsePortExtIndex OBJECT-TYPE
    SYNTAX     Integer32
    MAX-ACCESS not-accessible
    STATUS     current
    DESCRIPTION
         "This object has the same value with the port index in pethPsePortTalbe."
     ::= { cmPethPsePortExtEntry 2 }

cmPethPsePortExtAssociatedPort OBJECT-TYPE
    SYNTAX     VariablePointer
    MAX-ACCESS read-write
    STATUS     current
    DESCRIPTION
         "This object means the oid of associated physical port."
     ::= { cmPethPsePortExtEntry 3 }

pethPsePortExtPowerConsumption OBJECT-TYPE
    SYNTAX     Unsigned32
    MAX-ACCESS read-only
    STATUS     current
    DESCRIPTION
         "This object means the power consumption of each port in mWatts."
     ::= { cmPethPsePortExtEntry 4 }

pethPsePortExtAvailablePowerLevel OBJECT-TYPE
    SYNTAX     PsePowerLevel
    MAX-ACCESS read-write
    STATUS     current
    DESCRIPTION
         "This object means the pse port available power level."
     ::= { cmPethPsePortExtEntry 5 }

pethMainPseEXTTable  OBJECT-TYPE
    SYNTAX      SEQUENCE OF PethMainPseEXTEntry
    MAX-ACCESS  not-accessible
    STATUS      current
    DESCRIPTION
            "A list of entries corresponding to PethMainPseEXTEntry."
    ::= { cmFacilityObjects 59 }

pethMainPseEXTEntry OBJECT-TYPE
    SYNTAX      PethMainPseEXTEntry 
    MAX-ACCESS  not-accessible
    STATUS      current
    DESCRIPTION
            "A conceptual row in the pethMainPseEXTEntry."
    INDEX { pethMainPseExtGroupIndex }
    ::= { pethMainPseEXTTable 1 }

PethMainPseEXTEntry ::= SEQUENCE {
    pethMainPseExtGroupIndex               Integer32,
    pethMainPseExtNonStandardPD            PSENonStandardPD
}

pethMainPseExtGroupIndex OBJECT-TYPE
    SYNTAX      Integer32
    MAX-ACCESS  not-accessible
    STATUS      current
    DESCRIPTION
            "This object has the same value with the group index in pethMainPseEXTTable."
    ::= { pethMainPseEXTEntry 1 }

pethMainPseExtNonStandardPD OBJECT-TYPE
    SYNTAX     PSENonStandardPD
    MAX-ACCESS read-write
    STATUS     current
    DESCRIPTION
         "disabled: don't support non-standard PD,
          enabled: support non-standard PD"
     ::= { pethMainPseEXTEntry 2 }

--
--  MPFlow Table 
--
cmMPFlowTable OBJECT-TYPE
    SYNTAX      SEQUENCE OF CmMPFlowEntry 
    MAX-ACCESS  not-accessible
    STATUS      current
    DESCRIPTION
            "A list of entries corresponding to MPFlow."
    ::= { cmFacilityObjects 60 }

cmMPFlowEntry OBJECT-TYPE
    SYNTAX      CmMPFlowEntry 
    MAX-ACCESS  not-accessible
    STATUS      current
    DESCRIPTION
            "A conceptual row in the cmMPFlowTable."
    INDEX { neIndex, cmMPFlowIndex }
    ::= { cmMPFlowTable 1 }

CmMPFlowEntry ::= SEQUENCE {
    cmMPFlowIndex                      Integer32,
    cmMPFlowCircuitName                F3DisplayString,
    cmMPFlowAdminState                 AdminState,
    cmMPFlowOperationalState           OperationalState,
    cmMPFlowSecondaryState             SecondaryState,
    cmMPFlowLearningEnabled            TruthValue,
    cmMPFlowAgingTimer                 Integer32,
    cmMPFlowFwdTableSizeProfileID      VariablePointer,
    cmMPFlowtableFullAction            LearningAction,
    cmMPFlowStorageType                StorageType,
    cmMPFlowRowStatus                  RowStatus,
    cmMPFlowLearningConfigAction       LearningConfigAction,
    cmMPFlowFPList                     F3DisplayString
}
    
cmMPFlowIndex OBJECT-TYPE
    SYNTAX      Integer32 (1..65535)
    MAX-ACCESS  not-accessible
    STATUS      current
    DESCRIPTION
         "An integer index value used to uniquely identify this MultiPointFlow." 
    ::= { cmMPFlowEntry 1 }

cmMPFlowCircuitName OBJECT-TYPE
    SYNTAX      F3DisplayString
    MAX-ACCESS  read-write
    STATUS      current
    DESCRIPTION
         "This object allows SNMP management entities to provide a
            circuit identifier with the MPFlow." 
    ::= { cmMPFlowEntry 2 }

cmMPFlowAdminState OBJECT-TYPE
    SYNTAX      AdminState
    MAX-ACCESS  read-write
    STATUS      current
    DESCRIPTION
         "This object represents the Administrative State of the Flow." 
    ::= { cmMPFlowEntry 3 }

cmMPFlowOperationalState OBJECT-TYPE
    SYNTAX      OperationalState
    MAX-ACCESS  read-only
    STATUS      current
    DESCRIPTION
         "This object represents the Operational State of the Flow." 
    ::= { cmMPFlowEntry 4 }

cmMPFlowSecondaryState OBJECT-TYPE
    SYNTAX      SecondaryState
    MAX-ACCESS  read-only
    STATUS      current
    DESCRIPTION
         "This object represents the Secondary State of the Flow." 
    ::= { cmMPFlowEntry 5 }

cmMPFlowLearningEnabled OBJECT-TYPE
    SYNTAX      TruthValue
    MAX-ACCESS  read-write
    STATUS      current
    DESCRIPTION
         "DISABLED: The forwarding function of the Flow does not 
         dynamically learn MAC address to flowpoint mapping.
         ENABLED: The forwarding function of the Flow dynamically 
         learns MAC address to flowpoint mapping based on ingress 
         flowpoing and source MAC address." 
    ::= { cmMPFlowEntry 6 }

cmMPFlowAgingTimer OBJECT-TYPE
    SYNTAX      Integer32
    MAX-ACCESS  read-write
    STATUS      current
    DESCRIPTION
         "MAC Table Entry will be removed from the forwarding table
          after an inactivity time represented by this entry.
          Not used in EG-X." 
    ::= { cmMPFlowEntry 7 }

cmMPFlowFwdTableSizeProfileID OBJECT-TYPE
    SYNTAX      VariablePointer
    MAX-ACCESS  read-write
    STATUS      current
    DESCRIPTION
         "Profile ID for Maximum number of MAC Table Entries for the flow" 
    ::= { cmMPFlowEntry 8 }

cmMPFlowtableFullAction OBJECT-TYPE
    SYNTAX      LearningAction
    MAX-ACCESS  read-write
    STATUS      current
    DESCRIPTION
         "Action on ingress frames when the number of MAC Table entires
          has reached the maximum defined by tableSize.
          BLOCK: A frame with a Source MAC address not in the MAC 
          Table will be discarded.
          FORWARD: A frame with a Source MAC address not in the MAC table 
          will not be learned and will be flooded to other flowpoints." 
    ::= { cmMPFlowEntry 9 }

cmMPFlowStorageType OBJECT-TYPE
    SYNTAX      StorageType
    MAX-ACCESS  read-create
    STATUS      current
    DESCRIPTION
         "The type of storage configured for this entry." 
    ::= { cmMPFlowEntry 10 }

cmMPFlowRowStatus OBJECT-TYPE
    SYNTAX      RowStatus
    MAX-ACCESS  read-create
    STATUS      current
    DESCRIPTION
         "The status of this row.
            An entry MUST NOT exist in the active state unless all
            objects in the entry have an appropriate value, as described
            in the description clause for each writable object.
            
            The values of cmMPFlowRowStatus supported are
            createAndGo(4) and destroy(6).  All mandatory attributes
            must be specified in a single SNMP SET request with
            cmFlowRowStatus value as createAndGo(4).
            Upon successful row creation, this object has a
            value of active(1).
            
            The cmMPFlowRowStatus object may be modified if
            the associated instance of this object is equal to active(1).
            
            Note that flow creation and deletion is only supported
            with access port in connection-oriented evpl mode." 
    ::= { cmMPFlowEntry 11 }

cmMPFlowLearningConfigAction OBJECT-TYPE
    SYNTAX      LearningConfigAction
    MAX-ACCESS  read-write
    STATUS      current
    DESCRIPTION
         "This objects allows performing user action on Learning Table." 
    ::= { cmMPFlowEntry 12 }

cmMPFlowFPList OBJECT-TYPE
    SYNTAX      F3DisplayString
    MAX-ACCESS  read-write
    STATUS      current
    DESCRIPTION
         "This object only used to display trap and Flow point list.
          Fp will be add in the cmMPFlowMemberTable." 
    ::= { cmMPFlowEntry 13 }

--
--  MP Flow Member Table 
--
cmMPFlowMemberTable OBJECT-TYPE
    SYNTAX      SEQUENCE OF CmMPFlowMemberEntry 
    MAX-ACCESS  not-accessible
    STATUS      current
    DESCRIPTION
            "A list of entries corresponding to MPFlowMember."
    ::= { cmFacilityObjects 61 }

cmMPFlowMemberEntry OBJECT-TYPE
    SYNTAX      CmMPFlowMemberEntry 
    MAX-ACCESS  not-accessible
    STATUS      current
    DESCRIPTION
            "A conceptual row in the cmMPFlowMemberTable."
    INDEX { neIndex, cmMPFlowIndex, cmMPFlowMemberFPIndex }
    ::= { cmMPFlowMemberTable 1 }

CmMPFlowMemberEntry ::= SEQUENCE {
    cmMPFlowMemberFPIndex            VariablePointer,
    cmMPFlowPointRowStatus           RowStatus
}
    
cmMPFlowMemberFPIndex OBJECT-TYPE
    SYNTAX      VariablePointer
    MAX-ACCESS  not-accessible
    STATUS      current
    DESCRIPTION
         "This object describes the relate Flow point." 
    ::= { cmMPFlowMemberEntry 1 }
    
cmMPFlowPointRowStatus OBJECT-TYPE
    SYNTAX      RowStatus
    MAX-ACCESS  read-create
    STATUS      current
    DESCRIPTION
         "The status of this row.
            An entry MUST NOT exist in the active state unless all
            objects in the entry have an appropriate value, as described
            in the description clause for each writable object.
            
            The values of cmMPFlowPointRowStatus supported are
            createAndGo(4) and destroy(6).  All mandatory attributes
            must be specified in a single SNMP SET request with
            cmFlowRowStatus value as createAndGo(4).
            Upon successful row creation, this object has a
            value of active(1).
            
            The cmMPFlowPointRowStatus object may be modified if
            the associated instance of this object is equal to active(1).
            
            Note that flow creation and deletion is only supported
            with access port in connection-oriented evpl mode."
    ::= { cmMPFlowMemberEntry 2 }

--
-- EthernetTraffic Port PCP encoding table 
--
cmEthernetTrafficPortPcpDEEncTable  OBJECT-TYPE
    SYNTAX      SEQUENCE OF CmEthernetTrafficPortPcpDEEncEntry 
    MAX-ACCESS  not-accessible
    STATUS      current
    DESCRIPTION
        "EthernetTraffic Port PCP drop eligibility encoding table. This
         is applied to a frame that is egressing at the EthernetTraffic port."
    ::= { cmFacilityObjects 62 }

cmEthernetTrafficPortPcpDEEncEntry OBJECT-TYPE
    SYNTAX      CmEthernetTrafficPortPcpDEEncEntry 
    MAX-ACCESS  not-accessible
    STATUS      current
    DESCRIPTION
            "A conceptual row in the ethernetPBPcpDEEncPortTable."
    INDEX { neIndex, shelfIndex, slotIndex, cmEthernetTrafficPortIndex, 
            cmEthernetTrafficPortPcpDEEncIndex }
    ::= { cmEthernetTrafficPortPcpDEEncTable 1 }

CmEthernetTrafficPortPcpDEEncEntry ::= SEQUENCE {
  cmEthernetTrafficPortPcpDEEncIndex              Integer32,
  cmEthernetTrafficPortPcpDEEncInPriority         VlanPriority,
  cmEthernetTrafficPortPcpDEEncDropIneligiblePrio VlanPriority,
  cmEthernetTrafficPortPcpDEEncDropEligiblePrio   VlanPriority
}

cmEthernetTrafficPortPcpDEEncIndex OBJECT-TYPE
    SYNTAX      Integer32 (1..8)
    MAX-ACCESS  read-only
    STATUS      current
    DESCRIPTION
            "An integer index value used to uniquely identify
             a row in the PCP drop eligible encoding table."
    ::= { cmEthernetTrafficPortPcpDEEncEntry 1 }

cmEthernetTrafficPortPcpDEEncInPriority OBJECT-TYPE
    SYNTAX     VlanPriority
    MAX-ACCESS read-write
    STATUS     current
    DESCRIPTION
         "This object is the input priority that is translated to a
          drop eligibility priority or a drop ineligibility priority."
     ::= { cmEthernetTrafficPortPcpDEEncEntry 2 }

cmEthernetTrafficPortPcpDEEncDropIneligiblePrio OBJECT-TYPE
    SYNTAX     VlanPriority
    MAX-ACCESS read-write
    STATUS     current
    DESCRIPTION
         "This object is the PCP value that has a priority value with
          implicit drop ineligibility encoded into it."
     ::= { cmEthernetTrafficPortPcpDEEncEntry 3 }

cmEthernetTrafficPortPcpDEEncDropEligiblePrio OBJECT-TYPE
    SYNTAX     VlanPriority
    MAX-ACCESS read-write
    STATUS     current
    DESCRIPTION
         "This object is the PCP value that has a priority value with
          implicit drop eligibility encoded into it."
     ::= { cmEthernetTrafficPortPcpDEEncEntry 4 }

--
-- EthernetTraffic Port PCP decoding table
--

cmEthernetTrafficPortPcpDEDecTable  OBJECT-TYPE
    SYNTAX      SEQUENCE OF CmEthernetTrafficPortPcpDEDecEntry
    MAX-ACCESS  not-accessible
    STATUS      current
    DESCRIPTION
            "EthernetTraffic Port PCP drop eligibility decoding table. This
             is applied to a frame that is ingressing at a port."
    ::= { cmFacilityObjects 63 }

cmEthernetTrafficPortPcpDEDecEntry OBJECT-TYPE
    SYNTAX      CmEthernetTrafficPortPcpDEDecEntry 
    MAX-ACCESS  not-accessible
    STATUS      current
    DESCRIPTION
            "A conceptual row in the ethernetPBPcpDEDecPortTable."
    INDEX { neIndex, shelfIndex, slotIndex, cmEthernetTrafficPortIndex, 
            cmEthernetTrafficPortPcpDEDecIndex }
    ::= { cmEthernetTrafficPortPcpDEDecTable 1 }

CmEthernetTrafficPortPcpDEDecEntry ::= SEQUENCE {
    cmEthernetTrafficPortPcpDEDecIndex        Integer32,
    cmEthernetTrafficPortPcpDEDecInPriority   VlanPriority,
    cmEthernetTrafficPortPcpDEDecOutPriority  VlanPriority,
    cmEthernetTrafficPortPcpDEDecDropEligible TruthValue
}


cmEthernetTrafficPortPcpDEDecIndex OBJECT-TYPE
    SYNTAX      Integer32 (1..8)
    MAX-ACCESS  read-only
    STATUS      current
    DESCRIPTION
            "An integer index value used to uniquely identify
             a row in the PCP drop eligible decoding table."
    ::= { cmEthernetTrafficPortPcpDEDecEntry 1 }

cmEthernetTrafficPortPcpDEDecInPriority OBJECT-TYPE
    SYNTAX     VlanPriority
    MAX-ACCESS read-write
    STATUS     current
    DESCRIPTION
         "This object is the input priority that is decoded to get
          priority and the drop eligibility of a frame."
     ::= { cmEthernetTrafficPortPcpDEDecEntry 2 }

cmEthernetTrafficPortPcpDEDecOutPriority OBJECT-TYPE
    SYNTAX     VlanPriority
    MAX-ACCESS read-write
    STATUS     current
    DESCRIPTION
         "This object is the priority value decoded from a incoming PCP value."
     ::= { cmEthernetTrafficPortPcpDEDecEntry 3 }

cmEthernetTrafficPortPcpDEDecDropEligible OBJECT-TYPE
    SYNTAX     TruthValue
    MAX-ACCESS read-write
    STATUS     current
    DESCRIPTION
         "This object is the drop eligibility decoded from a incoming
          PCP value."
     ::= { cmEthernetTrafficPortPcpDEDecEntry 4 }

-- 
-- EthernetTraffic Port PCP pair table
--

cmEthernetTrafficPortPcpDEPairTable  OBJECT-TYPE
    SYNTAX      SEQUENCE OF CmEthernetTrafficPortPcpDEPairEntry
    MAX-ACCESS  not-accessible
    STATUS      current
    DESCRIPTION
            "EthernetTraffic Port PCP drop eligibility priority pair table.
             The priority pair is encoded to same drop eligibility and
             drop ineligibility priority. Depending on the PCP DE Enc/Dec
             mode there can be upto 3 pairs in the table. There will one
             pair for 7P1D, two pairs for 6P2D and three pairs for 5P3D."
    ::= { cmFacilityObjects 64 }

cmEthernetTrafficPortPcpDEPairEntry OBJECT-TYPE
    SYNTAX      CmEthernetTrafficPortPcpDEPairEntry 
    MAX-ACCESS  not-accessible
    STATUS      current
    DESCRIPTION
            "A conceptual row in the cmAccPortPcpDEPairEntry."
    INDEX { neIndex, shelfIndex, slotIndex, cmEthernetTrafficPortIndex, 
            cmEthernetTrafficPortPcpDEPairIndex }
    ::= { cmEthernetTrafficPortPcpDEPairTable 1 }

CmEthernetTrafficPortPcpDEPairEntry ::= SEQUENCE {
    cmEthernetTrafficPortPcpDEPairIndex          Integer32,
    cmEthernetTrafficPortPcpDEDropIneligiblePrio VlanPriority,
    cmEthernetTrafficPortPcpDEDropEligiblePrio   VlanPriority
}

cmEthernetTrafficPortPcpDEPairIndex OBJECT-TYPE
    SYNTAX      Integer32 (1..3)
    MAX-ACCESS  read-only
    STATUS      current
    DESCRIPTION
            "An integer index value used to uniquely identify
             a row in the PCP drop eligible priority pair table."
    ::= { cmEthernetTrafficPortPcpDEPairEntry 1 }

cmEthernetTrafficPortPcpDEDropIneligiblePrio OBJECT-TYPE
    SYNTAX     VlanPriority
    MAX-ACCESS read-write
    STATUS     current
    DESCRIPTION
         "This object is the drop ineligible priority."
     ::= { cmEthernetTrafficPortPcpDEPairEntry 2 }

cmEthernetTrafficPortPcpDEDropEligiblePrio OBJECT-TYPE
    SYNTAX     VlanPriority
    MAX-ACCESS read-write
    STATUS     current
    DESCRIPTION
         "This object is the drop eligible priority."
     ::= { cmEthernetTrafficPortPcpDEPairEntry 3 }

--
--  Ethernet Traffic Port Cable Length Benchmark 
--
cmEthernetTrafficPortClbTable  OBJECT-TYPE
    SYNTAX      SEQUENCE OF CmEthernetTrafficPortClbEntry
    MAX-ACCESS  not-accessible
    STATUS      current
    DESCRIPTION
            "A list of entries corresponding to Ethernet Traffic Port 
             Cable Length Benchmark."
    ::= { cmFacilityObjects 65 }

cmEthernetTrafficPortClbEntry OBJECT-TYPE
    SYNTAX      CmEthernetTrafficPortClbEntry 
    MAX-ACCESS  not-accessible
    STATUS      current
    DESCRIPTION
            "A conceptual row in the cmEthernetTrafficPortClbTable. 
             These entries represent Cable Length Benchmarks 
             on the Ethernet Traffic Port."
    INDEX { neIndex, shelfIndex, slotIndex, cmEthernetTrafficPortIndex, 
            cmEthernetTrafficPortClbIndex }
    ::= { cmEthernetTrafficPortClbTable 1 }


CmEthernetTrafficPortClbEntry ::= SEQUENCE {
    cmEthernetTrafficPortClbIndex          Integer32,
    cmEthernetTrafficPortClbEnabled        TruthValue,
    cmEthernetTrafficPortClbLength         DisplayString,
    cmEthernetTrafficPortClbDescr          DisplayString
}

cmEthernetTrafficPortClbIndex OBJECT-TYPE
    SYNTAX      Integer32 (1..5)
    MAX-ACCESS  read-only
    STATUS      current
    DESCRIPTION
            "An integer index value used to uniquely identify
             this Cable Length Benchmark Entry specification."
    ::= { cmEthernetTrafficPortClbEntry 1 }

cmEthernetTrafficPortClbEnabled OBJECT-TYPE
    SYNTAX     TruthValue
    MAX-ACCESS read-write
    STATUS     current
    DESCRIPTION
            "This enables specification of Cable Length Benchmark entry."
    ::= { cmEthernetTrafficPortClbEntry 2 }

cmEthernetTrafficPortClbLength OBJECT-TYPE
    SYNTAX  DisplayString 
    MAX-ACCESS read-write
    STATUS     current
    DESCRIPTION
            "Cable length of Cable Points Entry. The cable length is of
             the form XXX[.YY] where XX can be any integer value and YY
             allows precision of 2 decimals after the floating point. Note
             that .YY is optional."
    ::= { cmEthernetTrafficPortClbEntry 3 }

cmEthernetTrafficPortClbDescr OBJECT-TYPE
    SYNTAX     DisplayString (SIZE (0..256))
    MAX-ACCESS read-write
    STATUS     current
    DESCRIPTION
         "A textual string containing description of cable span."
    ::= { cmEthernetTrafficPortClbEntry 4 }

--
--  cmNeTrafficElementTable
--
networkElementTMParamsTable  OBJECT-TYPE
    SYNTAX          SEQUENCE OF NetworkElementTMParamsEntry
    MAX-ACCESS  not-accessible
    STATUS          current
    DESCRIPTION
         "Entries may be auto discovered, or can be explicitly created by 
          SNMP Manager.  Each remotely discovered shelf is represented as 
          a row in this table." 
    ::= { cmFacilityObjects 66 }

networkElementTMParamsEntry  OBJECT-TYPE
    SYNTAX          NetworkElementTMParamsEntry
    MAX-ACCESS  not-accessible
    STATUS          current
    DESCRIPTION
            "A conceptual row in the networkElementTMParamsTable."
    AUGMENTS { networkElementEntry }
    ::= { networkElementTMParamsTable 1 }


NetworkElementTMParamsEntry ::= SEQUENCE {
    neTMParamsBandwidthProfileMode     BandwidthProfileMode, 
    neTMParamsAgingtime                Integer32
}

neTMParamsBandwidthProfileMode OBJECT-TYPE
    SYNTAX          BandwidthProfileMode  
    MAX-ACCESS      read-create
    STATUS          current
    DESCRIPTION
        "A Network Element level Bandwidth Profile Mode shall be supported 
         which will indicate if the CIR/EIR is interpreted as Information Rate (IR) 
         or Line Rate (LR). In IR mode BWP is enforced based on number of bytes beginning 
         with DA and ending with FCS as it was received at a port which is called the Service 
         Frame in MEF terminology. In LR mode the BWP is enforced based on the whole frame 
         including IFG, Preamble and SFD."
    ::= { networkElementTMParamsEntry 1 }

neTMParamsAgingtime OBJECT-TYPE
    SYNTAX     Integer32
    MAX-ACCESS read-create
    STATUS     current
    DESCRIPTION
            "The object describe the system aging time."
    ::= { networkElementTMParamsEntry 2 }

--
-- Access Port JDSU Ext Table
--

cmEthernetAccPortJdsuExtTable OBJECT-TYPE
    SYNTAX      SEQUENCE OF CmEthernetAccPortJdsuExtEntry
    MAX-ACCESS  not-accessible
    STATUS      current
    DESCRIPTION
            "A list of entries corresponding to Ethernet Access Port 
            Facilities for JDSU configuration purposes."
    ::= { cmFacilityObjects 67 }

cmEthernetAccPortJdsuExtEntry OBJECT-TYPE
    SYNTAX      CmEthernetAccPortJdsuExtEntry
    MAX-ACCESS  not-accessible
    STATUS      current
    DESCRIPTION
            "A conceptual row in the cmEthernetAccPortJdsuExtTable."
    AUGMENTS { cmEthernetAccPortEntry }
    ::= { cmEthernetAccPortJdsuExtTable 1 }

CmEthernetAccPortJdsuExtEntry ::= SEQUENCE {
    cmEthernetAccPortJDSUControlFramesSnoopingEnabled   TruthValue,
    cmEthernetAccPortJDSULoopbackVlan                   VlanId,
    cmEthernetAccPortJDSULoopbackVlanList               DisplayString
}

cmEthernetAccPortJDSUControlFramesSnoopingEnabled OBJECT-TYPE
    SYNTAX      TruthValue  
    MAX-ACCESS  read-write
    STATUS      current
    DESCRIPTION
        "Enabled: reaction/response to JDSU in-band loopback requests and hallo requests.
         Disabled: Not reaction/response to JDSU in-band loopback requests and hallo requests. 
         FPGA shall not filter the JDSU control frames to processor.
         From enabled to disabled, if there is already a JDSU loopback on the port, 
         release current loopback.
         JDSU loopback doesn't need port in maintenance state."
     ::= { cmEthernetAccPortJdsuExtEntry 1 }

cmEthernetAccPortJDSULoopbackVlan OBJECT-TYPE
    SYNTAX      VlanId  
    MAX-ACCESS  read-only
    STATUS      current
    DESCRIPTION
        "Applicable when port in JDSU VLAN loopback."
     ::= { cmEthernetAccPortJdsuExtEntry 2 }

cmEthernetAccPortJDSULoopbackVlanList OBJECT-TYPE
    SYNTAX      DisplayString  
    MAX-ACCESS  read-only
    STATUS      current
    DESCRIPTION
        "The format is like 'OuterVid1-OuterPri1;InnerVid1-InnerPri1, OuterVid2-OuterPri2, 
        OuterVid3-OuterPri3;InnerVid3-InnerPri3'('1-*;2-*, 3-*, 4-*;5-*')."
     ::= { cmEthernetAccPortJdsuExtEntry 3 }

--
-- Network Port JDSU Ext Table
--

cmEthernetNetPortJdsuExtTable OBJECT-TYPE
    SYNTAX      SEQUENCE OF CmEthernetNetPortJdsuExtEntry
    MAX-ACCESS  not-accessible
    STATUS      current
    DESCRIPTION
            "A list of entries corresponding to Ethernet Network Port 
            Facilities for JDSU configuration purposes."
    ::= { cmFacilityObjects 68 }

cmEthernetNetPortJdsuExtEntry OBJECT-TYPE
    SYNTAX      CmEthernetNetPortJdsuExtEntry
    MAX-ACCESS  not-accessible
    STATUS      current
    DESCRIPTION
            "A conceptual row in the cmEthernetNetPortJdsuExtTable."
    AUGMENTS { cmEthernetNetPortEntry }
    ::= { cmEthernetNetPortJdsuExtTable 1 }

CmEthernetNetPortJdsuExtEntry ::= SEQUENCE {
    cmEthernetNetPortJDSUControlFramesSnoopingEnabled   TruthValue,
    cmEthernetNetPortJDSULoopbackVlan                   VlanId,
    cmEthernetNetPortJDSULoopbackVlanList               DisplayString
}

cmEthernetNetPortJDSUControlFramesSnoopingEnabled OBJECT-TYPE
    SYNTAX      TruthValue  
    MAX-ACCESS  read-write
    STATUS      current
    DESCRIPTION
        "Enabled: reaction/response to JDSU in-band loopback requests and hallo requests.
         Disabled: Not reaction/response to JDSU in-band loopback requests and hallo requests. 
         FPGA shall not filter the JDSU control frames to processor.
         From enabled to disabled, if there is already a JDSU loopback on the port, 
         release current loopback.
         JDSU loopback doesn't need port in maintenance state."
     ::= { cmEthernetNetPortJdsuExtEntry 1 }

cmEthernetNetPortJDSULoopbackVlan OBJECT-TYPE
    SYNTAX      VlanId  
    MAX-ACCESS  read-only
    STATUS      current
    DESCRIPTION
        "Applicable when port in JDSU VLAN loopback."
     ::= { cmEthernetNetPortJdsuExtEntry 2 }

cmEthernetNetPortJDSULoopbackVlanList OBJECT-TYPE
    SYNTAX      DisplayString  
    MAX-ACCESS  read-only
    STATUS      current
    DESCRIPTION
        "The format is like 'OuterVid1-OuterPri1;InnerVid1-InnerPri1, OuterVid2-OuterPri2, 
        OuterVid3-OuterPri3;InnerVid3-InnerPri3'('1-*;2-*, 3-*, 4-*;5-*')."
     ::= { cmEthernetNetPortJdsuExtEntry 3 }
     

--
--  Ethernet Traffic Port LPBK entry 
--
cmEthernetTrafficPortLpbkTable  OBJECT-TYPE
    SYNTAX      SEQUENCE OF CmEthernetTrafficPortLpbkEntry
    MAX-ACCESS  not-accessible
    STATUS      current
    DESCRIPTION
            "A list of entries corresponding to Vlan loopback on
            Ethernet Traffic Port."
    ::= { cmFacilityObjects 69 }

cmEthernetTrafficPortLpbkEntry OBJECT-TYPE
    SYNTAX      CmEthernetTrafficPortLpbkEntry 
    MAX-ACCESS  not-accessible
    STATUS      current
    DESCRIPTION
            "A conceptual row in the cmEthernetTrafficPortLpbkTable. 
             These entries represent Vlan loopback 
             on the Ethernet Traffic Port."
    INDEX { neIndex, shelfIndex, slotIndex, cmEthernetTrafficPortIndex, 
            cmEthernetTrafficPortLpbkIndex }
    ::= { cmEthernetTrafficPortLpbkTable 1 }

CmEthernetTrafficPortLpbkEntry ::= SEQUENCE {
    cmEthernetTrafficPortLpbkIndex                    Integer32,
    cmEthernetTrafficPortLpbkInnerVlanEnabled         TruthValue,
    cmEthernetTrafficPortLpbkInnerVlanTag             DisplayString,
    cmEthernetTrafficPortLpbkOuterVlanEnabled         TruthValue,
    cmEthernetTrafficPortLpbkOuterVlanTag             DisplayString,
    cmEthernetTrafficPortLpbkTime                     Integer32,
    cmEthernetTrafficPortLpbkStatus                   CmLoopbackType,
    cmEthernetTrafficPortLpbkConfig                   CmLoopbackType
}

cmEthernetTrafficPortLpbkIndex OBJECT-TYPE
    SYNTAX      Integer32
    MAX-ACCESS  not-accessible
    STATUS      current
    DESCRIPTION
            "An integer index value used to uniquely identify
             this vlan loopback entry."
    ::= { cmEthernetTrafficPortLpbkEntry 1 }

cmEthernetTrafficPortLpbkInnerVlanEnabled OBJECT-TYPE
    SYNTAX      TruthValue
    MAX-ACCESS  read-write
    STATUS      current
    DESCRIPTION
            "This object represent the inner vlan whether enabled."
    ::= { cmEthernetTrafficPortLpbkEntry 2 }

cmEthernetTrafficPortLpbkInnerVlanTag OBJECT-TYPE
    SYNTAX      DisplayString
    MAX-ACCESS  read-write
    STATUS      current
    DESCRIPTION
            "This object represent the inner vlanid value and priority value.
            The value to be specified should be in the form 
            X-Y where X is the VLAN Id and Y is the VLAN Priority.  
            If Y is specified as a *, all Priorities (0 to 7) 
            are looped back."
    ::= { cmEthernetTrafficPortLpbkEntry 3 }

cmEthernetTrafficPortLpbkOuterVlanEnabled OBJECT-TYPE
    SYNTAX      TruthValue
    MAX-ACCESS  read-write
    STATUS      current
    DESCRIPTION
            "This object represent the outter vlan whether enabled."
    ::= { cmEthernetTrafficPortLpbkEntry 4 }

cmEthernetTrafficPortLpbkOuterVlanTag OBJECT-TYPE
    SYNTAX      DisplayString
    MAX-ACCESS  read-write
    STATUS      current
    DESCRIPTION
            "This object represent the outter vlanid value and priority value.
            The value to be specified should be in the form 
            X-Y where X is the VLAN Id and Y is the VLAN Priority.  
            If Y is specified as a *, all Priorities (0 to 7) 
            are looped back."
    ::= { cmEthernetTrafficPortLpbkEntry 5 }

cmEthernetTrafficPortLpbkTime OBJECT-TYPE
    SYNTAX      Integer32
    MAX-ACCESS  read-write
    STATUS      current
    DESCRIPTION
            "This object represent the vlan loopback time."
    ::= { cmEthernetTrafficPortLpbkEntry 6 }

cmEthernetTrafficPortLpbkStatus OBJECT-TYPE
    SYNTAX      CmLoopbackType
    MAX-ACCESS  read-only
    STATUS      current
    DESCRIPTION
            "This object represent the vlan loopback status."
    ::= { cmEthernetTrafficPortLpbkEntry 7 }

cmEthernetTrafficPortLpbkConfig OBJECT-TYPE
    SYNTAX      CmLoopbackType
    MAX-ACCESS  read-write
    STATUS      current
    DESCRIPTION
            "This object represent the vlan loopback action."
    ::= { cmEthernetTrafficPortLpbkEntry 8 }

--
--Priority Mapping Profile Table
--
cmPrioMapV2ProfileTable  OBJECT-TYPE
    SYNTAX      SEQUENCE OF CmPrioMapV2ProfileEntry
    MAX-ACCESS  not-accessible
    STATUS      current
    DESCRIPTION
            "A list of entries corresponding to Ethernet Priority Mappings V2 Profile."
    ::= { cmFacilityObjects 70 }

cmPrioMapV2ProfileEntry OBJECT-TYPE
    SYNTAX      CmPrioMapV2ProfileEntry
    MAX-ACCESS  not-accessible
    STATUS      current
    DESCRIPTION
            "A conceptual row in the cmPrioMapV2ProfileTable."
    INDEX { cmPrioMapV2ProfileIndex }
    ::= { cmPrioMapV2ProfileTable 1 }

CmPrioMapV2ProfileEntry ::= SEQUENCE {
    cmPrioMapV2ProfileIndex              Integer32,
    cmPrioMapV2ProfileAlias              DisplayString,
    cmPrioMapV2ProfileMapModeType        PriorityMapMode,
    cmPrioMapV2ProfileStorageType        StorageType,
    cmPrioMapV2ProfileRowStatus          RowStatus,
    cmPrioMapV2ProfileIngressCosPriority VlanTagType,
    cmPrioMapV2ProfileCosMapModeType     CosMappingMode,
    cmPrioMapV2ProfileCosMapControl      TruthValue,
    cmPrioMapV2ProfileDefaultCos         Unsigned32,
    cmPrioMapV2ProfileEgressCos         Unsigned32
}

cmPrioMapV2ProfileIndex OBJECT-TYPE
    SYNTAX      Integer32
    MAX-ACCESS  not-accessible
    STATUS      current
    DESCRIPTION
            "The integer index value describes the profile index."
    ::= { cmPrioMapV2ProfileEntry 1 }

cmPrioMapV2ProfileAlias OBJECT-TYPE
    SYNTAX      DisplayString
    MAX-ACCESS  read-write
    STATUS      current
    DESCRIPTION
            "The integer index value describes the profile alias."
    ::= { cmPrioMapV2ProfileEntry 2 }

cmPrioMapV2ProfileMapModeType OBJECT-TYPE
    SYNTAX      PriorityMapMode
    MAX-ACCESS  read-write
    STATUS      current
    DESCRIPTION
            "The integer index value describes the profile PriorityMapMode."
    ::= { cmPrioMapV2ProfileEntry 3 }

cmPrioMapV2ProfileStorageType OBJECT-TYPE
    SYNTAX     StorageType
    MAX-ACCESS read-create
    STATUS     current
    DESCRIPTION
            "The type of storage configured for this entry."
    ::= { cmPrioMapV2ProfileEntry 4 }

cmPrioMapV2ProfileRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmPrioMapV2ProfileStatus supported are
            createAndGo(4) and destroy(6).  All mandatory attributes
            must be specified in a single SNMP SET request with
            cmPrioMapV2ProfileRowStatus value as createAndGo(4).
            Upon successful row creation, this object has a
            value of active(1).

            The cmPrioMapV2ProfileRowStatus object may be modified if
            the associated instance of this object is equal to active(1)."
    ::= { cmPrioMapV2ProfileEntry 5 }

cmPrioMapV2ProfileIngressCosPriority OBJECT-TYPE
    SYNTAX     VlanTagType
    MAX-ACCESS read-create
    STATUS     deprecated
    DESCRIPTION
         "This object is used to specify whether the profile
          uses the inner-tag or the outer-tag in determining the COS (Class of Service)." 
    ::= { cmPrioMapV2ProfileEntry 6 }

cmPrioMapV2ProfileCosMapModeType OBJECT-TYPE
    SYNTAX     CosMappingMode
    MAX-ACCESS read-write
    STATUS     current
    DESCRIPTION
         "This object is used to specify Cos mapping mode type." 
    ::= { cmPrioMapV2ProfileEntry 7 }

cmPrioMapV2ProfileCosMapControl OBJECT-TYPE
    SYNTAX     TruthValue
    MAX-ACCESS read-write
    STATUS     current
    DESCRIPTION
         "This object is used to control whether has cmPrioMapV2PrioMappingCOSTable in profile." 
    ::= { cmPrioMapV2ProfileEntry 8 }

cmPrioMapV2ProfileDefaultCos OBJECT-TYPE
    SYNTAX     Unsigned32
    MAX-ACCESS read-write
    STATUS     current
    DESCRIPTION
         "This object is used to specify the Default COS to be used when the
         Ingress Priority Mapping function does not match." 
    ::= { cmPrioMapV2ProfileEntry 9 }

cmPrioMapV2ProfileEgressCos OBJECT-TYPE
    SYNTAX     Unsigned32
    MAX-ACCESS read-write
    STATUS     current
    DESCRIPTION
         "This object is used to specify the Default COS to be used when the
         Egress Priority Mapping function does not match." 
    ::= { cmPrioMapV2ProfileEntry 10 }

--
--Priority Mapping V2 Table
--
cmPrioMapV2IngressPrioMappingTable  OBJECT-TYPE
    SYNTAX      SEQUENCE OF CmPrioMapV2IngressPrioMappingEntry
    MAX-ACCESS  not-accessible
    STATUS      current
    DESCRIPTION
            "A list of entries corresponding to Ethernet Priority Mappings."
    ::= { cmFacilityObjects 71 }

cmPrioMapV2IngressPrioMappingEntry OBJECT-TYPE
    SYNTAX      CmPrioMapV2IngressPrioMappingEntry
    MAX-ACCESS  not-accessible
    STATUS      current
    DESCRIPTION
            "A conceptual row in the cmPrioMapV2IngressPrioMappingTable."
    INDEX { cmPrioMapV2ProfileIndex, cmPrioMapV2IngressPrioMappingIndex }
    ::= { cmPrioMapV2IngressPrioMappingTable 1 }

CmPrioMapV2IngressPrioMappingEntry ::= SEQUENCE {
    cmPrioMapV2IngressPrioMappingIndex            Integer32,
    cmPrioMapV2IngressPrioMappingInPriority       Integer32,
    cmPrioMapV2IngressPrioMappingCOS              Integer32
}

cmPrioMapV2IngressPrioMappingIndex OBJECT-TYPE
    SYNTAX      Integer32
    MAX-ACCESS  not-accessible
    STATUS      current
    DESCRIPTION
            "The integer index value corresponding to a priority value
             based on the cmPrioMapV2ProfileMode.
             In case of TOS and 8021P, valid indices are 1 to 8,
             in case of DSCP, valid indices are 1 to 64."
    ::= { cmPrioMapV2IngressPrioMappingEntry 1 }

cmPrioMapV2IngressPrioMappingInPriority OBJECT-TYPE
    SYNTAX      Integer32 (0..63)
    MAX-ACCESS  read-write
    STATUS      current
    DESCRIPTION
            "The integer index value corresponding to a priority value
             based on the cmPrioMapV2ProfileMode.
             In case of TOS and 8021P, valid indices are 0 to 7,
             in case of DSCP, valid indices are 0 to 63."
    ::= { cmPrioMapV2IngressPrioMappingEntry 2 }

cmPrioMapV2IngressPrioMappingCOS OBJECT-TYPE
    SYNTAX      Integer32 (0..7)
    MAX-ACCESS  read-write
    STATUS      current
    DESCRIPTION
            "This allows specification of the COS Priority, i.e.
             this helps in determining the appropriate COS Policer for
             the Flow."
    ::= { cmPrioMapV2IngressPrioMappingEntry 3 }


--
--Priority Mapping V2 Table
--
cmPrioMapV2PrioMappingCOSTable  OBJECT-TYPE
    SYNTAX      SEQUENCE OF CmPrioMapV2PrioMappingCOSEntry
    MAX-ACCESS  not-accessible
    STATUS      current
    DESCRIPTION
            "A list of entries corresponding to Ethernet Priority Mappings."
    ::= { cmFacilityObjects 72 }

cmPrioMapV2PrioMappingCOSEntry OBJECT-TYPE
    SYNTAX      CmPrioMapV2PrioMappingCOSEntry
    MAX-ACCESS  not-accessible
    STATUS      current
    DESCRIPTION
            "A conceptual row in the cmPrioMapV2PrioMappingCOSTable."
    INDEX { cmPrioMapV2ProfileIndex, cmPrioMapV2PrioMappingCOSIndex }
    ::= { cmPrioMapV2PrioMappingCOSTable 1 }

CmPrioMapV2PrioMappingCOSEntry ::= SEQUENCE {
    cmPrioMapV2PrioMappingCOSIndex               Integer32,
    cmPrioMapV2PrioMappingCOSValue               Integer32,
    cmPrioMapV2PrioMappingCOSOuterTagPri         Integer32,
    cmPrioMapV2PrioMappingCOSInnerTagPri         Integer32,
    cmPrioMapV2PrioMappingEncapOuterTagPriority  Integer32,
    cmPrioMapV2PrioMappingEncapInnerTagPriority  Integer32,
    cmPrioMapV2PrioMappingEncapOuterDscpValue    Integer32,
    cmPrioMapV2PrioMappingDscpValue              Integer32
}

cmPrioMapV2PrioMappingCOSIndex OBJECT-TYPE
    SYNTAX      Integer32
    MAX-ACCESS  not-accessible
    STATUS      current
    DESCRIPTION
            "The index of this entry."
    ::= { cmPrioMapV2PrioMappingCOSEntry 1 }

cmPrioMapV2PrioMappingCOSValue OBJECT-TYPE
    SYNTAX      Integer32 (0..7)
    MAX-ACCESS  read-only
    STATUS      current
    DESCRIPTION
            "This allows specification of the COS Value, i.e.
             this helps in determining the appropriate COS Policer for
             the Flow."
    ::= { cmPrioMapV2PrioMappingCOSEntry 2 }

cmPrioMapV2PrioMappingCOSOuterTagPri OBJECT-TYPE
    SYNTAX      Integer32
    MAX-ACCESS  read-write
    STATUS      current
    DESCRIPTION
            "This allows specification of the VLAN priority that
             will replace the outgoing (A2N direction) outer-tag's priority."
    ::= { cmPrioMapV2PrioMappingCOSEntry 3 }

cmPrioMapV2PrioMappingCOSInnerTagPri OBJECT-TYPE
    SYNTAX      Integer32
    MAX-ACCESS  read-write
    STATUS      current
    DESCRIPTION
            "This allows specification of the VLAN priority that
             will replace the outgoing (A2N direction) inner-tag's (i.e. second tag) 
             priority."
    ::= { cmPrioMapV2PrioMappingCOSEntry 4 }

cmPrioMapV2PrioMappingEncapOuterTagPriority OBJECT-TYPE
     SYNTAX     Integer32 (0..7)
     MAX-ACCESS read-write
     STATUS     current
     DESCRIPTION
         "This object allows configuring encapsulation outer tag priority value of ingress cos mapping."
     ::= { cmPrioMapV2PrioMappingCOSEntry 5 }

cmPrioMapV2PrioMappingEncapInnerTagPriority OBJECT-TYPE
     SYNTAX     Integer32 (0..7)
     MAX-ACCESS read-write
     STATUS     current
     DESCRIPTION
         "This object allows configuring encapsulation inner tag priority value of ingress cos mapping."
     ::= { cmPrioMapV2PrioMappingCOSEntry 6 }

cmPrioMapV2PrioMappingEncapOuterDscpValue OBJECT-TYPE
     SYNTAX     Integer32 (0..63)
     MAX-ACCESS read-write
     STATUS     current
     DESCRIPTION
         "This object allows configuring encapsulation outer DSCP value of ingress cos mapping."
     ::= { cmPrioMapV2PrioMappingCOSEntry 7 }

cmPrioMapV2PrioMappingDscpValue OBJECT-TYPE
     SYNTAX     Integer32 (0..63)
     MAX-ACCESS read-write
     STATUS     current
     DESCRIPTION
         "This object allows configuring DSCP value of ingress cos mapping."
     ::= { cmPrioMapV2PrioMappingCOSEntry 8 }

--
--Priority Mapping V2 Table
--
cmPrioMapV2PrioMappingPriTable  OBJECT-TYPE
    SYNTAX      SEQUENCE OF CmPrioMapV2PrioMappingPriEntry
    MAX-ACCESS  not-accessible
    STATUS      current
    DESCRIPTION
            "A list of entries corresponding to Ethernet Priority Mappings."
    ::= { cmFacilityObjects 73 }

cmPrioMapV2PrioMappingPriEntry OBJECT-TYPE
    SYNTAX      CmPrioMapV2PrioMappingPriEntry
    MAX-ACCESS  not-accessible
    STATUS      current
    DESCRIPTION
            "A conceptual row in the cmPrioMapV2PrioMappingPriTable."
    INDEX { cmPrioMapV2ProfileIndex, cmPrioMapV2PrioMappingPriIndex }
    ::= { cmPrioMapV2PrioMappingPriTable 1 }

CmPrioMapV2PrioMappingPriEntry ::= SEQUENCE {
    cmPrioMapV2PrioMappingPriIndex            Integer32,
    cmPrioMapV2PrioMappingPriInPrio           Integer32,
    cmPrioMapV2PrioMappingPriPrioControl      PrioMapControlType,
    cmPrioMapV2PrioMappingPriXTagPrio         Integer32,
    cmPrioMapV2PrioMappingPriCOS              Integer32
}

cmPrioMapV2PrioMappingPriIndex OBJECT-TYPE
    SYNTAX      Integer32
    MAX-ACCESS  not-accessible
    STATUS      current
    DESCRIPTION
            "The integer index value corresponding to a priority value
             based on the cmPrioMapV2ProfileMode.
             In case of TOS and 8021P, valid indices are 1 to 8,
             in case of DSCP, valid indices are 1 to 64."
    ::= { cmPrioMapV2PrioMappingPriEntry 1 }

cmPrioMapV2PrioMappingPriInPrio OBJECT-TYPE
    SYNTAX      Integer32
    MAX-ACCESS  read-write
    STATUS      current
    DESCRIPTION
            "The integer index value corresponding to a priority value
             based on the cmPrioMapV2ProfileMode.
             In case of TOS and 8021P, valid indices are 0 to 7,
             in case of DSCP, valid indices are 0 to 63."
    ::= { cmPrioMapV2PrioMappingPriEntry 2 }

cmPrioMapV2PrioMappingPriPrioControl OBJECT-TYPE
    SYNTAX      PrioMapControlType
    MAX-ACCESS  read-write
    STATUS      current
    DESCRIPTION
            "This allows specification of whether the priority of
             incoming X-TAG should be swapped with cmPrioMapV2XTagPriority."
    ::= { cmPrioMapV2PrioMappingPriEntry 3 }

cmPrioMapV2PrioMappingPriXTagPrio OBJECT-TYPE
    SYNTAX      Integer32
    MAX-ACCESS  read-write
    STATUS      current
    DESCRIPTION
            "This allows specification of the VLAN priority that
             will replace the incoming X-TAG's priority.  This is
             applicable with cmPrioMapV2XTagControl as 'swap'."
    ::= { cmPrioMapV2PrioMappingPriEntry 4 }

cmPrioMapV2PrioMappingPriCOS OBJECT-TYPE
    SYNTAX      Integer32
    MAX-ACCESS  read-write
    STATUS      current
    DESCRIPTION
            "This allows specification of the COS Priority, i.e.
             this helps in determining the appropriate COS Policer for
             the Flow."
    ::= { cmPrioMapV2PrioMappingPriEntry 5 }

--
--cmPrioMapV2ProfileAppliedObjTable
--
cmPrioMapV2ProfileAppliedObjTable  OBJECT-TYPE
    SYNTAX      SEQUENCE OF CmPrioMapV2ProfileAppliedObjEntry
    MAX-ACCESS  not-accessible
    STATUS      current
    DESCRIPTION
            "A list of entries corresponding to Ethernet Priority Mappings V2 Profile AppliedObj."
    ::= { cmFacilityObjects 74 }

cmPrioMapV2ProfileAppliedObjEntry OBJECT-TYPE
    SYNTAX      CmPrioMapV2ProfileAppliedObjEntry
    MAX-ACCESS  not-accessible
    STATUS      current
    DESCRIPTION
            "A conceptual row in the cmPrioMapV2ProfileAppliedObjTable."
    INDEX { cmPrioMapV2ProfileIndex, cmPrioMapV2ProfileAppliedObj }
    ::= { cmPrioMapV2ProfileAppliedObjTable 1 }

CmPrioMapV2ProfileAppliedObjEntry ::= SEQUENCE {
    cmPrioMapV2ProfileAppliedObj            VariablePointer
}

cmPrioMapV2ProfileAppliedObj OBJECT-TYPE
    SYNTAX      VariablePointer
    MAX-ACCESS  read-only
    STATUS      current
    DESCRIPTION
            "The object describe the profile Applied to. It maybe the access port or network port or flow etc."
    ::= { cmPrioMapV2ProfileAppliedObjEntry 1 }


--
-- access port extension Table
--
cmAccPortExtTable OBJECT-TYPE
    SYNTAX      SEQUENCE OF CmAccPortExtEntry
    MAX-ACCESS  not-accessible
    STATUS      current
    DESCRIPTION
            "A list of entries corresponding to Access Port for configuration purposes."
    ::= { cmFacilityObjects 75 }

cmAccPortExtEntry OBJECT-TYPE
    SYNTAX      CmAccPortExtEntry
    MAX-ACCESS  not-accessible
    STATUS      current
    DESCRIPTION
            "A conceptual row in the cmAccPortExtTable."
    AUGMENTS { cmEthernetAccPortEntry }
    ::= { cmAccPortExtTable 1 }

CmAccPortExtEntry ::= SEQUENCE {
    cmAccPortExtMcastRateLimitEnabled           TruthValue,
    cmAccPortExtMcastRateLimitSpeedLo           Unsigned32,
    cmAccPortExtMcastRateLimitSpeedHi           Unsigned32,
    cmAccPortExtBcastRateLimitEnabled           TruthValue,
    cmAccPortExtBcastRateLimitSpeedLo           Unsigned32,
    cmAccPortExtBcastRateLimitSpeedHi           Unsigned32,
    cmAccPortExtCombinedRateLimitEnabled        TruthValue,
    cmAccPortExtCombinedRateLimitSpeedLo        Unsigned32,
    cmAccPortExtCombinedRateLimitSpeedHi        Unsigned32,
    cmAccPortExtRefPrioMapProfile               VariablePointer
}

cmAccPortExtMcastRateLimitEnabled OBJECT-TYPE
    SYNTAX      TruthValue
    MAX-ACCESS  read-write
    STATUS      current
    DESCRIPTION
            "Whether multicast packets need be limited on this port." 
    ::= { cmAccPortExtEntry 1 }

cmAccPortExtMcastRateLimitSpeedLo OBJECT-TYPE
    SYNTAX      Unsigned32
    MAX-ACCESS  read-write
    STATUS      current
    DESCRIPTION
            "The rate limiting for multicast packets per port
             When cmAccPortExtMcastRateLimitEnabled and the value is 0, 
             it means all multicast frame are dropped.

             This objects only represents low 32 bits." 
    ::= { cmAccPortExtEntry 2 }

cmAccPortExtMcastRateLimitSpeedHi OBJECT-TYPE
    SYNTAX      Unsigned32
    MAX-ACCESS  read-write
    STATUS      current
    DESCRIPTION
            "The rate limiting for multicast packets per port
             When cmAccPortExtMcastRateLimitEnabled and the value is 0, 
             it means all multicast frame are dropped.

             This objects only represents high 32 bits." 
    ::= { cmAccPortExtEntry 3 }

cmAccPortExtBcastRateLimitEnabled OBJECT-TYPE
    SYNTAX      TruthValue
    MAX-ACCESS  read-write
    STATUS      current
    DESCRIPTION
            "Whether broadcast packets need be limited per port." 
    ::= { cmAccPortExtEntry 4 }

cmAccPortExtBcastRateLimitSpeedLo OBJECT-TYPE
    SYNTAX      Unsigned32
    MAX-ACCESS  read-write
    STATUS      current
    DESCRIPTION
            "The rate limiting for broadcast packets per port
             When cmAccPortExtBcastRateLimitEnabled and the value is 0, 
             it means all multicast frame are dropped.

             This objects only represents low 32 bits." 
    ::= { cmAccPortExtEntry 5 }

cmAccPortExtBcastRateLimitSpeedHi OBJECT-TYPE
    SYNTAX      Unsigned32
    MAX-ACCESS  read-write
    STATUS      current
    DESCRIPTION
            "The rate limiting for broadcast packets per port
             When cmAccPortExtBcastRateLimitEnabled and the value is 0, 
             it means all multicast frame are dropped.

             This objects only represents high 32 bits." 
    ::= { cmAccPortExtEntry 6 }

cmAccPortExtCombinedRateLimitEnabled OBJECT-TYPE
    SYNTAX      TruthValue
    MAX-ACCESS  read-write
    STATUS      current
    DESCRIPTION
            "Whether multicast and broadcast packets need be limited per port." 
    ::= { cmAccPortExtEntry 7 }

cmAccPortExtCombinedRateLimitSpeedLo OBJECT-TYPE
    SYNTAX      Unsigned32
    MAX-ACCESS  read-write
    STATUS      current
    DESCRIPTION
            "The rate limiting for multicast and broadcast packets per port.
             This objects only represents low 32 bits." 
    ::= { cmAccPortExtEntry 8 }

cmAccPortExtCombinedRateLimitSpeedHi OBJECT-TYPE
    SYNTAX      Unsigned32
    MAX-ACCESS  read-write
    STATUS      current
    DESCRIPTION
            "The rate limiting for multicast and broadcast packets per port.
             This objects only represents high 32 bits." 
    ::= { cmAccPortExtEntry 9 }

cmAccPortExtRefPrioMapProfile OBJECT-TYPE
    SYNTAX      VariablePointer
    MAX-ACCESS  read-write
    STATUS      current
    DESCRIPTION
            "This object allows to set priority map profile." 
    ::= { cmAccPortExtEntry 10 }

--
-- Network port extension Table
--
cmNetPortExtTable OBJECT-TYPE
    SYNTAX      SEQUENCE OF CmNetPortExtEntry
    MAX-ACCESS  not-accessible
    STATUS      current
    DESCRIPTION
            "A list of entries corresponding to Network Port for configuration purposes."
    ::= { cmFacilityObjects 76 }

cmNetPortExtEntry OBJECT-TYPE
    SYNTAX      CmNetPortExtEntry
    MAX-ACCESS  not-accessible
    STATUS      current
    DESCRIPTION
            "A conceptual row in the cmNetPortExtTable."
    AUGMENTS { cmEthernetNetPortEntry }
    ::= { cmNetPortExtTable 1 }

CmNetPortExtEntry ::= SEQUENCE {
    cmNetPortExtMcastRateLimitEnabled           TruthValue,
    cmNetPortExtMcastRateLimitSpeedLo           Unsigned32,
    cmNetPortExtMcastRateLimitSpeedHi           Unsigned32,
    cmNetPortExtBcastRateLimitEnabled           TruthValue,
    cmNetPortExtBcastRateLimitSpeedLo           Unsigned32,
    cmNetPortExtBcastRateLimitSpeedHi           Unsigned32,
    cmNetPortExtCombinedRateLimitEnabled        TruthValue,
    cmNetPortExtCombinedRateLimitSpeedLo        Unsigned32,
    cmNetPortExtCombinedRateLimitSpeedHi        Unsigned32,
    cmNetPortExtRefPrioMapProfile               VariablePointer
}

cmNetPortExtMcastRateLimitEnabled OBJECT-TYPE
    SYNTAX      TruthValue
    MAX-ACCESS  read-write
    STATUS      current
    DESCRIPTION
            "Whether multicast packets need be limited on this port." 
    ::= { cmNetPortExtEntry 1 }

cmNetPortExtMcastRateLimitSpeedLo OBJECT-TYPE
    SYNTAX      Unsigned32
    MAX-ACCESS  read-write
    STATUS      current
    DESCRIPTION
            "The rate limiting for multicast packets per port
             When cmNetPortExtMcastRateLimitEnabled and the value is 0, 
             it means all multicast frame are dropped.

             This objects only represents low 32 bits." 
    ::= { cmNetPortExtEntry 2 }

cmNetPortExtMcastRateLimitSpeedHi OBJECT-TYPE
    SYNTAX      Unsigned32
    MAX-ACCESS  read-write
    STATUS      current
    DESCRIPTION
            "The rate limiting for multicast packets per port
             When cmNetPortExtMcastRateLimitEnabled and the value is 0, 
             it means all multicast frame are dropped.

             This objects only represents high 32 bits." 
    ::= { cmNetPortExtEntry 3 }

cmNetPortExtBcastRateLimitEnabled OBJECT-TYPE
    SYNTAX      TruthValue
    MAX-ACCESS  read-write
    STATUS      current
    DESCRIPTION
            "Whether broadcast packets need be limited per port." 
    ::= { cmNetPortExtEntry 4 }

cmNetPortExtBcastRateLimitSpeedLo OBJECT-TYPE
    SYNTAX      Unsigned32
    MAX-ACCESS  read-write
    STATUS      current
    DESCRIPTION
            "The rate limiting for broadcast packets per port
             When cmNetPortExtBcastRateLimitEnabled and the value is 0, 
             it means all multicast frame are dropped.

             This objects only represents low 32 bits." 
    ::= { cmNetPortExtEntry 5 }

cmNetPortExtBcastRateLimitSpeedHi OBJECT-TYPE
    SYNTAX      Unsigned32
    MAX-ACCESS  read-write
    STATUS      current
    DESCRIPTION
            "The rate limiting for broadcast packets per port
             When cmNetPortExtBcastRateLimitEnabled and the value is 0, 
             it means all multicast frame are dropped.

             This objects only represents high 32 bits." 
    ::= { cmNetPortExtEntry 6 }

cmNetPortExtCombinedRateLimitEnabled OBJECT-TYPE
    SYNTAX      TruthValue
    MAX-ACCESS  read-write
    STATUS      current
    DESCRIPTION
            "Whether multicast and broadcast packets need be limited per port." 
    ::= { cmNetPortExtEntry 7 }

cmNetPortExtCombinedRateLimitSpeedLo OBJECT-TYPE
    SYNTAX      Unsigned32
    MAX-ACCESS  read-write
    STATUS      current
    DESCRIPTION
            "The rate limiting for multicast and broadcast packets per port.
             This objects only represents low 32 bits." 
    ::= { cmNetPortExtEntry 8 }

cmNetPortExtCombinedRateLimitSpeedHi OBJECT-TYPE
    SYNTAX      Unsigned32
    MAX-ACCESS  read-write
    STATUS      current
    DESCRIPTION
            "The rate limiting for multicast and broadcast packets per port.
             This objects only represents high 32 bits." 
    ::= { cmNetPortExtEntry 9 }

cmNetPortExtRefPrioMapProfile OBJECT-TYPE
    SYNTAX      VariablePointer
    MAX-ACCESS  read-write
    STATUS      current
    DESCRIPTION
            "This object allows to set priority map profile." 
    ::= { cmNetPortExtEntry 10 }

--
-- usb WIFI dongle port Table
--
f3UsbWIFIDonglePortTable OBJECT-TYPE
    SYNTAX      SEQUENCE OF F3UsbWIFIDonglePortEntry
    MAX-ACCESS  not-accessible
    STATUS      current
    DESCRIPTION
            "A list of entries corresponding to wifi dongle Port for configuration purposes."
    ::= { cmFacilityObjects 77 }

f3UsbWIFIDonglePortEntry OBJECT-TYPE
    SYNTAX      F3UsbWIFIDonglePortEntry
    MAX-ACCESS  not-accessible
    STATUS      current
    DESCRIPTION
            "A conceptual row in the f3UsbWIFIDonglePortTable."
    INDEX { neIndex, shelfIndex, slotIndex, f3UsbHostIndex }
    ::= { f3UsbWIFIDonglePortTable 1 }

F3UsbWIFIDonglePortEntry ::= SEQUENCE {
    f3UsbWIFIDonglePortIndex                    Integer32,
    f3UsbWIFIDonglePortIfIndex                  InterfaceIndex,
    f3UsbWIFIDonglePortEntityIndex              PhysicalIndex,
    f3UsbWIFIDonglePortAdminState               AdminState,
    f3UsbWIFIDonglePortOperationalState         OperationalState,
    f3UsbWIFIDonglePortSecondaryState           SecondaryState,
    f3UsbWIFIDonglePortSSID                     DisplayString,
    f3UsbWIFIDonglePortPassword                 DisplayString,
    f3UsbWIFIDonglePortEncryption               WIFIEncryptionType,
    f3UsbWIFIDonglePortIPAddress                IpAddress,
    f3UsbWIFIDonglePortwWIFIIPNetMask           IpAddress,
    f3UsbWIFIDonglePortWIFIDHCPRole             DHCPType,
    f3UsbWIFIDonglePortWIFIAllocatedIPFrom      IpAddress,
    f3UsbWIFIDonglePortWIFIAllocatedIPEnd       IpAddress,
    f3UsbWIFIDonglePortStorageType              StorageType,
    f3UsbWIFIDonglePortRowStatus                RowStatus,
    f3UsbWIFIDonglePortAccessdUsers             DisplayString,
    f3UsbWIFIDonglePortName                     DisplayString
}

f3UsbWIFIDonglePortIndex OBJECT-TYPE
    SYNTAX      Integer32
    MAX-ACCESS  not-accessible
    STATUS      current
    DESCRIPTION
            "An integer index value used to uniquely identify WIFI dongle port." 
    ::= { f3UsbWIFIDonglePortEntry 1 }

f3UsbWIFIDonglePortIfIndex OBJECT-TYPE
    SYNTAX      InterfaceIndex
    MAX-ACCESS  read-only
    STATUS      current
    DESCRIPTION
            "This object has the same value as ifIndex for WIFI dongle Port.
            An integer index value used to uniquely identify this Port" 
    ::= { f3UsbWIFIDonglePortEntry 2 }

f3UsbWIFIDonglePortEntityIndex OBJECT-TYPE
    SYNTAX      PhysicalIndex
    MAX-ACCESS  read-only
    STATUS      current
    DESCRIPTION
            "Entity Index from ENTITY-MIB for this port." 
    ::= { f3UsbWIFIDonglePortEntry 3 }

f3UsbWIFIDonglePortAdminState OBJECT-TYPE
    SYNTAX      AdminState
    MAX-ACCESS  read-write
    STATUS      current
    DESCRIPTION
            "This object represents the Administrative State of this Port." 
    ::= { f3UsbWIFIDonglePortEntry 4 }

f3UsbWIFIDonglePortOperationalState OBJECT-TYPE
    SYNTAX      OperationalState
    MAX-ACCESS  read-only
    STATUS      current
    DESCRIPTION
            "This object represents the Operational State of this Port." 
    ::= { f3UsbWIFIDonglePortEntry 5 }

f3UsbWIFIDonglePortSecondaryState OBJECT-TYPE
    SYNTAX      SecondaryState
    MAX-ACCESS  read-only
    STATUS      current
    DESCRIPTION
            "This object represents the Secondary State of this Port." 
    ::= { f3UsbWIFIDonglePortEntry 6 }

f3UsbWIFIDonglePortSSID OBJECT-TYPE
    SYNTAX      DisplayString (SIZE (0..32))
    MAX-ACCESS  read-write
    STATUS      current
    DESCRIPTION
            "This object represents the SSID value of this port." 
    ::= { f3UsbWIFIDonglePortEntry 7 }

f3UsbWIFIDonglePortPassword OBJECT-TYPE
    SYNTAX      DisplayString
    MAX-ACCESS  read-write
    STATUS      current
    DESCRIPTION
            "This object represents the password value of this SSID." 
    ::= { f3UsbWIFIDonglePortEntry 8 }

f3UsbWIFIDonglePortEncryption OBJECT-TYPE
    SYNTAX      WIFIEncryptionType
    MAX-ACCESS  read-write
    STATUS      current
    DESCRIPTION
            "The encryption type of this port." 
    ::= { f3UsbWIFIDonglePortEntry 9 }

f3UsbWIFIDonglePortIPAddress OBJECT-TYPE
    SYNTAX      IpAddress
    MAX-ACCESS  read-write
    STATUS      current
    DESCRIPTION
            "The IP address of this port." 
    ::= { f3UsbWIFIDonglePortEntry 10 }

f3UsbWIFIDonglePortwWIFIIPNetMask OBJECT-TYPE
    SYNTAX      IpAddress
    MAX-ACCESS  read-write
    STATUS      current
    DESCRIPTION
            "The IP address mask of this port." 
    ::= { f3UsbWIFIDonglePortEntry 11 }

f3UsbWIFIDonglePortWIFIDHCPRole OBJECT-TYPE
    SYNTAX      DHCPType
    MAX-ACCESS  read-only
    STATUS      current
    DESCRIPTION
            "The DHCP role type of this port." 
    ::= { f3UsbWIFIDonglePortEntry 12 }

f3UsbWIFIDonglePortWIFIAllocatedIPFrom OBJECT-TYPE
    SYNTAX      IpAddress
    MAX-ACCESS  read-write
    STATUS      current
    DESCRIPTION
            "The start IP address could be allocated." 
    ::= { f3UsbWIFIDonglePortEntry 13 }

f3UsbWIFIDonglePortWIFIAllocatedIPEnd OBJECT-TYPE
    SYNTAX      IpAddress
    MAX-ACCESS  read-write
    STATUS      current
    DESCRIPTION
            "The last IP address could be allocated." 
    ::= { f3UsbWIFIDonglePortEntry 14 }

f3UsbWIFIDonglePortStorageType OBJECT-TYPE
    SYNTAX      StorageType
    MAX-ACCESS  read-create
    STATUS      current
    DESCRIPTION
            "The type of storage configured for this entry." 
    ::= { f3UsbWIFIDonglePortEntry 15 }

f3UsbWIFIDonglePortRowStatus OBJECT-TYPE
    SYNTAX      RowStatus
    MAX-ACCESS  read-create
    STATUS      current
    DESCRIPTION
            "The status of this row.
               An entry MUST NOT exist in the active state unless all
               objects in the entry have an appropriate value, as described
               in the description clause for each writable object.
               
               The values of f3UsbWIFIDonglePortRowStatus supported are
               createAndGo(4) and destroy(6).  All mandatory attributes
               must be specified in a single SNMP SET request with
               f3UsbWIFIDonglePortRowStatus value as createAndGo(4).
               Upon successful row creation, this object has a
               value of active(1).
               
               The f3UsbWIFIDonglePortRowStatus object may be modified if
               the associated instance of this object is equal to active(1).
               
               Note that flow creation and deletion is only supported
               with access port in connection-oriented evpl mode." 
    ::= { f3UsbWIFIDonglePortEntry 16 }

f3UsbWIFIDonglePortAccessdUsers OBJECT-TYPE
    SYNTAX      DisplayString
    MAX-ACCESS  read-only
    STATUS      current
    DESCRIPTION
            "The users list of accessed via WIFI dongle port." 
    ::= { f3UsbWIFIDonglePortEntry 17 }

f3UsbWIFIDonglePortName OBJECT-TYPE
    SYNTAX      DisplayString
    MAX-ACCESS  read-only
    STATUS      current
    DESCRIPTION
            "The WIFI dongle port name." 
    ::= { f3UsbWIFIDonglePortEntry 18 }

--
--  BITS 8 PORT GROUP (Building Integrated Timing System) Port 
--
bits8PortGroupTable OBJECT-TYPE
    SYNTAX      SEQUENCE OF Bits8PortGroupEntry
    MAX-ACCESS  not-accessible
    STATUS      current
    DESCRIPTION
            "A list of entries corresponding to BITS 8 Port Group 
             Facilities for configuration purposes."
    ::= { cmFacilityObjects 78 }

bits8PortGroupEntry OBJECT-TYPE
    SYNTAX      Bits8PortGroupEntry 
    MAX-ACCESS  not-accessible
    STATUS      current
    DESCRIPTION
            "A conceptual row in the bits8PortGroupTable."
    INDEX { neIndex, shelfIndex, slotIndex, bits8PortGroupIndex }
    ::= { bits8PortGroupTable 1 }

Bits8PortGroupEntry ::= SEQUENCE {
    -- Port Indices 
    bits8PortGroupIndex                      Integer32,
    bits8PortGroupIfIndex                    InterfaceIndex,

    -- State Management params
    bits8PortGroupAdminState                 AdminState,
    bits8PortGroupOperationalState           OperationalState,
    bits8PortGroupSecondaryState             SecondaryState,

    -- bits port specific params 
    bits8PortGroupLineType                   BitsPortLineType,
    bits8PortGroupLineCode                   BitsPortLineCode,
    bits8PortGroupFrameFormat                BitsFrameFormat,
    bits8PortGroupSaBitDesignation           SaBitDesignation,

    --Synchronous Port params
    bits8PortGroupQLModeEnabled              TruthValue,
    bits8PortGroupTransmitQL                 SSMQualityLevel,
    bits8PortGroupSquelchQL                  SSMQualityLevel,
    bits8PortGroupLineBuildOut               LineBuildOut,
    bits8PortGroupImpedance                  BitsPortImpedanceMode,
    bits8PortGroupRowStatus                  RowStatus,
    bits8PortGroupActivePorts                PortState,
    bits8PortGroupClkIfEnabledPorts          PortState

}
    
-- bits8PortGroup Indices 


bits8PortGroupIndex OBJECT-TYPE
    SYNTAX      Integer32 (1..65535)
    MAX-ACCESS  read-only
    STATUS      current
    DESCRIPTION
         "An integer index value used to uniquely identify
          this BITS Port within the card.
          Note that each BITs Port is uniquely identified
          by the indices neIndex, shelfIndex, 
          slotIndex, portIndex, bits8PortGroupIndex." 
    ::= { bits8PortGroupEntry 1 }


bits8PortGroupIfIndex OBJECT-TYPE
    SYNTAX      InterfaceIndex (1..65535)
    MAX-ACCESS  read-only
    STATUS      current
    DESCRIPTION
         "An integer index value used to uniquely identify
          this BITS Port within the card.
          Note that each BITs Port is uniquely identified
          by the indices neIndex, shelfIndex, 
          slotIndex, bits8PortGroupIndex, bits8PortGroupIfIndex. " 
    ::= { bits8PortGroupEntry 2 }


-- State Management params
bits8PortGroupAdminState OBJECT-TYPE
    SYNTAX      AdminState 
    MAX-ACCESS  read-write
    STATUS      current
    DESCRIPTION
            "This object represents the Administrative State of the BITS 
             8 Port Group."
    ::= { bits8PortGroupEntry 3 }

bits8PortGroupOperationalState OBJECT-TYPE
    SYNTAX      OperationalState 
    MAX-ACCESS  read-only
    STATUS      current
    DESCRIPTION
            "This object represents the Operational State of the BITS 
             8 Port Group."
    ::= { bits8PortGroupEntry 4 }

bits8PortGroupSecondaryState OBJECT-TYPE
    SYNTAX      SecondaryState 
    MAX-ACCESS  read-only
    STATUS      current
    DESCRIPTION
            "This object represents the Secondary State of the BITS 
             8 Port Group."
    ::= { bits8PortGroupEntry 5 }

bits8PortGroupLineType OBJECT-TYPE
    SYNTAX      BitsPortLineType 
    MAX-ACCESS  read-write
    STATUS      current
    DESCRIPTION
            "This object represents the BITS 8 Port Group Line Type.
             Determines whether the T1/E1 BITS port operates in T1, E1, 
             or 2048kHz mode."
    ::= { bits8PortGroupEntry 6 }

bits8PortGroupLineCode OBJECT-TYPE
    SYNTAX      BitsPortLineCode 
    MAX-ACCESS  read-write
    STATUS      current
    DESCRIPTION
            "This object represents the BITS 8 Port Group Line Code.
             When the group is configured for a Line Type of T1, 
             the valid values are t1-b8zs and t1-ami and the default value
             is t1-b8zs. When the group is configured for a Line Type of E1, 
             the valid values are e1-hdb3 and e1-ami and the default value 
             is e1-hdb3. When the group is configured for a Line Type of 
             2048kHz, the value is none."
    ::= { bits8PortGroupEntry 7 }

bits8PortGroupFrameFormat OBJECT-TYPE
    SYNTAX      BitsFrameFormat 
    MAX-ACCESS  read-write
    STATUS      current
    DESCRIPTION
            "This object represents the BITS 8 Port Group Frame Format.
             When the group is configured for a Line Type of T1, the
             valid values are t1-sf and t1-esf and the default value is t1-esf.
             When the group is configured for a Line Type of E1, the
             valid values are e1-unframed, e1-crc4, and e1-dualFrame 
             and the default value is e1-crc4. When the group is configured 
             for a Line Type of 2048kHz, the value is none.

             R4.1CC and R4.3CC do not support e1-unframed."
    ::= { bits8PortGroupEntry 8 }

bits8PortGroupSaBitDesignation OBJECT-TYPE
    SYNTAX      SaBitDesignation 
    MAX-ACCESS  read-write
    STATUS      current
    DESCRIPTION
            "This object represents the BITS 8 Port Group Sa Bit Designation.
             Determines which E1 Sa Bit is used to transmit/receive the SSM. 
             For T1 and 2048khz Line Types, the only allowed value is None. 
             For E1 Line Type, the default value is bit4 and it can 
             only have a value of None if QL Mode is disabled, otherwise, 
             None is an invalid value."
    ::= { bits8PortGroupEntry 9 }

bits8PortGroupQLModeEnabled OBJECT-TYPE 
    SYNTAX     TruthValue
    MAX-ACCESS read-write
    STATUS     current
    DESCRIPTION
         "This object allows to specify whether the BITS 8 Port Group 
          can be enabled/disabled for QL Mode. 
          When enabled, on receive side 
            -port shall PEER the SSM (Sync Status Messages) slow protocol PDUs 
             and take appropriate action 
          When enabled, on transmit side 
            -port shall periodically (once a second) transmit QL TLV 
             information PDUs
          When disabled, on receive side,
            -port shall terminate and discard any SSM slow protocol PDUs 
          When disabled, on transmit side 
            -port shall not transmit any SSM slow protocol PDUs."
     ::= { bits8PortGroupEntry 10 }

bits8PortGroupTransmitQL OBJECT-TYPE 
    SYNTAX     SSMQualityLevel
    MAX-ACCESS read-only
    STATUS     current
    DESCRIPTION
         "This object provides the Transmitted QL value for the BITS 8 Port Group. 
          If the BITS group's QL Mode is disabled, then the received 
          QL value is not applicable."
     ::= { bits8PortGroupEntry 11 }

bits8PortGroupSquelchQL OBJECT-TYPE 
    SYNTAX     SSMQualityLevel
    MAX-ACCESS read-write
    STATUS     current
    DESCRIPTION
         "This object allows to set the Squelch QL for the BITS 8 Port Group. 
          The Squelch QL is only meaningful if the QL Mode is Enabled. 
          The Squelch QL is used to determine whether or not to squelch 
          the output of the BITS 8 Port Group. If the system's QL is lower 
          than the Squelch QL, the output is squelched.
          If the BITS group's QL Mode is disabled, then the received 
          QL value is not applicable."
     ::= { bits8PortGroupEntry 12 }

bits8PortGroupLineBuildOut OBJECT-TYPE 
    SYNTAX     LineBuildOut
    MAX-ACCESS read-write
    STATUS     current
    DESCRIPTION
         "This object allows to manage the line build out on the BITS 8 Port Group when
          the Line Type is T1."
     ::= { bits8PortGroupEntry 13 }

bits8PortGroupImpedance OBJECT-TYPE 
    SYNTAX     BitsPortImpedanceMode
    MAX-ACCESS read-write
    STATUS     current
    DESCRIPTION
         "This object provides the line impedance mode for the BITS 8 Port Group."
     ::= { bits8PortGroupEntry 14 }

bits8PortGroupRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of bits8PortGroupRowStatus supported are
            createAndGo(4) and destroy(6).  All mandatory attributes
            must be specified in a single SNMP SET request with
            bits8PortGroupRowStatus value as createAndGo(4).
            Upon successful row creation, this object has a
            value of active(1).

            The bits8PortGroupRowStatus object may be modified if
            the associated instance of this object is equal to active(1)."
    ::= { bits8PortGroupEntry 15 }

bits8PortGroupActivePorts OBJECT-TYPE
    SYNTAX      PortState 
    MAX-ACCESS  read-write
    STATUS      current
    DESCRIPTION
            "This object represents the Active State for each port of the BITS 
             8 Port Group."
    ::= { bits8PortGroupEntry 16 }

bits8PortGroupClkIfEnabledPorts OBJECT-TYPE
    SYNTAX      PortState 
    MAX-ACCESS  read-write
    STATUS      current
    DESCRIPTION
            "This object represents the Clock Enabling State for each port of the BITS 
             8 Port Group."
    ::= { bits8PortGroupEntry 17 }



--
--  PPS 16 port group 
--
pps16PortGroupTable OBJECT-TYPE
    SYNTAX      SEQUENCE OF Pps16PortGroupEntry 
    MAX-ACCESS  not-accessible
    STATUS      current
    DESCRIPTION
            "A list of entries corresponding to Pulse Per Second 
             Port Facilities."
    ::= { cmFacilityObjects 79 }


pps16PortGroupEntry OBJECT-TYPE
    SYNTAX      Pps16PortGroupEntry 
    MAX-ACCESS  not-accessible
    STATUS      current
    DESCRIPTION
            "A conceptual row in the pps16PortGroupTable."
    INDEX { neIndex, shelfIndex, slotIndex, pps16PortGroupIndex }
    ::= { pps16PortGroupTable 1 }

Pps16PortGroupEntry ::= SEQUENCE {
    -- Port Indices 
    pps16PortGroupIndex                  Integer32,
    pps16PortGroupIfIndex                InterfaceIndex,

    -- State Management params
    pps16PortGroupAdminState             AdminState,
    pps16PortGroupOperationalState       OperationalState,
    pps16PortGroupSecondaryState         SecondaryState,
    pps16PortGroupAlias                  DisplayString,

    -- port specific params
    pps16PortGroupSquelchControl         SquelchControl,

    pps16PortGroupTODSource              VariablePointer,
    pps16PortGroupDirection              SignalDirectionType,
    pps16PortGroupDelayCompensation      Integer32,
    pps16PortGroupRowStatus                  RowStatus

   -- pps16PortGroupOutputType             PPSPhyInterfaceType

}
    
pps16PortGroupIndex OBJECT-TYPE
    SYNTAX      Integer32 (1..65535)
    MAX-ACCESS  read-only
    STATUS      current
    DESCRIPTION
         "An integer index value used to uniquely identify
          this Pulse Per Second Port within the card." 
    ::= { pps16PortGroupEntry 1 }

pps16PortGroupIfIndex OBJECT-TYPE
    SYNTAX      InterfaceIndex
    MAX-ACCESS  read-only
    STATUS      current
    DESCRIPTION
         "This object has the same value as ifIndex for 
          Pulse Per Second Port.  An integer index value used to 
          uniquely identify this Pulse Per Second Port."
    ::= { pps16PortGroupEntry 2 }

-- State Management params
pps16PortGroupAdminState OBJECT-TYPE
    SYNTAX      AdminState 
    MAX-ACCESS  read-only
    STATUS      current
    DESCRIPTION
            "This object represents the Administrative State of the Pulse Per Second 
             Port."
    ::= { pps16PortGroupEntry 3 }

pps16PortGroupOperationalState OBJECT-TYPE
    SYNTAX      OperationalState 
    MAX-ACCESS  read-only
    STATUS      current
    DESCRIPTION
            "This object represents the Operational State of the Pulse Per Second 
             Port."
    ::= { pps16PortGroupEntry 4 }

pps16PortGroupSecondaryState OBJECT-TYPE
    SYNTAX      SecondaryState 
    MAX-ACCESS  read-only
    STATUS      current
    DESCRIPTION
            "This object represents the Secondary State of the Pulse Per Second 
             Port."
    ::= { pps16PortGroupEntry 5 }

pps16PortGroupAlias    OBJECT-TYPE
    SYNTAX      DisplayString (SIZE(0..64))
    MAX-ACCESS  read-only
    STATUS      current
    DESCRIPTION
         "This object allows SNMP management entities to provide an 
          alias to the gps 10MHz Port entity."
     ::= { pps16PortGroupEntry 6 }


pps16PortGroupSquelchControl  OBJECT-TYPE 
    SYNTAX     SquelchControl
    MAX-ACCESS read-only
    STATUS     current
    DESCRIPTION
         "This object allows to set the Squelch Control for the Pulse Per Second port. 
          The Squelch Control is used to determine the type of squelch control 
          used to squelch the output of the TOD port."
     ::= { pps16PortGroupEntry 7 }


pps16PortGroupTODSource OBJECT-TYPE 
    SYNTAX     VariablePointer
    MAX-ACCESS read-only
    STATUS     current
    DESCRIPTION
         "This object allows to set the Pulse Per Second Source for the Port." 
     ::= { pps16PortGroupEntry 8 }

pps16PortGroupDirection OBJECT-TYPE
    SYNTAX      SignalDirectionType 
    MAX-ACCESS  read-only
    STATUS      current
    DESCRIPTION
            "This object allows specification of the signal type 
             (i.e. input or output)."
    ::= { pps16PortGroupEntry 9 }


pps16PortGroupDelayCompensation OBJECT-TYPE
    SYNTAX      Integer32 (0..90)
    MAX-ACCESS  read-write
    STATUS      current
    DESCRIPTION
            "This object allows specification of the PPS external Delay
             Compensation in nanoseconds. The valid values are 0 to 96 in 
             8 nanoseconds steps. Values which are not multiple of 8 will
             be automatically rounded up to the next multiple of 8." 
    ::= { pps16PortGroupEntry 10 }

pps16PortGroupRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of pps16PortGroupRowStatus supported are
            createAndGo(4) and destroy(6).  All mandatory attributes
            must be specified in a single SNMP SET request with
            pps16PortGroupRowStatus value as createAndGo(4).
            Upon successful row creation, this object has a
            value of active(1).

            The pps16PortGroupRowStatus object may be modified if
            the associated instance of this object is equal to active(1)."
    ::= { pps16PortGroupEntry 11 }


--pps16PortGroupOutputType OBJECT-TYPE
--    SYNTAX      PPSPhyInterfaceType
--    MAX-ACCESS  read-only
--    STATUS      current
--    DESCRIPTION
--           "This object specify PPS physical interface type."
--    ::= { pps16PortGroupEntry 11 }








--
--  CLK 16 port group 
--
clk16PortGroupTable OBJECT-TYPE
    SYNTAX      SEQUENCE OF Clk16PortGroupEntry 
    MAX-ACCESS  not-accessible
    STATUS      current
    DESCRIPTION
            "A list of entries corresponding to Pulse Per Second 
             Port Facilities."
    ::= { cmFacilityObjects 80 }


clk16PortGroupEntry OBJECT-TYPE
    SYNTAX      Clk16PortGroupEntry 
    MAX-ACCESS  not-accessible
    STATUS      current
    DESCRIPTION
            "A conceptual row in the clk16PortGroupTable."
    INDEX { neIndex, shelfIndex, slotIndex, clk16PortGroupIndex }
    ::= { clk16PortGroupTable 1 }

Clk16PortGroupEntry ::= SEQUENCE {
    -- Port Indices 
    clk16PortGroupIndex                  Integer32,
    clk16PortGroupIfIndex                InterfaceIndex,

    -- State Management params
    clk16PortGroupAdminState             AdminState,
    clk16PortGroupOperationalState       OperationalState,
    clk16PortGroupSecondaryState         SecondaryState,
    clk16PortGroupAlias                  DisplayString,

    -- port specific params

    clk16PortGroupDirection              SignalDirectionType,
    clk16PortGroupSquelchControl         SquelchControl,
    clk16PortGroupSquelchQL              SSMQualityLevel,

    clk16PortGroupRowStatus              RowStatus

}
    
clk16PortGroupIndex OBJECT-TYPE
    SYNTAX      Integer32 (1..65535)
    MAX-ACCESS  read-only
    STATUS      current
    DESCRIPTION
         "An integer index value used to uniquely identify
          this Pulse Per Second Port within the card." 
    ::= { clk16PortGroupEntry 1 }

clk16PortGroupIfIndex OBJECT-TYPE
    SYNTAX      InterfaceIndex
    MAX-ACCESS  read-only
    STATUS      current
    DESCRIPTION
         "This object has the same value as ifIndex for 
          Pulse Per Second Port.  An integer index value used to 
          uniquely identify this Pulse Per Second Port."
    ::= { clk16PortGroupEntry 2 }

-- State Management params
clk16PortGroupAdminState OBJECT-TYPE
    SYNTAX      AdminState 
    MAX-ACCESS  read-only
    STATUS      current
    DESCRIPTION
            "This object represents the Administrative State of the Pulse Per Second 
             Port."
    ::= { clk16PortGroupEntry 3 }

clk16PortGroupOperationalState OBJECT-TYPE
    SYNTAX      OperationalState 
    MAX-ACCESS  read-only
    STATUS      current
    DESCRIPTION
            "This object represents the Operational State of the Pulse Per Second 
             Port."
    ::= { clk16PortGroupEntry 4 }

clk16PortGroupSecondaryState OBJECT-TYPE
    SYNTAX      SecondaryState 
    MAX-ACCESS  read-only
    STATUS      current
    DESCRIPTION
            "This object represents the Secondary State of the Pulse Per Second 
             Port."
    ::= { clk16PortGroupEntry 5 }

clk16PortGroupAlias    OBJECT-TYPE
    SYNTAX      DisplayString (SIZE(0..64))
    MAX-ACCESS  read-only
    STATUS      current
    DESCRIPTION
         "This object allows SNMP management entities to provide an 
          alias to the gps 10MHz Port entity."
     ::= { clk16PortGroupEntry 6 }



clk16PortGroupDirection OBJECT-TYPE
    SYNTAX      SignalDirectionType 
    MAX-ACCESS  read-only
    STATUS      current
    DESCRIPTION
            "This object allows specification of the signal type 
             (i.e. input or output)."
    ::= { clk16PortGroupEntry 7 }


clk16PortGroupSquelchControl  OBJECT-TYPE 
    SYNTAX     SquelchControl
    MAX-ACCESS read-only
    STATUS     current
    DESCRIPTION
         "This object allows to set the Squelch Control for the Pulse Per Second port. 
          The Squelch Control is used to determine the type of squelch control 
          used to squelch the output of the TOD port."
     ::= { clk16PortGroupEntry 8 }

clk16PortGroupSquelchQL OBJECT-TYPE 
    SYNTAX     SSMQualityLevel
    MAX-ACCESS read-only
    STATUS     current
    DESCRIPTION
         "This object allows to set the Squelch QL for the 10MHz port. 
          This value is used when f310MHzClockPortSquelchControl is squelch-ql.
          The Squelch QL is used to determine whether or not to squelch 
          the output of the TOD port. If the system's QL is lower 
          than the Squelch QL, the output is squelched."
     ::= { clk16PortGroupEntry 9 }



clk16PortGroupRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of clk16PortGroupRowStatus supported are
            createAndGo(4) and destroy(6).  All mandatory attributes
            must be specified in a single SNMP SET request with
            clk16PortGroupRowStatus value as createAndGo(4).
            Upon successful row creation, this object has a
            value of active(1).

            The clk16PortGroupRowStatus object may be modified if
            the associated instance of this object is equal to active(1)."
    ::= { clk16PortGroupEntry 10 }





--
--  TodPps 16 Port 
--
todPps16PortGroupTable OBJECT-TYPE
    SYNTAX      SEQUENCE OF TodPps16PortGroupEntry 
    MAX-ACCESS  not-accessible
    STATUS      current
    DESCRIPTION
            "A list of entries corresponding to Time Of Day 
             Port Facilities."
    ::= { cmFacilityObjects 81 }

todPps16PortGroupEntry OBJECT-TYPE
    SYNTAX      TodPps16PortGroupEntry 
    MAX-ACCESS  not-accessible
    STATUS      current
    DESCRIPTION
            "A conceptual row in the todPps16PortGroupTable."
    INDEX { neIndex, shelfIndex, slotIndex, todPps16PortGroupIndex  }
    ::= { todPps16PortGroupTable 1 }

TodPps16PortGroupEntry ::= SEQUENCE {
    -- Port Indices 
    todPps16PortGroupIndex                  Integer32,
    todPps16PortGroupIfIndex                InterfaceIndex,

    -- State Management params
    todPps16PortGroupAdminState             AdminState,
    todPps16PortGroupOperationalState       OperationalState,
    todPps16PortGroupSecondaryState         SecondaryState,
    todPps16PortGroupAlias                  DisplayString,

    -- port specific params
    todPps16PortGroupSquelchControl         SquelchControl,
    todPps16PortGroupSquelchQL              SSMQualityLevel,
    todPps16PortGroupTODSource              VariablePointer,
    todPps16PortGroupOutputFormat           TODOutputFormat,
    todPps16PortGroupDelayCompensation      Integer32,


    todPps16PortGroupRowStatus              RowStatus


}
    
todPps16PortGroupIndex OBJECT-TYPE
    SYNTAX      Integer32 (1..65535)
    MAX-ACCESS  read-only
    STATUS      current
    DESCRIPTION
         "An integer index value used to uniquely identify
          this Time Of Day Port within the card." 
    ::= { todPps16PortGroupEntry 1 }

todPps16PortGroupIfIndex OBJECT-TYPE
    SYNTAX      InterfaceIndex
    MAX-ACCESS  read-only
    STATUS      current
    DESCRIPTION
         "This object has the same value as ifIndex for 
          Time Of Day Port.  An integer index value used to 
          uniquely identify this Time Of Day Port."
    ::= { todPps16PortGroupEntry 2 }


-- State Management params
todPps16PortGroupAdminState OBJECT-TYPE
    SYNTAX      AdminState 
    MAX-ACCESS  read-only
    STATUS      current
    DESCRIPTION
            "This object represents the Administrative State of the Time Of Day 
             Port."
    ::= { todPps16PortGroupEntry 3 }

todPps16PortGroupOperationalState OBJECT-TYPE
    SYNTAX      OperationalState 
    MAX-ACCESS  read-only
    STATUS      current
    DESCRIPTION
            "This object represents the Operational State of the Time Of Day 
             Port."
    ::= { todPps16PortGroupEntry 4 }

todPps16PortGroupSecondaryState OBJECT-TYPE
    SYNTAX      SecondaryState 
    MAX-ACCESS  read-only
    STATUS      current
    DESCRIPTION
            "This object represents the Secondary State of the Time Of Day 
             Port."
    ::= { todPps16PortGroupEntry 5 }

todPps16PortGroupAlias    OBJECT-TYPE
    SYNTAX      DisplayString (SIZE(0..64))
    MAX-ACCESS  read-only
    STATUS      current
    DESCRIPTION
         "This object allows SNMP management entities to provide an 
          alias to the gps 10MHz Port entity."
     ::= { todPps16PortGroupEntry 6 }



todPps16PortGroupSquelchControl  OBJECT-TYPE 
    SYNTAX     SquelchControl
    MAX-ACCESS read-only
    STATUS     current
    DESCRIPTION
         "This object allows to set the Squelch Control for the Time Of Day port. 
          The Squelch Control is used to determine the type of squelch control 
          used to squelch the output of the TOD port."
     ::= { todPps16PortGroupEntry 7 }

todPps16PortGroupSquelchQL OBJECT-TYPE 
    SYNTAX     SSMQualityLevel
    MAX-ACCESS read-only
    STATUS     current
    DESCRIPTION
         "This object allows to set the Squelch QL for the Time Of Day port. 
          This value is used when todPps16PortGroupSquelchControl is squelch-ql.
          The Squelch QL is used to determine whether or not to squelch 
          the output of the TOD port. If the system's QL is lower 
          than the Squelch QL, the output is squelched."
     ::= { todPps16PortGroupEntry 8 }

todPps16PortGroupTODSource OBJECT-TYPE 
    SYNTAX     VariablePointer
    MAX-ACCESS read-only
    STATUS     current
    DESCRIPTION
         "This object allows to set the Time Of Day Source for the Port." 
     ::= { todPps16PortGroupEntry 9 }

todPps16PortGroupOutputFormat  OBJECT-TYPE 
    SYNTAX     TODOutputFormat
    MAX-ACCESS read-only
    STATUS     current
    DESCRIPTION
         "This object allows to set the Output Format for the Time Of Day port. 
          The Output Format is used to determine the type of output format 
          of the TOD port."
     ::= { todPps16PortGroupEntry 10 }


todPps16PortGroupDelayCompensation OBJECT-TYPE
    SYNTAX      Integer32 (0..90)
    MAX-ACCESS  read-write
    STATUS      current
    DESCRIPTION
            "This object allows specification of the PPS external Delay
             Compensation in nanoseconds. The valid values are 0 to 96 in 
             8 nanoseconds steps. Values which are not multiple of 8 will
             be automatically rounded up to the next multiple of 8." 
    ::= { todPps16PortGroupEntry 11 }

todPps16PortGroupRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of clk16PortGroupRowStatus supported are
            createAndGo(4) and destroy(6).  All mandatory attributes
            must be specified in a single SNMP SET request with
            todPps16PortGroupRowStatus value as createAndGo(4).
            Upon successful row creation, this object has a
            value of active(1).

            The clk16PortGroupRowStatus object may be modified if
            the associated instance of this object is equal to active(1)."
    ::= { todPps16PortGroupEntry 12 }

--
-- Policer Envelope Table
--
f3PolicerEnvelopeTable OBJECT-TYPE
    SYNTAX      SEQUENCE OF F3PolicerEnvelopeEntry
    MAX-ACCESS  not-accessible
    STATUS      current
    DESCRIPTION
            "A list of entries corresponding to policer envelope for configuration purposes."
    ::= { cmFacilityObjects 82 }

f3PolicerEnvelopeEntry OBJECT-TYPE
    SYNTAX      F3PolicerEnvelopeEntry
    MAX-ACCESS  not-accessible
    STATUS      current
    DESCRIPTION
            "A conceptual row in the f3PolicerEnvelopeTable."
    INDEX { neIndex, f3PolicerEnvelopeIndex }
    ::= { f3PolicerEnvelopeTable 1 }

F3PolicerEnvelopeEntry ::= SEQUENCE {
    f3PolicerEnvelopeIndex                    Integer32,
    f3PolicerEnvelopeCouplingFlag             TruthValue,
    f3PolicerEnvelopeStorageType              StorageType,
    f3PolicerEnvelopeRowStatus                RowStatus
}

f3PolicerEnvelopeIndex OBJECT-TYPE
    SYNTAX      Integer32
    MAX-ACCESS  not-accessible
    STATUS      current
    DESCRIPTION
            "An integer index value used to uniquely identify policer envelope." 
    ::= { f3PolicerEnvelopeEntry 1 }

f3PolicerEnvelopeCouplingFlag OBJECT-TYPE
    SYNTAX      TruthValue
    MAX-ACCESS  read-write
    STATUS      current
    DESCRIPTION
            "This object allows specification of Policer Envelope Coupling Flag.
            When coupling is enabled, tokens that would normally be 
            added to the C-bucket are passed to the E-bucket only once the CIR
            bucket has reached its CBS level. Therefore under this condition
            the E-bucket is being filled at the rate of CIR + EIR. 
            Normally the long term average of frames declared yellow, which is 
            bounded by the EIR. Coupling is a function to allow the 
            long term average of frames declared yellow to be bounded by 
            CIR + EIR. This allows a higher volume of yellow frames 
            to be delivered/received if the arrival of green marked frames 
            is low.  Tokens from the E-bucket do NOT get passed to the 
            C-bucket once the EBS level has been reached.
            Enabling coupling in combination with a provisioned EIR of 0 
            allows for a single rate three color marking (srTCM) algorithm 
            to be established.  In this situation the E-bucket is filled at the 
            CIR rate in the case the C-bucket is filled to its CBS level" 
    ::= { f3PolicerEnvelopeEntry 2 }

f3PolicerEnvelopeStorageType OBJECT-TYPE
    SYNTAX      StorageType
    MAX-ACCESS  read-create
    STATUS      current
    DESCRIPTION
            "The type of storage configured for this entry." 
    ::= { f3PolicerEnvelopeEntry 3 }

f3PolicerEnvelopeRowStatus OBJECT-TYPE
    SYNTAX      RowStatus
    MAX-ACCESS  read-create
    STATUS      current
    DESCRIPTION
            "The status of this row.
               An entry MUST NOT exist in the active state unless all
               objects in the entry have an appropriate value, as described
               in the description clause for each writable object.
               
               The values of f3PolicerEnvelopeRowStatus supported are
               createAndGo(4) and destroy(6).  All mandatory attributes
               must be specified in a single SNMP SET request with
               f3UsbWIFIDonglePortRowStatus value as createAndGo(4).
               Upon successful row creation, this object has a
               value of active(1).
               
               The f3PolicerEnvelopeRowStatus object may be modified if
               the associated instance of this object is equal to active(1).
               
               Note that flow creation and deletion is only supported
               with access port in connection-oriented evpl mode." 
    ::= { f3PolicerEnvelopeEntry 4 }


--
--  Envelope Assoc Policer Flows
--
f3EnvelopeAssocPolicerTable  OBJECT-TYPE
    SYNTAX      SEQUENCE OF F3EnvelopeAssocPolicerEntry
    MAX-ACCESS  not-accessible
    STATUS      current
    DESCRIPTION
            "A list of entries corresponding to Flows which are envelope associated policers instance"
    ::= { cmFacilityObjects 83 }

f3EnvelopeAssocPolicerEntry OBJECT-TYPE
    SYNTAX      F3EnvelopeAssocPolicerEntry
    MAX-ACCESS  not-accessible
    STATUS      current
    DESCRIPTION
            "A conceptual row in the f3EnvelopeAssocPolicerTable."
    INDEX { neIndex, f3PolicerEnvelopeIndex, f3EnvelopeAssocPolicer } 
    ::= { f3EnvelopeAssocPolicerTable 1 }

F3EnvelopeAssocPolicerEntry ::= SEQUENCE {
    f3EnvelopeAssocPolicer                   VariablePointer
}

f3EnvelopeAssocPolicer OBJECT-TYPE
    SYNTAX        VariablePointer
    MAX-ACCESS    read-only
    STATUS        current
    DESCRIPTION
         "Pointer to a policer instance which is associated with envelope."
    ::= { f3EnvelopeAssocPolicerEntry 1 }


--
-- Network Port Exp encoding table 
--
cmNetPortExpDEEncTable  OBJECT-TYPE
    SYNTAX      SEQUENCE OF CmNetPortExpDEEncEntry 
    MAX-ACCESS  not-accessible
    STATUS      current
    DESCRIPTION
        "Ethernet Network Port Exp drop eligibility encoding table. This
         is applied to a frame that is egressing at the Network port."
    ::= { cmFacilityObjects 84 }

cmNetPortExpDEEncEntry OBJECT-TYPE
    SYNTAX      CmNetPortExpDEEncEntry 
    MAX-ACCESS  not-accessible
    STATUS      current
    DESCRIPTION
            "A conceptual row in the cmNetPortExpDEEncTable."
    INDEX { neIndex, shelfIndex, slotIndex, cmEthernetNetPortIndex, 
            cmNetPortExpDEEncIndex }
    ::= { cmNetPortExpDEEncTable 1 }

CmNetPortExpDEEncEntry ::= SEQUENCE {
  cmNetPortExpDEEncIndex              Integer32,
  cmNetPortExpDEEncInPriority         VlanPriority,
  cmNetPortExpDEEncDropIneligiblePrio VlanPriority,
  cmNetPortExpDEEncDropEligiblePrio   VlanPriority
}

cmNetPortExpDEEncIndex OBJECT-TYPE
    SYNTAX      Integer32
    MAX-ACCESS  not-accessible
    STATUS      current
    DESCRIPTION
            "An integer index value used to uniquely identify
             a row in the Exp drop eligible encoding table."
    ::= { cmNetPortExpDEEncEntry 1 }

cmNetPortExpDEEncInPriority OBJECT-TYPE
    SYNTAX     VlanPriority
    MAX-ACCESS read-write
    STATUS     current
    DESCRIPTION
         "This object is the input priority that is translated to a
          drop eligibility priority or a drop ineligibility priority."
     ::= { cmNetPortExpDEEncEntry 2 }

cmNetPortExpDEEncDropIneligiblePrio OBJECT-TYPE
    SYNTAX     VlanPriority
    MAX-ACCESS read-write
    STATUS     current
    DESCRIPTION
         "This object is the Exp value that has a priority value with
          implicit drop ineligibility encoded into it."
     ::= { cmNetPortExpDEEncEntry 3 }

cmNetPortExpDEEncDropEligiblePrio OBJECT-TYPE
    SYNTAX     VlanPriority
    MAX-ACCESS read-write
    STATUS     current
    DESCRIPTION
         "This object is the Exp value that has a priority value with
          implicit drop eligibility encoded into it."
     ::= { cmNetPortExpDEEncEntry 4 }

--
-- Network Port Exp decoding table
--

cmNetPortExpDEDecTable  OBJECT-TYPE
    SYNTAX      SEQUENCE OF CmNetPortExpDEDecEntry
    MAX-ACCESS  not-accessible
    STATUS      current
    DESCRIPTION
            "Ethernet Network Port Exp drop eligibility decoding table. This
             is applied to a frame that is ingressing at a port."
    ::= { cmFacilityObjects 85 }

cmNetPortExpDEDecEntry OBJECT-TYPE
    SYNTAX      CmNetPortExpDEDecEntry 
    MAX-ACCESS  not-accessible
    STATUS      current
    DESCRIPTION
            "A conceptual row in the cmNetPortExpDEDecTable."
    INDEX { neIndex, shelfIndex, slotIndex, cmEthernetNetPortIndex, 
            cmNetPortExpDEDecIndex }
    ::= { cmNetPortExpDEDecTable 1 }

CmNetPortExpDEDecEntry ::= SEQUENCE {
    cmNetPortExpDEDecIndex        Integer32,
    cmNetPortExpDEDecInPriority   VlanPriority,
    cmNetPortExpDEDecOutPriority  VlanPriority,
    cmNetPortExpDEDecDropEligible TruthValue
}


cmNetPortExpDEDecIndex OBJECT-TYPE
    SYNTAX      Integer32
    MAX-ACCESS  not-accessible
    STATUS      current
    DESCRIPTION
            "An integer index value used to uniquely identify
             a row in the Exp drop eligible decoding table."
    ::= { cmNetPortExpDEDecEntry 1 }

cmNetPortExpDEDecInPriority OBJECT-TYPE
    SYNTAX     VlanPriority
    MAX-ACCESS read-write
    STATUS     current
    DESCRIPTION
         "This object is the input priority that is decoded to get
          priority and the drop eligibility of a frame."
     ::= { cmNetPortExpDEDecEntry 2 }

cmNetPortExpDEDecOutPriority OBJECT-TYPE
    SYNTAX     VlanPriority
    MAX-ACCESS read-write
    STATUS     current
    DESCRIPTION
         "This object is the priority value decoded from a incoming Exp value."
     ::= { cmNetPortExpDEDecEntry 3 }

cmNetPortExpDEDecDropEligible OBJECT-TYPE
    SYNTAX     TruthValue
    MAX-ACCESS read-write
    STATUS     current
    DESCRIPTION
         "This object is the drop eligibility decoded from a incoming
          Exp value."
     ::= { cmNetPortExpDEDecEntry 4 }

-- 
-- Network Port Exp pair table
--

cmNetPortExpDEPairTable  OBJECT-TYPE
    SYNTAX      SEQUENCE OF CmNetPortExpDEPairEntry
    MAX-ACCESS  not-accessible
    STATUS      current
    DESCRIPTION
            "Ethernet Network Port Exp drop eligibility priority pair table.
             The priority pair is encoded to same drop eligibility and
             drop ineligibility priority. Depending on the Exp DE Enc/Dec
             mode there can be upto 3 pairs in the table. There will one
             pair for 7P1D, two pairs for 6P2D and three pairs for 5P3D."
    ::= { cmFacilityObjects 86 }

cmNetPortExpDEPairEntry OBJECT-TYPE
    SYNTAX      CmNetPortExpDEPairEntry 
    MAX-ACCESS  not-accessible
    STATUS      current
    DESCRIPTION
            "A conceptual row in the cmNetPortExpDEPairEntry."
    INDEX { neIndex, shelfIndex, slotIndex, cmEthernetNetPortIndex, 
            cmNetPortExpDEPairIndex }
    ::= { cmNetPortExpDEPairTable 1 }

CmNetPortExpDEPairEntry ::= SEQUENCE {
    cmNetPortExpDEPairIndex          Integer32,
    cmNetPortExpDEDropIneligiblePrio VlanPriority,
    cmNetPortExpDEDropEligiblePrio   VlanPriority
}

cmNetPortExpDEPairIndex OBJECT-TYPE
    SYNTAX      Integer32
    MAX-ACCESS  not-accessible
    STATUS      current
    DESCRIPTION
            "An integer index value used to uniquely identify
             a row in the Exp drop eligible priority pair table."
    ::= { cmNetPortExpDEPairEntry 1 }

cmNetPortExpDEDropIneligiblePrio OBJECT-TYPE
    SYNTAX     VlanPriority
    MAX-ACCESS read-write
    STATUS     current
    DESCRIPTION
         "This object is the drop ineligible priority."
     ::= { cmNetPortExpDEPairEntry 2 }

cmNetPortExpDEDropEligiblePrio OBJECT-TYPE
    SYNTAX     VlanPriority
    MAX-ACCESS read-write
    STATUS     current
    DESCRIPTION
         "This object is the drop eligible priority."
     ::= { cmNetPortExpDEPairEntry 3 }


--
-- Network Port IpPrec encoding table 
--
cmNetPortIpPrecDEEncTable  OBJECT-TYPE
    SYNTAX      SEQUENCE OF CmNetPortIpPrecDEEncEntry 
    MAX-ACCESS  not-accessible
    STATUS      current
    DESCRIPTION
        "Ethernet Network Port IpPrec drop eligibility encoding table. This
         is applied to a frame that is egressing at the Network port."
    ::= { cmFacilityObjects 87 }

cmNetPortIpPrecDEEncEntry OBJECT-TYPE
    SYNTAX      CmNetPortIpPrecDEEncEntry 
    MAX-ACCESS  not-accessible
    STATUS      current
    DESCRIPTION
            "A conceptual row in the cmNetPortIpPrecDEEncTable."
    INDEX { neIndex, shelfIndex, slotIndex, cmEthernetNetPortIndex, 
            cmNetPortIpPrecDEEncIndex }
    ::= { cmNetPortIpPrecDEEncTable 1 }

CmNetPortIpPrecDEEncEntry ::= SEQUENCE {
  cmNetPortIpPrecDEEncIndex              Integer32,
  cmNetPortIpPrecDEEncInPriority         VlanPriority,
  cmNetPortIpPrecDEEncDropIneligiblePrio VlanPriority,
  cmNetPortIpPrecDEEncDropEligiblePrio   VlanPriority
}

cmNetPortIpPrecDEEncIndex OBJECT-TYPE
    SYNTAX      Integer32
    MAX-ACCESS  not-accessible
    STATUS      current
    DESCRIPTION
            "An integer index value used to uniquely identify
             a row in the IpPrec drop eligible encoding table."
    ::= { cmNetPortIpPrecDEEncEntry 1 }

cmNetPortIpPrecDEEncInPriority OBJECT-TYPE
    SYNTAX     VlanPriority
    MAX-ACCESS read-write
    STATUS     current
    DESCRIPTION
         "This object is the input priority that is translated to a
          drop eligibility priority or a drop ineligibility priority."
     ::= { cmNetPortIpPrecDEEncEntry 2 }

cmNetPortIpPrecDEEncDropIneligiblePrio OBJECT-TYPE
    SYNTAX     VlanPriority
    MAX-ACCESS read-write
    STATUS     current
    DESCRIPTION
         "This object is the IpPrec value that has a priority value with
          implicit drop ineligibility encoded into it."
     ::= { cmNetPortIpPrecDEEncEntry 3 }

cmNetPortIpPrecDEEncDropEligiblePrio OBJECT-TYPE
    SYNTAX     VlanPriority
    MAX-ACCESS read-write
    STATUS     current
    DESCRIPTION
         "This object is the IpPrec value that has a priority value with
          implicit drop eligibility encoded into it."
     ::= { cmNetPortIpPrecDEEncEntry 4 }

--
-- Network Port IpPrec decoding table
--

cmNetPortIpPrecDEDecTable  OBJECT-TYPE
    SYNTAX      SEQUENCE OF CmNetPortIpPrecDEDecEntry
    MAX-ACCESS  not-accessible
    STATUS      current
    DESCRIPTION
            "Ethernet Network Port IpPrec drop eligibility decoding table. This
             is applied to a frame that is ingressing at a port."
    ::= { cmFacilityObjects 88 }

cmNetPortIpPrecDEDecEntry OBJECT-TYPE
    SYNTAX      CmNetPortIpPrecDEDecEntry 
    MAX-ACCESS  not-accessible
    STATUS      current
    DESCRIPTION
            "A conceptual row in the cmNetPortIpPrecDEDecTable."
    INDEX { neIndex, shelfIndex, slotIndex, cmEthernetNetPortIndex, 
            cmNetPortIpPrecDEDecIndex }
    ::= { cmNetPortIpPrecDEDecTable 1 }

CmNetPortIpPrecDEDecEntry ::= SEQUENCE {
    cmNetPortIpPrecDEDecIndex        Integer32,
    cmNetPortIpPrecDEDecInPriority   VlanPriority,
    cmNetPortIpPrecDEDecOutPriority  VlanPriority,
    cmNetPortIpPrecDEDecDropEligible TruthValue
}


cmNetPortIpPrecDEDecIndex OBJECT-TYPE
    SYNTAX      Integer32
    MAX-ACCESS  not-accessible
    STATUS      current
    DESCRIPTION
            "An integer index value used to uniquely identify
             a row in the IpPrec drop eligible decoding table."
    ::= { cmNetPortIpPrecDEDecEntry 1 }

cmNetPortIpPrecDEDecInPriority OBJECT-TYPE
    SYNTAX     VlanPriority
    MAX-ACCESS read-write
    STATUS     current
    DESCRIPTION
         "This object is the input priority that is decoded to get
          priority and the drop eligibility of a frame."
     ::= { cmNetPortIpPrecDEDecEntry 2 }

cmNetPortIpPrecDEDecOutPriority OBJECT-TYPE
    SYNTAX     VlanPriority
    MAX-ACCESS read-write
    STATUS     current
    DESCRIPTION
         "This object is the priority value decoded from a incoming IpPrec value."
     ::= { cmNetPortIpPrecDEDecEntry 3 }

cmNetPortIpPrecDEDecDropEligible OBJECT-TYPE
    SYNTAX     TruthValue
    MAX-ACCESS read-write
    STATUS     current
    DESCRIPTION
         "This object is the drop eligibility decoded from a incoming
          IpPrec value."
     ::= { cmNetPortIpPrecDEDecEntry 4 }

-- 
-- Network Port IpPrec pair table
--

cmNetPortIpPrecDEPairTable  OBJECT-TYPE
    SYNTAX      SEQUENCE OF CmNetPortIpPrecDEPairEntry
    MAX-ACCESS  not-accessible
    STATUS      current
    DESCRIPTION
            "Ethernet Network Port IpPrec drop eligibility priority pair table.
             The priority pair is encoded to same drop eligibility and
             drop ineligibility priority. Depending on the IpPrec DE Enc/Dec
             mode there can be upto 3 pairs in the table. There will one
             pair for 7P1D, two pairs for 6P2D and three pairs for 5P3D."
    ::= { cmFacilityObjects 89 }

cmNetPortIpPrecDEPairEntry OBJECT-TYPE
    SYNTAX      CmNetPortIpPrecDEPairEntry 
    MAX-ACCESS  not-accessible
    STATUS      current
    DESCRIPTION
            "A conceptual row in the cmNetPortIpPrecDEPairEntry."
    INDEX { neIndex, shelfIndex, slotIndex, cmEthernetNetPortIndex, 
            cmNetPortIpPrecDEPairIndex }
    ::= { cmNetPortIpPrecDEPairTable 1 }

CmNetPortIpPrecDEPairEntry ::= SEQUENCE {
    cmNetPortIpPrecDEPairIndex          Integer32,
    cmNetPortIpPrecDEDropIneligiblePrio VlanPriority,
    cmNetPortIpPrecDEDropEligiblePrio   VlanPriority
}

cmNetPortIpPrecDEPairIndex OBJECT-TYPE
    SYNTAX      Integer32
    MAX-ACCESS  not-accessible
    STATUS      current
    DESCRIPTION
            "An integer index value used to uniquely identify
             a row in the IpPrec drop eligible priority pair table."
    ::= { cmNetPortIpPrecDEPairEntry 1 }

cmNetPortIpPrecDEDropIneligiblePrio OBJECT-TYPE
    SYNTAX     VlanPriority
    MAX-ACCESS read-write
    STATUS     current
    DESCRIPTION
         "This object is the drop ineligible priority."
     ::= { cmNetPortIpPrecDEPairEntry 2 }

cmNetPortIpPrecDEDropEligiblePrio OBJECT-TYPE
    SYNTAX     VlanPriority
    MAX-ACCESS read-write
    STATUS     current
    DESCRIPTION
         "This object is the drop eligible priority."
     ::= { cmNetPortIpPrecDEPairEntry 3 }


--
-- Network Port EncapPcp encoding table 
--
cmNetPortEncapPcpDEEncTable  OBJECT-TYPE
    SYNTAX      SEQUENCE OF CmNetPortEncapPcpDEEncEntry 
    MAX-ACCESS  not-accessible
    STATUS      current
    DESCRIPTION
        "Ethernet Network Port EncapPcp drop eligibility encoding table. This
         is applied to a frame that is egressing at the Network port."
    ::= { cmFacilityObjects 90 }

cmNetPortEncapPcpDEEncEntry OBJECT-TYPE
    SYNTAX      CmNetPortEncapPcpDEEncEntry 
    MAX-ACCESS  not-accessible
    STATUS      current
    DESCRIPTION
            "A conceptual row in the cmNetPortEncapPcpDEEncTable."
    INDEX { neIndex, shelfIndex, slotIndex, cmEthernetNetPortIndex, 
            cmNetPortEncapPcpDEEncIndex }
    ::= { cmNetPortEncapPcpDEEncTable 1 }

CmNetPortEncapPcpDEEncEntry ::= SEQUENCE {
  cmNetPortEncapPcpDEEncIndex              Integer32,
  cmNetPortEncapPcpDEEncInPriority         VlanPriority,
  cmNetPortEncapPcpDEEncDropIneligiblePrio VlanPriority,
  cmNetPortEncapPcpDEEncDropEligiblePrio   VlanPriority
}

cmNetPortEncapPcpDEEncIndex OBJECT-TYPE
    SYNTAX      Integer32
    MAX-ACCESS  not-accessible
    STATUS      current
    DESCRIPTION
            "An integer index value used to uniquely identify
             a row in the EncapPcp drop eligible encoding table."
    ::= { cmNetPortEncapPcpDEEncEntry 1 }

cmNetPortEncapPcpDEEncInPriority OBJECT-TYPE
    SYNTAX     VlanPriority
    MAX-ACCESS read-write
    STATUS     current
    DESCRIPTION
         "This object is the input priority that is translated to a
          drop eligibility priority or a drop ineligibility priority."
     ::= { cmNetPortEncapPcpDEEncEntry 2 }

cmNetPortEncapPcpDEEncDropIneligiblePrio OBJECT-TYPE
    SYNTAX     VlanPriority
    MAX-ACCESS read-write
    STATUS     current
    DESCRIPTION
         "This object is the EncapPcp value that has a priority value with
          implicit drop ineligibility encoded into it."
     ::= { cmNetPortEncapPcpDEEncEntry 3 }

cmNetPortEncapPcpDEEncDropEligiblePrio OBJECT-TYPE
    SYNTAX     VlanPriority
    MAX-ACCESS read-write
    STATUS     current
    DESCRIPTION
         "This object is the EncapPcp value that has a priority value with
          implicit drop eligibility encoded into it."
     ::= { cmNetPortEncapPcpDEEncEntry 4 }

--
-- Network Port EncapPcp decoding table
--

cmNetPortEncapPcpDEDecTable  OBJECT-TYPE
    SYNTAX      SEQUENCE OF CmNetPortEncapPcpDEDecEntry
    MAX-ACCESS  not-accessible
    STATUS      current
    DESCRIPTION
            "Ethernet Network Port EncapPcp drop eligibility decoding table. This
             is applied to a frame that is ingressing at a port."
    ::= { cmFacilityObjects 91 }

cmNetPortEncapPcpDEDecEntry OBJECT-TYPE
    SYNTAX      CmNetPortEncapPcpDEDecEntry 
    MAX-ACCESS  not-accessible
    STATUS      current
    DESCRIPTION
            "A conceptual row in the cmNetPortEncapPcpDEDecTable."
    INDEX { neIndex, shelfIndex, slotIndex, cmEthernetNetPortIndex, 
            cmNetPortEncapPcpDEDecIndex }
    ::= { cmNetPortEncapPcpDEDecTable 1 }

CmNetPortEncapPcpDEDecEntry ::= SEQUENCE {
    cmNetPortEncapPcpDEDecIndex        Integer32,
    cmNetPortEncapPcpDEDecInPriority   VlanPriority,
    cmNetPortEncapPcpDEDecOutPriority  VlanPriority,
    cmNetPortEncapPcpDEDecDropEligible TruthValue
}


cmNetPortEncapPcpDEDecIndex OBJECT-TYPE
    SYNTAX      Integer32
    MAX-ACCESS  not-accessible
    STATUS      current
    DESCRIPTION
            "An integer index value used to uniquely identify
             a row in the EncapPcp drop eligible decoding table."
    ::= { cmNetPortEncapPcpDEDecEntry 1 }

cmNetPortEncapPcpDEDecInPriority OBJECT-TYPE
    SYNTAX     VlanPriority
    MAX-ACCESS read-write
    STATUS     current
    DESCRIPTION
         "This object is the input priority that is decoded to get
          priority and the drop eligibility of a frame."
     ::= { cmNetPortEncapPcpDEDecEntry 2 }

cmNetPortEncapPcpDEDecOutPriority OBJECT-TYPE
    SYNTAX     VlanPriority
    MAX-ACCESS read-write
    STATUS     current
    DESCRIPTION
         "This object is the priority value decoded from a incoming EncapPcp value."
     ::= { cmNetPortEncapPcpDEDecEntry 3 }

cmNetPortEncapPcpDEDecDropEligible OBJECT-TYPE
    SYNTAX     TruthValue
    MAX-ACCESS read-write
    STATUS     current
    DESCRIPTION
         "This object is the drop eligibility decoded from a incoming
          EncapPcp value."
     ::= { cmNetPortEncapPcpDEDecEntry 4 }

-- 
-- Network Port EncapPcp pair table
--

cmNetPortEncapPcpDEPairTable  OBJECT-TYPE
    SYNTAX      SEQUENCE OF CmNetPortEncapPcpDEPairEntry
    MAX-ACCESS  not-accessible
    STATUS      current
    DESCRIPTION
            "Ethernet Network Port EncapPcp drop eligibility priority pair table.
             The priority pair is encoded to same drop eligibility and
             drop ineligibility priority. Depending on the EncapPcp DE Enc/Dec
             mode there can be upto 3 pairs in the table. There will one
             pair for 7P1D, two pairs for 6P2D and three pairs for 5P3D."
    ::= { cmFacilityObjects 92 }

cmNetPortEncapPcpDEPairEntry OBJECT-TYPE
    SYNTAX      CmNetPortEncapPcpDEPairEntry 
    MAX-ACCESS  not-accessible
    STATUS      current
    DESCRIPTION
            "A conceptual row in the cmNetPortEncapPcpDEPairEntry."
    INDEX { neIndex, shelfIndex, slotIndex, cmEthernetNetPortIndex, 
            cmNetPortEncapPcpDEPairIndex }
    ::= { cmNetPortEncapPcpDEPairTable 1 }

CmNetPortEncapPcpDEPairEntry ::= SEQUENCE {
    cmNetPortEncapPcpDEPairIndex          Integer32,
    cmNetPortEncapPcpDEDropIneligiblePrio VlanPriority,
    cmNetPortEncapPcpDEDropEligiblePrio   VlanPriority
}

cmNetPortEncapPcpDEPairIndex OBJECT-TYPE
    SYNTAX      Integer32
    MAX-ACCESS  not-accessible
    STATUS      current
    DESCRIPTION
            "An integer index value used to uniquely identify
             a row in the EncapPcp drop eligible priority pair table."
    ::= { cmNetPortEncapPcpDEPairEntry 1 }

cmNetPortEncapPcpDEDropIneligiblePrio OBJECT-TYPE
    SYNTAX     VlanPriority
    MAX-ACCESS read-write
    STATUS     current
    DESCRIPTION
         "This object is the drop ineligible priority."
     ::= { cmNetPortEncapPcpDEPairEntry 2 }

cmNetPortEncapPcpDEDropEligiblePrio OBJECT-TYPE
    SYNTAX     VlanPriority
    MAX-ACCESS read-write
    STATUS     current
    DESCRIPTION
         "This object is the drop eligible priority."
     ::= { cmNetPortEncapPcpDEPairEntry 3 }

f3SatelliteTable  OBJECT-TYPE
    SYNTAX      SEQUENCE OF F3SatelliteEntry
    MAX-ACCESS  not-accessible
    STATUS      current
    DESCRIPTION
            "A list of GNSS Satellite entries on the NIDs."
    ::= { cmFacilityObjects 93 }

f3SatelliteEntry  OBJECT-TYPE
    SYNTAX      F3SatelliteEntry
    MAX-ACCESS  not-accessible
    STATUS      current
    DESCRIPTION
            "A conceptual row in the f3SatelliteTable Entries can
            be created/deleted in this table by management application action."
    INDEX { f3SatelliteIndex }
    ::= { f3SatelliteTable 1 }

F3SatelliteEntry ::= SEQUENCE {
    f3SatelliteIndex        Unsigned32,
    f3SatelliteSV           Unsigned32,
    f3SatelliteInUse        TruthValue,
    f3SatelliteSVType       ConstellationTypesBitMap,
    f3SatelliteCNO          Unsigned32,
    f3SatelliteHealth       SatelliteHealth,
    f3SatelliteAzimuth      Unsigned32,
    f3SatelliteElevation         Unsigned32,
    f3SatelliteGnssReceiverPort  VariablePointer

}

f3SatelliteIndex OBJECT-TYPE
    SYNTAX       Unsigned32 (1..32)
    MAX-ACCESS   not-accessible
    STATUS       current
    DESCRIPTION
            "An integer index value used to uniquely identify
             this Satellite Entry in the f3SatelliteTable."
    ::= { f3SatelliteEntry 1 }

f3SatelliteInUse OBJECT-TYPE
    SYNTAX     TruthValue
    MAX-ACCESS read-only
    STATUS     current
    DESCRIPTION
         "This object indicates whether the Satellite Entry been used by GNSS receiver.
     It is supported only on OSA542x devices."
     ::= { f3SatelliteEntry 2 }

f3SatelliteSV       OBJECT-TYPE
    SYNTAX          Unsigned32 (1..255)
    MAX-ACCESS      read-only
    STATUS          current
    DESCRIPTION
         "This object indicates the Satellite Entry SV PRN number."
     ::= { f3SatelliteEntry 3 }

f3SatelliteSVType   OBJECT-TYPE
    SYNTAX          ConstellationTypesBitMap
    MAX-ACCESS      read-only
    STATUS          current
    DESCRIPTION
         "This object indicates the Satellite Entry Constellation Type."
     ::= { f3SatelliteEntry 4 }

f3SatelliteCNO      OBJECT-TYPE
    SYNTAX          Unsigned32 
    MAX-ACCESS      read-only
    STATUS          current
    DESCRIPTION
         "This object indicates the Satellite Entry Signal Level (Carrier-to-Noise power ratio)
     in dB-Hz units."
     ::= { f3SatelliteEntry 5 }

f3SatelliteHealth    OBJECT-TYPE
    SYNTAX           SatelliteHealth
    MAX-ACCESS       read-only
    STATUS           current
    DESCRIPTION
         "This object indicates the Satellite Entry Health."
    ::= { f3SatelliteEntry 6 }

f3SatelliteAzimuth   OBJECT-TYPE
    SYNTAX           Unsigned32 (0..360)
    MAX-ACCESS       read-only
    STATUS           current
    DESCRIPTION
         "This object indicates the Satellite Entry Azimuth Angle in degrees."
    ::= { f3SatelliteEntry 7 }

f3SatelliteElevation  OBJECT-TYPE
    SYNTAX            Unsigned32 (0..90)
    MAX-ACCESS        read-only 
    STATUS            current
    DESCRIPTION
         "This object indicates the Satellite Entry Elevation Angle in degrees."
    ::= { f3SatelliteEntry 8 }
f3SatelliteGnssReceiverPort  OBJECT-TYPE
    SYNTAX            VariablePointer
    MAX-ACCESS        read-only 
    STATUS            current
    DESCRIPTION       "This object provides the GNSS Receiver Port OID related to this Satellite Entry."
    ::= { f3SatelliteEntry 9 }

--
-- Traffic Port JDSU Ext Table
--

cmEthernetTrafficPortJdsuExtTable OBJECT-TYPE
    SYNTAX      SEQUENCE OF CmEthernetTrafficPortJdsuExtEntry
    MAX-ACCESS  not-accessible
    STATUS      current
    DESCRIPTION
            "A list of entries corresponding to Ethernet Traffic Port 
            Facilities for JDSU configuration purposes."
    ::= { cmFacilityObjects 94 }

cmEthernetTrafficPortJdsuExtEntry OBJECT-TYPE
    SYNTAX      CmEthernetTrafficPortJdsuExtEntry
    MAX-ACCESS  not-accessible
    STATUS      current
    DESCRIPTION
            "A conceptual row in the cmEthernetTrafficPortJdsuExtTable."
    AUGMENTS { cmEthernetTrafficPortEntry }
    ::= { cmEthernetTrafficPortJdsuExtTable 1 }

CmEthernetTrafficPortJdsuExtEntry ::= SEQUENCE {
    cmEthernetTrafficPortJDSUControlFramesSnoopingEnabled   TruthValue,
    cmEthernetTrafficPortJDSULoopbackVlan                   VlanId,
    cmEthernetTrafficPortJDSULoopbackVlanList               DisplayString
}

cmEthernetTrafficPortJDSUControlFramesSnoopingEnabled OBJECT-TYPE
    SYNTAX      TruthValue  
    MAX-ACCESS  read-write
    STATUS      current
    DESCRIPTION
        "Enabled: reaction/response to JDSU in-band loopback requests and hallo requests.
         Disabled: Not reaction/response to JDSU in-band loopback requests and hallo requests. 
         FPGA shall not filter the JDSU control frames to processor.
         From enabled to disabled, if there is already a JDSU loopback on the port, 
         release current loopback.
         JDSU loopback doesn't need port in maintenance state."
     ::= { cmEthernetTrafficPortJdsuExtEntry 1 }

cmEthernetTrafficPortJDSULoopbackVlan OBJECT-TYPE
    SYNTAX      VlanId  
    MAX-ACCESS  read-only
    STATUS      current
    DESCRIPTION
        "Applicable when port in JDSU VLAN loopback."
     ::= { cmEthernetTrafficPortJdsuExtEntry 2 }

cmEthernetTrafficPortJDSULoopbackVlanList OBJECT-TYPE
    SYNTAX      DisplayString  
    MAX-ACCESS  read-only
    STATUS      current
    DESCRIPTION
        "The format is like 'OuterVid1-OuterPri1;InnerVid1-InnerPri1, OuterVid2-OuterPri2, 
        OuterVid3-OuterPri3;InnerVid3-InnerPri3'('1-*;2-*, 3-*, 4-*;5-*')."
     ::= { cmEthernetTrafficPortJdsuExtEntry 3 }

--
--  Flow Point QoS Shaper
--
f3FpQosShaperTable OBJECT-TYPE
    SYNTAX      SEQUENCE OF F3FpQosShaperEntry
    MAX-ACCESS  not-accessible
    STATUS      current
    DESCRIPTION
       "A list of entries corresponding to Flow Point 
        Quality of Service Shaper for configuration purposes."
    ::= { cmFacilityObjects 95 }

f3FpQosShaperEntry OBJECT-TYPE
    SYNTAX      F3FpQosShaperEntry 
    MAX-ACCESS  not-accessible
    STATUS      current
    DESCRIPTION
       "A conceptual row in the f3FpQosShaperTable. 
        These entries represent an Flow Point Quality 
        of Service Shaper."
    INDEX { neIndex, shelfIndex, slotIndex, cmEthernetTrafficPortIndex, 
            cmFlowPointIndex, f3FpQosShaperIndex }
    ::= { f3FpQosShaperTable 1 }

F3FpQosShaperEntry ::= SEQUENCE {
    f3FpQosShaperIndex               Integer32,

    f3FpQosShaperAdminState          AdminState,
    f3FpQosShaperOperationalState    OperationalState,
    f3FpQosShaperSecondaryState      SecondaryState,

    f3FpQosShaperCIRLo               Unsigned32,
    f3FpQosShaperCIRHi               Unsigned32,
    f3FpQosShaperEIRLo               Unsigned32,
    f3FpQosShaperEIRHi               Unsigned32,
    f3FpQosShaperCBS                 Unsigned32,
    f3FpQosShaperEBS                 Unsigned32,
    f3FpQosShaperBufferSize          Unsigned32,
    f3FpQosShaperCOS                 Integer32,
    
    f3FpQosShaperStorageType         StorageType,
    f3FpQosShaperRowStatus           RowStatus,
    f3FpQosShaperWfqWeight           Integer32
}

f3FpQosShaperIndex OBJECT-TYPE
    SYNTAX      Integer32 (1..8)
    MAX-ACCESS  not-accessible
    STATUS      current
    DESCRIPTION
       "The unique integer index value corresponding to a Quality 
        of Service Shaper."
    ::= { f3FpQosShaperEntry 1 }

f3FpQosShaperAdminState OBJECT-TYPE
    SYNTAX      AdminState 
    MAX-ACCESS  read-create
    STATUS      current
    DESCRIPTION
       "This object represents the Administrative State of a Shaper." 
    ::= { f3FpQosShaperEntry 2 }

f3FpQosShaperOperationalState OBJECT-TYPE
    SYNTAX      OperationalState 
    MAX-ACCESS  read-only
    STATUS      current
    DESCRIPTION
       "This object represents the Operational State of a Shaper." 
    ::= { f3FpQosShaperEntry 3 }

f3FpQosShaperSecondaryState OBJECT-TYPE
    SYNTAX      SecondaryState 
    MAX-ACCESS  read-only
    STATUS      current
    DESCRIPTION
       "This object represents the Secondary State of the Shaper." 
    ::= { f3FpQosShaperEntry 4 }

f3FpQosShaperCIRLo OBJECT-TYPE
    SYNTAX      Unsigned32
    MAX-ACCESS  read-create
    STATUS      current
    DESCRIPTION
       "This object represents the Commited Information Rate (CIR)
        (Lower 32 bits) of the Shaper."
    ::= { f3FpQosShaperEntry 5 }
     
f3FpQosShaperCIRHi OBJECT-TYPE
    SYNTAX      Unsigned32
    MAX-ACCESS  read-create
    STATUS      current
    DESCRIPTION
       "This object represents the Commited Information Rate (CIR)
        (Higher 32 bits) of the Shaper."
    ::= { f3FpQosShaperEntry 6 }

f3FpQosShaperEIRLo OBJECT-TYPE
    SYNTAX      Unsigned32
    MAX-ACCESS  read-create
    STATUS      current
    DESCRIPTION
       "This object represents the Excess Information Rate (EIR)
        (Lower 32 bits) of a Shaper."
    ::= { f3FpQosShaperEntry 7 }

f3FpQosShaperEIRHi OBJECT-TYPE
    SYNTAX      Unsigned32
    MAX-ACCESS  read-create
    STATUS      current
    DESCRIPTION
       "This object represents the Excess Information Rate (EIR)
        (Lower 32 bits) of a Shaper."
    ::= { f3FpQosShaperEntry 8 }

f3FpQosShaperCBS OBJECT-TYPE
    SYNTAX      Unsigned32
    MAX-ACCESS  read-create
    STATUS      current
    DESCRIPTION
       "This object represents the Commited Burst Size (CBS) 
        of a Shaper."
    ::= { f3FpQosShaperEntry 9 }

f3FpQosShaperEBS OBJECT-TYPE
    SYNTAX      Unsigned32
    MAX-ACCESS  read-create
    STATUS      current
    DESCRIPTION
       "This object represents the Excess Burst Size (EBS) 
        of a Shaper."
    ::= { f3FpQosShaperEntry 10 }

f3FpQosShaperBufferSize OBJECT-TYPE
    SYNTAX      Unsigned32
    MAX-ACCESS  read-create
    STATUS      current
    DESCRIPTION
       "This object represents the Buffer Size of the Shaper."
    ::= { f3FpQosShaperEntry 11 }

f3FpQosShaperCOS OBJECT-TYPE
    SYNTAX      Integer32 (0..7)
    MAX-ACCESS  read-only
    STATUS      current
    DESCRIPTION
       "This object provides the COS (Class of Service) value for
        the QOS Shaper."
    ::= { f3FpQosShaperEntry 12 }

f3FpQosShaperStorageType OBJECT-TYPE
    SYNTAX      StorageType
    MAX-ACCESS  read-create
    STATUS      current
    DESCRIPTION
       "The type of storage configured for this entry."
    ::= { f3FpQosShaperEntry 13 }

f3FpQosShaperRowStatus OBJECT-TYPE
    SYNTAX      RowStatus
    MAX-ACCESS  read-create
    STATUS      current
    DESCRIPTION
       "The status of this row.
        An entry MUST NOT exist in the active state unless all
        objects in the entry have an appropriate value, as described
        in the description clause for each writable object.

        The values of f3FpQosShaperRowStatus supported are
        createAndGo(4) and destroy(6). All mandatory attributes
        must be specified in a single SNMP SET request with
        f3FpQosShaperRowStatus value as createAndGo(4).
        Upon successful row creation, this object has a
        value of active(1).

        The f3FpQosShaperRowStatus object may be modified if
        the associated instance of this object is equal to active(1)."
    ::= { f3FpQosShaperEntry 14 }

f3FpQosShaperWfqWeight OBJECT-TYPE
    SYNTAX     Integer32
    MAX-ACCESS read-write
    STATUS     current
    DESCRIPTION
        "This object represents the wfq weight of the QoS Shaper."
    ::= { f3FpQosShaperEntry 15 }

--
--  Flow Point QoS Policer
--
f3FpQosPolicerTable  OBJECT-TYPE
    SYNTAX      SEQUENCE OF F3FpQosPolicerEntry
    MAX-ACCESS  not-accessible
    STATUS      current
    DESCRIPTION
       "A list of entries corresponding to Flow Point
        Quality of Service Policer for configuration purposes."
    ::= { cmFacilityObjects 96 }

f3FpQosPolicerEntry OBJECT-TYPE
    SYNTAX      F3FpQosPolicerEntry 
    MAX-ACCESS  not-accessible
    STATUS      current
    DESCRIPTION
       "A conceptual row in the f3FpQosPolicerTable. 
        These entries represent an Flow Point Quality
        of Service Policer."
    INDEX { neIndex, shelfIndex, slotIndex, cmEthernetTrafficPortIndex, 
            cmFlowPointIndex, f3FpQosPolicerIndex }
    ::= { f3FpQosPolicerTable 1 }

F3FpQosPolicerEntry ::= SEQUENCE {
    f3FpQosPolicerIndex                 Integer32,

    f3FpQosPolicerAdminState            AdminState,
    f3FpQosPolicerOperationalState      OperationalState,
    f3FpQosPolicerSecondaryState        SecondaryState,

    f3FpQosPolicerCIRLo                 Unsigned32,
    f3FpQosPolicerCIRHi                 Unsigned32,
    f3FpQosPolicerEIRLo                 Unsigned32,
    f3FpQosPolicerEIRHi                 Unsigned32,
    f3FpQosPolicerCBS                   Integer32,
    f3FpQosPolicerEBS                   Integer32,
    
    f3FpQosPolicerAlgorithm             PolicerAlgorithmType,
    f3FpQosPolicerColorMode             PolicerColorMode,
    f3FpQosPolicerCouplingFlag          TruthValue,
    f3FpQosPolicerPolicingEnabled       TruthValue,
    
    f3FpQosPolicerStorageType           StorageType,
    f3FpQosPolicerRowStatus             RowStatus, 

    f3FpQosPolicerCIRMaxHi              Unsigned32,
    f3FpQosPolicerCIRMaxLo              Unsigned32,
    f3FpQosPolicerEIRMaxHi              Unsigned32,
    f3FpQosPolicerEIRMaxLo              Unsigned32,
    f3FpQosPolicerEnvelopeObject        VariablePointer,
    f3FpQosPolicerRank                  Integer32    
}

f3FpQosPolicerIndex OBJECT-TYPE
    SYNTAX      Integer32 (1..8)
    MAX-ACCESS  not-accessible
    STATUS      current
    DESCRIPTION
       "The unique integer index value corresponding to a Quality 
        of Service Policer.
        The Policer Index represents the COS level. This
        is applicable in case of a Multi COS Flow Point. Index 1
        represents COS 0; Index 2 represents COS 1 and so on."
    ::= { f3FpQosPolicerEntry 1 }

f3FpQosPolicerAdminState OBJECT-TYPE
    SYNTAX      AdminState 
    MAX-ACCESS  read-create
    STATUS      current
    DESCRIPTION
       "This object represents the Administrative State of a Policer."
    ::= { f3FpQosPolicerEntry 2 }

f3FpQosPolicerOperationalState OBJECT-TYPE
    SYNTAX      OperationalState 
    MAX-ACCESS  read-only
    STATUS      current
    DESCRIPTION
       "This object represents the Operational State of a Policer." 
    ::= { f3FpQosPolicerEntry 3 }

f3FpQosPolicerSecondaryState OBJECT-TYPE
    SYNTAX      SecondaryState 
    MAX-ACCESS  read-only
    STATUS      current
    DESCRIPTION
       "This object represents the Secondary State of a Policer." 
    ::= { f3FpQosPolicerEntry 4 }

f3FpQosPolicerCIRLo OBJECT-TYPE
    SYNTAX      Unsigned32
    MAX-ACCESS  read-create
    STATUS      current
    DESCRIPTION
       "This object represents the Commited Information Rate (CIR)
        (Lower 32 bits) of the Policer."
    ::= { f3FpQosPolicerEntry 5 }

f3FpQosPolicerCIRHi OBJECT-TYPE
    SYNTAX      Unsigned32
    MAX-ACCESS  read-create
    STATUS      current
    DESCRIPTION
       "This object represents the Commited Information Rate (CIR)
        (Higher 32 bits) of the Policer."
    ::= { f3FpQosPolicerEntry 6 }

f3FpQosPolicerEIRLo OBJECT-TYPE
    SYNTAX      Unsigned32
    MAX-ACCESS  read-create
    STATUS      current
    DESCRIPTION
       "This object represents the Excess Information Rate (EIR)
        (Lower 32 bits) of a Policer."
    ::= { f3FpQosPolicerEntry 7 }

f3FpQosPolicerEIRHi OBJECT-TYPE
    SYNTAX      Unsigned32
    MAX-ACCESS  read-create
    STATUS      current
    DESCRIPTION
       "This object represents the Excess Information Rate (EIR)
        (Lower 32 bits) of a Policer."
    ::= { f3FpQosPolicerEntry 8 }

f3FpQosPolicerCBS OBJECT-TYPE
    SYNTAX      Integer32
    MAX-ACCESS  read-create
    STATUS      current
    DESCRIPTION
       "This object represents the Commited Burst Size (CBS) 
        of a Policer."
    ::= { f3FpQosPolicerEntry 9 }

f3FpQosPolicerEBS OBJECT-TYPE
    SYNTAX      Integer32
    MAX-ACCESS  read-create
    STATUS      current
    DESCRIPTION
       "This object represents the Excess Burst Size (EBS) 
        of a Policer."
    ::= { f3FpQosPolicerEntry 10 }

f3FpQosPolicerAlgorithm OBJECT-TYPE
    SYNTAX      PolicerAlgorithmType 
    MAX-ACCESS  read-only
    STATUS      current
    DESCRIPTION
       "This object represents Policer algorithm as 'srTCM'
        (Single Rate Triple Color Marking) or 'trTCM' 
        (Two Rate Triple Color Marking)."
    ::= { f3FpQosPolicerEntry 11 }

f3FpQosPolicerColorMode OBJECT-TYPE
    SYNTAX      PolicerColorMode 
    MAX-ACCESS  read-create
    STATUS      current
    DESCRIPTION
       "This object allows specification of Policer Color Mode as
        'color-aware' or 'color-blind'."
    ::= { f3FpQosPolicerEntry 12 }

f3FpQosPolicerCouplingFlag OBJECT-TYPE
    SYNTAX      TruthValue
    MAX-ACCESS  read-create
    STATUS      current
    DESCRIPTION
       "This object allows specification of Policer Coupling Flag.
        When coupling is enabled, tokens that would normally be 
        added to the C-bucket are passed to the E-bucket only once the CIR
        bucket has reached its CBS level. Therefore under this condition
        the E-bucket is being filled at the rate of CIR + EIR. 
        Normally the long term average of frames declared yellow is 
        bounded by the EIR. Coupling is a function to allow the 
        long term average of frames declared yellow to be bounded by 
        CIR + EIR. This allows a higher volume of yellow frames 
        to be delivered/received if the arrival of green marked frames 
        is low. Tokens from the E-bucket do NOT get passed to the 
        C-bucket once the EBS level has been reached.
        Enabling coupling in combination with a provisioned EIR of 0 
        allows for a single rate three color marking (srTCM) algorithm 
        to be established.  In this situation the E-bucket is filled at the 
        CIR rate in the case the C-bucket is filled to its CBS level."
    ::= { f3FpQosPolicerEntry 13 }

f3FpQosPolicerPolicingEnabled OBJECT-TYPE
    SYNTAX      TruthValue
    MAX-ACCESS  read-create
    STATUS      current
    DESCRIPTION
       "This object allows specification of Policer Policing.
        When Policing is disabled, traffic policing is bypassed. 
        When Policing is enabled, traffic policing is applied."
    ::= { f3FpQosPolicerEntry 14 }

f3FpQosPolicerStorageType OBJECT-TYPE
    SYNTAX      StorageType
    MAX-ACCESS  read-create
    STATUS      current
    DESCRIPTION
       "The type of storage configured for this entry."
    ::= { f3FpQosPolicerEntry 15 }

f3FpQosPolicerRowStatus OBJECT-TYPE
    SYNTAX      RowStatus
    MAX-ACCESS  read-create
    STATUS      current
    DESCRIPTION
       "The status of this row.
        An entry MUST NOT exist in the active state unless all
        objects in the entry have an appropriate value, as described
        in the description clause for each writable object.

        The values of f3FpQosPolicerRowStatus supported are
        createAndGo(4) and destroy(6). All mandatory attributes
        must be specified in a single SNMP SET request with
        f3FpQosPolicerRowStatus value as createAndGo(4).
        Upon successful row creation, this object has a
        value of active(1).

        The f3FpQosPolicerRowStatus object may be modified if
        the associated instance of this object is equal to active(1)."
    ::= { f3FpQosPolicerEntry 16 }

f3FpQosPolicerCIRMaxHi OBJECT-TYPE
    SYNTAX     Unsigned32
    MAX-ACCESS read-write
    STATUS     current
    DESCRIPTION
         "This object allows specification of the Commited Information
          Rate(CIR) MAX on Policer.  This represents the high 32 bits."
     ::= { f3FpQosPolicerEntry 17 }

f3FpQosPolicerCIRMaxLo OBJECT-TYPE
    SYNTAX     Unsigned32
    MAX-ACCESS read-write
    STATUS     current
    DESCRIPTION
         "This object allows specification of the Commited Information
          Rate(CIR) MAX on Policer.  This represents the lower 32 bits."
     ::= { f3FpQosPolicerEntry 18 }

f3FpQosPolicerEIRMaxHi OBJECT-TYPE
    SYNTAX     Unsigned32
    MAX-ACCESS read-write
    STATUS     current
    DESCRIPTION
         "This object allows specification of the Excess Information
          Rate(EIR) MAX on the Policer.  This represents the high 32 bits."
     ::= { f3FpQosPolicerEntry 19 }

f3FpQosPolicerEIRMaxLo OBJECT-TYPE
    SYNTAX     Unsigned32
    MAX-ACCESS read-write
    STATUS     current
    DESCRIPTION
         "This object allows specification of the Excess Information
          Rate(EIR) MAX on the Policer.  This represents the lower 32 bits."
     ::= { f3FpQosPolicerEntry 20 }

f3FpQosPolicerEnvelopeObject OBJECT-TYPE
    SYNTAX     VariablePointer
    MAX-ACCESS read-write
    STATUS     current
    DESCRIPTION
         "This object allows specification of envelope object."
     ::= { f3FpQosPolicerEntry 21 }

f3FpQosPolicerRank OBJECT-TYPE
    SYNTAX     Integer32
    MAX-ACCESS read-write
    STATUS     current
    DESCRIPTION
         "This object allows specification of rank value."
     ::= { f3FpQosPolicerEntry 22 }

--
--
--  Ethernet Traffic Port Control Protocol Disposition V2
--

cmEthernetTrafficPortCpdV2Table  OBJECT-TYPE
    SYNTAX      SEQUENCE OF CmEthernetTrafficPortCpdV2Entry
    MAX-ACCESS  not-accessible
    STATUS      current
    DESCRIPTION
            "A list of entries corresponding to Ethernet Traffic Port 
             Control Protocol Disposition (CPD) V2.  This support of
             CPD is provided on the GE206/GE201 device."
    ::= { cmFacilityObjects 97 }

cmEthernetTrafficPortCpdV2Entry OBJECT-TYPE
    SYNTAX      CmEthernetTrafficPortCpdV2Entry 
    MAX-ACCESS  not-accessible
    STATUS      current
    DESCRIPTION
            "A conceptual row in the cmEthernetTrafficPortCpdV2Table. 
             These entries represent a Control Protocol Disposition 
             filtering criteria on the Ethernet Traffic Port."
    INDEX { neIndex, shelfIndex, slotIndex, cmEthernetTrafficPortIndex, 
            cmEthernetTrafficPortCpdV2Index }
    ::= { cmEthernetTrafficPortCpdV2Table 1 }

CmEthernetTrafficPortCpdV2Entry ::= SEQUENCE {
    -- Index
    cmEthernetTrafficPortCpdV2Index            Integer32,

    -- Filtering Criteria
    cmEthernetTrafficPortCpdV2CiscoGroupDispType        CmControlProtocolDispType,
    cmEthernetTrafficPortCpdV2IslDispType               CmControlProtocolDispType,
    cmEthernetTrafficPortCpdV2PagpDispType              CmControlProtocolDispType,
    cmEthernetTrafficPortCpdV2UdldDispType              CmControlProtocolDispType,
    cmEthernetTrafficPortCpdV2CdpDispType               CmControlProtocolDispType,
    cmEthernetTrafficPortCpdV2VtpDispType               CmControlProtocolDispType,
    cmEthernetTrafficPortCpdV2DtpDispType               CmControlProtocolDispType,
    cmEthernetTrafficPortCpdV2PvstpPlusDispType         CmControlProtocolDispType,
    cmEthernetTrafficPortCpdV2UplinkFastDispType        CmControlProtocolDispType,
    cmEthernetTrafficPortCpdV2VlanBridgeDispType        CmControlProtocolDispType,
    cmEthernetTrafficPortCpdV2L2PTDispType              CmControlProtocolDispType,
    cmEthernetTrafficPortCpdV2BridgeGroupDispType       CmControlProtocolDispType,
    cmEthernetTrafficPortCpdV2BPDUDispType              CmControlProtocolDispType,
    cmEthernetTrafficPortCpdV2PauseDispType             CmControlProtocolDispType,
    cmEthernetTrafficPortCpdV2LACPDispType              CmControlProtocolDispType,
    cmEthernetTrafficPortCpdV2LACPMarkerDispType        CmControlProtocolDispType,
    cmEthernetTrafficPortCpdV2EfmOamDispType            CmControlProtocolDispType,
    cmEthernetTrafficPortCpdV2SSMDispType               CmControlProtocolDispType,
    cmEthernetTrafficPortCpdV2PortAuthenDispType        CmControlProtocolDispType,
    cmEthernetTrafficPortCpdV2BridgeReservedDispType    CmControlProtocolDispType,
    cmEthernetTrafficPortCpdV2LANBridgesDispType        CmControlProtocolDispType,
    cmEthernetTrafficPortCpdV2GARPGroupDispType         CmControlProtocolDispType,
    cmEthernetTrafficPortCpdV2GMRPDispType              CmControlProtocolDispType,
    cmEthernetTrafficPortCpdV2GVRPDispType              CmControlProtocolDispType,
    cmEthernetTrafficPortCpdV2GARPDispType              CmControlProtocolDispType,
    --
    cmEthernetTrafficPortCpdV2LLDPDispType              CmControlProtocolDispType,
    cmEthernetTrafficPortCpdV2ELMIDispType              CmControlProtocolDispType,
    cmEthernetTrafficPortCpdV2L2PTTunnelMac             MacAddress,
    --
    cmEthernetTrafficPortCpdV2Mac00DispType             CmControlProtocolDispType,
    cmEthernetTrafficPortCpdV2Mac01DispType             CmControlProtocolDispType,
    cmEthernetTrafficPortCpdV2Mac02DispType             CmControlProtocolDispType,
    cmEthernetTrafficPortCpdV2Mac03DispType             CmControlProtocolDispType,
    cmEthernetTrafficPortCpdV2Mac04DispType             CmControlProtocolDispType,
    cmEthernetTrafficPortCpdV2Mac05DispType             CmControlProtocolDispType,
    cmEthernetTrafficPortCpdV2Mac06DispType             CmControlProtocolDispType,
    cmEthernetTrafficPortCpdV2Mac07DispType             CmControlProtocolDispType,
    cmEthernetTrafficPortCpdV2Mac08DispType             CmControlProtocolDispType,
    cmEthernetTrafficPortCpdV2Mac09DispType             CmControlProtocolDispType,
    cmEthernetTrafficPortCpdV2Mac0ADispType             CmControlProtocolDispType,
    cmEthernetTrafficPortCpdV2Mac0BDispType             CmControlProtocolDispType,
    cmEthernetTrafficPortCpdV2Mac0CDispType             CmControlProtocolDispType,
    cmEthernetTrafficPortCpdV2Mac0DDispType             CmControlProtocolDispType,
    cmEthernetTrafficPortCpdV2Mac0EDispType             CmControlProtocolDispType,
    cmEthernetTrafficPortCpdV2Mac0FDispType             CmControlProtocolDispType,
    cmEthernetTrafficPortCpdV2NearestLLDPDispType       CmControlProtocolDispType,
    cmEthernetTrafficPortCpdV2NonTpmrLLDPDispType       CmControlProtocolDispType,
    cmEthernetTrafficPortCpdV2CustomerLLDPDispType      CmControlProtocolDispType,
    cmEthernetTrafficPortCpdV2PtpUntaggedDispType       CmControlProtocolDispType,
    cmEthernetTrafficPortCpdV2PtpTaggedDispType         CmControlProtocolDispType    
}

cmEthernetTrafficPortCpdV2Index OBJECT-TYPE
    SYNTAX      Integer32 
    MAX-ACCESS  read-only
    STATUS      current
    DESCRIPTION
        "Unique Index value to access the CPD row."
    ::= { cmEthernetTrafficPortCpdV2Entry 1 }

cmEthernetTrafficPortCpdV2CiscoGroupDispType OBJECT-TYPE
    SYNTAX      CmControlProtocolDispType 
    MAX-ACCESS  read-write
    STATUS      deprecated
    DESCRIPTION
        "Deprecated - each Cisco protocol has its own disposition.
         Control Protocol Disposition for Cisco Group.  This includes
         ISL, PAGP, UDLD, CDP, VTP, DTP, PSVTP+, UplinkFast, VLAN Bridge,
         L2PT.  Note that a specific protocol filter overrides the
         group setting."
    ::= { cmEthernetTrafficPortCpdV2Entry 2 }

cmEthernetTrafficPortCpdV2IslDispType OBJECT-TYPE
    SYNTAX      CmControlProtocolDispType 
    MAX-ACCESS  read-write
    STATUS      current
    DESCRIPTION
        "Control Protocol Disposition for ISL (Inter Switch Link).
         MAC Address (01:00:0C:00:00:00)."
    ::= { cmEthernetTrafficPortCpdV2Entry 3 }

cmEthernetTrafficPortCpdV2PagpDispType OBJECT-TYPE
    SYNTAX      CmControlProtocolDispType 
    MAX-ACCESS  read-write
    STATUS      current
    DESCRIPTION
        "Control Protocol Disposition for PAGP (Port Aggregation Protocol).
         MAC Address (01:00:0C:CC:CC:CC), Ethertype(0x104)."
    ::= { cmEthernetTrafficPortCpdV2Entry 4 }

cmEthernetTrafficPortCpdV2UdldDispType OBJECT-TYPE
    SYNTAX      CmControlProtocolDispType 
    MAX-ACCESS  read-write
    STATUS      current
    DESCRIPTION
        "Control Protocol Disposition for UDLD (Unidirectional Link Detection).
         MAC Address (01:00:0C:CC:CC:CC), Ethertype(0x111)."
    ::= { cmEthernetTrafficPortCpdV2Entry 5 }

cmEthernetTrafficPortCpdV2CdpDispType OBJECT-TYPE
    SYNTAX      CmControlProtocolDispType 
    MAX-ACCESS  read-write
    STATUS      current
    DESCRIPTION
        "Control Protocol Disposition for CDP (Cisco Discovery Protocol).
         MAC Address (01:00:0C:CC:CC:CC), Ethertype(0x2000)."
    ::= { cmEthernetTrafficPortCpdV2Entry 6 }

cmEthernetTrafficPortCpdV2VtpDispType OBJECT-TYPE
    SYNTAX      CmControlProtocolDispType 
    MAX-ACCESS  read-write
    STATUS      current
    DESCRIPTION
        "Control Protocol Disposition for VTP (VLAN Trunking Protocol).
         MAC Address (01:00:0C:CC:CC:CC), Ethertype(0x2003)."
    ::= { cmEthernetTrafficPortCpdV2Entry 7 }

cmEthernetTrafficPortCpdV2DtpDispType OBJECT-TYPE
    SYNTAX      CmControlProtocolDispType 
    MAX-ACCESS  read-write
    STATUS      current
    DESCRIPTION
        "Control Protocol Disposition for DTP (Dynamic Trunking).
         MAC Address (01:00:0C:CC:CC:CC), Ethertype(0x2004)."
    ::= { cmEthernetTrafficPortCpdV2Entry 8 }

cmEthernetTrafficPortCpdV2PvstpPlusDispType OBJECT-TYPE
    SYNTAX      CmControlProtocolDispType 
    MAX-ACCESS  read-write
    STATUS      current
    DESCRIPTION
        "Control Protocol Disposition for Spanning Tree PVSTP+.
         MAC Address (01:00:0C:CC:CC:CC), Ethertype(0x10B)."
    ::= { cmEthernetTrafficPortCpdV2Entry 9 }

cmEthernetTrafficPortCpdV2UplinkFastDispType OBJECT-TYPE
    SYNTAX      CmControlProtocolDispType 
    MAX-ACCESS  read-write
    STATUS      current
    DESCRIPTION
        "Control Protocol Disposition for STP UplinkFast.
         MAC Address (01:00:0C:CD:CD:CD), Ethertype(0x200A)."
    ::= { cmEthernetTrafficPortCpdV2Entry 10 }

cmEthernetTrafficPortCpdV2VlanBridgeDispType OBJECT-TYPE
    SYNTAX      CmControlProtocolDispType 
    MAX-ACCESS  read-write
    STATUS      current
    DESCRIPTION
        "Control Protocol Disposition for VLAN Bridge.
         MAC Address (01:00:0C:CD:CD:CE), Ethertype(0x10C)."
    ::= { cmEthernetTrafficPortCpdV2Entry 11 }

cmEthernetTrafficPortCpdV2L2PTDispType OBJECT-TYPE
    SYNTAX      CmControlProtocolDispType 
    MAX-ACCESS  read-write
    STATUS      current
    DESCRIPTION
        "Control Protocol Disposition for Layer 2 Protocol Tunnelling(L2PT).
         MAC Address (01:00:0C:CD:CD:D0)."
    ::= { cmEthernetTrafficPortCpdV2Entry 12 }

cmEthernetTrafficPortCpdV2BridgeGroupDispType OBJECT-TYPE
    SYNTAX      CmControlProtocolDispType 
    MAX-ACCESS  read-write
    STATUS      deprecated
    DESCRIPTION
        "Deprecated - individual dispositions available for each MAC.
         Bridge Group Control Protocol Disposition Type.  This
         includes BPDU, PAUSE (IEEE 802.3x Flow Control), 
         LACP (Link Aggregation), LACP Marker (Marker), 
         EFM OAM (IEEE 802.3 ah) and IEEE 802.1x Port Authentication, 
         besides reserved MAC addresses from 
         01:80:C2:00:00:04 thru 01:80:C2:00:00:0F."
    ::= { cmEthernetTrafficPortCpdV2Entry 13 }

cmEthernetTrafficPortCpdV2BPDUDispType OBJECT-TYPE
    SYNTAX      CmControlProtocolDispType 
    MAX-ACCESS  read-write
    STATUS      current
    DESCRIPTION
        "Control Protocol Disposition for IEEE Spanning Tree(STP),
         MSTP (Multiple Spanning Tree) and RSTP (Rapid Reconfiguration of
         Spanning Tree). MAC Address (01:80:C2:00:00:00)."
    ::= { cmEthernetTrafficPortCpdV2Entry 14 }

cmEthernetTrafficPortCpdV2PauseDispType OBJECT-TYPE
    SYNTAX      CmControlProtocolDispType 
    MAX-ACCESS  read-write
    STATUS      current
    DESCRIPTION
        "Control Protocol Disposition for IEEE 802.3x Flow Control 
         (PAUSE frames)."
    ::= { cmEthernetTrafficPortCpdV2Entry 15 }

cmEthernetTrafficPortCpdV2LACPDispType OBJECT-TYPE
    SYNTAX      CmControlProtocolDispType 
    MAX-ACCESS  read-write
    STATUS      current
    DESCRIPTION
        "Control Protocol Disposition for 802.3ad Link Aggregation
         Protocol.
         MAC Address (01:80:C2:00:00:03), Ethertype (0x8809), Subtype(01)."
    ::= { cmEthernetTrafficPortCpdV2Entry 16 }

cmEthernetTrafficPortCpdV2LACPMarkerDispType OBJECT-TYPE
    SYNTAX      CmControlProtocolDispType 
    MAX-ACCESS  read-write
    STATUS      current
    DESCRIPTION
        "Control Protocol Disposition for IEEE 802.3ad Marker Protocol.
         MAC Address (01:80:C2:00:00:03), Ethertype (0x8809), Subtype(02)."
    ::= { cmEthernetTrafficPortCpdV2Entry 17 }

cmEthernetTrafficPortCpdV2EfmOamDispType OBJECT-TYPE
    SYNTAX      CmControlProtocolDispType 
    MAX-ACCESS  read-write
    STATUS      current
    DESCRIPTION
        "Control Protocol Disposition for IEEE 802.3ah EFM OAM.
         MAC Address (01:80:C2:00:00:03), Ethertype (0x8809), Subtype(03)."
    ::= { cmEthernetTrafficPortCpdV2Entry 18 }

cmEthernetTrafficPortCpdV2SSMDispType OBJECT-TYPE
    SYNTAX      CmControlProtocolDispType 
    MAX-ACCESS  read-write
    STATUS      current
    DESCRIPTION
        "Control Protocol Disposition for Sync Status Messages.
         MAC Address (01:80:C2:00:00:02), Ethertype (0x19A7), Subtype(0A)."
    ::= { cmEthernetTrafficPortCpdV2Entry 19 }

cmEthernetTrafficPortCpdV2PortAuthenDispType OBJECT-TYPE
    SYNTAX      CmControlProtocolDispType 
    MAX-ACCESS  read-write
    STATUS      current
    DESCRIPTION
        "Control Protocol Disposition for IEEE 802.1x Protocol.
         MAC Address (01:80:C2:00:00:03), Ethertype (0x888E)."
    ::= { cmEthernetTrafficPortCpdV2Entry 20 }

cmEthernetTrafficPortCpdV2BridgeReservedDispType OBJECT-TYPE
    SYNTAX      CmControlProtocolDispType 
    MAX-ACCESS  read-write
    STATUS      deprecated
    DESCRIPTION
        "Deprecated - individual dispositions available for each MAC.
         Control Protocol Disposition for Range of MAC Addresses
         from 01:80:C2:00:00:04 to 01:80:C2:00:00:0F."
    ::= { cmEthernetTrafficPortCpdV2Entry 21 }

cmEthernetTrafficPortCpdV2LANBridgesDispType OBJECT-TYPE
    SYNTAX      CmControlProtocolDispType 
    MAX-ACCESS  read-write
    STATUS      current
    DESCRIPTION
        "Control Protocol Disposition for IEEE 802.1d LAN Bridge Managment.
         MAC Address (01:80:C2:00:00:10)."
    ::= { cmEthernetTrafficPortCpdV2Entry 22 }

cmEthernetTrafficPortCpdV2GARPGroupDispType OBJECT-TYPE
    SYNTAX      CmControlProtocolDispType 
    MAX-ACCESS  read-write
    STATUS      deprecated
    DESCRIPTION
        "Deprecated - each GARP Group protocol has its own disposition.
         Group Disposition type which includes GMRP, GVRP and
         MAC Address from range 01:80:C2:00:00:20 to 01:80:C2:00:00:2F."
    ::= { cmEthernetTrafficPortCpdV2Entry 23 }

cmEthernetTrafficPortCpdV2GMRPDispType OBJECT-TYPE
    SYNTAX      CmControlProtocolDispType 
    MAX-ACCESS  read-write
    STATUS      current
    DESCRIPTION
        "Control Protocol Disposition for GARP Multicast Registration
         Protocol. MAC Address (01:80:C2:00:00:20)."
    ::= { cmEthernetTrafficPortCpdV2Entry 24 }

cmEthernetTrafficPortCpdV2GVRPDispType OBJECT-TYPE
    SYNTAX      CmControlProtocolDispType 
    MAX-ACCESS  read-write
    STATUS      current
    DESCRIPTION
        "Control Protocol Disposition for GARP VLAN Registration
         Protocol. MAC Address (01:80:C2:00:00:21)."
    ::= { cmEthernetTrafficPortCpdV2Entry 25 }

cmEthernetTrafficPortCpdV2GARPDispType OBJECT-TYPE
    SYNTAX      CmControlProtocolDispType 
    MAX-ACCESS  read-write
    STATUS      current
    DESCRIPTION
        "Group Disposition type which includes GARP Reserved 
         MAC Address from range 01:80:C2:00:00:22 to 01:80:C2:00:00:2F."
    ::= { cmEthernetTrafficPortCpdV2Entry 26 }

cmEthernetTrafficPortCpdV2LLDPDispType OBJECT-TYPE
    SYNTAX      CmControlProtocolDispType 
    MAX-ACCESS  read-write
    STATUS      deprecated
    DESCRIPTION
        "Deprecated - each LLDP MAC protocol has its own disposition.
         LLDP (Link Layer Discovery Protocol) Disposition type. 
         MAC Address 01:80:C2:00:00:0e, 01:80:C2:00:00:03, or
         01:80:C2:00:00:00."
    ::= { cmEthernetTrafficPortCpdV2Entry 27 }

cmEthernetTrafficPortCpdV2ELMIDispType OBJECT-TYPE
    SYNTAX      CmControlProtocolDispType 
    MAX-ACCESS  read-write
    STATUS      current
    DESCRIPTION
        "ELMI (Ethernet Local Management Interface) Disposition type. 
         MAC Address 01:80:C2:00:00:07 and EtherType of 0x88EE."
    ::= { cmEthernetTrafficPortCpdV2Entry 28 }

cmEthernetTrafficPortCpdV2L2PTTunnelMac    OBJECT-TYPE
    SYNTAX      MacAddress 
    MAX-ACCESS  read-write
    STATUS      current
    DESCRIPTION
        "Configurable Layer 2 Protocol Tunneling MAC Address.  
         For protocols STP, CDP and VTP, with control protocol disposition as 
         pass-thru-l2pt, this configured MAC address replaces the DA, upon
         encapsulation.  For decapsulation, protocol signature and this 
         configured MAC address are matched and the MAC address is replaced
         with the protocol's inferred MAC address." 
    ::= { cmEthernetTrafficPortCpdV2Entry 29 }

cmEthernetTrafficPortCpdV2Mac00DispType OBJECT-TYPE
    SYNTAX      CmControlProtocolDispType 
    MAX-ACCESS  read-write
    STATUS      current
    DESCRIPTION
        "MAC Address 01:80:C2:00:00:00 Disposition type."
    ::= { cmEthernetTrafficPortCpdV2Entry 30 }

cmEthernetTrafficPortCpdV2Mac01DispType OBJECT-TYPE
    SYNTAX      CmControlProtocolDispType 
    MAX-ACCESS  read-write
    STATUS      current
    DESCRIPTION
        "MAC Address 01:80:C2:00:00:01 Disposition type."
    ::= { cmEthernetTrafficPortCpdV2Entry 31 }

cmEthernetTrafficPortCpdV2Mac02DispType OBJECT-TYPE
    SYNTAX      CmControlProtocolDispType 
    MAX-ACCESS  read-write
    STATUS      current
    DESCRIPTION
        "MAC Address 01:80:C2:00:00:02 Disposition type."
    ::= { cmEthernetTrafficPortCpdV2Entry 32 }

cmEthernetTrafficPortCpdV2Mac03DispType OBJECT-TYPE
    SYNTAX      CmControlProtocolDispType 
    MAX-ACCESS  read-write
    STATUS      current
    DESCRIPTION
        "MAC Address 01:80:C2:00:00:03 Disposition type."
    ::= { cmEthernetTrafficPortCpdV2Entry 33 }

cmEthernetTrafficPortCpdV2Mac04DispType OBJECT-TYPE
    SYNTAX      CmControlProtocolDispType 
    MAX-ACCESS  read-write
    STATUS      current
    DESCRIPTION
        "MAC Address 01:80:C2:00:00:04 Disposition type."
    ::= { cmEthernetTrafficPortCpdV2Entry 34 }

cmEthernetTrafficPortCpdV2Mac05DispType OBJECT-TYPE
    SYNTAX      CmControlProtocolDispType 
    MAX-ACCESS  read-write
    STATUS      current
    DESCRIPTION
        "MAC Address 01:80:C2:00:00:05 Disposition type."
    ::= { cmEthernetTrafficPortCpdV2Entry 35 }

cmEthernetTrafficPortCpdV2Mac06DispType OBJECT-TYPE
    SYNTAX      CmControlProtocolDispType 
    MAX-ACCESS  read-write
    STATUS      current
    DESCRIPTION
        "MAC Address 01:80:C2:00:00:06 Disposition type."
    ::= { cmEthernetTrafficPortCpdV2Entry 36 }

cmEthernetTrafficPortCpdV2Mac07DispType OBJECT-TYPE
    SYNTAX      CmControlProtocolDispType 
    MAX-ACCESS  read-write
    STATUS      current
    DESCRIPTION
        "MAC Address 01:80:C2:00:00:07 Disposition type."
    ::= { cmEthernetTrafficPortCpdV2Entry 37 }

cmEthernetTrafficPortCpdV2Mac08DispType OBJECT-TYPE
    SYNTAX      CmControlProtocolDispType 
    MAX-ACCESS  read-write
    STATUS      current
    DESCRIPTION
        "MAC Address 01:80:C2:00:00:08 Disposition type."
    ::= { cmEthernetTrafficPortCpdV2Entry 38 }

cmEthernetTrafficPortCpdV2Mac09DispType OBJECT-TYPE
    SYNTAX      CmControlProtocolDispType 
    MAX-ACCESS  read-write
    STATUS      current
    DESCRIPTION
        "MAC Address 01:80:C2:00:00:09 Disposition type."
    ::= { cmEthernetTrafficPortCpdV2Entry 39 }

cmEthernetTrafficPortCpdV2Mac0ADispType OBJECT-TYPE
    SYNTAX      CmControlProtocolDispType 
    MAX-ACCESS  read-write
    STATUS      current
    DESCRIPTION
        "MAC Address 01:80:C2:00:00:0A Disposition type."
    ::= { cmEthernetTrafficPortCpdV2Entry 40 }

cmEthernetTrafficPortCpdV2Mac0BDispType OBJECT-TYPE
    SYNTAX      CmControlProtocolDispType 
    MAX-ACCESS  read-write
    STATUS      current
    DESCRIPTION
        "MAC Address 01:80:C2:00:00:0B Disposition type."
    ::= { cmEthernetTrafficPortCpdV2Entry 41 }

cmEthernetTrafficPortCpdV2Mac0CDispType OBJECT-TYPE
    SYNTAX      CmControlProtocolDispType 
    MAX-ACCESS  read-write
    STATUS      current
    DESCRIPTION
        "MAC Address 01:80:C2:00:00:0C Disposition type."
    ::= { cmEthernetTrafficPortCpdV2Entry 42 }

cmEthernetTrafficPortCpdV2Mac0DDispType OBJECT-TYPE
    SYNTAX      CmControlProtocolDispType 
    MAX-ACCESS  read-write
    STATUS      current
    DESCRIPTION
        "MAC Address 01:80:C2:00:00:0D Disposition type."
    ::= { cmEthernetTrafficPortCpdV2Entry 43 }

cmEthernetTrafficPortCpdV2Mac0EDispType OBJECT-TYPE
    SYNTAX      CmControlProtocolDispType 
    MAX-ACCESS  read-write
    STATUS      current
    DESCRIPTION
        "MAC Address 01:80:C2:00:00:0E Disposition type."
    ::= { cmEthernetTrafficPortCpdV2Entry 44 }

cmEthernetTrafficPortCpdV2Mac0FDispType OBJECT-TYPE
    SYNTAX      CmControlProtocolDispType 
    MAX-ACCESS  read-write
    STATUS      current
    DESCRIPTION
        "MAC Address 01:80:C2:00:00:0F Disposition type."
    ::= { cmEthernetTrafficPortCpdV2Entry 45 }

cmEthernetTrafficPortCpdV2NearestLLDPDispType OBJECT-TYPE
    SYNTAX      CmControlProtocolDispType 
    MAX-ACCESS  read-write
    STATUS      current
    DESCRIPTION
        "LLDP (Link Layer Discovery Protocol) Nearest Bridge Disposition type."
    ::= { cmEthernetTrafficPortCpdV2Entry 46 }

cmEthernetTrafficPortCpdV2NonTpmrLLDPDispType OBJECT-TYPE
    SYNTAX      CmControlProtocolDispType 
    MAX-ACCESS  read-write
    STATUS      current
    DESCRIPTION
        "LLDP (Link Layer Discovery Protocol) Non-TPMR Bridge Disposition type."
    ::= { cmEthernetTrafficPortCpdV2Entry 47 }

cmEthernetTrafficPortCpdV2CustomerLLDPDispType OBJECT-TYPE
    SYNTAX      CmControlProtocolDispType 
    MAX-ACCESS  read-write
    STATUS      current
    DESCRIPTION
        "LLDP (Link Layer Discovery Protocol) Customer Bridge Disposition type."
    ::= { cmEthernetTrafficPortCpdV2Entry 48 }

cmEthernetTrafficPortCpdV2PtpUntaggedDispType OBJECT-TYPE
    SYNTAX      CmControlProtocolDispType
    MAX-ACCESS  read-write
    STATUS      current
    DESCRIPTION
        "PTP untagged frame Disposition type."
    ::= { cmEthernetTrafficPortCpdV2Entry 49 }

cmEthernetTrafficPortCpdV2PtpTaggedDispType OBJECT-TYPE
    SYNTAX      CmControlProtocolDispType
    MAX-ACCESS  read-write
    STATUS      current
    DESCRIPTION
        "PTP tagged frame Disposition type."
    ::= { cmEthernetTrafficPortCpdV2Entry 50 }  

--
--   Flow Point Control Protocol Disposition 
--
f3FlowPointCpdV2Table  OBJECT-TYPE
    SYNTAX      SEQUENCE OF F3FlowPointCpdV2Entry
    MAX-ACCESS  not-accessible
    STATUS      current
    DESCRIPTION
       "A list of entries corresponding to  Flow Point
        Control Protocol Disposition V2."
    ::= { cmFacilityObjects 98 }

f3FlowPointCpdV2Entry OBJECT-TYPE
    SYNTAX      F3FlowPointCpdV2Entry 
    MAX-ACCESS  not-accessible
    STATUS      current
    DESCRIPTION
       "A conceptual row in the f3FlowPointCpdV2Table. 
        These entries represent a Control Protocol Disposition 
        filtering criteria on the  Flow Point."
    INDEX { neIndex, shelfIndex, slotIndex, cmEthernetTrafficPortIndex, 
            cmFlowPointIndex, f3FlowPointCpdV2Index }
    ::= { f3FlowPointCpdV2Table 1 }

F3FlowPointCpdV2Entry ::= SEQUENCE {
    f3FlowPointCpdV2Index                     Integer32,
    f3FlowPointCpdV2IslDispType               CmControlProtocolDispType,
    f3FlowPointCpdV2PagpDispType              CmControlProtocolDispType,
    f3FlowPointCpdV2UdldDispType              CmControlProtocolDispType,
    f3FlowPointCpdV2CdpDispType               CmControlProtocolDispType,
    f3FlowPointCpdV2VtpDispType               CmControlProtocolDispType,
    f3FlowPointCpdV2DtpDispType               CmControlProtocolDispType,
    f3FlowPointCpdV2PvstpPlusDispType         CmControlProtocolDispType,
    f3FlowPointCpdV2UplinkFastDispType        CmControlProtocolDispType,
    f3FlowPointCpdV2VlanBridgeDispType        CmControlProtocolDispType,
    f3FlowPointCpdV2L2PTDispType              CmControlProtocolDispType,
    f3FlowPointCpdV2BPDUDispType              CmControlProtocolDispType,
    f3FlowPointCpdV2PauseDispType             CmControlProtocolDispType,
    f3FlowPointCpdV2LACPDispType              CmControlProtocolDispType,
    f3FlowPointCpdV2LACPMarkerDispType        CmControlProtocolDispType,
    f3FlowPointCpdV2EfmOamDispType            CmControlProtocolDispType,
    f3FlowPointCpdV2SSMDispType               CmControlProtocolDispType,
    f3FlowPointCpdV2PortAuthenDispType        CmControlProtocolDispType,
    f3FlowPointCpdV2LANBridgesDispType        CmControlProtocolDispType,
    f3FlowPointCpdV2GMRPDispType              CmControlProtocolDispType,
    f3FlowPointCpdV2GVRPDispType              CmControlProtocolDispType,
    f3FlowPointCpdV2GARPDispType              CmControlProtocolDispType,
    f3FlowPointCpdV2ActiveControlProtocols    CmActiveControlProtocolsType,
    f3FlowPointCpdV2ELMIDispType              CmControlProtocolDispType,
    f3FlowPointCpdV2Mac00DispType             CmControlProtocolDispType,
    f3FlowPointCpdV2Mac01DispType             CmControlProtocolDispType,
    f3FlowPointCpdV2Mac02DispType             CmControlProtocolDispType,
    f3FlowPointCpdV2Mac03DispType             CmControlProtocolDispType,
    f3FlowPointCpdV2Mac04DispType             CmControlProtocolDispType,
    f3FlowPointCpdV2Mac05DispType             CmControlProtocolDispType,
    f3FlowPointCpdV2Mac06DispType             CmControlProtocolDispType,
    f3FlowPointCpdV2Mac07DispType             CmControlProtocolDispType,
    f3FlowPointCpdV2Mac08DispType             CmControlProtocolDispType,
    f3FlowPointCpdV2Mac09DispType             CmControlProtocolDispType,
    f3FlowPointCpdV2Mac0ADispType             CmControlProtocolDispType,
    f3FlowPointCpdV2Mac0BDispType             CmControlProtocolDispType,
    f3FlowPointCpdV2Mac0CDispType             CmControlProtocolDispType,
    f3FlowPointCpdV2Mac0DDispType             CmControlProtocolDispType,
    f3FlowPointCpdV2Mac0EDispType             CmControlProtocolDispType,
    f3FlowPointCpdV2Mac0FDispType             CmControlProtocolDispType,
    f3FlowPointCpdV2NearestLLDPDispType       CmControlProtocolDispType,
    f3FlowPointCpdV2NonTpmrLLDPDispType       CmControlProtocolDispType,
    f3FlowPointCpdV2CustomerLLDPDispType      CmControlProtocolDispType
}

f3FlowPointCpdV2Index OBJECT-TYPE
    SYNTAX      Integer32 
    MAX-ACCESS  not-accessible
    STATUS      current
    DESCRIPTION
       "Unique Index value to access the CPD row."
    ::= { f3FlowPointCpdV2Entry 1 }

f3FlowPointCpdV2IslDispType OBJECT-TYPE
    SYNTAX      CmControlProtocolDispType 
    MAX-ACCESS  read-write
    STATUS      current
    DESCRIPTION
       "Control Protocol Disposition for ISL (Inter Switch Link).
        MAC Address (01:00:0C:00:00:00)."
    ::= { f3FlowPointCpdV2Entry 2 }

f3FlowPointCpdV2PagpDispType OBJECT-TYPE
    SYNTAX      CmControlProtocolDispType 
    MAX-ACCESS  read-write
    STATUS      current
    DESCRIPTION
       "Control Protocol Disposition for PAGP (Port Aggregation Protocol).
        MAC Address (01:00:0C:CC:CC:CC), Ethertype(0x104)."
    ::= { f3FlowPointCpdV2Entry 3 }

f3FlowPointCpdV2UdldDispType OBJECT-TYPE
    SYNTAX      CmControlProtocolDispType 
    MAX-ACCESS  read-write
    STATUS      current
    DESCRIPTION
       "Control Protocol Disposition for UDLD (Unidirectional Link Detection).
        MAC Address (01:00:0C:CC:CC:CC), Ethertype(0x111)."
    ::= { f3FlowPointCpdV2Entry 4 }

f3FlowPointCpdV2CdpDispType OBJECT-TYPE
    SYNTAX      CmControlProtocolDispType 
    MAX-ACCESS  read-write
    STATUS      current
    DESCRIPTION
       "Control Protocol Disposition for CDP (Cisco Discovery Protocol).
        MAC Address (01:00:0C:CC:CC:CC), Ethertype(0x2000)."
    ::= { f3FlowPointCpdV2Entry 5 }

f3FlowPointCpdV2VtpDispType OBJECT-TYPE
    SYNTAX      CmControlProtocolDispType 
    MAX-ACCESS  read-write
    STATUS      current
    DESCRIPTION
       "Control Protocol Disposition for VTP (VLAN Trunking Protocol).
        MAC Address (01:00:0C:CC:CC:CC), Ethertype(0x2003)."
    ::= { f3FlowPointCpdV2Entry 6 }

f3FlowPointCpdV2DtpDispType OBJECT-TYPE
    SYNTAX      CmControlProtocolDispType 
    MAX-ACCESS  read-write
    STATUS      current
    DESCRIPTION
       "Control Protocol Disposition for DTP (Dynamic Trunking).
        MAC Address (01:00:0C:CC:CC:CC), Ethertype(0x2004)."
    ::= { f3FlowPointCpdV2Entry 7 }

f3FlowPointCpdV2PvstpPlusDispType OBJECT-TYPE
    SYNTAX      CmControlProtocolDispType 
    MAX-ACCESS  read-write
    STATUS      current
    DESCRIPTION
       "Control Protocol Disposition for Spanning Tree PVSTP+.
        MAC Address (01:00:0C:CC:CC:CC), Ethertype(0x10B)."
    ::= { f3FlowPointCpdV2Entry 8 }

f3FlowPointCpdV2UplinkFastDispType OBJECT-TYPE
    SYNTAX      CmControlProtocolDispType 
    MAX-ACCESS  read-write
    STATUS      current
    DESCRIPTION
       "Control Protocol Disposition for STP UplinkFast.
        MAC Address (01:00:0C:CD:CD:CD), Ethertype(0x200A)."
    ::= { f3FlowPointCpdV2Entry 9 }

f3FlowPointCpdV2VlanBridgeDispType OBJECT-TYPE
    SYNTAX      CmControlProtocolDispType 
    MAX-ACCESS  read-write
    STATUS      current
    DESCRIPTION
       "Control Protocol Disposition for VLAN Bridge.
        MAC Address (01:00:0C:CD:CD:CE), Ethertype(0x10C)."
    ::= { f3FlowPointCpdV2Entry 10 }

f3FlowPointCpdV2L2PTDispType OBJECT-TYPE
    SYNTAX      CmControlProtocolDispType 
    MAX-ACCESS  read-write
    STATUS      current
    DESCRIPTION
       "Control Protocol Disposition for Layer 2 Protocol Tunnelling(L2PT).
        MAC Address (01:00:0C:CD:CD:D0)."
    ::= { f3FlowPointCpdV2Entry 11 }

f3FlowPointCpdV2BPDUDispType OBJECT-TYPE
    SYNTAX      CmControlProtocolDispType 
    MAX-ACCESS  read-write
    STATUS      current
    DESCRIPTION
       "Control Protocol Disposition for IEEE Spanning Tree(STP),
        MSTP (Multiple Spanning Tree) and RSTP (Rapid Reconfiguration of
        Spanning Tree). MAC Address (01:80:C2:00:00:00)."
    ::= { f3FlowPointCpdV2Entry 12 }

f3FlowPointCpdV2PauseDispType OBJECT-TYPE
    SYNTAX      CmControlProtocolDispType 
    MAX-ACCESS  read-write
    STATUS      current
    DESCRIPTION
       "Control Protocol Disposition for IEEE 802.3x Flow Control 
        (PAUSE frames)."
    ::= { f3FlowPointCpdV2Entry 13 }

f3FlowPointCpdV2LACPDispType OBJECT-TYPE
    SYNTAX      CmControlProtocolDispType 
    MAX-ACCESS  read-write
    STATUS      current
    DESCRIPTION
       "Control Protocol Disposition for 802.3ad Link Aggregation
        Protocol.
        MAC Address (01:80:C2:00:00:03), Ethertype (0x8809), Subtype(01)."
    ::= { f3FlowPointCpdV2Entry 14 }

f3FlowPointCpdV2LACPMarkerDispType OBJECT-TYPE
    SYNTAX      CmControlProtocolDispType 
    MAX-ACCESS  read-write
    STATUS      current
    DESCRIPTION
       "Control Protocol Disposition for IEEE 802.3ad Marker Protocol.
        MAC Address (01:80:C2:00:00:03), Ethertype (0x8809), Subtype(02)."
    ::= { f3FlowPointCpdV2Entry 15 }

f3FlowPointCpdV2EfmOamDispType OBJECT-TYPE
    SYNTAX      CmControlProtocolDispType 
    MAX-ACCESS  read-write
    STATUS      current
    DESCRIPTION
       "Control Protocol Disposition for IEEE 802.3ah EFM OAM.
        MAC Address (01:80:C2:00:00:03), Ethertype (0x8809), Subtype(03)."
    ::= { f3FlowPointCpdV2Entry 16 }

f3FlowPointCpdV2SSMDispType OBJECT-TYPE
    SYNTAX      CmControlProtocolDispType 
    MAX-ACCESS  read-write
    STATUS      current
    DESCRIPTION
       "Control Protocol Disposition for Sync Status Messages.
        MAC Address (01:80:C2:00:00:02), Ethertype (0x19A7), Subtype(0A)."
    ::= { f3FlowPointCpdV2Entry 17 }

f3FlowPointCpdV2PortAuthenDispType OBJECT-TYPE
    SYNTAX      CmControlProtocolDispType 
    MAX-ACCESS  read-write
    STATUS      current
    DESCRIPTION
       "Control Protocol Disposition for IEEE 802.1x Protocol.
        MAC Address (01:80:C2:00:00:03), Ethertype (0x888E)."
    ::= { f3FlowPointCpdV2Entry 18 }

f3FlowPointCpdV2LANBridgesDispType OBJECT-TYPE
    SYNTAX      CmControlProtocolDispType 
    MAX-ACCESS  read-write
    STATUS      current
    DESCRIPTION
       "Control Protocol Disposition for IEEE 802.1d LAN Bridge Managment.
        MAC Address (01:80:C2:00:00:10)."
    ::= { f3FlowPointCpdV2Entry 19 }

f3FlowPointCpdV2GMRPDispType OBJECT-TYPE
    SYNTAX      CmControlProtocolDispType 
    MAX-ACCESS  read-write
    STATUS      current
    DESCRIPTION
       "Control Protocol Disposition for GARP Multicast Registration
        Protocol. MAC Address (01:80:C2:00:00:20)."
    ::= { f3FlowPointCpdV2Entry 20 }

f3FlowPointCpdV2GVRPDispType OBJECT-TYPE
    SYNTAX      CmControlProtocolDispType 
    MAX-ACCESS  read-write
    STATUS      current
    DESCRIPTION
       "Control Protocol Disposition for GARP VLAN Registration
        Protocol. MAC Address (01:80:C2:00:00:21)."
    ::= { f3FlowPointCpdV2Entry 21 }

f3FlowPointCpdV2GARPDispType OBJECT-TYPE
    SYNTAX      CmControlProtocolDispType 
    MAX-ACCESS  read-write
    STATUS      current
    DESCRIPTION
       "Group Disposition type which includes GARP Reserved 
        MAC Address from range 01:80:C2:00:00:22 to 01:80:C2:00:00:2F."
    ::= { f3FlowPointCpdV2Entry 22 }

f3FlowPointCpdV2ActiveControlProtocols OBJECT-TYPE
    SYNTAX      CmActiveControlProtocolsType
    MAX-ACCESS  read-only
    STATUS      current
    DESCRIPTION
       "List of Active Control Protocol Dispositions. Note that
        if the Port Level Disposition control is set to PEER or 
        DISCARD, the flow level disposition is no longer active.
        This object provides information on all the active
        dispositions."
    ::= { f3FlowPointCpdV2Entry 23 }

f3FlowPointCpdV2ELMIDispType OBJECT-TYPE
    SYNTAX      CmControlProtocolDispType 
    MAX-ACCESS  read-write
    STATUS      current
    DESCRIPTION
       "ELMI (Ethernet Local Management Interface) Disposition type. 
        MAC Address 01:80:C2:00:00:07 and EtherType of 0x88EE."
    ::= { f3FlowPointCpdV2Entry 24 }

f3FlowPointCpdV2Mac00DispType OBJECT-TYPE
    SYNTAX      CmControlProtocolDispType 
    MAX-ACCESS  read-write
    STATUS      current
    DESCRIPTION
       "MAC Address 01:80:C2:00:00:00 Disposition type."
    ::= { f3FlowPointCpdV2Entry 25 }

f3FlowPointCpdV2Mac01DispType OBJECT-TYPE
    SYNTAX      CmControlProtocolDispType 
    MAX-ACCESS  read-write
    STATUS      current
    DESCRIPTION
       "MAC Address 01:80:C2:00:00:01 Disposition type."
    ::= { f3FlowPointCpdV2Entry 26 }

f3FlowPointCpdV2Mac02DispType OBJECT-TYPE
    SYNTAX      CmControlProtocolDispType 
    MAX-ACCESS  read-write
    STATUS      current
    DESCRIPTION
       "MAC Address 01:80:C2:00:00:02 Disposition type."
    ::= { f3FlowPointCpdV2Entry 27 }

f3FlowPointCpdV2Mac03DispType OBJECT-TYPE
    SYNTAX      CmControlProtocolDispType 
    MAX-ACCESS  read-write
    STATUS      current
    DESCRIPTION
       "MAC Address 01:80:C2:00:00:03 Disposition type."
    ::= { f3FlowPointCpdV2Entry 28 }

f3FlowPointCpdV2Mac04DispType OBJECT-TYPE
    SYNTAX      CmControlProtocolDispType 
    MAX-ACCESS  read-write
    STATUS      current
    DESCRIPTION
       "MAC Address 01:80:C2:00:00:04 Disposition type."
    ::= { f3FlowPointCpdV2Entry 29 }

f3FlowPointCpdV2Mac05DispType OBJECT-TYPE
    SYNTAX      CmControlProtocolDispType 
    MAX-ACCESS  read-write
    STATUS      current
    DESCRIPTION
       "MAC Address 01:80:C2:00:00:05 Disposition type."
    ::= { f3FlowPointCpdV2Entry 30 }

f3FlowPointCpdV2Mac06DispType OBJECT-TYPE
    SYNTAX      CmControlProtocolDispType 
    MAX-ACCESS  read-write
    STATUS      current
    DESCRIPTION
       "MAC Address 01:80:C2:00:00:06 Disposition type."
    ::= { f3FlowPointCpdV2Entry 31 }

f3FlowPointCpdV2Mac07DispType OBJECT-TYPE
    SYNTAX      CmControlProtocolDispType 
    MAX-ACCESS  read-write
    STATUS      current
    DESCRIPTION
       "MAC Address 01:80:C2:00:00:07 Disposition type."
    ::= { f3FlowPointCpdV2Entry 32 }

f3FlowPointCpdV2Mac08DispType OBJECT-TYPE
    SYNTAX      CmControlProtocolDispType 
    MAX-ACCESS  read-write
    STATUS      current
    DESCRIPTION
       "MAC Address 01:80:C2:00:00:08 Disposition type."
    ::= { f3FlowPointCpdV2Entry 33 }

f3FlowPointCpdV2Mac09DispType OBJECT-TYPE
    SYNTAX      CmControlProtocolDispType 
    MAX-ACCESS  read-write
    STATUS      current
    DESCRIPTION
       "MAC Address 01:80:C2:00:00:09 Disposition type."
    ::= { f3FlowPointCpdV2Entry 34 }

f3FlowPointCpdV2Mac0ADispType OBJECT-TYPE
    SYNTAX      CmControlProtocolDispType 
    MAX-ACCESS  read-write
    STATUS      current
    DESCRIPTION
       "MAC Address 01:80:C2:00:00:0A Disposition type."
    ::= { f3FlowPointCpdV2Entry 35 }

f3FlowPointCpdV2Mac0BDispType OBJECT-TYPE
    SYNTAX      CmControlProtocolDispType 
    MAX-ACCESS  read-write
    STATUS      current
    DESCRIPTION
       "MAC Address 01:80:C2:00:00:0B Disposition type."
    ::= { f3FlowPointCpdV2Entry 36 }

f3FlowPointCpdV2Mac0CDispType OBJECT-TYPE
    SYNTAX      CmControlProtocolDispType 
    MAX-ACCESS  read-write
    STATUS      current
    DESCRIPTION
       "MAC Address 01:80:C2:00:00:0C Disposition type."
    ::= { f3FlowPointCpdV2Entry 37 }

f3FlowPointCpdV2Mac0DDispType OBJECT-TYPE
    SYNTAX      CmControlProtocolDispType 
    MAX-ACCESS  read-write
    STATUS      current
    DESCRIPTION
       "MAC Address 01:80:C2:00:00:0D Disposition type."
    ::= { f3FlowPointCpdV2Entry 38 }

f3FlowPointCpdV2Mac0EDispType OBJECT-TYPE
    SYNTAX      CmControlProtocolDispType 
    MAX-ACCESS  read-write
    STATUS      current
    DESCRIPTION
       "MAC Address 01:80:C2:00:00:0E Disposition type."
    ::= { f3FlowPointCpdV2Entry 39 }

f3FlowPointCpdV2Mac0FDispType OBJECT-TYPE
    SYNTAX      CmControlProtocolDispType 
    MAX-ACCESS  read-write
    STATUS      current
    DESCRIPTION
       "MAC Address 01:80:C2:00:00:0F Disposition type."
    ::= { f3FlowPointCpdV2Entry 40 }

f3FlowPointCpdV2NearestLLDPDispType OBJECT-TYPE
    SYNTAX      CmControlProtocolDispType 
    MAX-ACCESS  read-write
    STATUS      current
    DESCRIPTION
       "LLDP (Link Layer Discovery Protocol) Nearest Bridge Disposition type."
    ::= { f3FlowPointCpdV2Entry 41 }

f3FlowPointCpdV2NonTpmrLLDPDispType OBJECT-TYPE
    SYNTAX      CmControlProtocolDispType 
    MAX-ACCESS  read-write
    STATUS      current
    DESCRIPTION
       "LLDP (Link Layer Discovery Protocol) Non-TPMR Bridge Disposition type."
    ::= { f3FlowPointCpdV2Entry 42 }

f3FlowPointCpdV2CustomerLLDPDispType OBJECT-TYPE
    SYNTAX      CmControlProtocolDispType 
    MAX-ACCESS  read-write
    STATUS      current
    DESCRIPTION
       "LLDP (Link Layer Discovery Protocol) Customer Bridge Disposition type."
    ::= { f3FlowPointCpdV2Entry 43 }

--
--  L2 ACL Rule Table
--

f3AclRuleTable  OBJECT-TYPE
    SYNTAX      SEQUENCE OF F3AclRuleEntry
    MAX-ACCESS  not-accessible
    STATUS      current
    DESCRIPTION
            "A list of entries for the L2 ACL rule."
    ::= { cmFacilityObjects 99 }

f3AclRuleEntry  OBJECT-TYPE
    SYNTAX      F3AclRuleEntry
    MAX-ACCESS  not-accessible
    STATUS      current
    DESCRIPTION
            "A conceptual row in the f3AclRuleTable."
    INDEX { neIndex, shelfIndex, slotIndex, cmEthernetTrafficPortIndex, 
            cmFlowPointIndex, f3AclRuleIndex }
    ::= { f3AclRuleTable 1 }

F3AclRuleEntry ::= SEQUENCE {
    f3AclRuleIndex                                     Integer32,
    f3AclRuleAdminState                                AdminState,
    f3AclRuleAlias                                     F3DisplayString,
    f3AclRulePriority                                  Integer32,
    f3AclRuleOperation                                 AclRuleOperation,
    f3AclRuleCosOverrideControl                        TruthValue,
    f3AclRuleCOS                                       Integer32,
    -- L2 attributes
    f3AclRuleSrcMacAddressControl                      TruthValue,
    f3AclRuleSrcMacAddress                             MacAddress,
    f3AclRuleSrcMacAddressMask                         MacAddress,
    f3AclRuleDstMacAddressControl                      TruthValue,
    f3AclRuleDstMacAddress                             MacAddress,
    f3AclRuleDstMacAddressMask                         MacAddress,
    f3AclRuleOuterVlanVIDControl                       TruthValue,
    f3AclRuleOuterVlanVIDLowLimit                      VlanId,
    f3AclRuleOuterVlanVIDHighLimit                     VlanId,
    f3AclRuleInnerVlanVIDControl                       TruthValue,
    f3AclRuleInnerVlanVIDLowLimit                      VlanId,
    f3AclRuleInnerVlanVIDHighLimit                     VlanId,
    f3AclRuleOuterVlanPcpControl                       TruthValue,
    f3AclRuleOuterVlanPcpLowLimit                      VlanPriority,
    f3AclRuleOuterVlanPcpHighLimit                     VlanPriority,
    f3AclRuleInnerVlanPcpControl                       TruthValue,
    f3AclRuleInnerVlanPcpLowLimit                      VlanPriority,
    f3AclRuleInnerVlanPcpHighLimit                     VlanPriority,
    f3AclRuleOuterVlanDeiControl                       TruthValue,
    f3AclRuleOuterVlanDei                              Unsigned32,
    f3AclRuleEtherTypeControl                          TruthValue,
    f3AclRuleEtherType                                 Integer32,
    -- L3 attributes
    f3AclRuleIpv4PriorityControl                       TruthValue,
    f3AclRuleIpv4PriorityLowLimit                      Integer32,
    f3AclRuleIpv4PriorityHighLimit                     Integer32,
    f3AclRuleProtocolControl                           TruthValue,
    f3AclRuleProtocolNumber                            Integer32,
    f3AclRuleSrcIpv4AddressControl                     TruthValue,
    f3AclRuleSrcIpv4AddressLowLimit                    IpAddress,
    f3AclRuleSrcIpv4AddressHighLimit                   IpAddress,
    f3AclRuleDstIpv4AddressControl                     TruthValue,
    f3AclRuleDstIpv4AddressLowLimit                    IpAddress,
    f3AclRuleDstIpv4AddressHighLimit                   IpAddress,
    -- L4 attributes
    f3AclRuleSrcPortControl                            TruthValue,
    f3AclRuleSrcPortLowLimit                           Integer32,
    f3AclRuleSrcPortHighLimit                          Integer32,
    f3AclRuleDstPortControl                            TruthValue,
    f3AclRuleDstPortLowLimit                           Integer32,
    f3AclRuleDstPortHighLimit                          Integer32,
    f3AclRuleTcpFlagsControl                           TruthValue,
    f3AclRuleTcpFlags                                  Integer32,
    f3AclRuleStorageType                               StorageType,
    f3AclRuleRowStatus                                 RowStatus,
    f3AclRuleActive                                    TruthValue,

    f3AclRuleSrcIpv6AddressControl                     TruthValue,
    f3AclRuleSrcIpv6Address                            Ipv6Address,
    f3AclRuleSrcIpv6AddressPrefixLen                   Integer32,
    f3AclRuleDstIpv6AddressControl                     TruthValue,
    f3AclRuleDstIpv6Address                            Ipv6Address,
    f3AclRuleDstIpv6AddressPrefixLen                   Integer32,
    f3AclRuleIpV6FlowLabelControl                      TruthValue,
    f3AclRuleIpV6FlowLabel                             Integer32,

    f3AclRulePriorityControl                           TruthValue,
    f3AclRulePriorityLowLimit                          Integer32,
    f3AclRulePriorityHighLimit                         Integer32
}

f3AclRuleIndex OBJECT-TYPE
    SYNTAX      Integer32
    MAX-ACCESS  not-accessible
    STATUS      current
    DESCRIPTION
           "The ACL rule number."
    ::= { f3AclRuleEntry 1 }

f3AclRuleAdminState OBJECT-TYPE
    SYNTAX      AdminState
    MAX-ACCESS  read-write
    STATUS      current
    DESCRIPTION
           "This object allows user configure the Acl Rule in-service or management state."
    ::= { f3AclRuleEntry 2 }

f3AclRuleAlias OBJECT-TYPE
    SYNTAX      F3DisplayString (SIZE (0..256))
    MAX-ACCESS  read-write
    STATUS      current
    DESCRIPTION
           "The ACL rule alias."
    ::= { f3AclRuleEntry 3 }

f3AclRulePriority OBJECT-TYPE
    SYNTAX      Integer32
    MAX-ACCESS  read-write
    STATUS      current
    DESCRIPTION
           "The ACL rule priority."
    ::= { f3AclRuleEntry 4 }

f3AclRuleOperation OBJECT-TYPE
    SYNTAX      AclRuleOperation
    MAX-ACCESS  read-write
    STATUS      current
    DESCRIPTION
           "The ACL rule action."
    ::= { f3AclRuleEntry 5 }

f3AclRuleCosOverrideControl OBJECT-TYPE
    SYNTAX      TruthValue
    MAX-ACCESS  read-write
    STATUS      current
    DESCRIPTION
           "The ACL rule COS Override control."
    ::= { f3AclRuleEntry 6 }

f3AclRuleCOS OBJECT-TYPE
    SYNTAX      Integer32
    MAX-ACCESS  read-write
    STATUS      current
    DESCRIPTION
           "The ACL rule class of service."
    ::= { f3AclRuleEntry 7 }

f3AclRuleSrcMacAddressControl OBJECT-TYPE
    SYNTAX      TruthValue
    MAX-ACCESS  read-write
    STATUS      current
    DESCRIPTION
           "The ACL rule Source MAC address control."
    ::= { f3AclRuleEntry 8 }

f3AclRuleSrcMacAddress OBJECT-TYPE
    SYNTAX      MacAddress
    MAX-ACCESS  read-write
    STATUS      current
    DESCRIPTION
           "The ACL rule dynamic Source MAC address."
    ::= { f3AclRuleEntry 9 }

f3AclRuleSrcMacAddressMask OBJECT-TYPE
    SYNTAX      MacAddress
    MAX-ACCESS  read-write
    STATUS      current
    DESCRIPTION
           "The ACL rule dynamic Source MAC address mask."
    ::= { f3AclRuleEntry 10 }

f3AclRuleDstMacAddressControl OBJECT-TYPE
    SYNTAX      TruthValue
    MAX-ACCESS  read-write
    STATUS      current
    DESCRIPTION
           "The ACL rule dynamic Destination MAC address control."
    ::= { f3AclRuleEntry 11 }

f3AclRuleDstMacAddress OBJECT-TYPE
    SYNTAX      MacAddress
    MAX-ACCESS  read-write
    STATUS      current
    DESCRIPTION
           "The ACL rule dynamic Destination MAC address."
    ::= { f3AclRuleEntry 12 }

f3AclRuleDstMacAddressMask OBJECT-TYPE
    SYNTAX      MacAddress
    MAX-ACCESS  read-write
    STATUS      current
    DESCRIPTION
           "The ACL rule dynamic Destination MAC address mask."
    ::= { f3AclRuleEntry 13 }

f3AclRuleOuterVlanVIDControl OBJECT-TYPE
    SYNTAX      TruthValue
    MAX-ACCESS  read-write
    STATUS      current
    DESCRIPTION
           "The ACL rule outer VID control."
    ::= { f3AclRuleEntry 14 }

f3AclRuleOuterVlanVIDLowLimit OBJECT-TYPE
    SYNTAX      VlanId
    MAX-ACCESS  read-write
    STATUS      current
    DESCRIPTION
           "The ACL rule outer Vlan ID low limit."
    ::= { f3AclRuleEntry 15 }

f3AclRuleOuterVlanVIDHighLimit OBJECT-TYPE
    SYNTAX      VlanId
    MAX-ACCESS  read-write
    STATUS      current
    DESCRIPTION
           "The ACL rule outer Vlan ID high limit."
    ::= { f3AclRuleEntry 16 }

f3AclRuleInnerVlanVIDControl OBJECT-TYPE
    SYNTAX      TruthValue
    MAX-ACCESS  read-write
    STATUS      current
    DESCRIPTION
           "The ACL rule inner VID control."
    ::= { f3AclRuleEntry 17 }

f3AclRuleInnerVlanVIDLowLimit OBJECT-TYPE
    SYNTAX      VlanId
    MAX-ACCESS  read-write
    STATUS      current
    DESCRIPTION
           "The ACL rule inner Vlan ID low limit."
    ::= { f3AclRuleEntry 18 }

f3AclRuleInnerVlanVIDHighLimit OBJECT-TYPE
    SYNTAX      VlanId
    MAX-ACCESS  read-write
    STATUS      current
    DESCRIPTION
           "The ACL rule Inner Vlan ID high limit."
    ::= { f3AclRuleEntry 19 }

f3AclRuleOuterVlanPcpControl OBJECT-TYPE
    SYNTAX      TruthValue
    MAX-ACCESS  read-write
    STATUS      current
    DESCRIPTION
           "The ACL rule outer vlan PCP control."
    ::= { f3AclRuleEntry 20 }

f3AclRuleOuterVlanPcpLowLimit OBJECT-TYPE
    SYNTAX      VlanPriority
    MAX-ACCESS  read-write
    STATUS      current
    DESCRIPTION
           "The ACL rule outer vlan PCP priority low limit."
    ::= { f3AclRuleEntry 21 }

f3AclRuleOuterVlanPcpHighLimit OBJECT-TYPE
    SYNTAX      VlanPriority
    MAX-ACCESS  read-write
    STATUS      current
    DESCRIPTION
           "The ACL rule outer vlan PCP priority high limit."
    ::= { f3AclRuleEntry 22 }

f3AclRuleInnerVlanPcpControl OBJECT-TYPE
    SYNTAX      TruthValue
    MAX-ACCESS  read-write
    STATUS      current
    DESCRIPTION
           "The ACL rule inner vlan PCP control."
    ::= { f3AclRuleEntry 23 }

f3AclRuleInnerVlanPcpLowLimit OBJECT-TYPE
    SYNTAX      VlanPriority
    MAX-ACCESS  read-write
    STATUS      current
    DESCRIPTION
           "The ACL rule inner vlan PCP priority low limit."
    ::= { f3AclRuleEntry 24 }

f3AclRuleInnerVlanPcpHighLimit OBJECT-TYPE
    SYNTAX      VlanPriority
    MAX-ACCESS  read-write
    STATUS      current
    DESCRIPTION
           "The ACL rule inner vlan PCP priority high limit."
    ::= { f3AclRuleEntry 25 }

f3AclRuleOuterVlanDeiControl OBJECT-TYPE
    SYNTAX      TruthValue
    MAX-ACCESS  read-write
    STATUS      current
    DESCRIPTION
           "The ACL rule outer vlan DEI control."
    ::= { f3AclRuleEntry 26 }

f3AclRuleOuterVlanDei OBJECT-TYPE
    SYNTAX      Unsigned32 (0..1)
    MAX-ACCESS  read-write
    STATUS      current
    DESCRIPTION
           "The ACL rule outer vlan DEI."
    ::= { f3AclRuleEntry 27 }

f3AclRuleEtherTypeControl OBJECT-TYPE
    SYNTAX      TruthValue
    MAX-ACCESS  read-write
    STATUS      current
    DESCRIPTION
           "The ACL rule outer vlan ether type control."
    ::= { f3AclRuleEntry 28 }

f3AclRuleEtherType OBJECT-TYPE
    SYNTAX      Integer32
    MAX-ACCESS  read-write
    STATUS      current
    DESCRIPTION
           "The ACL rule outer vlan ether type."
    ::= { f3AclRuleEntry 29 }

f3AclRuleIpv4PriorityControl OBJECT-TYPE
    SYNTAX      TruthValue
    MAX-ACCESS  read-write
    STATUS      deprecated
    DESCRIPTION
           "The ACL rule IPv4 Priority control whether enabled."
    ::= { f3AclRuleEntry 30 }

f3AclRuleIpv4PriorityLowLimit OBJECT-TYPE
    SYNTAX      Integer32
    MAX-ACCESS  read-write
    STATUS      deprecated
    DESCRIPTION
           "The ACL rule IPv4 priority low limit."
    ::= { f3AclRuleEntry 31 }

f3AclRuleIpv4PriorityHighLimit OBJECT-TYPE
    SYNTAX      Integer32
    MAX-ACCESS  read-write
    STATUS      deprecated
    DESCRIPTION
           "The ACL rule ipv4 priority high limit."
    ::= { f3AclRuleEntry 32 }

f3AclRuleProtocolControl OBJECT-TYPE
    SYNTAX      TruthValue
    MAX-ACCESS  read-write
    STATUS      current
    DESCRIPTION
           "The ACL rule protocol control whether enabled."
    ::= { f3AclRuleEntry 33 }

f3AclRuleProtocolNumber OBJECT-TYPE
    SYNTAX      Integer32
    MAX-ACCESS  read-write
    STATUS      current
    DESCRIPTION
           "The ACL rule protocol number."
    ::= { f3AclRuleEntry 34 }

f3AclRuleSrcIpv4AddressControl OBJECT-TYPE
    SYNTAX      TruthValue
    MAX-ACCESS  read-write
    STATUS      current
    DESCRIPTION
           "The ACL rule source IPv4 Adress control whether enabled."
    ::= { f3AclRuleEntry 35 }

f3AclRuleSrcIpv4AddressLowLimit OBJECT-TYPE
    SYNTAX      IpAddress
    MAX-ACCESS  read-write
    STATUS      current
    DESCRIPTION
           "The ACL rule source IPv4 Adress low limit."
    ::= { f3AclRuleEntry 36 }

f3AclRuleSrcIpv4AddressHighLimit OBJECT-TYPE
    SYNTAX      IpAddress
    MAX-ACCESS  read-write
    STATUS      current
    DESCRIPTION
           "The ACL rule source ipv4 adress high limit."
    ::= { f3AclRuleEntry 37 }

f3AclRuleDstIpv4AddressControl OBJECT-TYPE
    SYNTAX      TruthValue
    MAX-ACCESS  read-write
    STATUS      current
    DESCRIPTION
           "The ACL rule Destination IPv4 Adress control whether enabled."
    ::= { f3AclRuleEntry 38 }

f3AclRuleDstIpv4AddressLowLimit OBJECT-TYPE
    SYNTAX      IpAddress
    MAX-ACCESS  read-write
    STATUS      current
    DESCRIPTION
           "The ACL rule Destination IPv4 Adress low limit."
    ::= { f3AclRuleEntry 39 }

f3AclRuleDstIpv4AddressHighLimit OBJECT-TYPE
    SYNTAX      IpAddress
    MAX-ACCESS  read-write
    STATUS      current
    DESCRIPTION
           "The ACL rule destination ipv4 adress high limit."
    ::= { f3AclRuleEntry 40 }

f3AclRuleSrcPortControl OBJECT-TYPE
    SYNTAX      TruthValue
    MAX-ACCESS  read-write
    STATUS      current
    DESCRIPTION
           "The ACL rule source port whether enabled."
    ::= { f3AclRuleEntry 41 }

f3AclRuleSrcPortLowLimit OBJECT-TYPE
    SYNTAX      Integer32
    MAX-ACCESS  read-write
    STATUS      current
    DESCRIPTION
           "The ACL rule source port low limit."
    ::= { f3AclRuleEntry 42 }

f3AclRuleSrcPortHighLimit OBJECT-TYPE
    SYNTAX      Integer32
    MAX-ACCESS  read-write
    STATUS      current
    DESCRIPTION
           "The ACL rule source port low limit."
    ::= { f3AclRuleEntry 43 }

f3AclRuleDstPortControl OBJECT-TYPE
    SYNTAX      TruthValue
    MAX-ACCESS  read-write
    STATUS      current
    DESCRIPTION
           "The ACL rule destination port whether enabled."
    ::= { f3AclRuleEntry 44 }

f3AclRuleDstPortLowLimit OBJECT-TYPE
    SYNTAX      Integer32
    MAX-ACCESS  read-write
    STATUS      current
    DESCRIPTION
           "The ACL rule destination port low limit."
    ::= { f3AclRuleEntry 45 }

f3AclRuleDstPortHighLimit OBJECT-TYPE
    SYNTAX      Integer32
    MAX-ACCESS  read-write
    STATUS      current
    DESCRIPTION
           "The ACL rule destination port low limit."
    ::= { f3AclRuleEntry 46 }

f3AclRuleTcpFlagsControl OBJECT-TYPE
    SYNTAX      TruthValue
    MAX-ACCESS  read-write
    STATUS      current
    DESCRIPTION
           "The ACL rule outer vlan TCP flags control."
    ::= { f3AclRuleEntry 47 }

f3AclRuleTcpFlags OBJECT-TYPE
    SYNTAX      Integer32
    MAX-ACCESS  read-write
    STATUS      current
    DESCRIPTION
           "The ACL rule outer vlan TCP flags."
    ::= { f3AclRuleEntry 48 }

f3AclRuleStorageType OBJECT-TYPE
    SYNTAX      StorageType
    MAX-ACCESS  read-create
    STATUS      current
    DESCRIPTION
           "The type of storage configured for this entry."
    ::= { f3AclRuleEntry 49 }

f3AclRuleRowStatus OBJECT-TYPE
    SYNTAX      RowStatus
    MAX-ACCESS  read-create
    STATUS      current
    DESCRIPTION
           "The status of this row.
            An entry MUST NOT exist in the active state unless all
            objects in the entry have an appropriate value, as described
            in the description clause for each writable object.
    
            The values of f3AclRuleRowStatus supported are
            createAndGo(4) and destroy(6).  All mandatory attributes
            must be specified in a single SNMP SET request with
            f3AclRuleRowStatus value as createAndGo(4).
            Upon successful row creation, this object has a
            value of active(1).
    
            The f3AclRuleRowStatus object may be modified if
            the associated instance of this object is equal to active(1)."
    ::= { f3AclRuleEntry 50 }

f3AclRuleActive OBJECT-TYPE
    SYNTAX      TruthValue
    MAX-ACCESS  read-write
    STATUS      current
    DESCRIPTION
           "The ACL Rule Active activates/deactivates ACL Rule."
    ::= { f3AclRuleEntry 51 }

f3AclRuleSrcIpv6AddressControl OBJECT-TYPE
    SYNTAX      TruthValue
    MAX-ACCESS  read-write
    STATUS      current
    DESCRIPTION
            "The ACL rule source ipv6 adress is control enabled."
    ::= { f3AclRuleEntry 52 }

f3AclRuleSrcIpv6Address OBJECT-TYPE
    SYNTAX      Ipv6Address
    MAX-ACCESS  read-write
    STATUS      current
    DESCRIPTION
            "The ACL rule source ipv6 adress high limit."
    ::= { f3AclRuleEntry 53 }

f3AclRuleSrcIpv6AddressPrefixLen OBJECT-TYPE
    SYNTAX      Integer32 (0..128)
    MAX-ACCESS  read-write
    STATUS      current
    DESCRIPTION
            "The ACL rule source ipv6 prefix length."
    ::= { f3AclRuleEntry 54 }

f3AclRuleDstIpv6AddressControl OBJECT-TYPE
    SYNTAX      TruthValue
    MAX-ACCESS  read-write
    STATUS      current
    DESCRIPTION
            "The ACL rule destination ipv6 Adress is control enabled."
    ::= { f3AclRuleEntry 55 }

f3AclRuleDstIpv6Address OBJECT-TYPE
    SYNTAX      Ipv6Address
    MAX-ACCESS  read-write
    STATUS      current
    DESCRIPTION
            "The ACL rule destination ipv6 adress."
    ::= { f3AclRuleEntry 56 }

f3AclRuleDstIpv6AddressPrefixLen OBJECT-TYPE
    SYNTAX      Integer32 (0..128)
    MAX-ACCESS  read-write
    STATUS      current
    DESCRIPTION
            "The ACL rule destination ipv6 prefix length."
    ::= { f3AclRuleEntry 57 }

f3AclRuleIpV6FlowLabelControl OBJECT-TYPE
    SYNTAX      TruthValue
    MAX-ACCESS  read-write
    STATUS      current
    DESCRIPTION
            "The ACL rule ipv6 Flow Label Control enables/disables Flow Label."
    ::= { f3AclRuleEntry 58 }

f3AclRuleIpV6FlowLabel OBJECT-TYPE
    SYNTAX      Integer32
    MAX-ACCESS  read-write
    STATUS      current
    DESCRIPTION
            "The ACL rule ipv6 Flow Label."
    ::= { f3AclRuleEntry 59 }

f3AclRulePriorityControl OBJECT-TYPE
    SYNTAX      TruthValue
    MAX-ACCESS  read-write
    STATUS      deprecated
    DESCRIPTION
           "The ACL rule Priority control whether enabled."
    ::= { f3AclRuleEntry 60 }

f3AclRulePriorityLowLimit OBJECT-TYPE
    SYNTAX      Integer32
    MAX-ACCESS  read-write
    STATUS      deprecated
    DESCRIPTION
           "The ACL rule priority low limit."
    ::= { f3AclRuleEntry 61 }

f3AclRulePriorityHighLimit OBJECT-TYPE
    SYNTAX      Integer32
    MAX-ACCESS  read-write
    STATUS      deprecated
    DESCRIPTION
           "The ACL rule priority high limit."
    ::= { f3AclRuleEntry 62 }

--
-- Ethernet Traffic Port Exp Encoding Table 
--
f3EthernetTrafficPortExpDEEncTable  OBJECT-TYPE
    SYNTAX      SEQUENCE OF F3EthernetTrafficPortExpDEEncEntry 
    MAX-ACCESS  not-accessible
    STATUS      current
    DESCRIPTION
        "Ethernet Traffic Port Exp drop eligibility encoding table. This
         is applied to a frame that is egressing at the Traffic Port."
    ::= { cmFacilityObjects 100 }

f3EthernetTrafficPortExpDEEncEntry OBJECT-TYPE
    SYNTAX      F3EthernetTrafficPortExpDEEncEntry 
    MAX-ACCESS  not-accessible
    STATUS      current
    DESCRIPTION
            "A conceptual row in the f3EthernetTrafficPortExpDEEncTable."
    INDEX { neIndex, shelfIndex, slotIndex, cmEthernetTrafficPortIndex, 
            f3EthernetTrafficPortExpDEEncIndex }
    ::= { f3EthernetTrafficPortExpDEEncTable 1 }

F3EthernetTrafficPortExpDEEncEntry ::= SEQUENCE {
  f3EthernetTrafficPortExpDEEncIndex              Integer32,
  f3EthernetTrafficPortExpDEEncInPriority         VlanPriority,
  f3EthernetTrafficPortExpDEEncDropIneligiblePrio VlanPriority,
  f3EthernetTrafficPortExpDEEncDropEligiblePrio   VlanPriority
}

f3EthernetTrafficPortExpDEEncIndex OBJECT-TYPE
    SYNTAX      Integer32
    MAX-ACCESS  not-accessible
    STATUS      current
    DESCRIPTION
            "An integer index value used to uniquely identify
             a row in the Exp drop eligible encoding table."
    ::= { f3EthernetTrafficPortExpDEEncEntry 1 }

f3EthernetTrafficPortExpDEEncInPriority OBJECT-TYPE
    SYNTAX     VlanPriority
    MAX-ACCESS read-write
    STATUS     current
    DESCRIPTION
         "This object is the input priority that is translated to a
          drop eligibility priority or a drop ineligibility priority."
     ::= { f3EthernetTrafficPortExpDEEncEntry 2 }

f3EthernetTrafficPortExpDEEncDropIneligiblePrio OBJECT-TYPE
    SYNTAX     VlanPriority
    MAX-ACCESS read-write
    STATUS     current
    DESCRIPTION
         "This object is the Exp value that has a priority value with
          implicit drop ineligibility encoded into it."
     ::= { f3EthernetTrafficPortExpDEEncEntry 3 }

f3EthernetTrafficPortExpDEEncDropEligiblePrio OBJECT-TYPE
    SYNTAX     VlanPriority
    MAX-ACCESS read-write
    STATUS     current
    DESCRIPTION
         "This object is the Exp value that has a priority value with
          implicit drop eligibility encoded into it."
     ::= { f3EthernetTrafficPortExpDEEncEntry 4 }

--
-- Ethernet Traffic Port Exp Decoding Table
--

f3EthernetTrafficPortExpDEDecTable  OBJECT-TYPE
    SYNTAX      SEQUENCE OF F3EthernetTrafficPortExpDEDecEntry
    MAX-ACCESS  not-accessible
    STATUS      current
    DESCRIPTION
            "Ethernet Traffic Port Exp drop eligibility decoding table. This
             is applied to a frame that is ingressing at a port."
    ::= { cmFacilityObjects 101 }

f3EthernetTrafficPortExpDEDecEntry OBJECT-TYPE
    SYNTAX      F3EthernetTrafficPortExpDEDecEntry 
    MAX-ACCESS  not-accessible
    STATUS      current
    DESCRIPTION
            "A conceptual row in the f3EthernetTrafficPortExpDEDecTable."
    INDEX { neIndex, shelfIndex, slotIndex, cmEthernetTrafficPortIndex, 
            f3EthernetTrafficPortExpDEDecIndex }
    ::= { f3EthernetTrafficPortExpDEDecTable 1 }

F3EthernetTrafficPortExpDEDecEntry ::= SEQUENCE {
    f3EthernetTrafficPortExpDEDecIndex        Integer32,
    f3EthernetTrafficPortExpDEDecInPriority   VlanPriority,
    f3EthernetTrafficPortExpDEDecOutPriority  VlanPriority,
    f3EthernetTrafficPortExpDEDecDropEligible TruthValue
}

f3EthernetTrafficPortExpDEDecIndex OBJECT-TYPE
    SYNTAX      Integer32
    MAX-ACCESS  not-accessible
    STATUS      current
    DESCRIPTION
            "An integer index value used to uniquely identify
             a row in the Exp drop eligible decoding table."
    ::= { f3EthernetTrafficPortExpDEDecEntry 1 }

f3EthernetTrafficPortExpDEDecInPriority OBJECT-TYPE
    SYNTAX     VlanPriority
    MAX-ACCESS read-write
    STATUS     current
    DESCRIPTION
         "This object is the input priority that is decoded to get
          priority and the drop eligibility of a frame."
     ::= { f3EthernetTrafficPortExpDEDecEntry 2 }

f3EthernetTrafficPortExpDEDecOutPriority OBJECT-TYPE
    SYNTAX     VlanPriority
    MAX-ACCESS read-write
    STATUS     current
    DESCRIPTION
         "This object is the priority value decoded from a incoming Exp value."
     ::= { f3EthernetTrafficPortExpDEDecEntry 3 }

f3EthernetTrafficPortExpDEDecDropEligible OBJECT-TYPE
    SYNTAX     TruthValue
    MAX-ACCESS read-write
    STATUS     current
    DESCRIPTION
         "This object is the drop eligibility decoded from a incoming
          Exp value."
     ::= { f3EthernetTrafficPortExpDEDecEntry 4 }

-- 
-- Ethernet Traffic Port Exp Pair Table
--

f3EthernetTrafficPortExpDEPairTable  OBJECT-TYPE
    SYNTAX      SEQUENCE OF F3EthernetTrafficPortExpDEPairEntry
    MAX-ACCESS  not-accessible
    STATUS      current
    DESCRIPTION
            "Ethernet Traffic Port Exp drop eligibility priority pair table.
             The priority pair is encoded to same drop eligibility and
             drop ineligibility priority. Depending on the Exp DE Enc/Dec
             mode there can be upto 3 pairs in the table. There will one
             pair for 7P1D, two pairs for 6P2D and three pairs for 5P3D."
    ::= { cmFacilityObjects 102 }

f3EthernetTrafficPortExpDEPairEntry OBJECT-TYPE
    SYNTAX      F3EthernetTrafficPortExpDEPairEntry 
    MAX-ACCESS  not-accessible
    STATUS      current
    DESCRIPTION
            "A conceptual row in the f3EthernetTrafficPortExpDEPairEntry."
    INDEX { neIndex, shelfIndex, slotIndex, cmEthernetTrafficPortIndex, 
            f3EthernetTrafficPortExpDEPairIndex }
    ::= { f3EthernetTrafficPortExpDEPairTable 1 }

F3EthernetTrafficPortExpDEPairEntry ::= SEQUENCE {
    f3EthernetTrafficPortExpDEPairIndex          Integer32,
    f3EthernetTrafficPortExpDEDropIneligiblePrio VlanPriority,
    f3EthernetTrafficPortExpDEDropEligiblePrio   VlanPriority
}

f3EthernetTrafficPortExpDEPairIndex OBJECT-TYPE
    SYNTAX      Integer32
    MAX-ACCESS  not-accessible
    STATUS      current
    DESCRIPTION
            "An integer index value used to uniquely identify
             a row in the Exp drop eligible priority pair table."
    ::= { f3EthernetTrafficPortExpDEPairEntry 1 }

f3EthernetTrafficPortExpDEDropIneligiblePrio OBJECT-TYPE
    SYNTAX     VlanPriority
    MAX-ACCESS read-write
    STATUS     current
    DESCRIPTION
         "This object is the drop ineligible priority."
     ::= { f3EthernetTrafficPortExpDEPairEntry 2 }

f3EthernetTrafficPortExpDEDropEligiblePrio OBJECT-TYPE
    SYNTAX     VlanPriority
    MAX-ACCESS read-write
    STATUS     current
    DESCRIPTION
         "This object is the drop eligible priority."
     ::= { f3EthernetTrafficPortExpDEPairEntry 3 }



--
--  Ethernet Network Port PPPoE Parameter 
--
cmEthernetNetPortPppoeParamTable  OBJECT-TYPE
    SYNTAX      SEQUENCE OF CmEthernetNetPortPppoeParamEntry
    MAX-ACCESS  not-accessible
    STATUS      current
    DESCRIPTION
            "A list of entries corresponding to Ethernet Network Port 
             PPPoE Parameters for configuration purposes."
    ::= { cmFacilityObjects 103 }

cmEthernetNetPortPppoeParamEntry OBJECT-TYPE
    SYNTAX      CmEthernetNetPortPppoeParamEntry 
    MAX-ACCESS  not-accessible
    STATUS      current
    DESCRIPTION
            "A conceptual row in the cmEthernetNetPortPppoeParamTable."
    AUGMENTS { cmEthernetNetPortEntry }
    ::= { cmEthernetNetPortPppoeParamTable 1 }

CmEthernetNetPortPppoeParamEntry ::= SEQUENCE {
    cmEthernetNetPortPppoeOuterVlanControl            TruthValue,
    cmEthernetNetPortPppoeOuterVlanEtherType          Unsigned32,
    cmEthernetNetPortPppoeOuterVlanId                 VlanId,
    cmEthernetNetPortPppoeOuterVlanPriority           VlanPriority,
    cmEthernetNetPortPppoeInnerVlanControl            TruthValue,
    cmEthernetNetPortPppoeInnerVlanEtherType          Unsigned32,
    cmEthernetNetPortPppoeInnerVlanId                 VlanId,
    cmEthernetNetPortPppoeInnerVlanPriority           VlanPriority,
    cmEthernetNetPortPppoeServiceName                 DisplayString,
    cmEthernetNetPortPppoeLcpKeepAlivePeriod          Unsigned32,
    cmEthernetNetPortPppoeLcpRetryThreshold           Unsigned32,
    cmEthernetNetPortPppoeRxAcName                    DisplayString,
    cmEthernetNetPortPppoeRxServiceName               DisplayString,
    cmEthernetNetPortPppoeSessionId                   Unsigned32,
    cmEthernetNetPortPppoeConnStatus                  PPPoEConnectionStatus
}

cmEthernetNetPortPppoeOuterVlanControl OBJECT-TYPE
    SYNTAX      TruthValue
    MAX-ACCESS  read-write
    STATUS      current
    DESCRIPTION
           "This object specify outer vlan whether enabled."
    ::= { cmEthernetNetPortPppoeParamEntry 1 }

cmEthernetNetPortPppoeOuterVlanEtherType OBJECT-TYPE
    SYNTAX      Unsigned32
    MAX-ACCESS  read-write
    STATUS      current
    DESCRIPTION
           "This object specify outer vlan ether type value."
    ::= { cmEthernetNetPortPppoeParamEntry 2 }

cmEthernetNetPortPppoeOuterVlanId OBJECT-TYPE
    SYNTAX      VlanId
    MAX-ACCESS  read-write
    STATUS      current
    DESCRIPTION
           "This object specify vlan id of outer tag."
    ::= { cmEthernetNetPortPppoeParamEntry 3 }

cmEthernetNetPortPppoeOuterVlanPriority OBJECT-TYPE
    SYNTAX      VlanPriority
    MAX-ACCESS  read-write
    STATUS      current
    DESCRIPTION
           "This object specify vlan priority of outer tag."
    ::= { cmEthernetNetPortPppoeParamEntry 4 }

cmEthernetNetPortPppoeInnerVlanControl OBJECT-TYPE
    SYNTAX      TruthValue
    MAX-ACCESS  read-write
    STATUS      current
    DESCRIPTION
           "This object specify inner vlan whether enabled."
    ::= { cmEthernetNetPortPppoeParamEntry 5 }

cmEthernetNetPortPppoeInnerVlanEtherType OBJECT-TYPE
    SYNTAX      Unsigned32
    MAX-ACCESS  read-write
    STATUS      current
    DESCRIPTION
           "This object specify inner vlan ether type value."
    ::= { cmEthernetNetPortPppoeParamEntry 6 }

cmEthernetNetPortPppoeInnerVlanId OBJECT-TYPE
    SYNTAX      VlanId
    MAX-ACCESS  read-write
    STATUS      current
    DESCRIPTION
           "This object specify vlan id of inner tag."
    ::= { cmEthernetNetPortPppoeParamEntry 7 }

cmEthernetNetPortPppoeInnerVlanPriority OBJECT-TYPE
    SYNTAX      VlanPriority
    MAX-ACCESS  read-write
    STATUS      current
    DESCRIPTION
           "This object specify vlan priority of inner tag."
    ::= { cmEthernetNetPortPppoeParamEntry 8 }

cmEthernetNetPortPppoeServiceName OBJECT-TYPE
    SYNTAX      DisplayString
    MAX-ACCESS  read-write
    STATUS      current
    DESCRIPTION
           "The service name requested."
    ::= { cmEthernetNetPortPppoeParamEntry 9 }

cmEthernetNetPortPppoeLcpKeepAlivePeriod OBJECT-TYPE
    SYNTAX      Unsigned32
    MAX-ACCESS  read-write
    STATUS      current
    DESCRIPTION
           "The service name requested."
    ::= { cmEthernetNetPortPppoeParamEntry 10 }

cmEthernetNetPortPppoeLcpRetryThreshold OBJECT-TYPE
    SYNTAX      Unsigned32
    MAX-ACCESS  read-write
    STATUS      current
    DESCRIPTION
           "This object specify the lcp retry threshold."
    ::= { cmEthernetNetPortPppoeParamEntry 11 }

cmEthernetNetPortPppoeRxAcName OBJECT-TYPE
    SYNTAX      DisplayString
    MAX-ACCESS  read-only
    STATUS      current
    DESCRIPTION
           "The ac name received."
    ::= { cmEthernetNetPortPppoeParamEntry 12 }

cmEthernetNetPortPppoeRxServiceName OBJECT-TYPE
    SYNTAX      DisplayString
    MAX-ACCESS  read-only
    STATUS      current
    DESCRIPTION
           "The service names received."
    ::= { cmEthernetNetPortPppoeParamEntry 13 }

cmEthernetNetPortPppoeSessionId OBJECT-TYPE
    SYNTAX      Unsigned32
    MAX-ACCESS  read-only
    STATUS      current
    DESCRIPTION
           "pppoe session id."
    ::= { cmEthernetNetPortPppoeParamEntry 14 }

cmEthernetNetPortPppoeConnStatus OBJECT-TYPE
    SYNTAX      PPPoEConnectionStatus
    MAX-ACCESS  read-only
    STATUS      current
    DESCRIPTION
           "This object provides the connection status of pppoe connection."
    ::= { cmEthernetNetPortPppoeParamEntry 15 }


--
--  Ethernet Network Port XDSL Parameter
--
cmEthernetNetPortXdslParamTable  OBJECT-TYPE
    SYNTAX      SEQUENCE OF CmEthernetNetPortXdslParamEntry
    MAX-ACCESS  not-accessible
    STATUS      current
    DESCRIPTION
            "A list of entries corresponding to Ethernet Network Port 
             XDSL Parameters for configuration purposes."
    ::= { cmFacilityObjects 104 }

cmEthernetNetPortXdslParamEntry OBJECT-TYPE
    SYNTAX      CmEthernetNetPortXdslParamEntry 
    MAX-ACCESS  not-accessible
    STATUS      current
    DESCRIPTION
            "A conceptual row in the cmEthernetNetPortXdslParamTable."
    AUGMENTS { cmEthernetNetPortEntry }
    ::= { cmEthernetNetPortXdslParamTable 1 }

CmEthernetNetPortXdslParamEntry ::= SEQUENCE {
    cmEthernetNetPortXdslConnControl         TruthValue,
    cmEthernetNetPortXdslModulationMode      XDSLModulationMode,
    cmEthernetNetPortXdslBitSwapEnabled      TruthValue,
    cmEthernetNetPortXdslGvectorEnabled      TruthValue,
    cmEthernetNetPortXdslVdslProfile         VDSLProfileFields,
    cmEthernetNetPortXdslStatus              XDSLStatus,
    cmEthernetNetPortXdslCurVdslProfile      VDSLProfileField,
    cmEthernetNetPortXdslActualLinkRateUpStream Unsigned32,
    cmEthernetNetPortXdslActualLinkRateDownStream Unsigned32,
    cmEthernetNetPortXdslControlChannel      XDSLControlChannel,
    cmEthernetNetPortXdslCarrierSet          XDSLCarrierSet,
    cmEthernetNetPortXdslMode                XDSLMode,
    cmEthernetNetPortXdslAnnex               XDSLAnnex,
    cmEthernetNetPortXdslDsSNRMargin         Integer32,
    cmEthernetNetPortXdslUsSNRMargin         Integer32,
    cmEthernetNetPortXdslDsSignalAttenuation Integer32,
    cmEthernetNetPortXdslDsLineAttenuation   Integer32,
    cmEthernetNetPortXdslDsTxPower           Integer32,
    cmEthernetNetPortXdslUsTxPower           Integer32,
    cmEthernetNetPortXdslDsAttainableRate    Unsigned32,
    cmEthernetNetPortXdslUsAttainableRate    Unsigned32
}

cmEthernetNetPortXdslConnControl OBJECT-TYPE
    SYNTAX      TruthValue
    MAX-ACCESS  read-write
    STATUS      current
    DESCRIPTION
           "This object enable/disable xdsl link."
    ::= { cmEthernetNetPortXdslParamEntry 1 }

cmEthernetNetPortXdslModulationMode OBJECT-TYPE
    SYNTAX      XDSLModulationMode
    MAX-ACCESS  read-write
    STATUS      current
    DESCRIPTION
           "Xdsl modulation."
    ::= { cmEthernetNetPortXdslParamEntry 2 }

cmEthernetNetPortXdslBitSwapEnabled OBJECT-TYPE
    SYNTAX      TruthValue
    MAX-ACCESS  read-write
    STATUS      current
    DESCRIPTION
           "Enable/disable bitswap."
    ::= { cmEthernetNetPortXdslParamEntry 3 }

cmEthernetNetPortXdslGvectorEnabled OBJECT-TYPE
    SYNTAX      TruthValue
    MAX-ACCESS  read-write
    STATUS      current
    DESCRIPTION
           "Enable/disable G.vector."
    ::= { cmEthernetNetPortXdslParamEntry 4 }

cmEthernetNetPortXdslVdslProfile OBJECT-TYPE
    SYNTAX      VDSLProfileFields
    MAX-ACCESS  read-write
    STATUS      current
    DESCRIPTION
           "Selected vdsl profile."
    ::= { cmEthernetNetPortXdslParamEntry 5 }

cmEthernetNetPortXdslStatus OBJECT-TYPE
    SYNTAX      XDSLStatus
    MAX-ACCESS  read-only
    STATUS      current
    DESCRIPTION
           "Xdsl link status."
    ::= { cmEthernetNetPortXdslParamEntry 6 }

cmEthernetNetPortXdslCurVdslProfile OBJECT-TYPE
    SYNTAX      VDSLProfileField
    MAX-ACCESS  read-only
    STATUS      current
    DESCRIPTION
           "Selected vdsl profile."
    ::= { cmEthernetNetPortXdslParamEntry 7 }

cmEthernetNetPortXdslActualLinkRateUpStream OBJECT-TYPE
    SYNTAX      Unsigned32
    MAX-ACCESS  read-only
    STATUS      current
    DESCRIPTION
           "Actual link rate upstream."
    ::= { cmEthernetNetPortXdslParamEntry 8 }

cmEthernetNetPortXdslActualLinkRateDownStream OBJECT-TYPE
    SYNTAX      Unsigned32
    MAX-ACCESS  read-only
    STATUS      current
    DESCRIPTION
           "Actual link rate downstream."
    ::= { cmEthernetNetPortXdslParamEntry 9 }

cmEthernetNetPortXdslControlChannel OBJECT-TYPE
    SYNTAX      XDSLControlChannel
    MAX-ACCESS  read-write
    STATUS      current
    DESCRIPTION
           "Actual link rate downstream."
    ::= { cmEthernetNetPortXdslParamEntry 10 }

cmEthernetNetPortXdslCarrierSet OBJECT-TYPE
    SYNTAX      XDSLCarrierSet
    MAX-ACCESS  read-write
    STATUS      current
    DESCRIPTION
           "Specify the carrier set."
    ::= { cmEthernetNetPortXdslParamEntry 11 }

cmEthernetNetPortXdslMode OBJECT-TYPE
    SYNTAX      XDSLMode
    MAX-ACCESS  read-only
    STATUS      current
    DESCRIPTION
           "Xdsl mode after handshake."
    ::= { cmEthernetNetPortXdslParamEntry 12 }

cmEthernetNetPortXdslAnnex OBJECT-TYPE
    SYNTAX      XDSLAnnex
    MAX-ACCESS  read-only
    STATUS      current
    DESCRIPTION
           "Annex version after handshake."
    ::= { cmEthernetNetPortXdslParamEntry 13 }

cmEthernetNetPortXdslDsSNRMargin OBJECT-TYPE
    SYNTAX      Integer32
    MAX-ACCESS  read-only
    STATUS      current
    DESCRIPTION
           "Downstream SNR margin."
    ::= { cmEthernetNetPortXdslParamEntry 14 }

cmEthernetNetPortXdslUsSNRMargin OBJECT-TYPE
    SYNTAX      Integer32
    MAX-ACCESS  read-only
    STATUS      current
    DESCRIPTION
           "Upstream SNR margin."
    ::= { cmEthernetNetPortXdslParamEntry 15 }

cmEthernetNetPortXdslDsSignalAttenuation OBJECT-TYPE
    SYNTAX      Integer32
    MAX-ACCESS  read-only
    STATUS      current
    DESCRIPTION
           "Downstream signal attenuation."
    ::= { cmEthernetNetPortXdslParamEntry 16 }

cmEthernetNetPortXdslDsLineAttenuation OBJECT-TYPE
    SYNTAX      Integer32
    MAX-ACCESS  read-only
    STATUS      current
    DESCRIPTION
           "Downstream line attenuation."
    ::= { cmEthernetNetPortXdslParamEntry 17 }

cmEthernetNetPortXdslDsTxPower OBJECT-TYPE
    SYNTAX      Integer32
    MAX-ACCESS  read-only
    STATUS      current
    DESCRIPTION
           "Downstream transmit power."
    ::= { cmEthernetNetPortXdslParamEntry 18 }

cmEthernetNetPortXdslUsTxPower OBJECT-TYPE
    SYNTAX      Integer32
    MAX-ACCESS  read-only
    STATUS      current
    DESCRIPTION
           "Upstream transmit power."
    ::= { cmEthernetNetPortXdslParamEntry 19 }

cmEthernetNetPortXdslDsAttainableRate OBJECT-TYPE
    SYNTAX      Unsigned32
    MAX-ACCESS  read-only
    STATUS      current
    DESCRIPTION
           "Attainable link rate downstream."
    ::= { cmEthernetNetPortXdslParamEntry 20 }

cmEthernetNetPortXdslUsAttainableRate OBJECT-TYPE
    SYNTAX      Unsigned32
    MAX-ACCESS  read-only
    STATUS      current
    DESCRIPTION
           "attainable link rate upstream."
    ::= { cmEthernetNetPortXdslParamEntry 21 }

--
-- SCI Port 
--
sciPortTable OBJECT-TYPE
    SYNTAX      SEQUENCE OF SciPortEntry
    MAX-ACCESS  not-accessible
    STATUS      current
    DESCRIPTION
            "A list of entries corresponding to SCI Port 
             Facilities for configuration purposes."
    ::= { cmFacilityObjects 105 }

sciPortEntry OBJECT-TYPE
    SYNTAX      SciPortEntry 
    MAX-ACCESS  not-accessible
    STATUS      current
    DESCRIPTION
            "A conceptual row in the sciPortTable."
    INDEX { neIndex, shelfIndex, slotIndex, sciPortIndex }
    ::= { sciPortTable 1 }

SciPortEntry ::= SEQUENCE {
    -- Port Indices 
    sciPortIndex                         Integer32,

    -- State Management params
    sciPortAdminState                    AdminState,
    sciPortOperationalState              OperationalState,

    -- SCI port specific params
    sciPortSignalMode                   SciSignalMode,
    sciPortSignalDirection              SciSignalDirection,
    sciPortRxSsmQL                      SciRxSsmQL
}

-- Port Indices 
sciPortIndex OBJECT-TYPE
    SYNTAX      Integer32 (1..65535)
    MAX-ACCESS  read-only
    STATUS      current
    DESCRIPTION
         "An integer index value used to uniquely identify
          this SCI Port." 
    ::= { sciPortEntry 1 }

-- State Management params
sciPortAdminState OBJECT-TYPE
    SYNTAX      AdminState 
    MAX-ACCESS  read-write
    STATUS      current
    DESCRIPTION
            "This object represents the Administrative State of the SCI 
             Port."
    ::= { sciPortEntry 2 }

sciPortOperationalState OBJECT-TYPE
    SYNTAX      OperationalState 
    MAX-ACCESS  read-only
    STATUS      current
    DESCRIPTION
            "This object represents the Operational State of the SCI 
             Port."
    ::= { sciPortEntry 3 }

-- SCI port specific params
sciPortSignalMode OBJECT-TYPE 
    SYNTAX     SciSignalMode
    MAX-ACCESS read-write
    STATUS     current
    DESCRIPTION
         "This object allows to manage the signal mode of the SCI port."
     ::= { sciPortEntry 4 }

sciPortSignalDirection OBJECT-TYPE 
    SYNTAX     SciSignalDirection
    MAX-ACCESS read-write
    STATUS     current
    DESCRIPTION
         "This object allows to manage the signal direction of the SCI port."
     ::= { sciPortEntry 5 } 

sciPortRxSsmQL OBJECT-TYPE 
    SYNTAX     SciRxSsmQL
    MAX-ACCESS read-write
    STATUS     current
    DESCRIPTION
         "This object allows to manage the RX QL of the SCI port."
     ::= { sciPortEntry 6 }

--
-- IRIG RS422 Output Port 
--
f3IrigRs422OutputPortTable OBJECT-TYPE
    SYNTAX      SEQUENCE OF IrigRs422OutputPortEntry
    MAX-ACCESS  not-accessible
    STATUS      current
    DESCRIPTION
            "A list of entries corresponding to IRIG RS422 output ports."
    ::= { cmFacilityObjects 106 }

f3IrigRs422OutputPortEntry OBJECT-TYPE
    SYNTAX      IrigRs422OutputPortEntry 
    MAX-ACCESS  not-accessible
    STATUS      current
    DESCRIPTION
            "A conceptual row in the f3IrigRs422OutputPortTable."
    INDEX { neIndex, shelfIndex, slotIndex, f3IrigRs422OutputPortIndex }
    ::= { f3IrigRs422OutputPortTable 1 }

IrigRs422OutputPortEntry ::= SEQUENCE {
    -- Port Indices
    f3IrigRs422OutputPortIndex            Integer32,
    f3IrigRs422OutputPortIfIndex          InterfaceIndex,
    f3IrigRs422OutputPortEntityIndex      PhysicalIndex,

    -- Alias
    f3IrigRs422OutputPortAlias            DisplayString,

    -- State Management
    f3IrigRs422OutputPortAdminState       AdminState,
    f3IrigRs422OutputPortOperationalState OperationalState,
    f3IrigRs422OutputPortSecondaryState   SecondaryState,

    -- IRIG RS422 Output Port specific attributes
    f3IrigRs422OutputPortTimeCode         IrigTimeCode,
    f3IrigRs422OutputPortControlField     IrigControlField
}

-- Port Indices 
f3IrigRs422OutputPortIndex OBJECT-TYPE
    SYNTAX      Integer32 (1..65535)
    MAX-ACCESS  not-accessible
    STATUS      current
    DESCRIPTION
         "An integer index value used to uniquely identify
          this IRIG RS422 output port in its parent card." 
    ::= { f3IrigRs422OutputPortEntry 1 }

f3IrigRs422OutputPortIfIndex OBJECT-TYPE
    SYNTAX      InterfaceIndex
    MAX-ACCESS  read-only
    STATUS      current
    DESCRIPTION
         "An integer index value used to uniquely identify this output port 
          as an interface in ifTable entries with ifIndex value." 
    ::= { f3IrigRs422OutputPortEntry 2 }

f3IrigRs422OutputPortEntityIndex OBJECT-TYPE
    SYNTAX      PhysicalIndex
    MAX-ACCESS  read-only
    STATUS      current
    DESCRIPTION
         "An integer index value used to uniquely identify this output port 
          as an entity in entityPhysical entries with entPhysicalIndex value." 
    ::= { f3IrigRs422OutputPortEntry 3 }

-- Alias
f3IrigRs422OutputPortAlias    OBJECT-TYPE
    SYNTAX      DisplayString (SIZE(0..64))
    MAX-ACCESS  read-write
    STATUS      current
    DESCRIPTION
         "This object allows SNMP management entities to provide an 
          alias to the output port entity."
    ::= { f3IrigRs422OutputPortEntry 4 }

-- State Management
f3IrigRs422OutputPortAdminState OBJECT-TYPE
    SYNTAX      AdminState 
    MAX-ACCESS  read-write
    STATUS      current
    DESCRIPTION
         "This object represents the administrative state of the IRIG output port."
    ::= { f3IrigRs422OutputPortEntry 5 }

f3IrigRs422OutputPortOperationalState OBJECT-TYPE
    SYNTAX      OperationalState 
    MAX-ACCESS  read-only
    STATUS      current
    DESCRIPTION
         "This object represents the operational state of the IRIG output port."
    ::= { f3IrigRs422OutputPortEntry 6 }

f3IrigRs422OutputPortSecondaryState OBJECT-TYPE
    SYNTAX      SecondaryState 
    MAX-ACCESS  read-only
    STATUS      current
    DESCRIPTION
         "This object represents the Secondary State of the IRIG output port." 
    ::= { f3IrigRs422OutputPortEntry 7 }

-- IRIG RS422 Output Port specific attributes
f3IrigRs422OutputPortTimeCode OBJECT-TYPE 
    SYNTAX     IrigTimeCode
    MAX-ACCESS read-write
    STATUS     current
    DESCRIPTION
         "This object allows to manage the Time Code of the IRIG output port."
    ::= { f3IrigRs422OutputPortEntry 8 }

f3IrigRs422OutputPortControlField OBJECT-TYPE 
    SYNTAX     IrigControlField
    MAX-ACCESS read-write
    STATUS     current
    DESCRIPTION
         "This object allows to manage the Control field of the IRIG output port."
     ::= { f3IrigRs422OutputPortEntry 9 } 

--
-- IRIG Optical Output Port 
--
f3IrigOpticalOutputPortTable OBJECT-TYPE
    SYNTAX      SEQUENCE OF IrigOpticalOutputPortEntry
    MAX-ACCESS  not-accessible
    STATUS      current
    DESCRIPTION
            "A list of entries corresponding to IRIG Optical output ports."
    ::= { cmFacilityObjects 107 }

f3IrigOpticalOutputPortEntry OBJECT-TYPE
    SYNTAX      IrigOpticalOutputPortEntry 
    MAX-ACCESS  not-accessible
    STATUS      current
    DESCRIPTION
            "A conceptual row in the f3IrigOpticalOutputPortTable."
    INDEX { neIndex, shelfIndex, slotIndex, f3IrigOpticalOutputPortIndex }
    ::= { f3IrigOpticalOutputPortTable 1 }

IrigOpticalOutputPortEntry ::= SEQUENCE {
    -- Port Indices
    f3IrigOpticalOutputPortIndex            Integer32,
    f3IrigOpticalOutputPortIfIndex          InterfaceIndex,
    f3IrigOpticalOutputPortEntityIndex      PhysicalIndex,

    -- Alias
    f3IrigOpticalOutputPortAlias            DisplayString,

    -- State Management
    f3IrigOpticalOutputPortAdminState       AdminState,
    f3IrigOpticalOutputPortOperationalState OperationalState,
    f3IrigOpticalOutputPortSecondaryState   SecondaryState,

    -- IRIG Optical Output Port specific attributes
    f3IrigOpticalOutputPortTimeCode         IrigTimeCode,
    f3IrigOpticalOutputPortControlField     IrigControlField
}

-- Port Indices 
f3IrigOpticalOutputPortIndex OBJECT-TYPE
    SYNTAX      Integer32 (1..65535)
    MAX-ACCESS  not-accessible
    STATUS      current
    DESCRIPTION
         "An integer index value used to uniquely identify
          this IRIG optical output port in it parent card." 
    ::= { f3IrigOpticalOutputPortEntry 1 }
    
f3IrigOpticalOutputPortIfIndex OBJECT-TYPE
    SYNTAX      InterfaceIndex
    MAX-ACCESS  read-only
    STATUS      current
    DESCRIPTION
         "An integer index value used to uniquely identify this output port 
          as an interface in ifTable entries with ifIndex value." 
    ::= { f3IrigOpticalOutputPortEntry 2 }

f3IrigOpticalOutputPortEntityIndex OBJECT-TYPE
    SYNTAX      PhysicalIndex
    MAX-ACCESS  read-only
    STATUS      current
    DESCRIPTION
         "An integer index value used to uniquely identify this output port 
          as an entity in entityPhysical entries with entPhysicalIndex value." 
    ::= { f3IrigOpticalOutputPortEntry 3 }

-- Alias
f3IrigOpticalOutputPortAlias    OBJECT-TYPE
    SYNTAX      DisplayString (SIZE(0..64))
    MAX-ACCESS  read-write
    STATUS      current
    DESCRIPTION
         "This object allows SNMP management entities to provide an 
          alias to the output port entity."
    ::= { f3IrigOpticalOutputPortEntry 4 }

-- State Management
f3IrigOpticalOutputPortAdminState OBJECT-TYPE
    SYNTAX      AdminState 
    MAX-ACCESS  read-write
    STATUS      current
    DESCRIPTION
         "This object represents the administrative state of the IRIG output port."
    ::= { f3IrigOpticalOutputPortEntry 5 }

f3IrigOpticalOutputPortOperationalState OBJECT-TYPE
    SYNTAX      OperationalState 
    MAX-ACCESS  read-only
    STATUS      current
    DESCRIPTION
         "This object represents the operational state of the IRIG output port."
    ::= { f3IrigOpticalOutputPortEntry 6 }

f3IrigOpticalOutputPortSecondaryState OBJECT-TYPE
    SYNTAX      SecondaryState 
    MAX-ACCESS  read-only
    STATUS      current
    DESCRIPTION
         "This object represents the Secondary State of the IRIG output port." 
    ::= { f3IrigOpticalOutputPortEntry 7 }

-- IRIG Optical Output port specific attributes
f3IrigOpticalOutputPortTimeCode OBJECT-TYPE 
    SYNTAX     IrigTimeCode
    MAX-ACCESS read-write
    STATUS     current
    DESCRIPTION
         "This object allows to manage the Time Code of the IRIG output port."
    ::= { f3IrigOpticalOutputPortEntry 8 }

f3IrigOpticalOutputPortControlField OBJECT-TYPE 
    SYNTAX     IrigControlField
    MAX-ACCESS read-write
    STATUS     current
    DESCRIPTION
         "This object allows to manage the Control field of the IRIG output port."
    ::= { f3IrigOpticalOutputPortEntry 9 } 

--
-- IRIG Time Relay Output Port 
--
f3IrigRelayOutputPortTable OBJECT-TYPE
    SYNTAX      SEQUENCE OF IrigRelayOutputPortEntry
    MAX-ACCESS  not-accessible
    STATUS      current
    DESCRIPTION
            "A list of entries corresponding to IRIG time relay output ports."
    ::= { cmFacilityObjects 108 }

f3IrigRelayOutputPortEntry OBJECT-TYPE
    SYNTAX      IrigRelayOutputPortEntry 
    MAX-ACCESS  not-accessible
    STATUS      current
    DESCRIPTION
            "A conceptual row in the f3IrigRelayOutputPortTable."
    INDEX { neIndex, shelfIndex, slotIndex, f3IrigRelayOutputPortIndex }
    ::= { f3IrigRelayOutputPortTable 1 }

IrigRelayOutputPortEntry ::= SEQUENCE {
    -- Port Indices
    f3IrigRelayOutputPortIndex            Integer32,
    f3IrigRelayOutputPortIfIndex          InterfaceIndex,
    f3IrigRelayOutputPortEntityIndex      PhysicalIndex,

    -- Alias
    f3IrigRelayOutputPortAlias            DisplayString,

    -- State Management
    f3IrigRelayOutputPortAdminState       AdminState,
    f3IrigRelayOutputPortOperationalState OperationalState,
    f3IrigRelayOutputPortSecondaryState   SecondaryState,

    -- IRIG Time Relay Output Port specific attributes
    f3IrigRelayOutputPortRelayOperation   IrigRelayOperation
}

-- Port Indices 
f3IrigRelayOutputPortIndex OBJECT-TYPE
    SYNTAX      Integer32 (1..65535)
    MAX-ACCESS  not-accessible
    STATUS      current
    DESCRIPTION
         "An integer index value used to uniquely identify
          this IRIG time relay output port in its parent card." 
    ::= { f3IrigRelayOutputPortEntry 1 }

f3IrigRelayOutputPortIfIndex OBJECT-TYPE
    SYNTAX      InterfaceIndex
    MAX-ACCESS  read-only
    STATUS      current
    DESCRIPTION
         "An integer index value used to uniquely identify this output port 
          as an interface in ifTable entries with ifIndex value." 
    ::= { f3IrigRelayOutputPortEntry 2 }

f3IrigRelayOutputPortEntityIndex OBJECT-TYPE
    SYNTAX      PhysicalIndex
    MAX-ACCESS  read-only
    STATUS      current
    DESCRIPTION
         "An integer index value used to uniquely identify this output port 
          as an entity in entityPhysical entries with entPhysicalIndex value." 
    ::= { f3IrigRelayOutputPortEntry 3 }

-- Alias
f3IrigRelayOutputPortAlias    OBJECT-TYPE
    SYNTAX      DisplayString (SIZE(0..64))
    MAX-ACCESS  read-write
    STATUS      current
    DESCRIPTION
         "This object allows SNMP management entities to provide an 
          alias to the output port entity."
    ::= { f3IrigRelayOutputPortEntry 4 }

-- State Management
f3IrigRelayOutputPortAdminState OBJECT-TYPE
    SYNTAX      AdminState 
    MAX-ACCESS  read-write
    STATUS      current
    DESCRIPTION
         "This object represents the administrative state of the IRIG output port."
    ::= { f3IrigRelayOutputPortEntry 5 }

f3IrigRelayOutputPortOperationalState OBJECT-TYPE
    SYNTAX      OperationalState 
    MAX-ACCESS  read-only
    STATUS      current
    DESCRIPTION
         "This object represents the operational state of the IRIG output port."
    ::= { f3IrigRelayOutputPortEntry 6 }

f3IrigRelayOutputPortSecondaryState OBJECT-TYPE
    SYNTAX      SecondaryState 
    MAX-ACCESS  read-only
    STATUS      current
    DESCRIPTION
         "This object represents the Secondary State of the IRIG output port." 
    ::= { f3IrigRelayOutputPortEntry 7 }

-- IRIG Time Relay Output Port specific attributes
f3IrigRelayOutputPortRelayOperation OBJECT-TYPE 
    SYNTAX     IrigRelayOperation
    MAX-ACCESS read-write
    STATUS     current
    DESCRIPTION
         "This object allows to manage the relay operation of the IRIG output port."
    ::= { f3IrigRelayOutputPortEntry 8 }

--
-- IRIG Output Group 
--
f3IrigOutputGroupTable OBJECT-TYPE
    SYNTAX      SEQUENCE OF IrigOutputGroupEntry
    MAX-ACCESS  not-accessible
    STATUS      current
    DESCRIPTION
            "A list of entries corresponding to output groups."
    ::= { cmFacilityObjects 109 }

f3IrigOutputGroupEntry OBJECT-TYPE
    SYNTAX      IrigOutputGroupEntry 
    MAX-ACCESS  not-accessible
    STATUS      current
    DESCRIPTION
            "A conceptual row in the f3IrigOutputGroupTable."
    INDEX { neIndex, shelfIndex, slotIndex, f3IrigOutputGroupIndex }
    ::= { f3IrigOutputGroupTable 1 }

IrigOutputGroupEntry ::= SEQUENCE {
    -- Group Index
    f3IrigOutputGroupIndex              Integer32,
    f3IrigOutputGroupIfIndex          InterfaceIndex,
    f3IrigOutputGroupEntityIndex      PhysicalIndex,
    -- Alias
    f3IrigOutputGroupAlias              DisplayString,
    -- IRIG Output Group specific attributes
    f3IrigOutputGroupExtensionType      IrigGroupExtensionType,
    f3IrigOutputGroupExtensionDetection TruthValue
}

-- Group Index 
f3IrigOutputGroupIndex OBJECT-TYPE
    SYNTAX      Integer32 (1..65535)
    MAX-ACCESS  not-accessible
    STATUS      current
    DESCRIPTION
         "An integer index value used to uniquely identify
          this IRIG output group in its parent card." 
    ::= { f3IrigOutputGroupEntry 1 }


f3IrigOutputGroupIfIndex OBJECT-TYPE
    SYNTAX      InterfaceIndex
    MAX-ACCESS  read-only
    STATUS      current
    DESCRIPTION
         "An integer index value used to uniquely identify this output port 
          as an interface in ifTable entries with ifIndex value." 
    ::= { f3IrigOutputGroupEntry 2 }

f3IrigOutputGroupEntityIndex OBJECT-TYPE
    SYNTAX      PhysicalIndex
    MAX-ACCESS  read-only
    STATUS      current
    DESCRIPTION
         "An integer index value used to uniquely identify this output port 
          as an entity in entityPhysical entries with entPhysicalIndex value." 
    ::= { f3IrigOutputGroupEntry 3 }

-- Alias
f3IrigOutputGroupAlias    OBJECT-TYPE
    SYNTAX      DisplayString (SIZE(0..64))
    MAX-ACCESS  read-write
    STATUS      current
    DESCRIPTION
         "This object allows SNMP management entities to provide an 
          alias to the output group entity."
     ::= { f3IrigOutputGroupEntry 4 }

-- IRIG Output Group specific attributes
f3IrigOutputGroupExtensionType OBJECT-TYPE 
    SYNTAX     IrigGroupExtensionType
    MAX-ACCESS read-write
    STATUS     current
    DESCRIPTION
         "This object allows to manage the Time Code of the IRIG output group."
     ::= { f3IrigOutputGroupEntry 5 }

f3IrigOutputGroupExtensionDetection OBJECT-TYPE 
    SYNTAX     TruthValue
    MAX-ACCESS read-only
    STATUS     current
    DESCRIPTION
         "This object allows to manage the Control field of the IRIG output group."
     ::= { f3IrigOutputGroupEntry 6 } 

--
-- IRIG Output Unit Port 
--
f3IrigOutputUnitPortTable OBJECT-TYPE
    SYNTAX      SEQUENCE OF IrigOutputUnitPortEntry
    MAX-ACCESS  not-accessible
    STATUS      current
    DESCRIPTION
            "A list of entries corresponding to IRIG output unit ports
             in IRIG output groups for management purposes."
    ::= { cmFacilityObjects 110 }

f3IrigOutputUnitPortEntry OBJECT-TYPE
    SYNTAX      IrigOutputUnitPortEntry 
    MAX-ACCESS  not-accessible
    STATUS      current
    DESCRIPTION
            "A conceptual row in the f3IrigOutputUnitPortTable."
    INDEX { neIndex, shelfIndex, slotIndex, f3IrigOutputGroupIndex, f3IrigOutputUnitPortIndex }
    ::= { f3IrigOutputUnitPortTable 1 }

IrigOutputUnitPortEntry ::= SEQUENCE {
    -- Port Indices
    f3IrigOutputUnitPortIndex            Integer32,
    f3IrigOutputUnitPortIfIndex          InterfaceIndex,
    f3IrigOutputUnitPortEntityIndex      PhysicalIndex,

    -- Alias
    f3IrigOutputUnitPortAlias            DisplayString,

    -- State Management
    f3IrigOutputUnitPortAdminState       AdminState,
    f3IrigOutputUnitPortOperationalState OperationalState,
    f3IrigOutputUnitPortSecondaryState   SecondaryState,

    -- IRIG  Output port specific attributes
    f3IrigOutputUnitPortTimeCode         IrigTimeCode,
    f3IrigOutputUnitPortControlField     IrigControlField,
    f3IrigOutputUnitPortType             IrigOutputType, 
    f3IrigOutputUnitPortDigitalVoltage   IrigDigitalSignalVoltage
}

-- Port Indices
f3IrigOutputUnitPortIndex OBJECT-TYPE
    SYNTAX      Integer32 (1..65535)
    MAX-ACCESS  not-accessible
    STATUS      current
    DESCRIPTION
         "An integer index value used to uniquely identify
          this IRIG output unit port in its output group." 
    ::= { f3IrigOutputUnitPortEntry 1 }

f3IrigOutputUnitPortIfIndex OBJECT-TYPE
    SYNTAX      InterfaceIndex
    MAX-ACCESS  read-only
    STATUS      current
    DESCRIPTION
         "An integer index value used to uniquely identify this output port 
          as an interface in ifTable entries with ifIndex value." 
    ::= { f3IrigOutputUnitPortEntry 2 }

f3IrigOutputUnitPortEntityIndex OBJECT-TYPE
    SYNTAX      PhysicalIndex
    MAX-ACCESS  read-only
    STATUS      current
    DESCRIPTION
         "An integer index value used to uniquely identify this output port 
          as an entity in entityPhysical entries with entPhysicalIndex value." 
    ::= { f3IrigOutputUnitPortEntry 3 }

-- Alias
f3IrigOutputUnitPortAlias    OBJECT-TYPE
    SYNTAX      DisplayString (SIZE(0..64))
    MAX-ACCESS  read-write
    STATUS      current
    DESCRIPTION
         "This object allows SNMP management entities to provide an 
          alias to the output port entity."
    ::= { f3IrigOutputUnitPortEntry 4 }

-- State Management
f3IrigOutputUnitPortAdminState OBJECT-TYPE
    SYNTAX      AdminState 
    MAX-ACCESS  read-write
    STATUS      current
    DESCRIPTION
         "This object represents the administrative state of the IRIG output port."
    ::= { f3IrigOutputUnitPortEntry 5 }

f3IrigOutputUnitPortOperationalState OBJECT-TYPE
    SYNTAX      OperationalState 
    MAX-ACCESS  read-only
    STATUS      current
    DESCRIPTION
         "This object represents the operational state of the IRIG output port."
    ::= { f3IrigOutputUnitPortEntry 6 }

f3IrigOutputUnitPortSecondaryState OBJECT-TYPE
    SYNTAX      SecondaryState 
    MAX-ACCESS  read-only
    STATUS      current
    DESCRIPTION
         "This object represents the Secondary State of the IRIG output port." 
    ::= { f3IrigOutputUnitPortEntry 7 }

-- IRIG  Output port specific attributes
f3IrigOutputUnitPortTimeCode OBJECT-TYPE 
    SYNTAX     IrigTimeCode
    MAX-ACCESS read-write
    STATUS     current
    DESCRIPTION
         "This object allows to manage the Time Code of the IRIG output port."
    ::= { f3IrigOutputUnitPortEntry 8 }

f3IrigOutputUnitPortControlField OBJECT-TYPE 
    SYNTAX     IrigControlField
    MAX-ACCESS read-write
    STATUS     current
    DESCRIPTION
         "This object allows to manage the Control field of the IRIG output port."
    ::= { f3IrigOutputUnitPortEntry 9 } 

f3IrigOutputUnitPortType OBJECT-TYPE 
    SYNTAX     IrigOutputType
    MAX-ACCESS read-write
    STATUS     current
    DESCRIPTION
         "This object allows to manage the output type, digital or analogous,
          of the IRIG output port."
    ::= { f3IrigOutputUnitPortEntry 10 } 

f3IrigOutputUnitPortDigitalVoltage OBJECT-TYPE 
    SYNTAX     IrigDigitalSignalVoltage
    MAX-ACCESS read-write
    STATUS     current
    DESCRIPTION
         "This object allows to manage, for digital output type only, the voltage 
          of the IRIG output port."
    ::= { f3IrigOutputUnitPortEntry 11 } 


--
-- CC Card Input port
--

ccInputPortTable OBJECT-TYPE
    SYNTAX      SEQUENCE OF CcInputPortEntry
    MAX-ACCESS  not-accessible
    STATUS      current
    DESCRIPTION
            "A list of entries corresponding to Composite input
             Port Facilities for configuration purposes."
    ::= { cmFacilityObjects 111 }

ccInputPortEntry OBJECT-TYPE
    SYNTAX      CcInputPortEntry 
    MAX-ACCESS  not-accessible
    STATUS      current
    DESCRIPTION
            "A conceptual row in the ccInputPortTable."
    INDEX { neIndex, shelfIndex, slotIndex, ccInputPortIndex }
    ::= { ccInputPortTable 1 }

CcInputPortEntry ::= SEQUENCE {
    -- Port Indices 
    ccInputPortIndex             Integer32,     
    
    ccInputPortIfIndex           InterfaceIndex,
    ccInputPortEntityIndex       PhysicalIndex,
    
    -- Alias
    ccInputPortAlias             DisplayString,
       
    -- State Management params
    ccInputPortAdminState        AdminState,
    ccInputPortOperationalState  OperationalState,
    ccInputPortSecondaryState    SecondaryState

    -- ccInputPort port specific params  
}
    
-- Port Indices 
ccInputPortIndex OBJECT-TYPE
    SYNTAX      Integer32 (1..65535)
    MAX-ACCESS  read-only
    STATUS      current
    DESCRIPTION
         "An integer index value used to uniquely identify
          this CC input Port." 
    ::= { ccInputPortEntry 1 }

ccInputPortIfIndex OBJECT-TYPE
    SYNTAX      InterfaceIndex
    MAX-ACCESS  read-only
    STATUS      current
    DESCRIPTION
         "An integer index value used to uniquely identify this input port 
          as an interface in ifTable entries with ifIndex value." 
    ::= { ccInputPortEntry 2 }

ccInputPortEntityIndex OBJECT-TYPE
    SYNTAX      PhysicalIndex
    MAX-ACCESS  read-only
    STATUS      current
    DESCRIPTION
         "An integer index value used to uniquely identify this input port 
          as an entity in entityPhysical entries with entPhysicalIndex value." 
    ::= { ccInputPortEntry 3 }

-- Alias
ccInputPortAlias    OBJECT-TYPE
    SYNTAX      DisplayString (SIZE(0..64))
    MAX-ACCESS  read-write
    STATUS      current
    DESCRIPTION
         "This object allows SNMP management entities to provide an 
          alias to the input port entity."
    ::= { ccInputPortEntry 4 }

-- State Management params
ccInputPortAdminState OBJECT-TYPE
    SYNTAX      AdminState 
    MAX-ACCESS  read-write
    STATUS      current
    DESCRIPTION
            "This object represents the Administrative State of the CC input Port."
    ::= { ccInputPortEntry 5 }

ccInputPortOperationalState OBJECT-TYPE
    SYNTAX      OperationalState 
    MAX-ACCESS  read-only
    STATUS      current
    DESCRIPTION
            "This object represents the Operational State of the CC input Port."
    ::= { ccInputPortEntry 6 }
  
ccInputPortSecondaryState OBJECT-TYPE
    SYNTAX      SecondaryState 
    MAX-ACCESS  read-only
    STATUS      current
    DESCRIPTION
         "This object represents the Secondary State of the CC input port." 
    ::= { ccInputPortEntry 7 }
    
-- ccInputPort port specific params

--
-- CC Card Input port
--

ccGroupTable OBJECT-TYPE
    SYNTAX      SEQUENCE OF CcGroupEntry
    MAX-ACCESS  not-accessible
    STATUS      current
    DESCRIPTION
            "A list of entries corresponding to Composite group
             output Facilities for configuration purposes."
    ::= { cmFacilityObjects 112 }

ccGroupEntry OBJECT-TYPE
    SYNTAX      CcGroupEntry 
    MAX-ACCESS  not-accessible
    STATUS      current
    DESCRIPTION
            "A conceptual row in the ccGroupTable."
    INDEX { neIndex, shelfIndex, slotIndex, ccGroupIndex }
    ::= { ccGroupTable 1 }

CcGroupEntry ::= SEQUENCE {
    -- Port Indices
    ccGroupIndex             Integer32,
    
    ccGroupIfIndex           InterfaceIndex,
    ccGroupEntityIndex       PhysicalIndex,
    
    -- Alias
    ccGroupAlias             DisplayString,

    -- ccGroup port specific params
    ccGroupActivePorts       CcActivePortState,
    ccGroupPhaseAdjust       Integer32,
    ccGroupDutyCycle         CcPortDutyCycle
}
    
-- Port Indices 
ccGroupIndex OBJECT-TYPE
    SYNTAX      Integer32 (1..65535)
    MAX-ACCESS  read-only
    STATUS      current
    DESCRIPTION
         "An integer index value used to uniquely identify
          this CC Group." 
    ::= { ccGroupEntry 1 }

ccGroupIfIndex OBJECT-TYPE
    SYNTAX      InterfaceIndex
    MAX-ACCESS  read-only
    STATUS      current
    DESCRIPTION
         "An integer index value used to uniquely identify this group 
          as an interface in ifTable entries with ifIndex value." 
    ::= { ccGroupEntry 2 }

ccGroupEntityIndex OBJECT-TYPE
    SYNTAX      PhysicalIndex
    MAX-ACCESS  read-only
    STATUS      current
    DESCRIPTION
         "An integer index value used to uniquely identify this input port 
          as an entity in entityPhysical entries with entPhysicalIndex value." 
    ::= { ccGroupEntry 3 }

-- Alias
ccGroupAlias    OBJECT-TYPE
    SYNTAX      DisplayString (SIZE(0..64))
    MAX-ACCESS  read-write
    STATUS      current
    DESCRIPTION
         "This object allows SNMP management entities to provide an 
          alias to the group entity."
    ::= { ccGroupEntry 4 }

-- ccGroup port specific params
ccGroupActivePorts OBJECT-TYPE
    SYNTAX      CcActivePortState 
    MAX-ACCESS  read-write
    STATUS      current
    DESCRIPTION
            "This object represents the Active State for each port of the CC 
             10 output port Group."
    ::= { ccGroupEntry 5 }

ccGroupPhaseAdjust OBJECT-TYPE
    SYNTAX      Integer32 (0..249999)
    MAX-ACCESS  read-write
    STATUS      current
    DESCRIPTION
         "The delay of CC output. This value is duplicated to all the CC outputs
          of all the CC cards in the same 54x0. This value is usually derived from
          a phase measurement of the CC input.
          It could also use a different method to derive the CC Phase Adjust.." 
    ::= { ccGroupEntry 6 }
    
ccGroupDutyCycle OBJECT-TYPE
    SYNTAX     CcPortDutyCycle
    MAX-ACCESS read-write
    STATUS     current
    DESCRIPTION
         "63/37 or 50/50 duty cycles."
     ::= { ccGroupEntry 7 }

--
--  Encap FlowPoint
--
cmEncapFlowPointTable  OBJECT-TYPE
    SYNTAX      SEQUENCE OF CmEncapFlowPointEntry
    MAX-ACCESS  not-accessible
    STATUS      current
    DESCRIPTION
            "A list of entries corresponding to Encap FlowPoint
             for configuration purposes."
    ::= { cmFacilityObjects 113 }

cmEncapFlowPointEntry OBJECT-TYPE
    SYNTAX      CmEncapFlowPointEntry 
    MAX-ACCESS  not-accessible
    STATUS      current
    DESCRIPTION
            "A conceptual row in the cmEncapFlowPointTable. These entries represent
             an Encap FlowPoint."
    INDEX { neIndex, cmEncapFlowPointIndex }
    ::= { cmEncapFlowPointTable 1 }

CmEncapFlowPointEntry ::= SEQUENCE {
    -- EncapFlowPoint Index/Id
    cmEncapFlowPointIndex                           Integer32,
    cmEncapFlowPointCircuitName                     DisplayString,

    cmEncapFlowPointAssociatedFlowId                VariablePointer,
    cmEncapFlowPointRefEoMplsPwObject               VariablePointer,

    cmEncapFlowPointCTagControl                     FlowTagControl,
    cmEncapFlowPointCTagVlanId                      VlanId,
    cmEncapFlowPointCTagVlanPriority                VlanPriority,
    cmEncapFlowPointSTagControl                     FlowTagControl,
    cmEncapFlowPointSTagVlanId                      VlanId,
    cmEncapFlowPointSTagVlanPriority                VlanPriority,

    cmEncapFlowPointEgressOuterTagPrioMapEnabled    TruthValue,
    cmEncapFlowPointEgressInnerTagPrioMapEnabled    TruthValue,
    cmEncapFlowPointRefPrioMapProfile               VariablePointer,

    cmEncapFlowPointStorageType                     StorageType,
    cmEncapFlowPointRowStatus                       RowStatus
}

cmEncapFlowPointIndex OBJECT-TYPE
    SYNTAX      Integer32 (1..65535)
    MAX-ACCESS  read-create
    STATUS      current
    DESCRIPTION
            "The integer index value corresponding to an Encap FlowPoint." 
    ::= { cmEncapFlowPointEntry 1 }

cmEncapFlowPointCircuitName    OBJECT-TYPE
    SYNTAX      DisplayString (SIZE(0..256))
    MAX-ACCESS  read-create
    STATUS      current
    DESCRIPTION
         "This object allows SNMP management entities to provide a
          circuit identifier with the FlowPoint."
     ::= { cmEncapFlowPointEntry 2 }

cmEncapFlowPointAssociatedFlowId OBJECT-TYPE
    SYNTAX      VariablePointer
    MAX-ACCESS  read-only
    STATUS      current
    DESCRIPTION
            "This object provides the association of an Flow with an Encap FlowPoint." 
    ::= { cmEncapFlowPointEntry 3 }

cmEncapFlowPointRefEoMplsPwObject OBJECT-TYPE
    SYNTAX      VariablePointer  
    MAX-ACCESS  read-create
    STATUS      current
    DESCRIPTION
         "This object specifies EoMpls Pw object OID."
    ::= { cmEncapFlowPointEntry 4 }

cmEncapFlowPointCTagControl OBJECT-TYPE
    SYNTAX     FlowTagControl
    MAX-ACCESS read-create
    STATUS     current
    DESCRIPTION
       "This object allows specification of the tag management 
        operation on the C-TAG.  Supported types are 'push', 'pushvid',
        'swaptag', 'swapvid' and 'none'. If the type is 'push',
        the VLAN Id (f3EncapFlowPointCTagVlanId) and priority
        (f3EncapFlowPointCTagVlanPriority) are pushed onto the frame;
        if the type is 'pushvid', only the VLAN Id (12 bits) is pushed,
        the Priority is copied from incoming tag's priority;
        if the type is 'swaptag', both VLAN Id and Priority (15 bits)
        are swapped with the specified f3EncapFlowPointCTagVlanId and 
        f3EncapFlowPointCTagVlanPriority;
        if the type is 'swapvid', only the VLAN Id (12 bits) are 
        swapped with the specified f3EncapFlowPointCTagVlanId; 
        if the type is 'none', no C-TAG management is performed."
    ::= { cmEncapFlowPointEntry 5 }

cmEncapFlowPointCTagVlanId OBJECT-TYPE
    SYNTAX     VlanId
    MAX-ACCESS read-create
    STATUS     current
    DESCRIPTION
       "This object allows specification of the VLAN Id to
        be pushed or swapped, based on the value of 
        f3EncapFlowPointIngressCTagControl. It is applicable 
        for 'push', 'swaptag', 'swapvid' and 'pushvid' control types."
    ::= { cmEncapFlowPointEntry 6 }

cmEncapFlowPointCTagVlanPriority OBJECT-TYPE
    SYNTAX     VlanPriority
    MAX-ACCESS read-create
    STATUS     current
    DESCRIPTION
       "This object allows specification of the VLAN Priority to
        be pushed or swapped, based on the value of f3EncapFlowPointIngressCTagControl.
        It is applicable for 'push' and 'swaptag' control types."
    ::= { cmEncapFlowPointEntry 7 }

cmEncapFlowPointSTagControl OBJECT-TYPE
    SYNTAX     FlowTagControl
    MAX-ACCESS read-create
    STATUS     current
    DESCRIPTION
       "This object allows specification of the tag management 
        operation on the S-TAG.  Supported types are 'push', 'pushvid',
        'swaptag', 'swapvid' and 'none'. If the type is 'push', 
        the VLAN Id (f3EncapFlowPointSTagVlanId) and priority
        (f3EncapFlowPointSTagVlanPriority) are pushed onto the frame;
        if the type is 'pushvid', only the VLAN Id (12 bits) is pushed,
        the Priority is copied from incoming tag's priority;
        if the type is 'swaptag', both VLAN Id and Priority (15 bits) 
        are swapped with the specified f3EncapFlowPointSTagVlanId and 
        f3EncapFlowPointSTagVlanPriority;
        if the type is 'swapvid', only the VLAN Id (12 bits) are 
        swapped with the specified f3EncapFlowPointSTagVlanId; 
        if the type is 'none', no S-TAG management is performed."
    ::= { cmEncapFlowPointEntry 8 }

cmEncapFlowPointSTagVlanId OBJECT-TYPE
    SYNTAX     VlanId
    MAX-ACCESS read-create
    STATUS     current
    DESCRIPTION
       "This object allows specification of the VLAN Id to
        be pushed or swapped, based on the value of 
        f3EncapFlowPointIngressSTagControl. It is applicable 
        for 'push', 'swaptag', 'swapvid' and 'pushvid' control types."
    ::= { cmEncapFlowPointEntry 9 }

cmEncapFlowPointSTagVlanPriority OBJECT-TYPE
    SYNTAX     VlanPriority
    MAX-ACCESS read-create
    STATUS     current
    DESCRIPTION
       "This object allows specification of the VLAN Priority to
        be pushed or swapped, based on the value of 
        f3EncapFlowPointIngressSTagControl. It is applicable
        for 'push' and 'swaptag' control types."
    ::= { cmEncapFlowPointEntry 10 }

cmEncapFlowPointEgressOuterTagPrioMapEnabled OBJECT-TYPE
    SYNTAX     TruthValue
    MAX-ACCESS read-create
    STATUS     current
    DESCRIPTION
       "This object defines whether to use the Egress Prio 
        Mapping to swap the priority of outer tag. When Enabled,
        it indicates that the operation specified in the 
        EgressPrioMapTable would be applied to Flow for specified COS.
        When Disabled,the EgressPrioMapTable operations are ignored 
        for specified Flow COS."
    ::= { cmEncapFlowPointEntry 11 }

cmEncapFlowPointEgressInnerTagPrioMapEnabled OBJECT-TYPE
    SYNTAX     TruthValue
    MAX-ACCESS read-create
    STATUS     current
    DESCRIPTION
       "This object defines whether to use the Egress Prio
        Mapping to swap the priority of inner tag. When Enabled,
        it indicates that the operation specified in the 
        EgressPrioMapTable would be applied to Flow for specified COS.
        When Disabled, the EgressPrioMapTable operations are ignored
        for specified Flow COS."
    ::= { cmEncapFlowPointEntry 12 }

cmEncapFlowPointRefPrioMapProfile OBJECT-TYPE
    SYNTAX      VariablePointer  
    MAX-ACCESS  read-write
    STATUS      current
    DESCRIPTION
         "This object allows to set priority map profile."
    ::= { cmEncapFlowPointEntry 13 }

cmEncapFlowPointStorageType OBJECT-TYPE
    SYNTAX     StorageType
    MAX-ACCESS read-create
    STATUS     current
    DESCRIPTION
            "The type of storage configured for this entry."
    ::= { cmEncapFlowPointEntry 14 }

cmEncapFlowPointRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of cmEncapFlowPointRowStatus supported are
            createAndGo(4) and destroy(6).  All mandatory attributes
            must be specified in a single SNMP SET request with
            cmEncapFlowPointRowStatus value as createAndGo(4).
            Upon successful row creation, this object has a
            value of active(1).

            The cmEncapFlowPointRowStatus object may be modified if
            the associated instance of this object is equal to active(1)."
    ::= { cmEncapFlowPointEntry 15 }

--
-- Conformance
--
cmFacilityCompliances OBJECT IDENTIFIER ::= {cmFacilityConformance 1}
cmFacilityGroups      OBJECT IDENTIFIER ::= {cmFacilityConformance 2}

cmFacilityCompliance MODULE-COMPLIANCE
    STATUS  current
    DESCRIPTION
            "Describes the requirements for conformance to the CM Facility
             group."
    MODULE  -- this module
        MANDATORY-GROUPS {
              cmFacilityObjectGroup,
              ethernetAccessPortGroup, ethernetNetworkPortGroup, 
              ethernetMgmtPortGroup, bitsPortGroup,
              trafficGroup, prioMapGroup, pcpEncodeGroup, cpdV2Group,

              trafficGroupCmHub, ocnStmGroup, stsVcPathGroup,
              vtVcPathGroup, e1t1InterfaceGroup, e3t3InterfaceGroup,

              f3PulsePerSecondPortGroup, f3TimeOfDayPortGroup,
              
              f3Gps10MhzPortGroup, neTMParamsGroup,
              
              cmEthernetTrafficPortJdsuExtGroup, f3FpQosShaperGroup,
              f3FpQosPolicerGroup, cpdV2TrafficPortGroup,
              
              f3AclRuleGroup
        }
    ::= { cmFacilityCompliances 1 }

cmFacilityObjectGroup OBJECT-GROUP
    OBJECTS {
    cmEthernetAccPortIndex, cmEthernetAccPortIfIndex,
    cmEthernetAccPortOperationalState, cmEthernetAccPortSecondaryState,
    cmEthernetAccPortMTU, cmEthernetAccPortMediaType,
    cmEthernetAccPortConfigSpeed, cmEthernetAccPortNegotiatedSpeed,
    cmEthernetAccPortMDIXType,
    cmEthernetAccPortJumboFramesEnabled, cmEthernetAccPortSfpVendorName,
    cmEthernetAccPortSfpPartNumber, cmEthernetAccPortSfpSerialNumber,
    cmEthernetAccPortSfpDateOfManufacture,
    cmEthernetAccPortSfpConnectorValue,
    cmEthernetAccPortInitiateDiag, cmEthernetAccPortDiagnosePair1Cond,
    cmEthernetAccPortDiagnosePair2Cond, cmEthernetAccPortDiagnosePair3Cond,
    cmEthernetAccPortDiagnosePair4Cond, cmEthernetAccPortDiagnoseAutoNegCond,
    cmEthernetAccPortDiagnoseLpbkCond, cmEthernetAccPortDiagnoseEfmLpbkCond,
    cmEthernetAccPortDiagnoseResult,cmEthernetAccPortDiagnoseTestStatus,
    cmEthernetAccPortDiagnoseTestTime,
    cmEthernetAccPortLoopbackConfig, cmEthernetAccPortLoopbackStatus,
    cmEthernetAccPortLoopbackTime,
    cmEthernetAccPortLoopbackSwapSADA, cmEthernetAccPortOuterVlanLoopbackMask,
    cmEthernetAccPortOuterVlanLoopback1, cmEthernetAccPortOuterVlanLoopback2,
    cmEthernetAccPortOuterVlanLoopback3, 
    cmEthernetAccPortInnerVlanLoopbackMask,
    cmEthernetAccPortInnerVlanLoopback1, cmEthernetAccPortInnerVlanLoopback2,
    cmEthernetAccPortInnerVlanLoopback3,
    cmEthernetAccPortLinkLossFwdEnabled, 
    cmEthernetAccPortLinkLossFwdSignalType,
    cmEthernetAccPortLinkLossFwdTriggerTypes,
    cmEthernetAccPortLinkLossFwdDelay, cmEthernetAccPortLinkLossFwdActive,
    cmEthernetAccPortLinkLossFwdPartnerEnabled,
    cmEthernetAccPortLinkLossFwdLocalLinkId,
    cmEthernetAccPortLinkLossFwdRemoteLinkIds,
    cmEthernetAccPortOamId, cmEthernetAccPortOamAdminDisposition,
    cmEthernetAccPortOamDiscoveryState, 
    cmEthernetAccPortOamLocalVarRtrvsEnabled,
    cmEthernetAccPortOamLocalLinkEventsEnabled,
    cmEthernetAccPortOamLocalOamLoopbacksSupported,
    cmEthernetAccPortOamLocalUnidirSupportEnabled,
    cmEthernetAccPortOamLocalMaxPDUSize, cmEthernetAccPortOamLocalMode,
    cmEthernetAccPortOamRemoteMacAddress, 
    cmEthernetAccPortOamRemoteVarRtrvsEnabled,
    cmEthernetAccPortOamRemoteLinkEventsEnabled,
    cmEthernetAccPortOamRemoteOamLoopbacksSupported,
    cmEthernetAccPortOamRemoteUnidirSupportEnabled,
    cmEthernetAccPortOamRemoteMaxPDUSize,
    cmEthernetAccPortOamRemoteMode, cmEthernetAccPortMode, 
    cmEthernetAccPortSvcType, cmEthernetAccPortRxPauseDisposition, 
    cmEthernetAccPortTxPauseEnabled, cmEthernetAccPortAfpType,

    cmEthernetAccPortCpdIndex, cmEthernetAccPortCpdFilterType,
    cmEthernetAccPortCpdFilterDescr, cmEthernetAccPortCpdDispType,
    cmEthernetAccPortCpdMacAddressMatch, cmEthernetAccPortCpdMacAddressMask,
    cmEthernetAccPortCpdEthertype, cmEthernetAccPortCpdEthertypeMask,
    cmEthernetAccPortCpdSubtype, cmEthernetAccPortCpdSubtypeMask,

    cmEthernetAccPortClbIndex, cmEthernetAccPortClbEnabled,
    cmEthernetAccPortClbLength, cmEthernetAccPortClbDescr,

    cmEthernetAccPortMDIXStatus, cmEthernetAccPortSfpReach,
    cmEthernetAccPortSfpLaserWaveLength,
    cmEthernetAccPortSfpMediaType, cmEthernetAccPortOamEnabled,
    cmEthernetAccPortOamAdminState,
    cmEthernetAccPortShapingEnabled,
    cmEthernetAccPortShapedSpeedLo, cmEthernetAccPortShapedSpeedHi,
    cmEthernetAccPortQinQEtherType, cmEthernetAccPortRxPauseEnabled,
    cmEthernetAccPortAutoDiagEnabled, cmEthernetAccPortLinkLossFwdTxActionType,
    cmEthernetAccPortLinkLossFwdRxRLDLinkIds,
    cmEthernetAccPortN2AVlanTrunkingEnabled, 
    cmEthernetAccPortA2NPushPVIDEnabled,
    cmEthernetAccPortN2APopPVIDEnabled, cmEthernetAccPortPortVlanId,
    cmEthernetAccPortPortVlanPriority,   
    cmEthernetAccPortPrioMapMode, cmEthernetAccPortSyncEEnabled,
    cmEthernetAccPortQLModeEnabled, cmEthernetAccPortExpectedQL,
    cmEthernetAccPortAssumedQL, cmEthernetAccPortReceivedQL, 
    cmEthernetAccPortTransmitQL,
    cmEthernetAccPortSfpName, cmEthernetAccPortSfpHardwareRevision,
    cmFlowIndex, cmFlowCircuitName, cmFlowAdminState,
    cmFlowOperationalState, cmFlowSecondaryState,
    cmFlowType, cmFlowMultiCOS, cmFlowA2NCIR,
    cmFlowA2NEIR, cmFlowN2ARateLimitingEnabled,
    cmFlowN2ACIR, cmFlowN2AEIR, cmFlowStorageType, cmFlowRowStatus,

    cmFlowTrafficType, cmFlowCOS, cmFlowVlanMemberList,
    cmFlowAction, cmFlowActionVlan, cmFlowUntaggedMemberEnabled,
    cmFlowA2NCIRHi, cmFlowA2NEIRHi,
    cmFlowN2ACIRHi, cmFlowN2AEIRHi, 
    cmFlowHCOSMgmtEnabled, cmFlowGuaranteedA2NBandwidthLo,
    cmFlowGuaranteedA2NBandwidthHi, cmFlowMaximumA2NBandwidthLo,
    cmFlowMaximumA2NBandwidthHi, cmFlowCTagControl,
    cmFlowCTagVlanId, cmFlowCTagVlanPriority, cmFlowCTagMatchRxPrio,
    cmFlowSTagControl, cmFlowSTagVlanId, cmFlowSTagVlanPriority,
    cmFlowOuterTagPrioEnabled, cmFlowN2ACOSPriorityTagType,
    cmFlowESFramesLossThreshold, cmFlowSESFramesLossThresholdRatio, 
    cmFlowPolicingEnabled, cmFlowPreserveSTagProperties, cmFlowInnerTagPrioEnabled,
    cmFlowN2AOuterTagPrioEnabled,

    cmFlowCpdIndex, cmFlowCpdFilterType, cmFlowCpdFilterDescr, 
    cmFlowCpdDispType, cmFlowCpdMacAddressMatch, cmFlowCpdMacAddressMask,
    cmFlowCpdEthertype, cmFlowCpdEthertypeMask, cmFlowCpdSubtype, 
    cmFlowCpdSubtypeMask,

    cmQosShaperTypeIndex, cmQosShaperIndex, cmQosShaperDirection,
    cmQosShaperAdminState, cmQosShaperOperationalState,cmQosShaperSecondaryState,
    cmQosShaperCIR, cmQosShaperCBS, cmQosShaperEIR, cmQosShaperEBS,
    cmQosShaperBufferSize, cmQosShaperStorageType,
    cmQosShaperRowStatus, 

    cmQosShaperCOS, cmQosShaperCIRHi, cmQosShaperEIRHi,

    cmEthernetNetPortIndex, cmEthernetNetPortIfIndex,
    cmEthernetNetPortEntityIndex, cmEthernetNetPortAdminState,
    cmEthernetNetPortOperationalState, cmEthernetNetPortSecondaryState,
    cmEthernetNetPortMTU, cmEthernetNetPortMediaType,
    cmEthernetNetPortConfigSpeed, cmEthernetNetPortNegotiatedSpeed,
    cmEthernetNetPortMDIXType,
    cmEthernetNetPortJumboFramesEnabled, cmEthernetNetPortSfpVendorName,
    cmEthernetNetPortSfpPartNumber, cmEthernetNetPortSfpSerialNumber,
    cmEthernetNetPortSfpDateOfManufacture, cmEthernetNetPortSfpConnectorValue,
    cmEthernetNetPortInitiateDiag, cmEthernetNetPortDiagnosePair1Cond,
    cmEthernetNetPortDiagnosePair2Cond, cmEthernetNetPortDiagnosePair3Cond,
    cmEthernetNetPortDiagnosePair4Cond, cmEthernetNetPortDiagnoseAutoNegCond,
    cmEthernetNetPortDiagnoseLpbkCond, cmEthernetNetPortDiagnoseEfmLpbkCond,
    cmEthernetNetPortDiagnoseResult,cmEthernetNetPortDiagnoseTestStatus,
    cmEthernetNetPortDiagnoseTestTime,
    cmEthernetNetPortLoopbackConfig, cmEthernetNetPortLoopbackStatus,
    cmEthernetNetPortLoopbackTime,
    cmEthernetNetPortLoopbackSwapSADA, cmEthernetNetPortOuterVlanLoopbackMask,
    cmEthernetNetPortOuterVlanLoopback1, cmEthernetNetPortOuterVlanLoopback2,
    cmEthernetNetPortOuterVlanLoopback3, 
    cmEthernetNetPortInnerVlanLoopbackMask,
    cmEthernetNetPortInnerVlanLoopback1, cmEthernetNetPortInnerVlanLoopback2, 
    cmEthernetNetPortInnerVlanLoopback3,
    cmEthernetNetPortLinkLossFwdEnabled, cmEthernetNetPortLinkLossFwdSignalType,
    cmEthernetNetPortLinkLossFwdTriggerTypes,cmEthernetNetPortLinkLossFwdDelay,
    cmEthernetNetPortLinkLossFwdActive, 
    cmEthernetNetPortLinkLossFwdPartnerEnabled,
    cmEthernetNetPortLinkLossFwdLocalLinkId, 
    cmEthernetNetPortLinkLossFwdRemoteLinkIds,
    cmEthernetNetPortOamId, cmEthernetNetPortOamAdminDisposition,
    cmEthernetNetPortOamDiscoveryState,
    cmEthernetNetPortOamLocalVarRtrvsEnabled, 
    cmEthernetNetPortOamLocalLinkEventsEnabled,
    cmEthernetNetPortOamLocalOamLoopbacksSupported,
    cmEthernetNetPortOamLocalUnidirSupportEnabled,
    cmEthernetNetPortOamLocalMaxPDUSize,
    cmEthernetNetPortOamLocalMode, cmEthernetNetPortOamRemoteMacAddress,
    cmEthernetNetPortOamRemoteVarRtrvsEnabled,
    cmEthernetNetPortOamRemoteLinkEventsEnabled,
    cmEthernetNetPortOamRemoteOamLoopbacksSupported,
    cmEthernetNetPortOamRemoteUnidirSupportEnabled,
    cmEthernetNetPortOamRemoteMaxPDUSize, cmEthernetNetPortOamRemoteMode,
    cmEthernetNetPortRxPauseDisposition, cmEthernetNetPortTxPauseEnabled,
    cmEthernetNetPortAfpType,
    cmEthernetNetPortSfpName,
    cmEthernetNetPortSfpHardwareRevision,

    cmEthernetNetPortMDIXStatus, cmEthernetNetPortSfpReach,
    cmEthernetNetPortSfpLaserWaveLength,
    cmEthernetNetPortSfpMediaType, cmEthernetNetPortOamEnabled,
    cmEthernetNetPortOamAdminState,
    cmEthernetNetPortShapingEnabled,
    cmEthernetNetPortShapedSpeedLo, cmEthernetNetPortShapedSpeedHi,
    cmEthernetNetPortQinQEtherType, cmEthernetNetPortLinkLossFwdTxActionType,
    cmEthernetNetPortLinkLossFwdRxRLDLinkIds,
    cmEthernetNetPortAutoDiagEnabled,
    cmEthernetNetPortSyncEEnabled, cmEthernetNetPortQLModeEnabled,
    cmEthernetNetPortExpectedQL, cmEthernetNetPortAssumedQL,
    cmEthernetNetPortReceivedQL, cmEthernetNetPortTransmitQL,

    cmEthernetNetPortCpdIndex, cmEthernetNetPortCpdFilterType,
    cmEthernetNetPortCpdFilterDescr, cmEthernetNetPortCpdDispType,
    cmEthernetNetPortCpdMacAddressMatch, cmEthernetNetPortCpdMacAddressMask,
    cmEthernetNetPortCpdEthertype, cmEthernetNetPortCpdEthertypeMask,
    cmEthernetNetPortCpdSubtype, cmEthernetNetPortCpdSubtypeMask,

    cmEthernetMgmtPortIndex, cmEthernetMgmtPortEntityIndex,
    cmEthernetMgmtPortAdminState, cmEthernetMgmtPortOperationalState,
    cmEthernetMgmtPortSecondaryState, cmEthernetMgmtPortMTU,
    cmEthernetMgmtPortConfigSpeed, cmEthernetMgmtPortNegotiatedSpeed,
    cmEthernetMgmtPortMDIXType,
    cmEthernetMgmtPortMDIXStatus,

    cmPrioMapIndex, cmPrioMapInPriority, cmPrioMapXTagControl,
    cmPrioMapXTagPriority, cmPrioMapCOS, cmPrioMapOuterTagPriority,
    cmPrioMapInnerTagPriority,

    cmQosFlowPolicerTypeIndex, cmQosFlowPolicerIndex,
    cmQosFlowPolicerDirection, cmQosFlowPolicerAdminState, 
    cmQosFlowPolicerOperationalState,
    cmQosFlowPolicerSecondaryState,
    cmQosFlowPolicerCIRLo, cmQosFlowPolicerCIRHi, cmQosFlowPolicerEIRLo,
    cmQosFlowPolicerEIRHi, cmQosFlowPolicerCBS,
    cmQosFlowPolicerEBS, cmQosFlowPolicerAlgorithm,
    cmQosFlowPolicerColorMode, cmQosFlowPolicerColorMarkingFlag,
    cmQosFlowPolicerCouplingFlag, cmQosFlowPolicerAssociatedShaper,
    cmQosFlowPolicerStorageType, cmQosFlowPolicerRowStatus,

    cmAccPortQosShaperIndex, cmAccPortQosShaperDirection,
    cmAccPortQosShaperAdminState, cmAccPortQosShaperOperationalState,
    cmAccPortQosShaperSecondaryState, cmAccPortQosShaperCIRLo,
    cmAccPortQosShaperCIRHi, cmAccPortQosShaperEIRLo,
    cmAccPortQosShaperEIRHi, cmAccPortQosShaperCBS,
    cmAccPortQosShaperEBS, cmAccPortQosShaperBufferSize, cmAccPortQosShaperCOS,

    cmEthernetAccPortCpdV2Index, cmEthernetAccPortCpdV2CiscoGroupDispType,
    cmEthernetAccPortCpdV2IslDispType, cmEthernetAccPortCpdV2PagpDispType,
    cmEthernetAccPortCpdV2UdldDispType, cmEthernetAccPortCpdV2CdpDispType,
    cmEthernetAccPortCpdV2VtpDispType, cmEthernetAccPortCpdV2DtpDispType,
    cmEthernetAccPortCpdV2PvstpPlusDispType, 
    cmEthernetAccPortCpdV2UplinkFastDispType,
    cmEthernetAccPortCpdV2VlanBridgeDispType,
    cmEthernetAccPortCpdV2L2PTDispType, 
    cmEthernetAccPortCpdV2BridgeGroupDispType,
    cmEthernetAccPortCpdV2BPDUDispType, cmEthernetAccPortCpdV2PauseDispType,
    cmEthernetAccPortCpdV2LACPDispType,
    cmEthernetAccPortCpdV2LACPMarkerDispType,
    cmEthernetAccPortCpdV2EfmOamDispType,
    cmEthernetAccPortCpdV2SSMDispType,
    cmEthernetAccPortCpdV2PortAuthenDispType,
    cmEthernetAccPortCpdV2BridgeReservedDispType,
    cmEthernetAccPortCpdV2LANBridgesDispType,
    cmEthernetAccPortCpdV2GARPGroupDispType,
    cmEthernetAccPortCpdV2GMRPDispType, cmEthernetAccPortCpdV2GVRPDispType,
    cmEthernetAccPortCpdV2GARPDispType,

    cmFlowCpdV2Index, cmFlowCpdV2CiscoGroupDispType,
    cmFlowCpdV2IslDispType, cmFlowCpdV2PagpDispType,
    cmFlowCpdV2UdldDispType, cmFlowCpdV2CdpDispType,
    cmFlowCpdV2VtpDispType, cmFlowCpdV2DtpDispType,
    cmFlowCpdV2PvstpPlusDispType, 
    cmFlowCpdV2UplinkFastDispType,
    cmFlowCpdV2VlanBridgeDispType,
    cmFlowCpdV2L2PTDispType, 
    cmFlowCpdV2BridgeGroupDispType,
    cmFlowCpdV2BPDUDispType, cmFlowCpdV2PauseDispType,
    cmFlowCpdV2LACPDispType,
    cmFlowCpdV2LACPMarkerDispType,
    cmFlowCpdV2EfmOamDispType,
    cmFlowCpdV2SSMDispType,            
    cmFlowCpdV2PortAuthenDispType,
    cmFlowCpdV2BridgeReservedDispType,
    cmFlowCpdV2LANBridgesDispType,
    cmFlowCpdV2GARPGroupDispType,
    cmFlowCpdV2GMRPDispType, cmFlowCpdV2GVRPDispType, cmFlowCpdV2GARPDispType,
    cmFlowCpdV2ActiveControlProtocols, 

    cmEthernetNetPortCpdV2Index, cmEthernetNetPortCpdV2CiscoGroupDispType,
    cmEthernetNetPortCpdV2IslDispType, cmEthernetNetPortCpdV2PagpDispType,
    cmEthernetNetPortCpdV2UdldDispType, cmEthernetNetPortCpdV2CdpDispType,
    cmEthernetNetPortCpdV2VtpDispType, cmEthernetNetPortCpdV2DtpDispType,
    cmEthernetNetPortCpdV2PvstpPlusDispType, 
    cmEthernetNetPortCpdV2UplinkFastDispType,
    cmEthernetNetPortCpdV2VlanBridgeDispType,
    cmEthernetNetPortCpdV2L2PTDispType, 
    cmEthernetNetPortCpdV2BridgeGroupDispType,
    cmEthernetNetPortCpdV2BPDUDispType, cmEthernetNetPortCpdV2PauseDispType,
    cmEthernetNetPortCpdV2LACPDispType,
    cmEthernetNetPortCpdV2LACPMarkerDispType,
    cmEthernetNetPortCpdV2EfmOamDispType,
    cmEthernetNetPortCpdV2SSMDispType,
    cmEthernetNetPortCpdV2PortAuthenDispType,
    cmEthernetNetPortCpdV2BridgeReservedDispType,
    cmEthernetNetPortCpdV2LANBridgesDispType,
    cmEthernetNetPortCpdV2GARPGroupDispType,
    cmEthernetNetPortCpdV2GMRPDispType, cmEthernetNetPortCpdV2GVRPDispType,
    cmEthernetNetPortCpdV2GARPDispType,

    bitsPortTypeIndex, bitsPortIndex, bitsPortIfIndex, bitsPortEntityIndex,
    bitsPortAdminState, bitsPortOperationalState, bitsPortSecondaryState,
    bitsPortType, bitsPortLineType, bitsPortLineCode, bitsPortFrameFormat,
    bitsPortSaBitDesignation, bitsPortQLModeEnabled, bitsPortExpectedQL,
    bitsPortAssumedQL, bitsPortReceivedQL, bitsPortTransmitQL, bitsPortSquelchQL,
    bitsPortLineBuildOut, bitsPortImpedance, bitsPortCrc4, bitsPortIdleCode,
    bitsPortAis, bitsPortSaBitsAdminState, bitsPortSquelchControl,
    bitsPortSignalShape, bitsPortSignalFrequency,

    ieee1588EthernetPortIndex, ieee1588EthernetPortIfIndex,
    ieee1588EthernetPortEntityIndex, ieee1588EthernetPortAdminState,
    ieee1588EthernetPortOperationalState, ieee1588EthernetPortSecondaryState,
    ieee1588EthernetPortMTU, ieee1588EthernetPortMediaType,
    ieee1588EthernetPortConfigSpeed, ieee1588EthernetPortNegotiatedSpeed,
    ieee1588EthernetPortMDIXType,

    gps10MHzPortIndex, gps10MHzPortIfIndex, gps10MHzPortEntityIndex,
    gps10MHzPortAdminState, gps10MHzPortOperationalState,
    gps10MHzPortSecondaryState, gps10MHzPortSignalDirection,
    gps10MHzPortSquelchControl, gps10MHzPortSquelchQL,
    gps10MHzPortFrequencySource,
    gps10MHzPortClockClass,
    gps10MHzPortClockAccuracy,
    gps10MHzPortTimeSource, gps10MHzPortAssumedQL,gps10MHzPortAlias,
    gps10MHzPortInputSignalType,
    
    cmEthernetNetPortClbIndex, cmEthernetNetPortClbEnabled, 
    cmEthernetNetPortClbLength, cmEthernetNetPortClbDescr,

    cmNetPortPrioMapIndex, cmNetPortPrioMapInPriority,
    cmNetPortPrioMapCOS, cmNetPortPrioMapOuterTagPriority,

    cmAccPortPcpDEEncIndex, cmAccPortPcpDEEncInPriority,
    cmAccPortPcpDEEncDropIneligiblePrio, cmAccPortPcpDEEncDropEligiblePrio,
    cmAccPortPcpDEDecIndex, cmAccPortPcpDEDecInPriority,
    cmAccPortPcpDEDecOutPriority, cmAccPortPcpDEDecDropEligible,
    cmAccPortPcpDEPairIndex, cmAccPortPcpDEDropIneligiblePrio,
    cmAccPortPcpDEDropEligiblePrio,

    cmNetPortPcpDEEncIndex, cmNetPortPcpDEEncInPriority,
    cmNetPortPcpDEEncDropIneligiblePrio, cmNetPortPcpDEEncDropEligiblePrio,
    cmNetPortPcpDEDecIndex, cmNetPortPcpDEDecInPriority,
    cmNetPortPcpDEDecOutPriority, cmNetPortPcpDEDecDropEligible,
    cmNetPortPcpDEPairIndex, cmNetPortPcpDEDropIneligiblePrio,
    cmNetPortPcpDEDropEligiblePrio,
    
    cmPortCpdProfileIndex, cmPortCpdProfileName,
    cmPortCpdProfileCiscoGroupDispType,
    cmPortCpdProfileIslDispType, cmPortCpdProfilePagpDispType,
    cmPortCpdProfileUdldDispType, cmPortCpdProfileCdpDispType,
    cmPortCpdProfileVtpDispType, cmPortCpdProfileDtpDispType,
    cmPortCpdProfilePvstpPlusDispType, cmPortCpdProfileUplinkFastDispType,
    cmPortCpdProfileVlanBridgeDispType, cmPortCpdProfileL2PTDispType,
    cmPortCpdProfileBridgeGroupDispType, cmPortCpdProfileBPDUDispType,
    cmPortCpdProfilePauseDispType, cmPortCpdProfileLACPDispType,
    cmPortCpdProfileLACPMarkerDispType, cmPortCpdProfileEfmOamDispType,
    cmPortCpdProfileSSMDispType, cmPortCpdProfilePortAuthenDispType, 
    cmPortCpdProfileBridgeReservedDispType, cmPortCpdProfileLANBridgesDispType,
    cmPortCpdProfileGARPGroupDispType, cmPortCpdProfileGMRPDispType,
    cmPortCpdProfileGVRPDispType, cmPortCpdProfileGARPDispType,
    cmPortCpdProfileLldpDispType,
    cmPortCpdProfileStorageType,cmPortCpdProfileRowStatus,
    cmPortCpdProfileMac00DispType, cmPortCpdProfileMac01DispType,
    cmPortCpdProfileMac02DispType, cmPortCpdProfileMac03DispType,
    cmPortCpdProfileMac04DispType, cmPortCpdProfileMac05DispType, cmPortCpdProfileMac06DispType,
    cmPortCpdProfileMac07DispType, cmPortCpdProfileMac08DispType,
    cmPortCpdProfileMac09DispType, cmPortCpdProfileMac0ADispType,
    cmPortCpdProfileMac0BDispType, cmPortCpdProfileMac0CDispType,
    cmPortCpdProfileMac0DDispType, cmPortCpdProfileMac0EDispType,
    cmPortCpdProfileMac0FDispType, cmPortCpdProfileNearestLLDPDispType,
    cmPortCpdProfileNonTpmrLLDPDispType, cmPortCpdProfileCustomerLLDPDispType,
    cmPortCpdProfileELMIDispType,

    cmFlowPointCpdProfileIndex, cmFlowPointCpdProfileName,
    cmFlowPointCpdProfileCiscoGroupDispType,
    cmFlowPointCpdProfileIslDispType, cmFlowPointCpdProfilePagpDispType,
    cmFlowPointCpdProfileUdldDispType, cmFlowPointCpdProfileCdpDispType,
    cmFlowPointCpdProfileVtpDispType, cmFlowPointCpdProfileDtpDispType,
    cmFlowPointCpdProfilePvstpPlusDispType, cmFlowPointCpdProfileUplinkFastDispType,
    cmFlowPointCpdProfileVlanBridgeDispType, cmFlowPointCpdProfileL2PTDispType,
    cmFlowPointCpdProfileBridgeGroupDispType, cmFlowPointCpdProfileBPDUDispType,
    cmFlowPointCpdProfilePauseDispType, cmFlowPointCpdProfileLACPDispType,
    cmFlowPointCpdProfileLACPMarkerDispType, cmFlowPointCpdProfileEfmOamDispType,
    cmFlowPointCpdProfileSSMDispType, cmFlowPointCpdProfilePortAuthenDispType, 
    cmFlowPointCpdProfileBridgeReservedDispType, cmFlowPointCpdProfileLANBridgesDispType,
    cmFlowPointCpdProfileGARPGroupDispType, cmFlowPointCpdProfileGMRPDispType,
    cmFlowPointCpdProfileGVRPDispType, cmFlowPointCpdProfileGARPDispType,
    cmFlowPointCpdProfileLldpDispType,
    cmFlowPointCpdProfileStorageType,cmFlowPointCpdProfileRowStatus,
    cmFlowPointCpdProfileMac00DispType, cmFlowPointCpdProfileMac01DispType,
    cmFlowPointCpdProfileMac02DispType, cmFlowPointCpdProfileMac03DispType,
    cmFlowPointCpdProfileMac04DispType, cmFlowPointCpdProfileMac05DispType,
    cmFlowPointCpdProfileMac06DispType, cmFlowPointCpdProfileMac07DispType,
    cmFlowPointCpdProfileMac08DispType, cmFlowPointCpdProfileMac09DispType,
    cmFlowPointCpdProfileMac0ADispType, cmFlowPointCpdProfileMac0BDispType,
    cmFlowPointCpdProfileMac0CDispType, cmFlowPointCpdProfileMac0DDispType,
    cmFlowPointCpdProfileMac0EDispType, cmFlowPointCpdProfileMac0FDispType,
    cmFlowPointCpdProfileNearestLLDPDispType, cmFlowPointCpdProfileNonTpmrLLDPDispType,
    cmFlowPointCpdProfileCustomerLLDPDispType, cmFlowPointCpdProfileELMIDispType,
    
    cmEthernetTrafficPortCpdIndex,cmEthernetTrafficPortAssociatedCpdProfile,
    
    cmEthernetFlowPointCpdIndex,cmEthernetFlowPointAssociatedCpdProfile,
    
    cmEthernetTrafficPortIndex,cmEthernetTrafficPortIfIndex,
    cmEthernetTrafficPortEntityIndex,cmEthernetTrafficPortAdminState,
    cmEthernetTrafficPortOperationalState,cmEthernetTrafficPortSecondaryState,
    cmEthernetTrafficPortMTU,cmEthernetTrafficPortMediaType,
    cmEthernetTrafficPortConfigSpeed,cmEthernetTrafficPortNegotiatedSpeed,
    cmEthernetTrafficPortMDIXType,cmEthernetTrafficPortMDIXStatus,
    cmEthernetTrafficPortSfpVendorName,cmEthernetTrafficPortSfpPartNumber,
    cmEthernetTrafficPortSfpSerialNumber,cmEthernetTrafficPortSfpDateOfManufacture,
    cmEthernetTrafficPortSfpConnectorValue,
    cmEthernetTrafficPortSfpLinkLength,cmEthernetTrafficPortSfpLaserWaveLength,
    cmEthernetTrafficPortSfpMediaType,cmEthernetTrafficPortLoopbackConfig,
    cmEthernetTrafficPortLoopbackStatus,cmEthernetTrafficPortLoopbackTime,
    cmEthernetTrafficPortLoopbackSwapSADA,cmEthernetTrafficPortOuterVlanLoopbackMask,
    cmEthernetTrafficPortOuterVlanLoopback1,cmEthernetTrafficPortOuterVlanLoopback2,
    cmEthernetTrafficPortOuterVlanLoopback3,cmEthernetTrafficPortLinkLossFwdEnabled,
    cmEthernetTrafficPortLinkLossFwdSignalType,cmEthernetTrafficPortLinkLossFwdTriggerTypes,
    cmEthernetTrafficPortLinkLossFwdDelay,cmEthernetTrafficPortLinkLossFwdActive,
    cmEthernetTrafficPortLinkLossFwdPartnerEnabled,cmEthernetTrafficPortLinkLossFwdLocalLinkId,
    cmEthernetTrafficPortLinkLossFwdRemoteLinkIds,cmEthernetTrafficPortLinkLossFwdTxActionType,
    cmEthernetTrafficPortLinkLossFwdRxRLDLinkIds,cmEthernetTrafficPortOamId,
    cmEthernetTrafficPortOamDiscoveryState,
    cmEthernetTrafficPortOamLocalVarRtrvsEnabled,cmEthernetTrafficPortOamLocalLinkEventsEnabled,
    cmEthernetTrafficPortOamLocalOamLoopbacksSupported,cmEthernetTrafficPortOamLocalUnidirSupportEnabled,
    cmEthernetTrafficPortOamLocalMaxPDUSize,cmEthernetTrafficPortOamLocalMode,
    cmEthernetTrafficPortOamRemoteMacAddress,cmEthernetTrafficPortOamRemoteVarRtrvsEnabled,
    cmEthernetTrafficPortOamRemoteLinkEventsEnabled,cmEthernetTrafficPortOamRemoteOamLoopbacksSupported,
    cmEthernetTrafficPortOamRemoteUnidirSupportEnabled,cmEthernetTrafficPortOamRemoteMaxPDUSize,
    cmEthernetTrafficPortOamRemoteMode,cmEthernetTrafficPortOamEnabled,
    cmEthernetTrafficPortOamAdminState,
    cmEthernetTrafficPortSvcType,
    cmEthernetTrafficPortTxPauseEnabled,cmEthernetTrafficPortAfpType,
    cmEthernetTrafficPortShapingEnabled,cmEthernetTrafficPortShapedSpeedLo,
    cmEthernetTrafficPortShapedSpeedHi,cmEthernetTrafficPortQinQEtherType,
    cmEthernetTrafficPortEgressVlanTrunkingEnabled,cmEthernetTrafficPortIngressPushPVIDEnabled,
    cmEthernetTrafficPortEgressPopPVIDEnabled,cmEthernetTrafficPortPortVlanId,
    cmEthernetTrafficPortPortVlanPriority,cmEthernetTrafficPortPriorityVlanId,
    cmEthernetTrafficPortIngressPrioMapMode,cmEthernetTrafficPortIngressCOSPriority,
    cmEthernetTrafficPortEgressPopPriorityVidEnabled,
    cmEthernetTrafficPortSyncEEnabled,
    cmEthernetTrafficPortQLModeEnabled,cmEthernetTrafficPortExpectedQL,
    cmEthernetTrafficPortAssumedQL,cmEthernetTrafficPortReceivedQL,
    cmEthernetTrafficPortTransmitQL,cmEthernetTrafficPortTagFrameControl,
    cmEthernetTrafficPortRxPauseEnabled, cmEthernetTrafficPortPhyType,
    cmEthernetTrafficPortSfpLaserWaveLengthPicometer, cmEthernetTrafficPortRowStatus,
    cmEthernetTrafficPortSSMRemoteMacAddress, cmEthernetTrafficPortInnerVlanLoopbackMask,
    cmEthernetTrafficPortInnerVlanLoopback1, cmEthernetTrafficPortInnerVlanLoopback2,
    cmEthernetTrafficPortInnerVlanLoopback3,
    cmEthernetTrafficPortSfpName, cmEthernetTrafficPortSfpHardwareRevision,
    cmEthernetTrafficPortPlugType, cmEthernetTrafficPortPlugMode,
    cmEthernetTrafficPortPlugGMetroAutoTuningMode, cmEthernetTrafficPortPlugChannelType,
    cmEthernetTrafficPortPlugITUCbandChannel, cmEthernetTrafficPortPlugRelativeChannel,
    cmEthernetTrafficPortPlugFrequency, cmEthernetTrafficPortPlugOutOfBandChannelStatus,
    cmEthernetTrafficPortRemotePlugITUCbandChannel, cmEthernetTrafficPortRemotePlugRelativeChannel,
    cmEthernetTrafficPortRemotePlugFrequency, cmEthernetTrafficPortRemoteSfpVendorName,
    cmEthernetTrafficPortRemoteSfpName, cmEthernetTrafficPortRemoteSfpPartNumber,
    cmEthernetTrafficPortRemoteSfpHardwareRevision, cmEthernetTrafficPortRemoteSfpSerialNumber,
    cmEthernetTrafficPortRemoteSfpDateOfManufacture, cmEthernetTrafficPortRemoteSfpLinkLength,
    cmEthernetTrafficPortRemoteSfpLaserWaveLength, cmEthernetTrafficPortRemoteSfpLaserFrequency,
    cmEthernetTrafficPortRemoteSfpMediaType, cmEthernetTrafficPortRemoteSfpConnectorValue,
    cmIngressPrioMapIndex, cmIngressPrioMapInPriority,cmIngressPrioMapCOS,
    
    cmEgressCOSIndex, cmEgressOuterTagCtrl,
    cmEgressCOS,cmEgressOuterTagPriority,
    
    cmElineFlowIndex,cmElineFlowCircuitName,
    cmElineFlowAdminState, cmElineFlowOperationalState,
    cmElineFlowSecondaryState,cmElineFlowFP1,cmElineFlowFP2,
    cmElineFlowStorageType,cmElineFlowRowStatus,
    
    cmFlowPointIndex,cmFlowPointCircuitName,
    cmFlowPointAdminState,cmFlowPointOperationalState,
    cmFlowPointSecondaryState,cmFlowPointAssociatedFlowId,
    cmFlowPointIngressMultiCOS,cmFlowPointIngressCOS,
    cmFlowPointIngressVlanMemberList,cmFlowPointVlanMemberAction,
    cmFlowPointAssociatedAclProfile,cmFlowPointSESFramesLossThresholdRatio,
    cmFlowPointVlanMemberActionVlan,cmFlowPointIngressUntaggedFrameEnabled,
    cmFlowPointCTagControl,cmFlowPointCTagVlanId,
    cmFlowPointCTagVlanPriority,cmFlowPointSTagControl,
    cmFlowPointSTagVlanId,cmFlowPointSTagVlanPriority,
    cmFlowPointEgressOuterTagPrioMapEnabled,cmFlowPointColorMarkingSupported, 
    cmFlowPointStorageType,
    cmFlowPointRowStatus,
    
    cmQosPolicerV2Index,cmQosPolicerV2AdminState,
    cmQosPolicerV2OperationalState,cmQosPolicerV2SecondaryState,
    cmQosPolicerV2ColorMarkingEnabled,cmQosPolicerV2AssociatedProfile,
    cmQosPolicerV2StorageType,cmQosPolicerV2RowStatus,
    
    cmQosShaperV2Index, cmQosShaperV2AdminState,
    cmQosShaperV2OperationalState, cmQosShaperV2SecondaryState,
    cmQosShaperV2AssociatedQueueProfile, 
    cmQosShaperV2CIRLo, cmQosShaperV2CIRHi,
    cmQosShaperV2EIRLo, cmQosShaperV2EIRHi,cmQosShaperV2IngressAverageFrameSize,
    cmQosShaperV2StorageType, cmQosShaperV2RowStatus, 
    cmQosShaperV2AdditionalCIRLo, cmQosShaperV2AdditionalCIRHi,
    cmQosShaperV2ActualCIR, cmQosShaperV2ActualEIR, cmQosShaperV2WFQWeight,
    cmQosShaperV2LowLatencyControl,
    
    cmTrafficPortQosShaperIndex, cmTrafficPortQosShaperAdminState,
    cmTrafficPortQosShaperOperationalState, cmTrafficPortQosShaperSecondaryState,
    cmTrafficPortQosShaperAssociatedQueueProfile, cmTrafficPortQosShaperBufferSize,
    cmTrafficPortQosShaperCIRLo, cmTrafficPortQosShaperCIRHi,
    cmTrafficPortQosShaperEIRLo, cmTrafficPortQosShaperEIRHi,
    cmTrafficPortQosShaperStorageType, cmTrafficPortQosShaperRowStatus, 
    cmTrafficPortQosShaperIngressAverageFrameSize, cmTrafficPortQosShaperAdditionalCIRLo,
    cmTrafficPortQosShaperAdditionalCIRHi, cmTrafficPortQosShaperWfqWeight,
    
    cmQosPolicerProfileIndex,cmQosPolicerProfileName,
    cmQosPolicerProfileCIRLo,cmQosPolicerProfileCIRHi,
    cmQosPolicerProfileEIRLo,cmQosPolicerProfileEIRHi,
    cmQosPolicerProfileCBS,cmQosPolicerProfileEBS,
    cmQosPolicerProfileColorMode,
    cmQosPolicerProfileCouplingFlag,
    cmQosPolicerProfileStorageType,cmQosPolicerProfileRowStatus,

    cmQosQueueProfileIndex,cmQosQueueProfileName,
    cmQosQueueProfileBufferSize,cmQosQueueProfileREDEnabled,
    cmQosQueueProfileStorageType,cmQosQueueProfileRowStatus,
    
    cmOAMFlowPointIndex,cmOAMFlowPointCircuitName,
    cmOAMFlowPointAdminState,cmOAMFlowPointOperationalState,
    cmOAMFlowPointSecondaryState,cmOAMFlowPointIngressVlanMemberList,
    cmOAMFlowPointVlanMemberAction,cmOAMFlowPointIngressUntaggedFrameSupported,
    cmOAMFlowPointSESFramesLossThresholdRatio,
    cmOAMFlowPointStorageType,cmOAMFlowPointRowStatus,

    cmTrafficAclRulesIndex, cmTrafficAclFilterAction,
    cmTrafficAclFilterType,
    cmTrafficAclEnabled, cmTrafficAclSrcMacAddr,
    cmTrafficAclSrcMacAddrEnabled, cmTrafficAclDstMacAddr,
    cmTrafficAclDstMacAddrEnabled, 
    cmTrafficAclSrcIpFilterEnabled, cmTrafficAclDstIpFilterEnabled, 
    cmTrafficAclSrcIpV4Addr, cmTrafficAclSrcIpV4AddrMask,
    cmTrafficAclDstIpV4Addr, cmTrafficAclDstIpV4AddrMask,
    cmTrafficAclSrcIpV6Addr, cmTrafficAclSrcIpV6AddrMask,
    cmTrafficAclDstIpV6Addr, cmTrafficAclDstIpV6AddrMask, 
    cmTrafficAclTcpUdpSrcPortNum, cmTrafficAclTcpUdpSrcPortMask,
    cmTrafficAclTcpUdpSrcPortEnabled, cmTrafficAclTcpUdpDstPortNum,
    cmTrafficAclTcpUdpDstPortMask, cmTrafficAclTcpUdpDstPortEnabled,
    cmTrafficAclIpQosType, cmTrafficAclIpQosValue,
    cmTrafficAclIpQosTypeEnabled, cmTrafficAclVlanId ,
    cmTrafficAclVlanIdEnabled, cmTrafficAclVlanPriority,
    cmTrafficAclVlanPriorityEnabled, cmTrafficAclProtocolType,
    cmTrafficAclProtocolTypeEnabled, cmTrafficAclStorageType,
    cmTrafficAclRowStatus,
    
    f3NetPortQosShaperIndex, f3NetPortQosShaperDirection,
    f3NetPortQosShaperAdminState, f3NetPortQosShaperOperationalState,
    f3NetPortQosShaperSecondaryState, f3NetPortQosShaperCIRLo,
    f3NetPortQosShaperCIRHi, f3NetPortQosShaperEIRLo,
    f3NetPortQosShaperEIRHi, f3NetPortQosShaperCBS,
    f3NetPortQosShaperEBS, f3NetPortQosShaperBufferSize,
    f3NetPortQosShaperCOS, f3NetPortQosShaperSoamCIRLo,
    f3NetPortQosShaperSoamCIRHi, f3NetPortQosShaperSoamEIRLo,
    f3NetPortQosShaperSoamEIRHi,
    
    f3Usb3GDCNPortIndex, f3Usb3GDCNPortIfIndex,
    f3Usb3GDCNPortEntityIndex, f3Usb3GDCNPortAdminState,
    f3Usb3GDCNPortOperationalState, f3Usb3GDCNPortSecondaryState,
    f3Usb3GDCNPortVendorName, f3Usb3GDCNPortModel,
    f3Usb3GDCNPortFSN, f3Usb3GDCNPortIMEI,
    f3Usb3GDCNPortHardwareVersion, f3Usb3GDCNPortFirmwareVersion,
    f3Usb3GDCNPortSIMStatus, f3Usb3GDCNPortPINLeftChances,
    f3Usb3GDCNPortPUKLeftChances, f3Usb3GDCNPortConnectionStatus,
    f3Usb3GDCNPortRSSI, f3Usb3GDCNPortSpeed,
    f3Usb3GDCNPortMTU, f3Usb3GDCNPortProviderName,
    f3Usb3GDCNPortDNS1, f3Usb3GDCNPortDNS2,
    f3Usb3GDCNPortAPN, f3Usb3GDCNPortUserName,
    f3Usb3GDCNPortPassword, f3Usb3GDCNPortDailNumber,
    f3Usb3GDCNPortRedialTimer, f3Usb3GDCNPortCurrentPinCode,
    f3Usb3GDCNPortNewPinCode, f3Usb3GDCNPortConfirmPinCode,
    f3Usb3GDCNPortCurrentPukCode, f3Usb3GDCNPINCodeAction,
    f3Usb3GDCNPortStorageType, f3Usb3GDCNPortRowStatus,
    f3Usb3GDCNPortIMSI, f3Usb3GDCNPortPINStatus, f3UsbDCNPortMobileNetworkType,
    f3Usb3GDCNMuxOperationalMode, f3Usb3GDCNPortIpAddress, f3Usb3GDCNPortNetMask,
    
    ocnStmIndex, ocnStmIfIndex,
    ocnStmEntityIndex, ocnStmAdminState, 
    ocnStmOperationalState, ocnStmSecondaryState, 
    ocnStmSfpVendorName, ocnStmSfpPartNumber, 
    ocnStmSfpSerialNumber, ocnStmSfpDateOfManufacture, 
    ocnStmSfpConnectorValue, ocnStmSfpLinkLength,
    ocnStmSfpLaserWaveLength, ocnStmSfpLaserWaveLengthPicometer,
    ocnStmSfpMediaType, ocnStmMultiplexingStructures, 
    ocnStmEoTDMMode, ocnStmLoopbackConfig, 
    ocnStmLoopbackStatus, ocnStmLoopbackTime, 
    ocnStmInsertingAIS, ocnStmBerExcThreshold, 
    ocnStmBerDegThreshold, ocnStmRxTrailTrace, 
    ocnStmTxTrailTrace, ocnStmExpectedTrailTrace, 
    ocnStmTrailTraceFormat, ocnStmQLModeEnabled, 
    ocnStmExpectedQL, ocnStmAssumedQL, 
    ocnStmReceivedQL, ocnStmTransmitQL,
    ocnStmSfpName,
    ocnStmSfpHardwareRevision,
    
    stsVcPathParentIfIndex, stsVcPathIndex,
    stsVcPathIfIndex, stsVcPathAdminState,
    stsVcPathOperationalState, stsVcPathSecondaryState,
    stsVcPathLoopbackConfig, stsVcPathLoopbackStatus,
    stsVcPathLoopbackTime, stsVcPathInsertingAIS,
    stsVcPathBerExcThreshold, stsVcPathBerDegThreshold,
    stsVcPathTrailTraceFormat, stsVcPathRxTrailTrace,
    stsVcPathTxTrailTrace, stsVcPathExpectedTrailTrace,
    stsVcPathRxSignalLabel, stsVcPathTxSignalLabel,
    stsVcPathExpectedSignalLabel, stsVcPathRowStatus,
    vtVcPathRowStatus,
    
    vtVcPathParentIfIndex, 
    vtVcPathIndex, vtVcPathIfIndex, 
    vtVcPathAdminState, vtVcPathOperationalState, 
    vtVcPathSecondaryState, vtVcPathLoopbackConfig, 
    vtVcPathLoopbackStatus, vtVcPathLoopbackTime, 
    vtVcPathInsertingAIS, vtVcPathBerExcThreshold, 
    vtVcPathBerDegThreshold, vtVcPathTrailTraceFormat, 
    vtVcPathRxTrailTrace, vtVcPathTxTrailTrace, 
    vtVcPathExpectedTrailTrace, vtVcPathRxSignalLabel, 
    vtVcPathTxSignalLabel, vtVcPathExpectedSignalLabel,
    
    e1t1ParentIfIndex, e1t1Index,
    e1t1IfIndex, e1t1AdminState,
    e1t1OperationalState, e1t1SecondaryState,
    e1t1LoopbackConfig, e1t1LoopbackStatus,
    e1t1LoopbackTime, e1t1RemoteLoopbackRequest,
    e1t1InsertingAIS, e1t1RowStatus,

    e3t3ParentIfIndex, e3t3Index,
    e3t3IfIndex, e3t3EntityIndex,
    e3t3AdminState, e3t3OperationalState, 
    e3t3SecondaryState, e3t3LoopbackConfig, 
    e3t3LoopbackStatus, e3t3LoopbackTime, 
    e3t3RemoteLoopbackRequest, e3t3InsertingAIS, 
    e3t3CBitEnable, e3t3T3Channelized, 
    e3t3RowStatus,
    
    cmEthernetTrafficPortTDMEncapsulation, cmEthernetTrafficPortRelatedVCG,
    
    bits8PortGroupIndex, bits8PortGroupIfIndex,
    bits8PortGroupAdminState, bits8PortGroupOperationalState, bits8PortGroupSecondaryState,
    bits8PortGroupLineType, bits8PortGroupLineCode, bits8PortGroupFrameFormat,
    bits8PortGroupSaBitDesignation, bits8PortGroupQLModeEnabled, bits8PortGroupTransmitQL,
    bits8PortGroupSquelchQL, bits8PortGroupLineBuildOut, bits8PortGroupImpedance, 
    bits8PortGroupRowStatus, bits8PortGroupActivePorts, bits8PortGroupClkIfEnabledPorts,
    pps16PortGroupIndex,pps16PortGroupIfIndex,pps16PortGroupAdminState,pps16PortGroupOperationalState,
    pps16PortGroupSecondaryState,pps16PortGroupAlias,pps16PortGroupSquelchControl,pps16PortGroupTODSource,
    pps16PortGroupDirection, pps16PortGroupDelayCompensation,pps16PortGroupRowStatus,
    --pps16PortGroupOutputType 
    
    clk16PortGroupIndex,clk16PortGroupIfIndex, clk16PortGroupAdminState, clk16PortGroupOperationalState, 
    clk16PortGroupSecondaryState, clk16PortGroupAlias,clk16PortGroupDirection,clk16PortGroupSquelchControl,   
    clk16PortGroupSquelchQL,clk16PortGroupRowStatus,  

    todPps16PortGroupIndex,todPps16PortGroupIfIndex,todPps16PortGroupAdminState ,  todPps16PortGroupOperationalState,
    todPps16PortGroupSecondaryState,todPps16PortGroupAlias , todPps16PortGroupSquelchControl, todPps16PortGroupSquelchQL,     
    todPps16PortGroupTODSource,todPps16PortGroupOutputFormat, todPps16PortGroupDelayCompensation,todPps16PortGroupRowStatus,


        -- f3IrigRs422OutputPortTable columns
    f3IrigRs422OutputPortIndex, f3IrigRs422OutputPortIfIndex, f3IrigRs422OutputPortEntityIndex,
    f3IrigRs422OutputPortAlias, f3IrigRs422OutputPortAdminState, f3IrigRs422OutputPortOperationalState,
    f3IrigRs422OutputPortSecondaryState, f3IrigRs422OutputPortTimeCode, f3IrigRs422OutputPortControlField,
    -- f3IrigOpticalOutputPortTable columns
    f3IrigOpticalOutputPortIndex, f3IrigOpticalOutputPortIfIndex, f3IrigOpticalOutputPortEntityIndex,
    f3IrigOpticalOutputPortAlias, f3IrigOpticalOutputPortAdminState, f3IrigOpticalOutputPortOperationalState,
    f3IrigOpticalOutputPortSecondaryState, f3IrigOpticalOutputPortTimeCode, f3IrigOpticalOutputPortControlField,
    -- f3IrigRelayOutputPortTable columns
    f3IrigRelayOutputPortIndex, f3IrigRelayOutputPortIfIndex, f3IrigRelayOutputPortEntityIndex,
    f3IrigRelayOutputPortAlias, f3IrigRelayOutputPortAdminState, f3IrigRelayOutputPortOperationalState,
    f3IrigRelayOutputPortSecondaryState, f3IrigRelayOutputPortRelayOperation,
    -- f3IrigOutputGroupTable columns
    f3IrigOutputGroupIndex, f3IrigOutputGroupIfIndex, f3IrigOutputGroupEntityIndex, f3IrigOutputGroupAlias, f3IrigOutputGroupExtensionType, 
    f3IrigOutputGroupExtensionDetection,
    -- f3IrigOutputUnitPortTable columns
    f3IrigOutputUnitPortIndex, f3IrigOutputUnitPortIfIndex, f3IrigOutputUnitPortEntityIndex,
    f3IrigOutputUnitPortAlias, f3IrigOutputUnitPortAdminState, f3IrigOutputUnitPortOperationalState,
    f3IrigOutputUnitPortSecondaryState, f3IrigOutputUnitPortTimeCode, f3IrigOutputUnitPortControlField,
    f3IrigOutputUnitPortType, f3IrigOutputUnitPortDigitalVoltage,



    ccInputPortIndex, ccInputPortIfIndex, ccInputPortEntityIndex, ccInputPortAlias,
    ccInputPortAdminState, ccInputPortOperationalState, ccInputPortSecondaryState,

    ccGroupIndex, ccGroupIfIndex, ccGroupEntityIndex, ccGroupAlias,
    ccGroupActivePorts, ccGroupPhaseAdjust, ccGroupDutyCycle
                      
    }
    STATUS  deprecated
    DESCRIPTION
            "*********************THIS GROUP IS NOW DEPRECATED *********************
             A collection of objects used to manage the CM Facility
             group."
    ::= { cmFacilityGroups 1 }

ethernetAccessPortGroup OBJECT-GROUP
    OBJECTS {
        cmEthernetAccPortIndex, cmEthernetAccPortIfIndex,
        cmEthernetAccPortOperationalState, cmEthernetAccPortSecondaryState,
        cmEthernetAccPortMTU, cmEthernetAccPortMediaType,
        cmEthernetAccPortConfigSpeed, cmEthernetAccPortNegotiatedSpeed,
        cmEthernetAccPortMDIXType,
        cmEthernetAccPortJumboFramesEnabled, cmEthernetAccPortSfpVendorName,
        cmEthernetAccPortSfpPartNumber, cmEthernetAccPortSfpSerialNumber,
        cmEthernetAccPortSfpDateOfManufacture,
        cmEthernetAccPortSfpConnectorValue,
        cmEthernetAccPortInitiateDiag, cmEthernetAccPortDiagnosePair1Cond,
        cmEthernetAccPortDiagnosePair2Cond, cmEthernetAccPortDiagnosePair3Cond,
        cmEthernetAccPortDiagnosePair4Cond, cmEthernetAccPortDiagnoseAutoNegCond,
        cmEthernetAccPortDiagnoseLpbkCond, cmEthernetAccPortDiagnoseEfmLpbkCond,
        cmEthernetAccPortDiagnoseResult,cmEthernetAccPortDiagnoseTestStatus,
        cmEthernetAccPortDiagnoseTestTime,
        cmEthernetAccPortLoopbackConfig, cmEthernetAccPortLoopbackStatus,
        cmEthernetAccPortLoopbackTime,
        cmEthernetAccPortLoopbackSwapSADA, cmEthernetAccPortOuterVlanLoopbackMask,
        cmEthernetAccPortOuterVlanLoopback1, cmEthernetAccPortOuterVlanLoopback2,
        cmEthernetAccPortOuterVlanLoopback3, 
        cmEthernetAccPortInnerVlanLoopbackMask,
        cmEthernetAccPortInnerVlanLoopback1, cmEthernetAccPortInnerVlanLoopback2,
        cmEthernetAccPortInnerVlanLoopback3,
        cmEthernetAccPortLinkLossFwdEnabled, 
        cmEthernetAccPortLinkLossFwdSignalType,
        cmEthernetAccPortLinkLossFwdTriggerTypes,
        cmEthernetAccPortLinkLossFwdDelay, cmEthernetAccPortLinkLossFwdActive,
        cmEthernetAccPortLinkLossFwdPartnerEnabled,
        cmEthernetAccPortLinkLossFwdLocalLinkId,
        cmEthernetAccPortLinkLossFwdRemoteLinkIds,
        cmEthernetAccPortOamId, cmEthernetAccPortOamAdminDisposition,
        cmEthernetAccPortOamDiscoveryState, 
        cmEthernetAccPortOamLocalVarRtrvsEnabled,
        cmEthernetAccPortOamLocalLinkEventsEnabled,
        cmEthernetAccPortOamLocalOamLoopbacksSupported,
        cmEthernetAccPortOamLocalUnidirSupportEnabled,
        cmEthernetAccPortOamLocalMaxPDUSize, cmEthernetAccPortOamLocalMode,
        cmEthernetAccPortOamRemoteMacAddress, 
        cmEthernetAccPortOamRemoteVarRtrvsEnabled,
        cmEthernetAccPortOamRemoteLinkEventsEnabled,
        cmEthernetAccPortOamRemoteOamLoopbacksSupported,
        cmEthernetAccPortOamRemoteUnidirSupportEnabled,
        cmEthernetAccPortOamRemoteMaxPDUSize,
        cmEthernetAccPortOamRemoteMode, cmEthernetAccPortMode, 
        cmEthernetAccPortSvcType, cmEthernetAccPortRxPauseDisposition, 
        cmEthernetAccPortTxPauseEnabled, cmEthernetAccPortAfpType,

        cmEthernetAccPortMDIXStatus, cmEthernetAccPortSfpReach,
        cmEthernetAccPortSfpLaserWaveLength,
        cmEthernetAccPortSfpMediaType, cmEthernetAccPortOamEnabled,
        cmEthernetAccPortOamAdminState,
        cmEthernetAccPortShapingEnabled,
        cmEthernetAccPortShapedSpeedLo, cmEthernetAccPortShapedSpeedHi,
        cmEthernetAccPortQinQEtherType, cmEthernetAccPortRxPauseEnabled,
        cmEthernetAccPortAutoDiagEnabled, cmEthernetAccPortLinkLossFwdTxActionType,
        cmEthernetAccPortLinkLossFwdRxRLDLinkIds,
        cmEthernetAccPortN2AVlanTrunkingEnabled, 
        cmEthernetAccPortA2NPushPVIDEnabled,
        cmEthernetAccPortN2APopPVIDEnabled, cmEthernetAccPortPortVlanId,
        cmEthernetAccPortPortVlanPriority,
        cmEthernetAccPortPrioMapMode, cmEthernetAccPortSyncEEnabled,
        cmEthernetAccPortQLModeEnabled, cmEthernetAccPortExpectedQL,
        cmEthernetAccPortAssumedQL, cmEthernetAccPortReceivedQL, 
        cmEthernetAccPortTransmitQL,cmEthernetAccPortDeiEnable,
        cmEthernetAccPortPcpDEEncType,cmEthernetAccPortPcpDEPairsAction,
        cmEthernetAccPortClbIndex, cmEthernetAccPortClbEnabled,
        cmEthernetAccPortClbLength, cmEthernetAccPortClbDescr,
        cmEthernetAccPortSSMRemoteMacAddress, cmEthernetAccPortXgePhyType,
        cmEthernetAccPortLoopbackSourceMacControlEnabled, cmEthernetAccPortLoopbackDestMacControlEnabled,
        cmEthernetAccPortLoopbackSourceMacAddress, cmEthernetAccPortLoopbackDestMacAddress,
        cmEthernetAccPortLoopbackBlockingEnabled, 
        cmEthernetAccPortRxDeiAction, cmEthernetAccPortTxDeiAction,
        cmEthernetAccPortRxDeiOuterTagType, cmEthernetAccPortTxDeiOuterTagType,
        cmEthernetAccPortLaserWDMChannel, cmEthernetAccPortLaserIsTunable, cmEthernetAccPortLaserFrequency,
        cmEthernetAccPortMediaTypeAutoSelected, cmEthernetAccPortLowLatencyQueuingEnabled,
        cmEthernetAccPortA2nSwapPriorityVIDEnabled, cmEthernetAccPortN2aSwapPriorityVIDEnabled,
        cmEthernetAccPortSwapPriorityVID, cmEthernetAccPortDiagnosticMacAddress,
        cmEthernetAccPortIngressCOSPriority, cmEthernetAccPortDefaultCOS, cmEthernetAccPortTrafficModel,
        
        cmEthernetAccPortIndependentShaperBW,
        cmEthernetAccPortJdsuLoopbackSrcIp,
        cmEthernetAccPortWfqSegmentationCOS,
        cmEthernetAccPortWfqGroupCOS,
        cmEthernetAccPortWfqGroupEirLo,
        cmEthernetAccPortWfqGroupEirHi,
        cmEthernetAccPortSilentStartControl,
        cmEthernetAccPortSfpLinkLength,
        cmEthernetAccPortOuterTagTpidOverride, 
        cmEthernetAccPortOuterTagTpid,

        cmEthernetAccPortSfpName,
        cmEthernetAccPortSfpHardwareRevision,
        cmEthernetAccPortPersistentLoopbackControl,
        cmEthernetAccPortLoopbackTestReflectorIPv4AddressControl,
        cmEthernetAccPortLoopbackTestReflectorIPv4Address,
        cmEthernetAccPortLoopbackTestReflectorIPv6AddressControl,
        cmEthernetAccPortLoopbackTestReflectorIPv6Address,
        cmEthernetAccPortPowerdDeviceDetection,
        cmEthernetAccPortPoEStatus,
        cmEthernetAccPortSfpIdentifierValue
    }
    STATUS  current
    DESCRIPTION
            "A collection of objects used to manage the F3 Ethernet Access Port 
             function."
    ::= { cmFacilityGroups 2 }

ethernetNetworkPortGroup OBJECT-GROUP
    OBJECTS {
        cmEthernetNetPortIndex, cmEthernetNetPortIfIndex,
        cmEthernetNetPortEntityIndex, cmEthernetNetPortAdminState,
        cmEthernetNetPortOperationalState, cmEthernetNetPortSecondaryState,
        cmEthernetNetPortMTU, cmEthernetNetPortMediaType,
        cmEthernetNetPortConfigSpeed, cmEthernetNetPortNegotiatedSpeed,
        cmEthernetNetPortMDIXType,
        cmEthernetNetPortJumboFramesEnabled, cmEthernetNetPortSfpVendorName,
        cmEthernetNetPortSfpPartNumber, cmEthernetNetPortSfpSerialNumber,
        cmEthernetNetPortSfpDateOfManufacture, cmEthernetNetPortSfpConnectorValue,
        cmEthernetNetPortInitiateDiag, cmEthernetNetPortDiagnosePair1Cond,
        cmEthernetNetPortDiagnosePair2Cond, cmEthernetNetPortDiagnosePair3Cond,
        cmEthernetNetPortDiagnosePair4Cond, cmEthernetNetPortDiagnoseAutoNegCond,
        cmEthernetNetPortDiagnoseLpbkCond, cmEthernetNetPortDiagnoseEfmLpbkCond,
        cmEthernetNetPortDiagnoseResult,cmEthernetNetPortDiagnoseTestStatus,
        cmEthernetNetPortDiagnoseTestTime,
        cmEthernetNetPortLoopbackConfig, cmEthernetNetPortLoopbackStatus,
        cmEthernetNetPortLoopbackTime,
        cmEthernetNetPortLoopbackSwapSADA, cmEthernetNetPortOuterVlanLoopbackMask,
        cmEthernetNetPortOuterVlanLoopback1, cmEthernetNetPortOuterVlanLoopback2,
        cmEthernetNetPortOuterVlanLoopback3, 
        cmEthernetNetPortInnerVlanLoopbackMask,
        cmEthernetNetPortInnerVlanLoopback1, cmEthernetNetPortInnerVlanLoopback2, 
        cmEthernetNetPortInnerVlanLoopback3,
        cmEthernetNetPortLinkLossFwdEnabled, cmEthernetNetPortLinkLossFwdSignalType,
        cmEthernetNetPortLinkLossFwdTriggerTypes,cmEthernetNetPortLinkLossFwdDelay,
        cmEthernetNetPortLinkLossFwdActive, 
        cmEthernetNetPortLinkLossFwdPartnerEnabled,
        cmEthernetNetPortLinkLossFwdLocalLinkId, 
        cmEthernetNetPortLinkLossFwdRemoteLinkIds,
        cmEthernetNetPortOamId, cmEthernetNetPortOamAdminDisposition,
        cmEthernetNetPortOamDiscoveryState,
        cmEthernetNetPortOamLocalVarRtrvsEnabled, 
        cmEthernetNetPortOamLocalLinkEventsEnabled,
        cmEthernetNetPortOamLocalOamLoopbacksSupported,
        cmEthernetNetPortOamLocalUnidirSupportEnabled,
        cmEthernetNetPortOamLocalMaxPDUSize,
        cmEthernetNetPortOamLocalMode, cmEthernetNetPortOamRemoteMacAddress,
        cmEthernetNetPortOamRemoteVarRtrvsEnabled,
        cmEthernetNetPortOamRemoteLinkEventsEnabled,
        cmEthernetNetPortOamRemoteOamLoopbacksSupported,
        cmEthernetNetPortOamRemoteUnidirSupportEnabled,
        cmEthernetNetPortOamRemoteMaxPDUSize, cmEthernetNetPortOamRemoteMode,
        cmEthernetNetPortRxPauseDisposition, cmEthernetNetPortTxPauseEnabled,
        cmEthernetNetPortAfpType,
    
        cmEthernetNetPortMDIXStatus, cmEthernetNetPortSfpReach,
        cmEthernetNetPortSfpLaserWaveLength,
        cmEthernetNetPortSfpMediaType, cmEthernetNetPortOamEnabled,
        cmEthernetNetPortOamAdminState,
        cmEthernetNetPortShapingEnabled,
        cmEthernetNetPortShapedSpeedLo, cmEthernetNetPortShapedSpeedHi,
        cmEthernetNetPortQinQEtherType, cmEthernetNetPortLinkLossFwdTxActionType,
        cmEthernetNetPortLinkLossFwdRxRLDLinkIds,
        cmEthernetNetPortAutoDiagEnabled,
        cmEthernetNetPortSyncEEnabled, cmEthernetNetPortQLModeEnabled,
        cmEthernetNetPortExpectedQL, cmEthernetNetPortAssumedQL,
        cmEthernetNetPortReceivedQL, cmEthernetNetPortTransmitQL,
        cmEthernetNetPortDeiEnable, cmEthernetNetPortPcpDEEncType,
        cmEthernetNetPortPcpDEPairsAction,cmEthernetNetPortClbIndex, 
        cmEthernetNetPortClbEnabled, cmEthernetNetPortClbLength, 
        cmEthernetNetPortClbDescr, cmEthernetNetPortSSMRemoteMacAddress, 
        cmEthernetNetPortXgePhyType, cmEthernetNetPortLoopbackSourceMacControlEnabled, 
        cmEthernetNetPortLoopbackDestMacControlEnabled, cmEthernetNetPortLoopbackSourceMacAddress, 
        cmEthernetNetPortLoopbackDestMacAddress, cmEthernetNetPortLoopbackBlockingEnabled,
        cmEthernetNetPortRxDeiAction, cmEthernetNetPortTxDeiAction,
        cmEthernetNetPortRxDeiOuterTagType, cmEthernetNetPortTxDeiOuterTagType,
        cmEthernetNetPortLaserWDMChannel, cmEthernetNetPortLaserIsTunable,
        cmEthernetNetPortLaserFrequency, cmEthernetNetPortMediaTypeAutoSelected, 
        cmEthernetNetPortLowLatencyQueuingEnabled, cmEthernetNetPortDiagnosticMacAddress,
        cmEthernetNetPortIngressCOSPriority, cmEthernetNetPortDefaultCOS, cmEthernetNetPortTrafficModel,
        
        cmEthernetNetPortIndependentShaperBW,
        cmEthernetNetPortExpDEEncType,
        cmEthernetNetPortExpDEPairsAction,
        cmEthernetNetPortIpPrecDEEncType,
        cmEthernetNetPortIpPrecDEPairsAction,
        cmEthernetNetPortEncapPcpDEEncodingType,
        cmEthernetNetPortEncapPcpDEPairsAction,
        cmEthernetNetPortJdsuLoopbackSrcIp,
        cmEthernetNetPortWfqSegmentationCOS,
        cmEthernetNetPortWfqGroupCOS,
        cmEthernetNetPortWfqGroupEirLo,
        cmEthernetNetPortWfqGroupEirHi,
        cmEthernetNetPortSilentStartControl,
        cmEthernetNetPortSfpLinkLength,
        cmEthernetNetPortOuterTagTpidOverride,
        cmEthernetNetPortOuterTagTpid,

        cmEthernetNetPortSfpName,
        cmEthernetNetPortSfpHardwareRevision,
        cmEthernetNetPortPersistentLoopbackControl,
        cmEthernetNetPortLoopbackTestReflectorIPv4AddressControl,
        cmEthernetNetPortLoopbackTestReflectorIPv4Address,
        cmEthernetNetPortLoopbackTestReflectorIPv6AddressControl,
        cmEthernetNetPortLoopbackTestReflectorIPv6Address,
        cmEthernetNetPortSfpIdentifierValue
    }
    STATUS  current
    DESCRIPTION
            " A collection of objects used to manage the F3 Ethernet Network Port 
              function."
    ::= { cmFacilityGroups 3 }

ethernetMgmtPortGroup OBJECT-GROUP
    OBJECTS {
        cmEthernetMgmtPortIndex, cmEthernetMgmtPortEntityIndex,
        cmEthernetMgmtPortAdminState, cmEthernetMgmtPortOperationalState,
        cmEthernetMgmtPortSecondaryState, cmEthernetMgmtPortMTU,
        cmEthernetMgmtPortConfigSpeed, cmEthernetMgmtPortNegotiatedSpeed,
        cmEthernetMgmtPortMDIXType,
        cmEthernetMgmtPortMDIXStatus,
        cmEthernetMgmtPortMediaType 
    }
    STATUS  current
    DESCRIPTION
            "A collection of objects used to manage the F3 Ethernet Management Port
             function."
    ::= { cmFacilityGroups 4 }

bitsPortGroup OBJECT-GROUP
    OBJECTS {
        bitsPortTypeIndex, bitsPortIndex, bitsPortIfIndex, bitsPortEntityIndex,
        bitsPortAdminState, bitsPortOperationalState, bitsPortSecondaryState,
        bitsPortType, bitsPortLineType, bitsPortLineCode, bitsPortFrameFormat,
        bitsPortSaBitDesignation, bitsPortQLModeEnabled, bitsPortExpectedQL,
        bitsPortAssumedQL, bitsPortReceivedQL, bitsPortTransmitQL,
        bitsPortSquelchQL, bitsPortLineBuildOut
    }
    STATUS  current
    DESCRIPTION
            "A collection of objects used to manage the F3 Bits Port 
             function."
    ::= { cmFacilityGroups 5 }

trafficGroup OBJECT-GROUP
    OBJECTS {
        cmFlowIndex, cmFlowCircuitName, cmFlowAdminState,
        cmFlowOperationalState, cmFlowSecondaryState,
        cmFlowType, cmFlowMultiCOS, cmFlowA2NCIR,
        cmFlowA2NEIR, cmFlowN2ARateLimitingEnabled,
        cmFlowN2ACIR, cmFlowN2AEIR, cmFlowStorageType, cmFlowRowStatus,
    
        cmFlowTrafficType, cmFlowCOS, cmFlowVlanMemberList,
        cmFlowAction, cmFlowActionVlan, cmFlowUntaggedMemberEnabled,
        cmFlowA2NCIRHi, cmFlowA2NEIRHi,
        cmFlowN2ACIRHi, cmFlowN2AEIRHi, 
        cmFlowHCOSMgmtEnabled, cmFlowGuaranteedA2NBandwidthLo,
        cmFlowGuaranteedA2NBandwidthHi, cmFlowMaximumA2NBandwidthLo,
        cmFlowMaximumA2NBandwidthHi, cmFlowCTagControl,
        cmFlowCTagVlanId, cmFlowCTagVlanPriority, cmFlowCTagMatchRxPrio,
        cmFlowSTagControl, cmFlowSTagVlanId, cmFlowSTagVlanPriority,
        cmFlowOuterTagPrioEnabled, cmFlowN2ACOSPriorityTagType,
        cmFlowESFramesLossThreshold, cmFlowSESFramesLossThresholdRatio, 
        cmFlowPolicingEnabled, cmFlowPreserveSTagProperties, cmFlowInnerTagPrioEnabled,
        cmFlowA2NShapingType, cmFlowN2AShapingType,
        cmFlowN2AOuterTagPrioEnabled, cmFlowSTagMatchRxPrio, 
        cmFlowAutoBandwidthConfigEnabled,
        cmFlowPort1, cmFlowPort2,
        cmFlowPolicingControl,
        cmFlowAutoCIRPercentage,
        cmFlowLoopAvoidanceObject,
        cmFlowConfigType,
        cmFlowN2NForwardingEnabled,
        cmFlowA2NMulticastRateLimitControl, cmFlowA2NMulticastRateLimitLo, cmFlowA2NMulticastRateLimitHi,
        cmFlowA2NBroadcastRateLimitControl, cmFlowA2NBroadcastRateLimitLo, cmFlowA2NBroadcastRateLimitHi,
        cmFlowA2NCombinedRateLimitControl,  cmFlowA2NCombinedRateLimitLo,  cmFlowA2NCombinedRateLimitHi,
        
        cmFlowRefPrioMapProfile,
        cmFlowRefEoMplsPwObject,
        cmFlowRefN2APrioMapProfile,
        cmFlowSecureBlockingEnabled,
        cmFlowRefConnectGuardFlowList,
        cmFlowSecureStateList,
        cmFlowIndependentA2NShaperBW,
        cmFlowWfqSegmentationCOS,
        cmFlowWfqGroupCOS,
        cmFlowWfqGroupEirLo,
        cmFlowWfqGroupEirHi,

        cmQosShaperTypeIndex, cmQosShaperIndex, cmQosShaperDirection,
        cmQosShaperAdminState, cmQosShaperOperationalState,cmQosShaperSecondaryState,
        cmQosShaperCIR, cmQosShaperCBS, cmQosShaperEIR, cmQosShaperEBS,
        cmQosShaperBufferSize, cmQosShaperStorageType,
        cmQosShaperRowStatus, cmQosShaperSoamCIRLo, cmQosShaperSoamCIRHi,
        cmQosShaperSoamEIRLo, cmQosShaperSoamEIRHi, 
        cmQosShaperWredGreenMinQueueThreshold,
        cmQosShaperWredGreenMaxQueueThreshold,
        cmQosShaperWredGreenDropProbability,
        cmQosShaperWredYellowMinQueueThreshold,
        cmQosShaperWredYellowMaxQueueThreshold,
        cmQosShaperWredYellowDropProbability,
        cmQosShaperAvgFrameSizeBeforeFragment, 
        cmQosShaperWfqWeight,
    
        cmQosShaperCOS, cmQosShaperCIRHi, cmQosShaperEIRHi,
    
        cmQosFlowPolicerTypeIndex, cmQosFlowPolicerIndex,
        cmQosFlowPolicerDirection, cmQosFlowPolicerAdminState, 
        cmQosFlowPolicerOperationalState,
        cmQosFlowPolicerSecondaryState,
        cmQosFlowPolicerCIRLo, cmQosFlowPolicerCIRHi, cmQosFlowPolicerEIRLo,
        cmQosFlowPolicerEIRHi, cmQosFlowPolicerCBS,
        cmQosFlowPolicerEBS, cmQosFlowPolicerAlgorithm,
        cmQosFlowPolicerColorMode, cmQosFlowPolicerColorMarkingFlag,
        cmQosFlowPolicerCouplingFlag, cmQosFlowPolicerAssociatedShaper,
        cmQosFlowPolicerStorageType, cmQosFlowPolicerRowStatus,
        
        cmQosFlowPolicerCIRMaxHi,
        cmQosFlowPolicerCIRMaxLo,
        cmQosFlowPolicerEIRMaxHi,
        cmQosFlowPolicerEIRMaxLo,
        cmQosFlowPolicerEnvelopeObject,
        cmQosFlowPolicerRank,
        cmQosFlowPolicerPolicingEnabled,
    
        cmAccPortQosShaperIndex, cmAccPortQosShaperDirection,
        cmAccPortQosShaperAdminState, cmAccPortQosShaperOperationalState,
        cmAccPortQosShaperSecondaryState, cmAccPortQosShaperCIRLo,
        cmAccPortQosShaperCIRHi, cmAccPortQosShaperEIRLo,
        cmAccPortQosShaperEIRHi, cmAccPortQosShaperCBS,
        cmAccPortQosShaperEBS, cmAccPortQosShaperBufferSize, cmAccPortQosShaperCOS,
        cmAccPortQosShaperSoamCIRLo, cmAccPortQosShaperSoamCIRHi,
        cmAccPortQosShaperSoamEIRLo, cmAccPortQosShaperSoamEIRHi,
        
        
        cmAccPortQosShaperWredGreenMinQueueThreshold,
        cmAccPortQosShaperWredGreenMaxQueueThreshold,
        cmAccPortQosShaperWredGreenDropProbability,
        cmAccPortQosShaperWredYellowMinQueueThreshold,
        cmAccPortQosShaperWredYellowMaxQueueThreshold,
        cmAccPortQosShaperWredYellowDropProbability,
        cmAccPortQosShaperAvgFrameSizeBeforeFragment,
        cmAccPortQosShaperWfqWeight,
        
        f3NetPortQosShaperIndex, f3NetPortQosShaperDirection,
        f3NetPortQosShaperAdminState, f3NetPortQosShaperOperationalState,
        f3NetPortQosShaperSecondaryState, f3NetPortQosShaperCIRLo,
        f3NetPortQosShaperCIRHi, f3NetPortQosShaperEIRLo,
        f3NetPortQosShaperEIRHi, f3NetPortQosShaperCBS,
        f3NetPortQosShaperEBS, f3NetPortQosShaperBufferSize,
        f3NetPortQosShaperCOS, f3NetPortQosShaperSoamCIRLo,
        f3NetPortQosShaperSoamCIRHi, f3NetPortQosShaperSoamEIRLo,
        f3NetPortQosShaperSoamEIRHi,
        f3NetPortQosShaperWredGreenMinQueueThreshold,
        f3NetPortQosShaperWredGreenMaxQueueThreshold,
        f3NetPortQosShaperWredGreenDropProbability,
        f3NetPortQosShaperWredYellowMinQueueThreshold,
        f3NetPortQosShaperWredYellowMaxQueueThreshold,
        f3NetPortQosShaperWredYellowDropProbability,
        f3NetPortQosShaperAvgFrameSizeBeforeFragment,
        f3NetPortQosShaperWfqWeight
    }
    STATUS  current
    DESCRIPTION
            "A collection of objects used to manage the F3 traffic path, consists of
             Flows, Policers and Shapers." 
    ::= { cmFacilityGroups 6 }

prioMapGroup OBJECT-GROUP
    OBJECTS {
        cmPrioMapIndex, cmPrioMapInPriority, cmPrioMapXTagControl,
        cmPrioMapXTagPriority, cmPrioMapCOS, cmPrioMapOuterTagPriority,
        cmPrioMapInnerTagPriority,
    
        cmNetPortPrioMapIndex, cmNetPortPrioMapInPriority,
        cmNetPortPrioMapCOS, cmNetPortPrioMapOuterTagPriority
    }
    STATUS  current
    DESCRIPTION
            "A collection of objects used to manage the F3 Priority Mapping function." 
    ::= { cmFacilityGroups 7 }

pcpEncodeGroup OBJECT-GROUP
    OBJECTS {
        cmAccPortPcpDEEncIndex, cmAccPortPcpDEEncInPriority,
        cmAccPortPcpDEEncDropIneligiblePrio, cmAccPortPcpDEEncDropEligiblePrio,
        cmAccPortPcpDEDecIndex, cmAccPortPcpDEDecInPriority,
        cmAccPortPcpDEDecOutPriority, cmAccPortPcpDEDecDropEligible,
        cmAccPortPcpDEPairIndex, cmAccPortPcpDEDropIneligiblePrio,
        cmAccPortPcpDEDropEligiblePrio,
    
        cmNetPortPcpDEEncIndex, cmNetPortPcpDEEncInPriority,
        cmNetPortPcpDEEncDropIneligiblePrio, cmNetPortPcpDEEncDropEligiblePrio,
        cmNetPortPcpDEDecIndex, cmNetPortPcpDEDecInPriority,
        cmNetPortPcpDEDecOutPriority, cmNetPortPcpDEDecDropEligible,
        cmNetPortPcpDEPairIndex, cmNetPortPcpDEDropIneligiblePrio,
        cmNetPortPcpDEDropEligiblePrio
    }
    STATUS  current
    DESCRIPTION
            "A collection of objects used to manage the F3 Priority Mapping function." 
    ::= { cmFacilityGroups 8 }

cpdV2Group OBJECT-GROUP
    OBJECTS {
    cmEthernetAccPortCpdV2Index, cmEthernetAccPortCpdV2CiscoGroupDispType,
    cmEthernetAccPortCpdV2IslDispType, cmEthernetAccPortCpdV2PagpDispType,
    cmEthernetAccPortCpdV2UdldDispType, cmEthernetAccPortCpdV2CdpDispType,
    cmEthernetAccPortCpdV2VtpDispType, cmEthernetAccPortCpdV2DtpDispType,
    cmEthernetAccPortCpdV2PvstpPlusDispType, 
    cmEthernetAccPortCpdV2UplinkFastDispType,
    cmEthernetAccPortCpdV2VlanBridgeDispType,
    cmEthernetAccPortCpdV2L2PTDispType, 
    cmEthernetAccPortCpdV2BridgeGroupDispType,
    cmEthernetAccPortCpdV2BPDUDispType, cmEthernetAccPortCpdV2PauseDispType,
    cmEthernetAccPortCpdV2LACPDispType,
    cmEthernetAccPortCpdV2LACPMarkerDispType,
    cmEthernetAccPortCpdV2EfmOamDispType,
    cmEthernetAccPortCpdV2SSMDispType,
    cmEthernetAccPortCpdV2PortAuthenDispType,
    cmEthernetAccPortCpdV2BridgeReservedDispType,
    cmEthernetAccPortCpdV2LANBridgesDispType,
    cmEthernetAccPortCpdV2GARPGroupDispType,
    cmEthernetAccPortCpdV2GMRPDispType, cmEthernetAccPortCpdV2GVRPDispType,
    cmEthernetAccPortCpdV2GARPDispType,
    cmEthernetAccPortCpdV2Mac00DispType, cmEthernetAccPortCpdV2Mac01DispType,
    cmEthernetAccPortCpdV2Mac02DispType, cmEthernetAccPortCpdV2Mac03DispType,
    cmEthernetAccPortCpdV2Mac04DispType, cmEthernetAccPortCpdV2Mac05DispType,
    cmEthernetAccPortCpdV2Mac06DispType, cmEthernetAccPortCpdV2Mac07DispType,
    cmEthernetAccPortCpdV2Mac08DispType, cmEthernetAccPortCpdV2Mac09DispType,
    cmEthernetAccPortCpdV2Mac0ADispType, cmEthernetAccPortCpdV2Mac0BDispType,
    cmEthernetAccPortCpdV2Mac0CDispType, cmEthernetAccPortCpdV2Mac0DDispType,
    cmEthernetAccPortCpdV2Mac0EDispType, cmEthernetAccPortCpdV2Mac0FDispType,
    cmEthernetAccPortCpdV2NearestLLDPDispType, cmEthernetAccPortCpdV2NonTpmrLLDPDispType,
    cmEthernetAccPortCpdV2CustomerLLDPDispType, cmEthernetAccPortCpdV2PtpUntaggedDispType,
    cmEthernetAccPortCpdV2PtpTaggedDispType,

    cmFlowCpdV2Index, cmFlowCpdV2CiscoGroupDispType,
    cmFlowCpdV2IslDispType, cmFlowCpdV2PagpDispType,
    cmFlowCpdV2UdldDispType, cmFlowCpdV2CdpDispType,
    cmFlowCpdV2VtpDispType, cmFlowCpdV2DtpDispType,
    cmFlowCpdV2PvstpPlusDispType, 
    cmFlowCpdV2UplinkFastDispType,
    cmFlowCpdV2VlanBridgeDispType,
    cmFlowCpdV2L2PTDispType, 
    cmFlowCpdV2BridgeGroupDispType,
    cmFlowCpdV2BPDUDispType, cmFlowCpdV2PauseDispType,
    cmFlowCpdV2LACPDispType,
    cmFlowCpdV2LACPMarkerDispType,
    cmFlowCpdV2EfmOamDispType,
    cmFlowCpdV2SSMDispType,            
    cmFlowCpdV2PortAuthenDispType,
    cmFlowCpdV2BridgeReservedDispType,
    cmFlowCpdV2LANBridgesDispType,
    cmFlowCpdV2GARPGroupDispType,
    cmFlowCpdV2GMRPDispType, cmFlowCpdV2GVRPDispType, cmFlowCpdV2GARPDispType,
    cmFlowCpdV2ActiveControlProtocols, 
    cmFlowCpdV2Mac00DispType, cmFlowCpdV2Mac01DispType,
    cmFlowCpdV2Mac02DispType, cmFlowCpdV2Mac03DispType,
    cmFlowCpdV2Mac04DispType, cmFlowCpdV2Mac05DispType,
    cmFlowCpdV2Mac06DispType, cmFlowCpdV2Mac07DispType,
    cmFlowCpdV2Mac08DispType, cmFlowCpdV2Mac09DispType,
    cmFlowCpdV2Mac0ADispType, cmFlowCpdV2Mac0BDispType,
    cmFlowCpdV2Mac0CDispType, cmFlowCpdV2Mac0DDispType,
    cmFlowCpdV2Mac0EDispType, cmFlowCpdV2Mac0FDispType,
    cmFlowCpdV2NearestLLDPDispType, cmFlowCpdV2NonTpmrLLDPDispType,
    cmFlowCpdV2CustomerLLDPDispType,

    cmEthernetNetPortCpdV2Index, cmEthernetNetPortCpdV2CiscoGroupDispType,
    cmEthernetNetPortCpdV2IslDispType, cmEthernetNetPortCpdV2PagpDispType,
    cmEthernetNetPortCpdV2UdldDispType, cmEthernetNetPortCpdV2CdpDispType,
    cmEthernetNetPortCpdV2VtpDispType, cmEthernetNetPortCpdV2DtpDispType,
    cmEthernetNetPortCpdV2PvstpPlusDispType, 
    cmEthernetNetPortCpdV2UplinkFastDispType,
    cmEthernetNetPortCpdV2VlanBridgeDispType,
    cmEthernetNetPortCpdV2L2PTDispType, 
    cmEthernetNetPortCpdV2BridgeGroupDispType,
    cmEthernetNetPortCpdV2BPDUDispType, cmEthernetNetPortCpdV2PauseDispType,
    cmEthernetNetPortCpdV2LACPDispType,
    cmEthernetNetPortCpdV2LACPMarkerDispType,
    cmEthernetNetPortCpdV2EfmOamDispType,
    cmEthernetNetPortCpdV2SSMDispType,
    cmEthernetNetPortCpdV2PortAuthenDispType,
    cmEthernetNetPortCpdV2BridgeReservedDispType,
    cmEthernetNetPortCpdV2LANBridgesDispType,
    cmEthernetNetPortCpdV2GARPGroupDispType,
    cmEthernetNetPortCpdV2GMRPDispType, cmEthernetNetPortCpdV2GVRPDispType,
    cmEthernetNetPortCpdV2GARPDispType,
    cmEthernetNetPortCpdV2Mac00DispType, cmEthernetNetPortCpdV2Mac01DispType,
    cmEthernetNetPortCpdV2Mac02DispType, cmEthernetNetPortCpdV2Mac03DispType,
    cmEthernetNetPortCpdV2Mac04DispType, cmEthernetNetPortCpdV2Mac05DispType,
    cmEthernetNetPortCpdV2Mac06DispType, cmEthernetNetPortCpdV2Mac07DispType,
    cmEthernetNetPortCpdV2Mac08DispType, cmEthernetNetPortCpdV2Mac09DispType,
    cmEthernetNetPortCpdV2Mac0ADispType, cmEthernetNetPortCpdV2Mac0BDispType,
    cmEthernetNetPortCpdV2Mac0CDispType, cmEthernetNetPortCpdV2Mac0DDispType,
    cmEthernetNetPortCpdV2Mac0EDispType, cmEthernetNetPortCpdV2Mac0FDispType,
    cmEthernetNetPortCpdV2NearestLLDPDispType, cmEthernetNetPortCpdV2NonTpmrLLDPDispType,
    cmEthernetNetPortCpdV2CustomerLLDPDispType, cmEthernetNetPortCpdV2PtpUntaggedDispType,
    cmEthernetNetPortCpdV2PtpTaggedDispType
    }
    STATUS  current
    DESCRIPTION
            "A collection of objects used to manage the 
             Control Protocol Disposition version 2 function."
    ::= { cmFacilityGroups 9 }
    
trafficGroupCmHub OBJECT-GROUP
    OBJECTS {
        cmFlowIndex, cmFlowCircuitName, cmFlowAdminState,
        cmFlowOperationalState, cmFlowSecondaryState,
        cmFlowType, cmFlowMultiCOS, cmFlowA2NCIR,
        cmFlowA2NEIR, cmFlowN2ARateLimitingEnabled,
        cmFlowN2ACIR, cmFlowN2AEIR, cmFlowStorageType, cmFlowRowStatus,
    
        cmFlowTrafficType, cmFlowCOS, cmFlowVlanMemberList,
        cmFlowAction, cmFlowActionVlan, cmFlowUntaggedMemberEnabled,
        cmFlowA2NCIRHi, cmFlowA2NEIRHi,
        cmFlowN2ACIRHi, cmFlowN2AEIRHi, 
        cmFlowHCOSMgmtEnabled, cmFlowGuaranteedA2NBandwidthLo,
        cmFlowGuaranteedA2NBandwidthHi, cmFlowMaximumA2NBandwidthLo,
        cmFlowMaximumA2NBandwidthHi, cmFlowCTagControl,
        cmFlowCTagVlanId, cmFlowCTagVlanPriority, cmFlowCTagMatchRxPrio,
        cmFlowSTagControl, cmFlowSTagVlanId, cmFlowSTagVlanPriority,
        cmFlowOuterTagPrioEnabled, cmFlowN2ACOSPriorityTagType,
        cmFlowESFramesLossThreshold, cmFlowSESFramesLossThresholdRatio, 
        cmFlowPolicingEnabled, cmFlowPreserveSTagProperties, cmFlowInnerTagPrioEnabled,
        cmFlowA2NShapingType, cmFlowN2AShapingType,
        cmFlowN2AOuterTagPrioEnabled, cmFlowSTagMatchRxPrio,
    
        cmQosShaperTypeIndex, cmQosShaperIndex, cmQosShaperDirection,
        cmQosShaperAdminState, cmQosShaperOperationalState,cmQosShaperSecondaryState,
        cmQosShaperCIR, cmQosShaperCBS, cmQosShaperEIR, cmQosShaperEBS,
        cmQosShaperBufferSize, cmQosShaperStorageType,
        cmQosShaperRowStatus, cmQosShaperCOS, cmQosShaperCIRHi, 
        cmQosShaperEIRHi

    }
    STATUS  current
    DESCRIPTION
            "A collection of objects used to manage the F3 traffic path, consists of
             Flows, Policers and Shapers." 
    ::= { cmFacilityGroups 10 }


ocnStmGroup OBJECT-GROUP
    OBJECTS {
        ocnStmIndex, ocnStmIfIndex, ocnStmEntityIndex,
        ocnStmAdminState, ocnStmOperationalState,
        ocnStmSecondaryState, ocnStmSfpVendorName,
        ocnStmSfpPartNumber, ocnStmSfpSerialNumber,
        ocnStmSfpDateOfManufacture, ocnStmMultiplexingStructures,
        ocnStmEoTDMMode, ocnStmLoopbackConfig,
        ocnStmLoopbackStatus, ocnStmLoopbackTime,
        ocnStmInsertingAIS, ocnStmBerExcThreshold,
        ocnStmBerDegThreshold, ocnStmRxTrailTrace,
        ocnStmTxTrailTrace, ocnStmExpectedTrailTrace,
        ocnStmTrailTraceFormat, ocnStmQLModeEnabled,
        ocnStmExpectedQL, ocnStmAssumedQL, ocnStmReceivedQL,
        ocnStmTransmitQL, ocnStmPortType, ocnStmFreqSourceType,
        ocnStmSfpName, ocnStmSfpHardwareRevision
    }
    STATUS  current
    DESCRIPTION
            "A collection of objects used to manage the OCN/STM Line."
    ::= { cmFacilityGroups 11 }

stsVcPathGroup OBJECT-GROUP
    OBJECTS {
        stsVcPathParentIfIndex, stsVcPathIndex,
        stsVcPathIfIndex, stsVcPathAdminState, stsVcPathOperationalState,
        stsVcPathSecondaryState, stsVcPathLoopbackConfig,
        stsVcPathLoopbackStatus, stsVcPathLoopbackTime,
        stsVcPathInsertingAIS, stsVcPathBerExcThreshold,
        stsVcPathBerDegThreshold, stsVcPathTrailTraceFormat,
        stsVcPathRxTrailTrace, stsVcPathTxTrailTrace,
        stsVcPathExpectedTrailTrace, stsVcPathRxSignalLabel,
        stsVcPathTxSignalLabel, stsVcPathExpectedSignalLabel,
        stsVcPathRowStatus, stsVcPathLowOrderPathType
    }
    STATUS  current
    DESCRIPTION
            "A collection of objects used to manage the STS/VC Higher Order Path."
    ::= { cmFacilityGroups 12 }

vtVcPathGroup OBJECT-GROUP
    OBJECTS {
        vtVcPathParentIfIndex, vtVcPathIndex, vtVcPathIfIndex,
        vtVcPathAdminState, vtVcPathOperationalState,
        vtVcPathSecondaryState, vtVcPathLoopbackConfig,
        vtVcPathLoopbackStatus, vtVcPathLoopbackTime,
        vtVcPathInsertingAIS, vtVcPathBerExcThreshold,
        vtVcPathBerDegThreshold, vtVcPathTrailTraceFormat,
        vtVcPathRxTrailTrace, vtVcPathTxTrailTrace,
        vtVcPathExpectedTrailTrace, vtVcPathRxSignalLabel,
        vtVcPathTxSignalLabel, vtVcPathExpectedSignalLabel,
        vtVcPathRowStatus
    }
    STATUS  current
    DESCRIPTION
            "A collection of objects used to manage the VT/VC Lower Order Path."
    ::= { cmFacilityGroups 13 }

e1t1InterfaceGroup OBJECT-GROUP
    OBJECTS {
        e1t1ParentIfIndex, e1t1Index, e1t1IfIndex,
        e1t1EntityIndex, e1t1AdminState,
        e1t1OperationalState, e1t1SecondaryState, e1t1LoopbackConfig,
        e1t1LoopbackStatus, e1t1LoopbackTime,
        e1t1RemoteLoopbackRequest, e1t1InsertingAIS, e1t1RowStatus,
        e1t1LineType, e1t1LineCode, e1t1FrameFormat,
        e1t1LineBuildOut, e1t1TimingDomain, e1t1RcvSensitivity,
        e1t1IdlePatternProfile, e1t1LoopbackProfile, e1t1RelatedContainerId,
        e1t1PatternLpbkControl
    }
    STATUS  current
    DESCRIPTION
            "A collection of objects used to manage the E1/T1 Interface Group."
    ::= { cmFacilityGroups 14 }

e3t3InterfaceGroup OBJECT-GROUP
    OBJECTS {
        e3t3ParentIfIndex, e3t3Index, e3t3IfIndex,
        e3t3EntityIndex, e3t3AdminState,
        e3t3OperationalState, e3t3SecondaryState, e3t3LoopbackConfig,
        e3t3LoopbackStatus, e3t3LoopbackTime,
        e3t3RemoteLoopbackRequest, e3t3InsertingAIS, e3t3CBitEnable,
        e3t3T3Channelized, e3t3RowStatus, 
        e3t3FrameFormat, e3t3RelatedContainerId
    }
    STATUS  current
    DESCRIPTION
            "A collection of objects used to manage the E3/T3 Interface Group."
    ::= { cmFacilityGroups 15 }

f3PulsePerSecondPortGroup OBJECT-GROUP
    OBJECTS {
        f3PulsePerSecondPortIndex, f3PulsePerSecondPortIfIndex,
        f3PulsePerSecondPortEntityIndex, f3PulsePerSecondPortAdminState,
        f3PulsePerSecondPortOperationalState, f3PulsePerSecondPortSecondaryState,
        f3PulsePerSecondPortSquelchControl, f3PulsePerSecondPortSquelchQL,
        f3PulsePerSecondPortTODSource, f3PulsePerSecondPortDirection, 
        f3PulsePerSecondPortInputRate, f3PulsePerSecondPortDelayCompensation,
        f3PulsePerSecondPortClockClass, f3PulsePerSecondPortClockAccuracy,
        f3PulsePerSecondPortTimeSource, f3PulsePerSecondPortPhyInterfaceType,
        f3PulsePerSecondPortOutputDelay, f3PulsePerSecondPortWidth,
        f3PulsePerSecondPortPolarity, f3PulsePerSecondPortImpedance, f3PulsePerSecondPortAlias, f3PulsePerSecondPortAssumedClockClass
    }
    STATUS  current
    DESCRIPTION
            "A collection of objects used to manage the F3 Pulse Per Second Group."
    ::= { cmFacilityGroups 16 }

f3TimeOfDayPortGroup OBJECT-GROUP
    OBJECTS {
        f3TimeOfDayPortIndex, f3TimeOfDayPortIfIndex, f3TimeOfDayPortEntityIndex, 
        f3TimeOfDayPortAdminState, f3TimeOfDayPortOperationalState,
        f3TimeOfDayPortSecondaryState, f3TimeOfDayPortSquelchControl,
        f3TimeOfDayPortSquelchQL, f3TimeOfDayPortTODSource,
        f3TimeOfDayPortOutputFormat, f3TimeOfDayPortSignalDirection,
        f3TimeOfDayPortInputRate, f3TimeOfDayPortDelayCompensation, f3TimeOfDayPortAlias,f3TimeOfDayPortAssumedClockClass
    }
    STATUS  current
    DESCRIPTION
            "A collection of objects used to manage the F3 Time of Day Port Group."
    ::= { cmFacilityGroups 17 }

f3Gps10MhzPortGroup OBJECT-GROUP
    OBJECTS {
        gps10MHzPortIndex, gps10MHzPortIfIndex, gps10MHzPortEntityIndex,
        gps10MHzPortAdminState, gps10MHzPortOperationalState,
        gps10MHzPortSecondaryState, gps10MHzPortSignalDirection,
        gps10MHzPortSquelchControl, gps10MHzPortSquelchQL,
        gps10MHzPortFrequencySource, gps10MHzPortClockClass,
        gps10MHzPortClockAccuracy, gps10MHzPortTimeSource,
        gps10MHzPortAssumedQL,gps10MHzPortAlias,
        gps10MHzPortInputSignalType
    }
    STATUS  current
    DESCRIPTION
            "A collection of objects used to manage the F3 GPS 10 Mhz Port Group."
    ::= { cmFacilityGroups 18 }

ethernetNetworkPortExtGroup OBJECT-GROUP
    OBJECTS {
        cmEthernetNetPortTDMEncapsulation, cmEthernetNetPortAssociatedTdmEntity,
        cmEthernetNetPortInsertingAIS
    }
    STATUS  current
    DESCRIPTION
            " A collection of objects used to manage the F3 Ethernet Network Port 
              extense function."
    ::= { cmFacilityGroups 19 }


f3GPSReceiverPortGroup OBJECT-GROUP
    OBJECTS { 
        f3GPSReceiverPortIndex, f3GPSReceiverPortIfIndex,
        f3GPSReceiverPortEntityIndex, f3GPSReceiverPortAdminState,
        f3GPSReceiverPortOperationalState, f3GPSReceiverPortSecondaryState,
        f3GPSReceiverPortPPSGenCondition, f3GPSReceiverPortAntennaCableLength,
        f3GPSReceiverPortAntennaStatus, f3GPSReceiverPortSatellitesUsableFlag,
        f3GPSReceiverPortNumTrackingSatellites, f3GPSReceiverPortSelfSurveyProgress,
        f3GPSReceiverPortPPSGeneratedFlag,

        f3GPSReceiverPortGnssSystem,
        f3GPSReceiverPortInstallationType,
        f3GPSReceiverPortGnssTOD, f3GPSReceiverPortGnssSystemsBitMap,
        f3GPSReceiverPortAlias, f3GPSReceiverPortAntennaDelayValue,
        f3GPSReceiverPortAntennaDelayType, f3GPSReceiverPortCNOMask,
        f3GPSReceiverPortElevationMask, f3GPSReceiverPortCoordinateLatitude,
        f3GPSReceiverPortCoordinateLongitude, f3GPSReceiverPortCoordinateAltitude,
        f3GPSReceiverPortFirmwareUpgradePercent,
        f3GPSReceiverPortPDOPMask, f3GPSReceiverPortSelfSurveyPeriod,
        f3GPSReceiverPortSatMin1Threshold, f3GPSReceiverPortSatMin2Threshold,
        f3GPSReceiverPortPDOP,
        f3GPSReceiverPortSelfSurveyControl, f3GPSReceiverPortCoordinateStringAltitude,
        f3GPSReceiverPortLocationMode, f3GPSReceiverPortTimeAdvanceMode, 
        f3GPSReceiverPortTimeAdvanceValue, f3GPSReceiverPortForcedAntennaConnected,
        f3GPSReceiverPortServiceAvailableTime, f3GPSReceiverPortServiceUnavailableTime,
        f3GPSReceiverPortServiceAvailablePercentage, f3GPSReceiverPortAGC,
        f3GPSReceiverPortSelfSurveyPositionAccuracy, f3GPSReceiverPortHorizontalAccuracy, f3GPSReceiverPortVerticalAccuracy,
        f3GPSReceiverPortTDOP, f3GPSReceiverPortHDOP, f3GPSReceiverPortVDOP,
        f3GPSReceiverPortFailureSuspendTime
    }
    STATUS  current
    DESCRIPTION
            "A collection of objects used to manage the F3 GPS Receiver Port Group."
    ::= { cmFacilityGroups 20 }

cmPsePortGroup OBJECT-GROUP
    OBJECTS{
    cmPethPsePortExtGroupIndex,
    cmPethPsePortExtIndex,
    cmPethPsePortExtAssociatedPort,
    pethPsePortExtPowerConsumption,
    pethPsePortExtAvailablePowerLevel
    }
    STATUS  current
    DESCRIPTION
            "A collection of objects used to manage the pse port ext entry Group."
    ::= { cmFacilityGroups 21 }

cmPseEXTGroup OBJECT-GROUP
    OBJECTS{
    pethMainPseExtGroupIndex,
    pethMainPseExtNonStandardPD
    }
    STATUS  current
    DESCRIPTION
            "A collection of objects used to manage the pse group ext entry Group."
    ::= { cmFacilityGroups 22 }

cmMPFlowGroup OBJECT-GROUP
    OBJECTS{
    cmMPFlowIndex,
    cmMPFlowCircuitName,
    cmMPFlowAdminState,
    cmMPFlowOperationalState,
    cmMPFlowSecondaryState,
    cmMPFlowLearningEnabled,
    cmMPFlowAgingTimer,
    cmMPFlowFwdTableSizeProfileID,
    cmMPFlowtableFullAction,
    cmMPFlowStorageType,
    cmMPFlowRowStatus,
    cmMPFlowLearningConfigAction,
    cmMPFlowFPList
    }
    STATUS  current
    DESCRIPTION
            "A collection of objects used to manage the MP flow entry Group."
    ::= { cmFacilityGroups 23 }

cmMPFlowMemberGroup OBJECT-GROUP
    OBJECTS{
    cmMPFlowMemberFPIndex,
    cmMPFlowPointRowStatus
    }
    STATUS  current
    DESCRIPTION
            "A collection of objects used to manage the MP flow Member entry Group."
    ::= { cmFacilityGroups 24 }

cmEthernetTrafficPortPcpGroup OBJECT-GROUP
    OBJECTS{
    cmEthernetTrafficPortPcpDEEncIndex,
    cmEthernetTrafficPortPcpDEEncInPriority,
    cmEthernetTrafficPortPcpDEEncDropIneligiblePrio,
    cmEthernetTrafficPortPcpDEEncDropEligiblePrio,
    cmEthernetTrafficPortPcpDEDecIndex,
    cmEthernetTrafficPortPcpDEDecInPriority,
    cmEthernetTrafficPortPcpDEDecOutPriority,
    cmEthernetTrafficPortPcpDEDecDropEligible,
    cmEthernetTrafficPortPcpDEPairIndex,
    cmEthernetTrafficPortPcpDEDropIneligiblePrio,
    cmEthernetTrafficPortPcpDEDropEligiblePrio,
    cmEthernetTrafficPortClbIndex,
    cmEthernetTrafficPortClbEnabled,
    cmEthernetTrafficPortClbLength,
    cmEthernetTrafficPortClbDescr
    }
    STATUS  current
    DESCRIPTION
            "A collection of objects used to manage the traffic port pcp Group."
    ::= { cmFacilityGroups 25 }

neTMParamsGroup OBJECT-GROUP
    OBJECTS{
    neTMParamsBandwidthProfileMode,
    neTMParamsAgingtime
    }
    STATUS  current
    DESCRIPTION
            "A collection of objects used to manage the ne facility entry Group."
    ::= { cmFacilityGroups 26 }

cmEthernetTrafficPortGroup OBJECT-GROUP
    OBJECTS{
    cmEthernetTrafficPortIndex,cmEthernetTrafficPortIfIndex,
    cmEthernetTrafficPortEntityIndex,cmEthernetTrafficPortAdminState,
    cmEthernetTrafficPortOperationalState,cmEthernetTrafficPortSecondaryState,
    cmEthernetTrafficPortMTU,cmEthernetTrafficPortMediaType,
    cmEthernetTrafficPortConfigSpeed,cmEthernetTrafficPortNegotiatedSpeed,
    cmEthernetTrafficPortMDIXType,cmEthernetTrafficPortMDIXStatus,
    cmEthernetTrafficPortSfpVendorName,cmEthernetTrafficPortSfpPartNumber,
    cmEthernetTrafficPortSfpSerialNumber,cmEthernetTrafficPortSfpDateOfManufacture,
    cmEthernetTrafficPortSfpConnectorValue,
    cmEthernetTrafficPortSfpLinkLength,cmEthernetTrafficPortSfpLaserWaveLength,
    cmEthernetTrafficPortSfpMediaType,cmEthernetTrafficPortLoopbackConfig,
    cmEthernetTrafficPortLoopbackStatus,cmEthernetTrafficPortLoopbackTime,
    cmEthernetTrafficPortLoopbackSwapSADA,cmEthernetTrafficPortOuterVlanLoopbackMask,
    cmEthernetTrafficPortOuterVlanLoopback1,cmEthernetTrafficPortOuterVlanLoopback2,
    cmEthernetTrafficPortOuterVlanLoopback3,cmEthernetTrafficPortLinkLossFwdEnabled,
    cmEthernetTrafficPortLinkLossFwdSignalType,cmEthernetTrafficPortLinkLossFwdTriggerTypes,
    cmEthernetTrafficPortLinkLossFwdDelay,cmEthernetTrafficPortLinkLossFwdActive,
    cmEthernetTrafficPortLinkLossFwdPartnerEnabled,cmEthernetTrafficPortLinkLossFwdLocalLinkId,
    cmEthernetTrafficPortLinkLossFwdRemoteLinkIds,cmEthernetTrafficPortLinkLossFwdTxActionType,
    cmEthernetTrafficPortLinkLossFwdRxRLDLinkIds,cmEthernetTrafficPortOamId,
    cmEthernetTrafficPortOamDiscoveryState,
    cmEthernetTrafficPortOamLocalVarRtrvsEnabled,cmEthernetTrafficPortOamLocalLinkEventsEnabled,
    cmEthernetTrafficPortOamLocalOamLoopbacksSupported,cmEthernetTrafficPortOamLocalUnidirSupportEnabled,
    cmEthernetTrafficPortOamLocalMaxPDUSize,cmEthernetTrafficPortOamLocalMode,
    cmEthernetTrafficPortOamRemoteMacAddress,cmEthernetTrafficPortOamRemoteVarRtrvsEnabled,
    cmEthernetTrafficPortOamRemoteLinkEventsEnabled,cmEthernetTrafficPortOamRemoteOamLoopbacksSupported,
    cmEthernetTrafficPortOamRemoteUnidirSupportEnabled,cmEthernetTrafficPortOamRemoteMaxPDUSize,
    cmEthernetTrafficPortOamRemoteMode,cmEthernetTrafficPortOamEnabled,
    cmEthernetTrafficPortOamAdminState,
    cmEthernetTrafficPortSvcType,
    cmEthernetTrafficPortTxPauseEnabled,cmEthernetTrafficPortAfpType,
    cmEthernetTrafficPortShapingEnabled,cmEthernetTrafficPortShapedSpeedLo,
    cmEthernetTrafficPortShapedSpeedHi,cmEthernetTrafficPortQinQEtherType,
    cmEthernetTrafficPortEgressVlanTrunkingEnabled,cmEthernetTrafficPortIngressPushPVIDEnabled,
    cmEthernetTrafficPortEgressPopPVIDEnabled,cmEthernetTrafficPortPortVlanId,
    cmEthernetTrafficPortPortVlanPriority,cmEthernetTrafficPortPriorityVlanId,
    cmEthernetTrafficPortIngressPrioMapMode,cmEthernetTrafficPortIngressCOSPriority,
    cmEthernetTrafficPortEgressPopPriorityVidEnabled,
    cmEthernetTrafficPortSyncEEnabled,
    cmEthernetTrafficPortQLModeEnabled,cmEthernetTrafficPortExpectedQL,
    cmEthernetTrafficPortAssumedQL,cmEthernetTrafficPortReceivedQL,
    cmEthernetTrafficPortTransmitQL,cmEthernetTrafficPortTagFrameControl,
    cmEthernetTrafficPortRxPauseEnabled, cmEthernetTrafficPortPhyType,
    cmEthernetTrafficPortSfpLaserWaveLengthPicometer, cmEthernetTrafficPortRowStatus,
    cmEthernetTrafficPortSSMRemoteMacAddress, cmEthernetTrafficPortInnerVlanLoopbackMask,
    cmEthernetTrafficPortInnerVlanLoopback1, cmEthernetTrafficPortInnerVlanLoopback2,
    cmEthernetTrafficPortInnerVlanLoopback3,
    cmEthernetTrafficPortLaserWDMChannel,
    cmEthernetTrafficPortLaserIsTunable,
    cmEthernetTrafficPortLaserFrequency,
    cmEthernetTrafficPortDeiEnable,
    cmEthernetTrafficPortPcpDEEncType,
    cmEthernetTrafficPortPcpDEPairsAction,
    cmEthernetTrafficPortInitiateDiag,
    cmEthernetTrafficPortDiagnosePair1Cond,
    cmEthernetTrafficPortDiagnosePair2Cond,
    cmEthernetTrafficPortDiagnosePair3Cond,
    cmEthernetTrafficPortDiagnosePair4Cond,
    cmEthernetTrafficPortDiagnoseAutoNegCond,
    cmEthernetTrafficPortDiagnoseLpbkCond,
    cmEthernetTrafficPortDiagnoseEfmLpbkCond,
    cmEthernetTrafficPortDiagnoseResult,
    cmEthernetTrafficPortDiagnoseTestStatus,
    cmEthernetTrafficPortDiagnoseTestTime,
    cmEthernetTrafficPortAutoDiagEnabled, cmEthernetTrafficPortDeleteEntitiesAction,
    cmEthernetTrafficPortMaxMpFpNum, cmEthernetTrafficPortJdsuLoopbackEnabled, cmEthernetTrafficPortJdsuLoopbackVlanId,
    cmEthernetTrafficPortIngressPopPriorityVidEnabled, cmEthernetTrafficPortRxDeiAction,
    cmEthernetTrafficPortTxDeiAction, cmEthernetTrafficPortRxDeiOuterTagType,
    cmEthernetTrafficPortTxDeiOuterTagType,
    cmEthernetTrafficPortMode,
    cmEthernetTrafficPortServiceType,
    cmEthernetTrafficPortLoopbackSourceMacControlEnabled,
    cmEthernetTrafficPortLoopbackDestMacControlEnabled,
    cmEthernetTrafficPortLoopbackSourceMacAddress,
    cmEthernetTrafficPortLoopbackDestMacAddress,
    cmEthernetTrafficPortLoopbackBlockingEnabled,
    cmEthernetTrafficPortMediaTypeAutoSelected,
    cmEthernetTrafficPortLowLatencyQueuingEnabled,
    cmEthernetTrafficPortDiagnosticMacAddress,

    cmEthernetTrafficPortMcastRateLimitSpeedHi,
    cmEthernetTrafficPortBcastRateLimitEnabled,
    cmEthernetTrafficPortBcastRateLimitSpeedLo,
    cmEthernetTrafficPortBcastRateLimitSpeedHi,
    cmEthernetTrafficPortCombinedRateLimitEnabled,
    cmEthernetTrafficPortCombinedRateLimitSpeedLo,
    cmEthernetTrafficPortCombinedRateLimitSpeedHi,
    cmEthernetTrafficPortRefPrioMapProfile,
    
    cmEthernetTrafficPortIngressSwapPriorityVIDEnabled,
    cmEthernetTrafficPortEgressSwapPriorityVIDEnabled,
    cmEthernetTrafficPortSwapPriorityVID,
    cmEthernetTrafficPortExpDEEncType,
    cmEthernetTrafficPortExpDEPairsAction,
    cmEthernetTrafficPortJdsuLoopbackSrcIp,
    cmEthernetTrafficPortTxSsm,
    cmEthernetTrafficPortRxSsmQL,
    cmEthernetTrafficPortSyncEMode,
    cmEthernetTrafficPortSyncEServiceAvailableTime,
    cmEthernetTrafficPortSyncEServiceUnavailableTime,
    cmEthernetTrafficPortSyncEServiceAvailablePercentage,
    cmEthernetTrafficPortWfqSegmentationCOS,
    cmEthernetTrafficPortWfqGroupCOS,
    cmEthernetTrafficPortWfqGroupEirLo,
    cmEthernetTrafficPortWfqGroupEirHi,
    cmEthernetTrafficPortOuterTagTpidOverride,
    cmEthernetTrafficPortOuterTagTpid,
    cmEthernetTrafficPortSfpTxPowerLevel,
    cmEthernetTrafficPortSfpRxPowerLevel,
    cmEthernetTrafficPortBwResourcePort,
    cmEthernetTrafficPortSfpName,
    cmEthernetTrafficPortSfpHardwareRevision,
    cmEthernetTrafficPortLoopbackTestReflectorIPv4AddressControl,
    cmEthernetTrafficPortLoopbackTestReflectorIPv4Address,
    cmEthernetTrafficPortLoopbackTestReflectorIPv6AddressControl,
    cmEthernetTrafficPortLoopbackTestReflectorIPv6Address,
    cmEthernetTrafficPortSfpIdentifierValue,
    cmEthernetTrafficPortPlugType,
    cmEthernetTrafficPortPlugMode,
    cmEthernetTrafficPortPlugGMetroAutoTuningMode,
    cmEthernetTrafficPortPlugChannelType,
    cmEthernetTrafficPortPlugITUCbandChannel,
    cmEthernetTrafficPortPlugRelativeChannel,
    cmEthernetTrafficPortPlugFrequency,
    cmEthernetTrafficPortPlugOutOfBandChannelStatus,
    cmEthernetTrafficPortRemotePlugITUCbandChannel,
    cmEthernetTrafficPortRemotePlugRelativeChannel,
    cmEthernetTrafficPortRemotePlugFrequency,
    cmEthernetTrafficPortRemoteSfpVendorName,
    cmEthernetTrafficPortRemoteSfpName,
    cmEthernetTrafficPortRemoteSfpPartNumber,
    cmEthernetTrafficPortRemoteSfpHardwareRevision,
    cmEthernetTrafficPortRemoteSfpSerialNumber,
    cmEthernetTrafficPortRemoteSfpDateOfManufacture,
    cmEthernetTrafficPortRemoteSfpLinkLength,
    cmEthernetTrafficPortRemoteSfpLaserWaveLength,
    cmEthernetTrafficPortRemoteSfpLaserFrequency,
    cmEthernetTrafficPortRemoteSfpMediaType,
    cmEthernetTrafficPortRemoteSfpConnectorValue,
    cmEthernetTrafficPortRemoteSfpIdentifierValue
    }
    STATUS  current
    DESCRIPTION
            "A collection of objects used to manage the traffic port entry Group."
    ::= { cmFacilityGroups 27 }

cmFlowPointGroup OBJECT-GROUP
    OBJECTS{
    cmFlowPointIndex,cmFlowPointCircuitName,
    cmFlowPointAdminState,cmFlowPointOperationalState,
    cmFlowPointSecondaryState,cmFlowPointAssociatedFlowId,
    cmFlowPointIngressMultiCOS,cmFlowPointIngressCOS,
    cmFlowPointIngressVlanMemberList,cmFlowPointVlanMemberAction,
    cmFlowPointAssociatedAclProfile,cmFlowPointSESFramesLossThresholdRatio,
    cmFlowPointVlanMemberActionVlan,cmFlowPointIngressUntaggedFrameEnabled,
    cmFlowPointCTagControl,cmFlowPointCTagVlanId,
    cmFlowPointCTagVlanPriority,cmFlowPointSTagControl,
    cmFlowPointSTagVlanId,cmFlowPointSTagVlanPriority,
    cmFlowPointEgressOuterTagPrioMapEnabled,cmFlowPointColorMarkingSupported, 
    cmFlowPointStorageType, cmFlowPointRowStatus,
    cmFlowPointDefaultMemberEnabled,
    cmFlowPointMcastRateLimitEnabled,
    cmFlowPointMcastRateLimitSpeedLo,
    cmFlowPointMcastRateLimitSpeedHi,
    cmFlowPointBcastRateLimitEnabled,
    cmFlowPointBcastRateLimitSpeedLo,
    cmFlowPointBcastRateLimitSpeedHi,
    cmFlowPointSplitHorizonGroupOID,
    cmFlowPointLoopAvoidance,
    cmFlowPointHierarchicalCosEnabled,
    cmFlowPointWfqQid,
    cmFlowPointWfqOutPriority,
    cmFlowPointMaximumBWLo,
    cmFlowPointGuaranteedBWLo,
    cmFlowPointMaximumBWHi,
    cmFlowPointGuaranteedBWHi,
    cmFlowPointRefPrioMapProfile,
    cmFlowPointMcastAndBcastRateLimitEnabled,
    cmFlowPointMcastAndBcastRateLimitSpeedLo,
    cmFlowPointMcastAndBcastRateLimitSpeedHi,
    cmFlowPointEgressShapingType,
    cmFlowPointEgressInnerTagPrioMapEnabled,
    cmFlowPointAutoBandwidthConfigEnabled,
    cmFlowPointAutoCIRPercentage,
    cmFlowPointFrameFwdEnabled,
    cmFlowPointUsePortPrioMapProfile,
    cmFlowPointRefEoMplsPwObject,
    cmFlowPointElmiEvcIdentifier,
    cmFlowPointRefElpObject,
    cmFlowPointEfEnabled,
    cmFlowPointEfIdentificationType,
    cmFlowPointEfRateThresholdLo,
    cmFlowPointEfRateThresholdHi,
    cmFlowPointAclNoMatchDisposition,
    cmFlowPointEfIdentificationFields,
    cmFlowPointWfqSegmentationCOS,
    cmFlowPointWfqGroupCOS,
    cmFlowPointWfqGroupEirLo,
    cmFlowPointWfqGroupEirHi
    }
    STATUS  current
    DESCRIPTION
            "A collection of objects used to manage the flow point entry Group."
    ::= { cmFacilityGroups 28 }

ethernetAccessPortJdsuExtGroup OBJECT-GROUP
    OBJECTS {
        cmEthernetAccPortJDSUControlFramesSnoopingEnabled,
        cmEthernetAccPortJDSULoopbackVlan,
        cmEthernetAccPortJDSULoopbackVlanList
    }
    STATUS  current
    DESCRIPTION
            " A collection of objects used to manage the F3 Ethernet Access Port 
              JDSU extense function."
    ::= { cmFacilityGroups 29 }

ethernetNetworkPortJdsuExtGroup OBJECT-GROUP
    OBJECTS {
        cmEthernetNetPortJDSUControlFramesSnoopingEnabled,
        cmEthernetNetPortJDSULoopbackVlan,
        cmEthernetNetPortJDSULoopbackVlanList
    }
    STATUS  current
    DESCRIPTION
            " A collection of objects used to manage the F3 Ethernet Network Port 
              JDSU extense function."
    ::= { cmFacilityGroups 30 }

cmTrafficPortLpbkGroup OBJECT-GROUP
    OBJECTS{
    cmEthernetTrafficPortLpbkIndex,
    cmEthernetTrafficPortLpbkInnerVlanEnabled,
    cmEthernetTrafficPortLpbkInnerVlanTag,
    cmEthernetTrafficPortLpbkOuterVlanEnabled,
    cmEthernetTrafficPortLpbkOuterVlanTag,
    cmEthernetTrafficPortLpbkTime,
    cmEthernetTrafficPortLpbkStatus,
    cmEthernetTrafficPortLpbkConfig
    }
    STATUS  current
    DESCRIPTION
            "A collection of objects used to manage the traffic port lpbk group."
    ::= { cmFacilityGroups 31 }

cmPrioMapV2ProfileGroup OBJECT-GROUP
    OBJECTS{
    cmPrioMapV2ProfileIndex,
    cmPrioMapV2ProfileAlias,
    cmPrioMapV2ProfileMapModeType,
    cmPrioMapV2ProfileStorageType,
    cmPrioMapV2ProfileRowStatus,
    cmPrioMapV2ProfileIngressCosPriority
    }
    STATUS  current
    DESCRIPTION
            "A collection of objects used to manage the priority map profile group."
    ::= { cmFacilityGroups 32 }

cmPrioMapV2IngressPrioMappingGroup OBJECT-GROUP
    OBJECTS{
    cmPrioMapV2IngressPrioMappingIndex,
    cmPrioMapV2IngressPrioMappingInPriority,
    cmPrioMapV2IngressPrioMappingCOS
    }
    STATUS  current
    DESCRIPTION
            "A collection of objects used to manage the priority map group."
    ::= { cmFacilityGroups 33 }

bits8PortGroupGroup OBJECT-GROUP
    OBJECTS {
        bits8PortGroupIndex, bits8PortGroupIfIndex,
        bits8PortGroupAdminState, bits8PortGroupOperationalState, bits8PortGroupSecondaryState,
        bits8PortGroupLineType, bits8PortGroupLineCode, bits8PortGroupFrameFormat,
        bits8PortGroupSaBitDesignation, bits8PortGroupQLModeEnabled, bits8PortGroupTransmitQL,
        bits8PortGroupSquelchQL, bits8PortGroupLineBuildOut,bits8PortGroupImpedance,
        bits8PortGroupRowStatus, bits8PortGroupActivePorts, bits8PortGroupClkIfEnabledPorts
    }
    STATUS  current
    DESCRIPTION
            "A collection of objects used to manage the Bits 8 Port Group
             function."
    ::= { cmFacilityGroups 34 }

pps16PortGroupGroup OBJECT-GROUP
    OBJECTS {
    pps16PortGroupIndex,pps16PortGroupIfIndex,pps16PortGroupAdminState,pps16PortGroupOperationalState,
    pps16PortGroupSecondaryState,pps16PortGroupAlias,pps16PortGroupSquelchControl,pps16PortGroupTODSource,
    pps16PortGroupDirection, pps16PortGroupDelayCompensation,pps16PortGroupRowStatus
    --,pps16PortGroupOutputType      


    }
    STATUS  current
    DESCRIPTION
            "A collection of objects used to manage the Pps 16 port card Group
             function."
    ::= { cmFacilityGroups 35 }



clk16PortGroupGroup OBJECT-GROUP
    OBJECTS {

    clk16PortGroupIndex,clk16PortGroupIfIndex, clk16PortGroupAdminState, clk16PortGroupOperationalState, 
    clk16PortGroupSecondaryState, clk16PortGroupAlias,clk16PortGroupDirection,clk16PortGroupSquelchControl,   
    clk16PortGroupSquelchQL,clk16PortGroupRowStatus  
    }
    STATUS  current
    DESCRIPTION
            "A collection of objects used to manage the CLK 16 port card Group
             function."
    ::= { cmFacilityGroups 36 }



todPps16PortGroupGroup OBJECT-GROUP
    OBJECTS {

        todPps16PortGroupIndex,todPps16PortGroupIfIndex,todPps16PortGroupAdminState ,  todPps16PortGroupOperationalState,
        todPps16PortGroupSecondaryState,todPps16PortGroupAlias , todPps16PortGroupSquelchControl, todPps16PortGroupSquelchQL,     
        todPps16PortGroupTODSource,todPps16PortGroupOutputFormat, todPps16PortGroupDelayCompensation,todPps16PortGroupRowStatus

    }
    STATUS  current
    DESCRIPTION
            "A collection of objects used to manage the TOD and PPS 16 port card Group
             function."
    ::= { cmFacilityGroups 37 }

f3PolicerEnvelopeGroup OBJECT-GROUP
    OBJECTS {
        f3PolicerEnvelopeIndex,f3PolicerEnvelopeCouplingFlag,
        f3PolicerEnvelopeStorageType,f3PolicerEnvelopeRowStatus,
        f3EnvelopeAssocPolicer
    }
    STATUS  current
    DESCRIPTION
            "A collection of objects used to manage the policer envelope group
             function."
    ::= { cmFacilityGroups 38 }

cmNetPortExpDeGroup OBJECT-GROUP
    OBJECTS {
      cmNetPortExpDEEncIndex,
      cmNetPortExpDEEncInPriority,
      cmNetPortExpDEEncDropIneligiblePrio,
      cmNetPortExpDEEncDropEligiblePrio,
      cmNetPortExpDEDecIndex,
      cmNetPortExpDEDecInPriority,
      cmNetPortExpDEDecOutPriority,
      cmNetPortExpDEDecDropEligible,
      cmNetPortExpDEPairIndex,
      cmNetPortExpDEDropIneligiblePrio,
      cmNetPortExpDEDropEligiblePrio
    }
    STATUS  current
    DESCRIPTION
            "A collection of objects used to manage the exp de decoding and encoding group
             function."
    ::= { cmFacilityGroups 39 }

cmNetPortIpPrecDeGroup OBJECT-GROUP
    OBJECTS {
        cmNetPortIpPrecDEEncIndex,
        cmNetPortIpPrecDEEncInPriority,
        cmNetPortIpPrecDEEncDropIneligiblePrio,
        cmNetPortIpPrecDEEncDropEligiblePrio,
        cmNetPortIpPrecDEDecIndex,
        cmNetPortIpPrecDEDecInPriority,
        cmNetPortIpPrecDEDecOutPriority,
        cmNetPortIpPrecDEDecDropEligible,
        cmNetPortIpPrecDEPairIndex,
        cmNetPortIpPrecDEDropIneligiblePrio,
        cmNetPortIpPrecDEDropEligiblePrio
    }
    STATUS  current
    DESCRIPTION
            "A collection of objects used to manage the ip prec de decoding and encoding group
             function."
    ::= { cmFacilityGroups 40 }

cmNetPortEncapPcpDeGroup OBJECT-GROUP
    OBJECTS {
        cmNetPortEncapPcpDEEncIndex,
        cmNetPortEncapPcpDEEncInPriority,
        cmNetPortEncapPcpDEEncDropIneligiblePrio,
        cmNetPortEncapPcpDEEncDropEligiblePrio,
        cmNetPortEncapPcpDEDecIndex,
        cmNetPortEncapPcpDEDecInPriority,
        cmNetPortEncapPcpDEDecOutPriority,
        cmNetPortEncapPcpDEDecDropEligible,
        cmNetPortEncapPcpDEPairIndex,
        cmNetPortEncapPcpDEDropIneligiblePrio,
        cmNetPortEncapPcpDEDropEligiblePrio
    }
    STATUS  current
    DESCRIPTION
            "A collection of objects used to manage the encap PCP de decoding and encoding group
             function."
    ::= { cmFacilityGroups 41 }

f3SatelliteGroup OBJECT-GROUP
    OBJECTS {
        f3SatelliteIndex,
        f3SatelliteSV,
        f3SatelliteInUse,
        f3SatelliteSVType,
        f3SatelliteCNO,
        f3SatelliteHealth,
        f3SatelliteAzimuth,
        f3SatelliteElevation,
        f3SatelliteGnssReceiverPort
    }
    STATUS  current
    DESCRIPTION
            "A collection of objects used to manage the GNSS satellite group
             function."
    ::= { cmFacilityGroups 42 }

cmEthernetTrafficPortJdsuExtGroup OBJECT-GROUP
    OBJECTS{
    cmEthernetTrafficPortJDSUControlFramesSnoopingEnabled,
    cmEthernetTrafficPortJDSULoopbackVlan,
    cmEthernetTrafficPortJDSULoopbackVlanList
    }
    STATUS  current
    DESCRIPTION
            "A collection of objects used to manage the F3 Ethernet Traffic Port 
              JDSU extense function."
    ::= { cmFacilityGroups 43 }

f3FpQosShaperGroup OBJECT-GROUP
    OBJECTS{
        f3FpQosShaperIndex,
        f3FpQosShaperAdminState,
        f3FpQosShaperOperationalState,
        f3FpQosShaperSecondaryState,
        f3FpQosShaperCIRLo,
        f3FpQosShaperCIRHi,
        f3FpQosShaperEIRLo,
        f3FpQosShaperEIRHi,
        f3FpQosShaperCBS,
        f3FpQosShaperEBS,
        f3FpQosShaperBufferSize,
        f3FpQosShaperCOS,
        f3FpQosShaperStorageType,
        f3FpQosShaperRowStatus,
        f3FpQosShaperWfqWeight
    }
    STATUS  current
    DESCRIPTION
            "A collection of objects used to manage the 
             F3 Ethernet Traffic Port FlowPoint Shaper."
    ::= { cmFacilityGroups 44 }

f3FpQosPolicerGroup OBJECT-GROUP
    OBJECTS{
        f3FpQosPolicerIndex,
        f3FpQosPolicerAdminState,
        f3FpQosPolicerOperationalState,
        f3FpQosPolicerSecondaryState,
        f3FpQosPolicerCIRLo,
        f3FpQosPolicerCIRHi,
        f3FpQosPolicerEIRLo,
        f3FpQosPolicerEIRHi,
        f3FpQosPolicerCBS,
        f3FpQosPolicerEBS,
        f3FpQosPolicerAlgorithm,
        f3FpQosPolicerColorMode,
        f3FpQosPolicerCouplingFlag,
        f3FpQosPolicerPolicingEnabled,
        f3FpQosPolicerStorageType,
        f3FpQosPolicerRowStatus,
        f3FpQosPolicerCIRMaxHi,
        f3FpQosPolicerCIRMaxLo,
        f3FpQosPolicerEIRMaxHi,
        f3FpQosPolicerEIRMaxLo,
        f3FpQosPolicerEnvelopeObject,
        f3FpQosPolicerRank
    }
    STATUS  current
    DESCRIPTION
            "A collection of objects used to manage the 
             F3 Ethernet Traffic Port FlowPoint Policer."
    ::= { cmFacilityGroups 45 }

cpdV2TrafficPortGroup OBJECT-GROUP
    OBJECTS {
        cmEthernetTrafficPortCpdV2Index, 
        cmEthernetTrafficPortCpdV2CiscoGroupDispType,
        cmEthernetTrafficPortCpdV2IslDispType, 
        cmEthernetTrafficPortCpdV2PagpDispType,
        cmEthernetTrafficPortCpdV2UdldDispType, 
        cmEthernetTrafficPortCpdV2CdpDispType,
        cmEthernetTrafficPortCpdV2VtpDispType, 
        cmEthernetTrafficPortCpdV2DtpDispType,
        cmEthernetTrafficPortCpdV2PvstpPlusDispType, 
        cmEthernetTrafficPortCpdV2UplinkFastDispType,
        cmEthernetTrafficPortCpdV2VlanBridgeDispType,
        cmEthernetTrafficPortCpdV2L2PTDispType, 
        cmEthernetTrafficPortCpdV2BridgeGroupDispType,
        cmEthernetTrafficPortCpdV2BPDUDispType, 
        cmEthernetTrafficPortCpdV2PauseDispType,
        cmEthernetTrafficPortCpdV2LACPDispType,
        cmEthernetTrafficPortCpdV2LACPMarkerDispType,
        cmEthernetTrafficPortCpdV2EfmOamDispType,
        cmEthernetTrafficPortCpdV2SSMDispType,
        cmEthernetTrafficPortCpdV2PortAuthenDispType,
        cmEthernetTrafficPortCpdV2BridgeReservedDispType,
        cmEthernetTrafficPortCpdV2LANBridgesDispType,
        cmEthernetTrafficPortCpdV2GARPGroupDispType,
        cmEthernetTrafficPortCpdV2GMRPDispType, 
        cmEthernetTrafficPortCpdV2GVRPDispType,
        cmEthernetTrafficPortCpdV2GARPDispType,
        cmEthernetTrafficPortCpdV2Mac00DispType, 
        cmEthernetTrafficPortCpdV2Mac01DispType,
        cmEthernetTrafficPortCpdV2Mac02DispType, 
        cmEthernetTrafficPortCpdV2Mac03DispType,
        cmEthernetTrafficPortCpdV2Mac04DispType, 
        cmEthernetTrafficPortCpdV2Mac05DispType,
        cmEthernetTrafficPortCpdV2Mac06DispType, 
        cmEthernetTrafficPortCpdV2Mac07DispType,
        cmEthernetTrafficPortCpdV2Mac08DispType, 
        cmEthernetTrafficPortCpdV2Mac09DispType,
        cmEthernetTrafficPortCpdV2Mac0ADispType, 
        cmEthernetTrafficPortCpdV2Mac0BDispType,
        cmEthernetTrafficPortCpdV2Mac0CDispType, 
        cmEthernetTrafficPortCpdV2Mac0DDispType,
        cmEthernetTrafficPortCpdV2Mac0EDispType, 
        cmEthernetTrafficPortCpdV2Mac0FDispType,
        cmEthernetTrafficPortCpdV2NearestLLDPDispType, 
        cmEthernetTrafficPortCpdV2NonTpmrLLDPDispType,
        cmEthernetTrafficPortCpdV2CustomerLLDPDispType, 
        cmEthernetTrafficPortCpdV2PtpUntaggedDispType,
        cmEthernetTrafficPortCpdV2PtpTaggedDispType,
        
        f3FlowPointCpdV2Index,
        f3FlowPointCpdV2IslDispType,
        f3FlowPointCpdV2PagpDispType,
        f3FlowPointCpdV2UdldDispType,
        f3FlowPointCpdV2CdpDispType,
        f3FlowPointCpdV2VtpDispType,
        f3FlowPointCpdV2DtpDispType,
        f3FlowPointCpdV2PvstpPlusDispType,
        f3FlowPointCpdV2UplinkFastDispType,
        f3FlowPointCpdV2VlanBridgeDispType,
        f3FlowPointCpdV2L2PTDispType,
        f3FlowPointCpdV2BPDUDispType,
        f3FlowPointCpdV2PauseDispType,
        f3FlowPointCpdV2LACPDispType,
        f3FlowPointCpdV2LACPMarkerDispType,
        f3FlowPointCpdV2EfmOamDispType,
        f3FlowPointCpdV2SSMDispType,
        f3FlowPointCpdV2PortAuthenDispType,
        f3FlowPointCpdV2LANBridgesDispType,
        f3FlowPointCpdV2GMRPDispType,
        f3FlowPointCpdV2GVRPDispType,
        f3FlowPointCpdV2GARPDispType,
        f3FlowPointCpdV2ActiveControlProtocols,
        f3FlowPointCpdV2ELMIDispType,
        f3FlowPointCpdV2Mac00DispType,
        f3FlowPointCpdV2Mac01DispType,
        f3FlowPointCpdV2Mac02DispType,
        f3FlowPointCpdV2Mac03DispType,
        f3FlowPointCpdV2Mac04DispType,
        f3FlowPointCpdV2Mac05DispType,
        f3FlowPointCpdV2Mac06DispType,
        f3FlowPointCpdV2Mac07DispType,
        f3FlowPointCpdV2Mac08DispType,
        f3FlowPointCpdV2Mac09DispType,
        f3FlowPointCpdV2Mac0ADispType,
        f3FlowPointCpdV2Mac0BDispType,
        f3FlowPointCpdV2Mac0CDispType,
        f3FlowPointCpdV2Mac0DDispType,
        f3FlowPointCpdV2Mac0EDispType,
        f3FlowPointCpdV2Mac0FDispType,
        f3FlowPointCpdV2NearestLLDPDispType,
        f3FlowPointCpdV2NonTpmrLLDPDispType,
        f3FlowPointCpdV2CustomerLLDPDispType  
    }
    STATUS  current
    DESCRIPTION
            "A collection of objects used to manage the 
             Control Protocol Disposition version 2 function."
    ::= { cmFacilityGroups 46 }

f3AclRuleGroup OBJECT-GROUP
    OBJECTS{
        f3AclRuleIndex,
        f3AclRuleAdminState,
        f3AclRuleAlias,
        f3AclRulePriority,
        f3AclRuleOperation,
        f3AclRuleCosOverrideControl,
        f3AclRuleCOS,
        f3AclRuleSrcMacAddressControl,
        f3AclRuleSrcMacAddress,
        f3AclRuleSrcMacAddressMask,
        f3AclRuleDstMacAddressControl,
        f3AclRuleDstMacAddress,
        f3AclRuleDstMacAddressMask,
        f3AclRuleOuterVlanVIDControl,
        f3AclRuleOuterVlanVIDLowLimit,
        f3AclRuleOuterVlanVIDHighLimit,
        f3AclRuleInnerVlanVIDControl,
        f3AclRuleInnerVlanVIDLowLimit,
        f3AclRuleInnerVlanVIDHighLimit,
        f3AclRuleOuterVlanPcpControl,
        f3AclRuleOuterVlanPcpLowLimit,
        f3AclRuleOuterVlanPcpHighLimit,
        f3AclRuleInnerVlanPcpControl,
        f3AclRuleInnerVlanPcpLowLimit,
        f3AclRuleInnerVlanPcpHighLimit,
        f3AclRuleOuterVlanDeiControl,
        f3AclRuleOuterVlanDei,
        f3AclRuleEtherTypeControl,
        f3AclRuleEtherType,
        f3AclRuleIpv4PriorityControl,
        f3AclRuleIpv4PriorityLowLimit,
        f3AclRuleIpv4PriorityHighLimit,
        f3AclRuleProtocolControl,
        f3AclRuleProtocolNumber,
        f3AclRuleSrcIpv4AddressControl,
        f3AclRuleSrcIpv4AddressLowLimit,
        f3AclRuleSrcIpv4AddressHighLimit,
        f3AclRuleDstIpv4AddressControl,
        f3AclRuleDstIpv4AddressLowLimit,
        f3AclRuleDstIpv4AddressHighLimit,
        f3AclRuleSrcPortControl,
        f3AclRuleSrcPortLowLimit,
        f3AclRuleSrcPortHighLimit,
        f3AclRuleDstPortControl,
        f3AclRuleDstPortLowLimit,
        f3AclRuleDstPortHighLimit,
        f3AclRuleTcpFlagsControl,
        f3AclRuleTcpFlags,
        f3AclRuleStorageType,
        f3AclRuleRowStatus,
        f3AclRuleActive,
        f3AclRuleSrcIpv6AddressControl,
        f3AclRuleSrcIpv6Address,
        f3AclRuleSrcIpv6AddressPrefixLen,
        f3AclRuleDstIpv6AddressControl,
        f3AclRuleDstIpv6Address,
        f3AclRuleDstIpv6AddressPrefixLen,
        f3AclRuleIpV6FlowLabelControl,
        f3AclRuleIpV6FlowLabel,
        f3AclRulePriorityControl,
        f3AclRulePriorityLowLimit,
        f3AclRulePriorityHighLimit
    }
    STATUS  current
    DESCRIPTION
            "A collection of objects used to manage the 
             F3 Ethernet Traffic Port FlowPoint ACL Rule."
    ::= { cmFacilityGroups 47 }
    
    f3EthernetTrafficPortExpDeGroup OBJECT-GROUP
    OBJECTS {
      f3EthernetTrafficPortExpDEEncIndex,
      f3EthernetTrafficPortExpDEEncInPriority,
      f3EthernetTrafficPortExpDEEncDropIneligiblePrio,
      f3EthernetTrafficPortExpDEEncDropEligiblePrio,
      f3EthernetTrafficPortExpDEDecIndex,
      f3EthernetTrafficPortExpDEDecInPriority,
      f3EthernetTrafficPortExpDEDecOutPriority,
      f3EthernetTrafficPortExpDEDecDropEligible,
      f3EthernetTrafficPortExpDEPairIndex,
      f3EthernetTrafficPortExpDEDropIneligiblePrio,
      f3EthernetTrafficPortExpDEDropEligiblePrio
    }
    STATUS  current
    DESCRIPTION
            "A collection of objects used to manage the 
             F3 Ethernet Traffic Port Exp De Decoding/Encoding 
             group function."
    ::= { cmFacilityGroups 48 }

f3XdslAndPpppoeParamGroup OBJECT-GROUP
    OBJECTS {
      cmEthernetNetPortXdslConnControl,
      cmEthernetNetPortXdslModulationMode,
      cmEthernetNetPortXdslBitSwapEnabled,
      cmEthernetNetPortXdslGvectorEnabled,
      cmEthernetNetPortXdslVdslProfile,
      cmEthernetNetPortXdslStatus,
      cmEthernetNetPortXdslCurVdslProfile,
      cmEthernetNetPortXdslActualLinkRateUpStream,
      cmEthernetNetPortXdslActualLinkRateDownStream,
      cmEthernetNetPortXdslControlChannel,
      cmEthernetNetPortXdslCarrierSet,
      cmEthernetNetPortXdslMode,
      cmEthernetNetPortXdslAnnex,
      cmEthernetNetPortXdslDsSNRMargin,
      cmEthernetNetPortXdslUsSNRMargin,
      cmEthernetNetPortXdslDsSignalAttenuation,
      cmEthernetNetPortXdslDsLineAttenuation,
      cmEthernetNetPortXdslDsTxPower,
      cmEthernetNetPortXdslUsTxPower,
      cmEthernetNetPortXdslDsAttainableRate,
      cmEthernetNetPortXdslUsAttainableRate,
      
      cmEthernetNetPortPppoeOuterVlanControl,
      cmEthernetNetPortPppoeOuterVlanEtherType,
      cmEthernetNetPortPppoeOuterVlanId,
      cmEthernetNetPortPppoeOuterVlanPriority,
      cmEthernetNetPortPppoeInnerVlanControl,
      cmEthernetNetPortPppoeInnerVlanEtherType,
      cmEthernetNetPortPppoeInnerVlanId,
      cmEthernetNetPortPppoeInnerVlanPriority,
      cmEthernetNetPortPppoeServiceName,
      cmEthernetNetPortPppoeLcpKeepAlivePeriod,
      cmEthernetNetPortPppoeLcpRetryThreshold,
      cmEthernetNetPortPppoeRxAcName,
      cmEthernetNetPortPppoeRxServiceName,
      cmEthernetNetPortPppoeSessionId,
      cmEthernetNetPortPppoeConnStatus
    }
    STATUS  current
    DESCRIPTION
            "A collection of objects used to manage the 
             F3 Ethernet Traffic Port XDSL Parameter."
    ::= { cmFacilityGroups 49 }

sciPortGroup OBJECT-GROUP
    OBJECTS {
        sciPortIndex,
        sciPortAdminState,
        sciPortOperationalState,
        sciPortSignalMode,
        sciPortSignalDirection,
        sciPortRxSsmQL
    }
    STATUS  current
    DESCRIPTION
            "A collection of objects used to manage the SCI port."
    ::= { cmFacilityGroups 50 }

cmTrafficPortQosShaperGroup OBJECT-GROUP
    OBJECTS {
        cmTrafficPortQosShaperIndex,
        cmTrafficPortQosShaperAdminState,
        cmTrafficPortQosShaperOperationalState,
        cmTrafficPortQosShaperSecondaryState,
        cmTrafficPortQosShaperAssociatedQueueProfile,
        cmTrafficPortQosShaperBufferSize,
        cmTrafficPortQosShaperCIRLo,
        cmTrafficPortQosShaperCIRHi,
        cmTrafficPortQosShaperEIRLo,
        cmTrafficPortQosShaperEIRHi,
        cmTrafficPortQosShaperStorageType,
        cmTrafficPortQosShaperRowStatus,
        cmTrafficPortQosShaperIngressAverageFrameSize,
        cmTrafficPortQosShaperAdditionalCIRLo,
        cmTrafficPortQosShaperAdditionalCIRHi,
        cmTrafficPortQosShaperWfqWeight
    }
    STATUS  current
    DESCRIPTION
            "A collection of objects used to manage the
             Ethernet Traffic Port QOS Shaper."
    ::= { cmFacilityGroups 51 }

f3IrigPortGroup OBJECT-GROUP
    OBJECTS {
        -- f3IrigRs422OutputPortTable columns
        f3IrigRs422OutputPortIndex, f3IrigRs422OutputPortIfIndex, f3IrigRs422OutputPortEntityIndex,
        f3IrigRs422OutputPortAlias, f3IrigRs422OutputPortAdminState, f3IrigRs422OutputPortOperationalState,
        f3IrigRs422OutputPortSecondaryState, f3IrigRs422OutputPortTimeCode, f3IrigRs422OutputPortControlField,
        -- f3IrigOpticalOutputPortTable columns
        f3IrigOpticalOutputPortIndex, f3IrigOpticalOutputPortIfIndex, f3IrigOpticalOutputPortEntityIndex,
        f3IrigOpticalOutputPortAlias, f3IrigOpticalOutputPortAdminState, f3IrigOpticalOutputPortOperationalState,
        f3IrigOpticalOutputPortSecondaryState, f3IrigOpticalOutputPortTimeCode, f3IrigOpticalOutputPortControlField,
        -- f3IrigRelayOutputPortTable columns
        f3IrigRelayOutputPortIndex, f3IrigRelayOutputPortIfIndex, f3IrigRelayOutputPortEntityIndex,
        f3IrigRelayOutputPortAlias, f3IrigRelayOutputPortAdminState, f3IrigRelayOutputPortOperationalState,
        f3IrigRelayOutputPortSecondaryState, f3IrigRelayOutputPortRelayOperation,
        -- f3IrigOutputGroupTable columns
        f3IrigOutputGroupIndex, f3IrigOutputGroupIfIndex, f3IrigOutputGroupEntityIndex, f3IrigOutputGroupAlias, f3IrigOutputGroupExtensionType, 
        f3IrigOutputGroupExtensionDetection,
        -- f3IrigOutputUnitPortTable columns
        f3IrigOutputUnitPortIndex, f3IrigOutputUnitPortIfIndex, f3IrigOutputUnitPortEntityIndex,
        f3IrigOutputUnitPortAlias, f3IrigOutputUnitPortAdminState, f3IrigOutputUnitPortOperationalState,
        f3IrigOutputUnitPortSecondaryState, f3IrigOutputUnitPortTimeCode, f3IrigOutputUnitPortControlField,
        f3IrigOutputUnitPortType, f3IrigOutputUnitPortDigitalVoltage
    }
    STATUS  current
    DESCRIPTION
            "A collection of objects used to manage IRIG Card and Port."
    ::= { cmFacilityGroups 52 }
    
ccGroup OBJECT-GROUP
    OBJECTS {
        -- ccInputPortTable
        ccInputPortIndex, ccInputPortIfIndex, ccInputPortEntityIndex, ccInputPortAlias,
        ccInputPortAdminState, ccInputPortOperationalState, ccInputPortSecondaryState,
        -- ccGroupPortTable
        ccGroupIndex, ccGroupIfIndex, ccGroupEntityIndex, ccGroupAlias,
        ccGroupActivePorts, ccGroupPhaseAdjust, ccGroupDutyCycle
    }
    STATUS  current
    DESCRIPTION
            "A collection of objects used to manage the CC Card."
    ::= { cmFacilityGroups 53 }

cmEncapFlowPointGroup OBJECT-GROUP
    OBJECTS{
        cmEncapFlowPointIndex,
        cmEncapFlowPointCircuitName,
        cmEncapFlowPointAssociatedFlowId,
        cmEncapFlowPointRefEoMplsPwObject,
        cmEncapFlowPointCTagControl,
        cmEncapFlowPointCTagVlanId,
        cmEncapFlowPointCTagVlanPriority,
        cmEncapFlowPointSTagControl,
        cmEncapFlowPointSTagVlanId,
        cmEncapFlowPointSTagVlanPriority,
        cmEncapFlowPointEgressOuterTagPrioMapEnabled,
        cmEncapFlowPointEgressInnerTagPrioMapEnabled,
        cmEncapFlowPointRefPrioMapProfile,
        cmEncapFlowPointStorageType, 
        cmEncapFlowPointRowStatus
    }
    STATUS  current
    DESCRIPTION
            "A collection of objects used to manage the encap flow point entry Group."
    ::= { cmFacilityGroups 54 }

END
