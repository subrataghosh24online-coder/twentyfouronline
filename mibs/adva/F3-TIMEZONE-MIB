F3-TIMEZONE-MIB DEFINITIONS ::= BEGIN

IMPORTS
    MODULE-COMPLIANCE, OBJECT-GROUP 
             FROM SNMPv2-CONF
    MODULE-IDENTITY, OBJECT-TYPE, Integer32
             FROM SNMPv2-SMI
    TEXTUAL-CONVENTION, DisplayString, TruthValue
             FROM SNMPv2-TC
    fsp150cm
             FROM  ADVA-MIB;

f3TimeZoneMIB MODULE-IDENTITY
    LAST-UPDATED        "201406050000Z"
    ORGANIZATION    "ADVA Optical Networking"
    CONTACT-INFO
            "        Michal Pawlowski
                     ADVA Optical Networking, Inc.
                Tel: +48 58 7716 416
             E-mail: mpawlowski@advaoptical.com
             Postal: ul. Slaska 35/37
                     81-310 Gdynia, Poland"
    DESCRIPTION
            "This module defines the Time Zone MIB definitions 
             used by the F3 (FSP150CM/CC) product lines.
             Copyright (C) ADVA Optical Networking."
    REVISION        "201406050000Z"
    DESCRIPTION
        "
         Notes from release 201406050000Z,
         (1) MIB version ready for release FSP150CC 6.5.CC." 

    ::= {fsp150cm 32}

-- 
-- OID definitions
-- 

f3TimeZoneConfigObjects            OBJECT IDENTIFIER ::= {f3TimeZoneMIB 1}
f3TimeZoneConformance              OBJECT IDENTIFIER ::= {f3TimeZoneMIB 2}

--
-- Textual Conventions 
-- 

MonthOfYear ::= TEXTUAL-CONVENTION
    STATUS      current
    DESCRIPTION
        "Month of year."
    SYNTAX      INTEGER {
                  january(1),
                  february(2),
                  march(3),
                  april(4),
                  may(5),
                  june(6),
                  july(7),
                  august(8),
                  september(9),
                  october(10),
                  november(11),
                  december(12)
                }

--
--  Time Zone Configure Scalars
--

f3TimeZoneUtcOffset OBJECT-TYPE
    SYNTAX     DisplayString
    MAX-ACCESS read-write
    STATUS     current
    DESCRIPTION
         "This object provides the ability to set UTC offset."
    ::= { f3TimeZoneConfigObjects 1 }

f3TimeZoneDstControlEnabled OBJECT-TYPE
    SYNTAX     TruthValue
    MAX-ACCESS read-write
    STATUS     current
    DESCRIPTION
         "This object provides the ability to toggle DST functionality."
    ::= { f3TimeZoneConfigObjects 2 }

f3TimeZoneDstUtcOffset OBJECT-TYPE
    SYNTAX     DisplayString
    MAX-ACCESS read-write
    STATUS     current
    DESCRIPTION
         "This object provides the ability to set DST Offset which is
          the Daylight Savings Time offset from Local Time."
    ::= { f3TimeZoneConfigObjects 3 }

f3TimeZoneDstStartMonth OBJECT-TYPE
    SYNTAX     MonthOfYear
    MAX-ACCESS read-write
    STATUS     current
    DESCRIPTION
         "This object provides the ability to set DST start month."
    ::= { f3TimeZoneConfigObjects 4 }

f3TimeZoneDstStartDay OBJECT-TYPE
    SYNTAX     DisplayString
    MAX-ACCESS read-write
    STATUS     current
    DESCRIPTION
         "This object provides the ability to set DST start day."
    ::= { f3TimeZoneConfigObjects 5 }

f3TimeZoneDstStartTime OBJECT-TYPE
    SYNTAX     DisplayString
    MAX-ACCESS read-write
    STATUS     current
    DESCRIPTION
         "This object provides the ability to set DST start time."
    ::= { f3TimeZoneConfigObjects 6 }

f3TimeZoneDstEndMonth OBJECT-TYPE
    SYNTAX     MonthOfYear
    MAX-ACCESS read-write
    STATUS     current
    DESCRIPTION
         "This object provides the ability to set DST end month."
    ::= { f3TimeZoneConfigObjects 7 }

f3TimeZoneDstEndDay OBJECT-TYPE
    SYNTAX     DisplayString
    MAX-ACCESS read-write
    STATUS     current
    DESCRIPTION
         "This object provides the ability to set DST end day."
    ::= { f3TimeZoneConfigObjects 8 }

f3TimeZoneDstEndTime OBJECT-TYPE
    SYNTAX     DisplayString
    MAX-ACCESS read-write
    STATUS     current
    DESCRIPTION
         "This object provides the ability to set DST end time."
    ::= { f3TimeZoneConfigObjects 9 }

--
-- Conformance
--

f3TimeZoneCompliances OBJECT IDENTIFIER ::= {f3TimeZoneConformance 1}
f3TimeZoneGroups    OBJECT IDENTIFIER ::= {f3TimeZoneConformance 2}

f3TimeZoneCompliance MODULE-COMPLIANCE
    STATUS  current
    DESCRIPTION
            "Describes the requirements for conformance to the F3-TIMEZONE-MIB compliance."
    MODULE  -- this module
        MANDATORY-GROUPS {
              f3TimeZoneConfigGroup
        }
    ::= { f3TimeZoneCompliances 1 }

f3TimeZoneConfigGroup OBJECT-GROUP
    OBJECTS {
       f3TimeZoneUtcOffset,
       f3TimeZoneDstControlEnabled,
       f3TimeZoneDstUtcOffset,
       f3TimeZoneDstStartMonth,
       f3TimeZoneDstStartDay,
       f3TimeZoneDstStartTime,
       f3TimeZoneDstEndMonth,
       f3TimeZoneDstEndDay,
       f3TimeZoneDstEndTime
    }
    STATUS  current
    DESCRIPTION
             "A collection of objects used to manage the Time Zone."
    ::= { f3TimeZoneGroups 1 }

END
