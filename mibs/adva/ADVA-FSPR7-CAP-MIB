--  ***************************************************************************
--  ADVA-FSPR7-CAP-MIB.txt
--
--               ADVA AG Optical Networking Capability MIB File
--
--  Copyright 2011 ADVA AG Optical Networking.
--
--  All rights reserved.
--  ***************************************************************************


--  MIB capability definitions required for entity management.

ADVA-FSPR7-CAP-MIB DEFINITIONS ::= BEGIN 

IMPORTS



    MODULE-COMPLIANCE,
    OBJECT-GROUP
                FROM SNMPv2-CONF


    OBJECT-TYPE,
    MODULE-IDENTITY,
    Integer32,
    Unsigned32
                FROM SNMPv2-SMI


    RowStatus
                FROM SNMPv2-TC


    SnmpAdminString
                FROM SNMP-FRAMEWORK-MIB


    fspR7,
    ApsHoldoffTimeCaps,
    ApsDirectionCaps,
    EnableStateCaps,
    EthDuplexModeCaps,
    FspR7EquipmentTypeCaps,
    LoopConfigCaps,
    OhTerminationLevelCaps,
    OtnPayloadTypeCaps,
    OtnTcmLevelCaps,
    SonetTimingSourceCaps,
    SonetTraceFormCaps,
    TimModeCaps,
    VirtualContainerTypeCaps,
    ProtectionMechCaps
                FROM ADVA-MIB


    ApsRevertModeCaps,
    ApsTypeCaps,
    Counter64StringCaps,
    CryptoFspR7EncryptionCommunicationCaps,
    FfpTypeCaps,
    FspR7AcpCaps,
    FspR7APSCommandCaps,
    FspR7ApsFarEndModuleCaps,
    FspR7AdminStateCaps,
    FspR7AlsModeCaps,
    FspR7BERThresholdCaps,
    FspR7BidirectionalChannelCaps,
    FspR7BaundCaps,
    FspR7BitrateCaps,
    FspR7CapInventoryCaps,
    FspR7CdCompensationRangeCaps,
    FspR7CdPostCompensationRangeCaps,
    FspR7ChannelBandwidthCaps,
    FspR7ChannelIdentifierCaps,
    FspR7ChannelRangeInventoryCaps,
    FspR7ChannelSpacingCaps,
    FspR7CodeGainCaps,
    FspR7ConnCaps,
    FspR7ConnectorTypeCaps,
    FspR7CpAuthTypeCaps,
    FspR7DCFiberTypeCaps,
    FspR7DeploymentScenarioCaps,
    FspR7DhcpServerCaps,
    FspR7DisableEnableCaps,
    FspR7DispersionCompensationCaps,
    FspR7DispersionModesCaps,
    FspR7DmsrmtOperationCaps,
    FspR7EdfaOutputPowerRatingCaps,
    FspR7EnableDisableCaps,
    FspR7ErrorFwdModeCaps,
    FspR7FecTypeCaps,
    FspR7FiberBrandCaps,
    FspR7FlowControlModeCaps,
    FspR7ForcedStatusCaps,
    FspR7FrameFormatCaps,
    FspR7FunctionCrsCaps,
    FspR7GainCaps,
    FspR7GainRangeCaps,
    FspR7GccUsageCaps,
    FspR7Integer32Caps,
    FspR7InterfaceCrossoverCaps,
    FspR7InterfaceTypeCaps,
    FspR7InvertTelemetryInputLogicCaps,
    FspR7IpModeCaps,
    FspR7IpTypeCaps,
    FspR7IPv6TypeCaps,
    FspR7LacpModeCaps,
    FspR7LacpTimeoutCaps,
    FspR7LagPortTypeCaps,
    FspR7LaneGroupInventoryCaps,
    FspR7LaserDelayTimerCaps,
    FspR7LengthCaps,
    FspR7LineCodingCaps,
    FspR7LLDPNeighborsCaps,
    FspR7LLDPScopeCaps,
    FspR7ManualAutoCaps,
    FspR7MappingCaps,
    FspR7MaxBitErrorRateCaps,
    FspR7MonLevelCaps,
    FspR7MuxMethodCaps,
    FspR7NoYesCaps,
    FspR7NumberOfChannelsCaps,
    FspR7OpticalBandCaps,
    FspR7OpticalFiberTypeCaps,
    FspR7OpticalGroupCaps,
    FspR7OpticalInterfaceReachCaps,
    FspR7OpticalSubBandCaps,
    FspR7OptimizeCaps,
    FspR7OpuPayloadTypeCaps,
    FspR7OscUsageCaps,
    FspR7OspfModeCaps,
    FspR7OtdrPeriodCaps,
    FspR7PathNodeCaps,
    FspR7PlugDataRateCaps,
    FspR7PlugTypeCaps,
    FspR7PlugModeCaps,
    FspR7PmResetCaps,
    FspR7PortBehaviourCaps,
    FspR7PortModeCaps,
    FspR7PortRoleCaps,
    FspR7PsuOutputPowerCaps,
    FspR7RlsActionCaps,
    FspR7RoadmNumberCaps,
    FspR7RowStatusCaps,
    FspR7SingleFiberLocationCaps,
    FspR7SnmpLongString,
    FspR7SupplyTypeCaps,
    FspR7TelemetryOutputCaps,
    FspR7TerminationModeCaps,
    FspR7TiltSetCaps,
    FspR7TimDetModeCaps,
    FspR7TopologyCaps,
    FspR7TrafficDirectionCaps,
    FspR7TransmissionModeCaps,
    FspR7TxOffOnTmCaps,
    FspR7TypeConnectionCaps,
    FspR7TypeCrsCaps,
    FspR7Unsigned32Caps,
    FspR7UntaggedFramesCaps,
    FspR7VoaModeCaps,
    FspR7XfpDecisionThresCaps,
    FspR7YcableTypeCaps,
    FspR7FltrCableTypeCaps,
    FspR7YesNoCaps,
    FspR7YesNo
                FROM ADVA-FSPR7-TC-MIB


    entityConnectionClassName,
    entityContainerShelfNo,
    entityContainerSlotNo,
    entityContainerPortNo,
    entityContainerExtNo,
    entityContainerClassName,
    entityCrossConnFromShelfNo,
    entityCrossConnFromSlotNo,
    entityCrossConnFromPortNo,
    entityCrossConnFromExtNo,
    entityCrossConnFromClassName,
    entityCrossConnToShelfNo,
    entityCrossConnToSlotNo,
    entityCrossConnToPortNo,
    entityCrossConnToExtNo,
    entityCrossConnToClassName,
    entityCrossConnClassName,
    entityCrsOptLineFromIndexNo1,
    entityCrsOptLineFromIndexNo2,
    entityCrsOptLineFromIndexNo3,
    entityCrsOptLineFromIndexNo4,
    entityCrsOptLineFromClassName,
    entityCrsOptLineToIndexNo1,
    entityCrsOptLineToIndexNo2,
    entityCrsOptLineToIndexNo3,
    entityCrsOptLineToIndexNo4,
    entityCrsOptLineToClassName,
    entityCrsOptLineClassName,
    entityDcnShelfNo,
    entityDcnSlotNo,
    entityDcnPortNo,
    entityDcnExtNo,
    entityDcnClassName,
    entityEqptShelfNo,
    entityEqptSlotNo,
    entityEqptPortNo,
    entityEqptExtNo,
    entityEqptClassName,
    entityExternalPortShelfNo,
    entityExternalPortSlotNo,
    entityExternalPortPortNo,
    entityExternalPortExtNo,
    entityExternalPortClassName,
    entityFacilityShelfNo,
    entityFacilitySlotNo,
    entityFacilityPortNo,
    entityFacilityExtNo,
    entityFacilityClassName,
    entityOpticalMuxShelfNo,
    entityOpticalMuxSlotNo,
    entityOpticalMuxPortNo,
    entityOpticalMuxExtNo,
    entityOpticalMuxClassName,
    entityOptLineIndexNo1,
    entityOptLineClassName,
    entityProtectionCableIndex1,
    entityProtectionCableIndex2,
    entityProtectionCableIndex3,
    entityProtectionCableIndex4,
    entityProtectionCableClassName,
    entityFilterCableIndex1,
    entityFilterCableIndex2,
    entityFilterCableIndex3,
    entityFilterCableIndex4,
    entityFilterCableClassName,
    entityShelfConnShelfNo,
    entityShelfConnSlotNo,
    entityShelfConnPortNo,
    entityShelfConnExtNo,
    entityShelfConnClassName,
    entityTerminPointIndexNo1,
    entityTerminPointIndexNo2,
    entityTerminPointIndexNo3,
    entityTerminPointIndexNo4,
    entityTerminPointClassName,
    entityFfpShelfNo,
    entityFfpSlotNo,
    entityFfpPortNo,
    entityFfpExtNo,
    entityFfpClassName,
    entityCrossDcnShelfNo,
    entityCrossDcnSlotNo,
    entityCrossDcnPortNo,
    entityCrossDcnExtNo,
    entityCrossDcnClassName
                FROM ADVA-FSPR7-MIB;

advaFspR7Cap MODULE-IDENTITY

    LAST-UPDATED "201812140000Z"

    ORGANIZATION "ADVA Optical Networking"

    CONTACT-INFO "EMEA Support
                  Phone : +49 89 89 0665 848
                  Fax   : +49 89 89 0665 22848
                  Email : support@advaoptical.com

                  North American Support
                  Phone : 886 442 ADVA (2382) (toll-free within the US, Canada and Mexico)
                  Fax   : + 1 806 741 8529 (elsewhere)
                  Email : support-usa@advaoptical.com

                  Asia Pacific Support
                  Phone : + 1 866 442 2382 (other toll-free numbers available in some countries)
                  Email : support-asia@advaoptical.com"

    DESCRIPTION   "This is a MIB definition for ADVA AG Optical Networking entity management."

    REVISION        "201812140000Z"
    DESCRIPTION     "FSP3000 F7 Release 18.2.1 MIB."

    REVISION        "201810300000Z"
    DESCRIPTION     "FSP3000 F7 Release 18.1.2 MIB."

    REVISION        "201808090000Z"
    DESCRIPTION     "FSP3000 F7 Release 18.1.1 MIB."

    REVISION        "201805280000Z"
    DESCRIPTION     "FSP3000 F7 Release 17.2.2 MIB."

    REVISION        "201804170000Z"
    DESCRIPTION     "FSP3000 F7 Release 17.2.1 MIB."

    REVISION        "201803150000Z"
    DESCRIPTION     "FSP3000 F7 Release 17.1.2 MIB."

    REVISION        "201802260000Z"
    DESCRIPTION     "FSP3000 F7 Release 16.3.3 MIB."

    REVISION        "201712070000Z"
    DESCRIPTION     "FSP3000 F7 Release 17.1.1 MIB."

    REVISION        "201711010000Z"
    DESCRIPTION     "FSP3000 F7 Release 16.3.2 MIB."

    REVISION        "201709110000Z"
    DESCRIPTION     "FSP3000 F7 Release 16.3.1 MIB."

    REVISION        "201706060000Z"
    DESCRIPTION     "FSP3000 F7 Release 16.2.2 MIB."

    REVISION        "201703230000Z"
    DESCRIPTION     "FSP3000 F7 Release 16.2.1 MIB."

    REVISION        "201604010000Z"
    DESCRIPTION     "FSP3000 F7 Release 16.1.1 MIB."

    REVISION        "201512100000Z"
    DESCRIPTION     "FSP3000 F7 Release 15.2.1 MIB."

    REVISION        "201510010000Z"
    DESCRIPTION     "FSP3000 F7 Release 15.1.2 MIB."

    REVISION        "201509030000Z"
    DESCRIPTION     "FSP3000 F7 Release 15.1.1 MIB."

    REVISION        "201503200000Z"
    DESCRIPTION     "FSP3000 F7 Release 13.3.1 MIB."

    REVISION        "201410150000Z"
    DESCRIPTION     "FSP3000 F7 Release 13.2.2 MIB."

    REVISION        "201409290000Z"
    DESCRIPTION     "FSP3000 F7 Release 13.2.1 MIB."

    REVISION        "201312040000Z"
    DESCRIPTION     "FSP3000 F7 Release 12.2.1 MIB."

    REVISION        "201308200000Z"
    DESCRIPTION     "FSP3000 F7 Release 12.1.1 MIB."

    REVISION        "201105220000Z"
    DESCRIPTION     "FSP3000 F7 Release 11.2 MIB."
    ::= { fspR7 9 }

managementCap
    OBJECT IDENTIFIER ::= { advaFspR7Cap 3 }

specificMgmtCap
    OBJECT IDENTIFIER ::= { managementCap 2 }

eqptMgmtCap
    OBJECT IDENTIFIER ::= { managementCap 3 }

facilityMgmtCap
    OBJECT IDENTIFIER ::= { managementCap 4 }

dcnMgmtCap
    OBJECT IDENTIFIER ::= { managementCap 5 }

opticalMuxMgmtCap
    OBJECT IDENTIFIER ::= { managementCap 6 }

shelfConnMgmtCap
    OBJECT IDENTIFIER ::= { managementCap 7 }

envMgmtCap
    OBJECT IDENTIFIER ::= { managementCap 8 }

containerMgmtCap
    OBJECT IDENTIFIER ::= { managementCap 9 }

opticalLineMgmtCap
    OBJECT IDENTIFIER ::= { managementCap 10 }

performanceCap
    OBJECT IDENTIFIER ::= { advaFspR7Cap 6 }

performanceFacilityCap
    OBJECT IDENTIFIER ::= { performanceCap 4 }

performanceFacilityThresholdCap
    OBJECT IDENTIFIER ::= { performanceFacilityCap 1 }

pmEqptCap
    OBJECT IDENTIFIER ::= { performanceCap 10 }

pmDcnCap
    OBJECT IDENTIFIER ::= { performanceCap 11 }

pmDcnDataCap
    OBJECT IDENTIFIER ::= { pmDcnCap 1 }

pmDcnPhysicalCap
    OBJECT IDENTIFIER ::= { pmDcnCap 2 }

pmDcnPhysThresholdCap
    OBJECT IDENTIFIER ::= { pmDcnPhysicalCap 2 }

pmFacilityCap
    OBJECT IDENTIFIER ::= { performanceCap 12 }

pmFacilityDataCap
    OBJECT IDENTIFIER ::= { pmFacilityCap 1 }

pmFacilityDataThresholdCap
    OBJECT IDENTIFIER ::= { pmFacilityDataCap 1 }

pmFacilityPhysicalCap
    OBJECT IDENTIFIER ::= { pmFacilityCap 2 }

pmFacilityPhysValueCap
    OBJECT IDENTIFIER ::= { pmFacilityPhysicalCap 1 }

pmFacilityPhysThresholdCap
    OBJECT IDENTIFIER ::= { pmFacilityPhysicalCap 2 }

pmTerminPointCap
    OBJECT IDENTIFIER ::= { performanceCap 13 }

pmOptMuxCap
    OBJECT IDENTIFIER ::= { performanceCap 14 }

pmOptMuxDataCap
    OBJECT IDENTIFIER ::= { pmOptMuxCap 1 }

pmOptMuxPhysicalCap
    OBJECT IDENTIFIER ::= { pmOptMuxCap 2 }

pmOptMuxPhysValueCap
    OBJECT IDENTIFIER ::= { pmOptMuxPhysicalCap 1 }

pmOptMuxPhysThresholdCap
    OBJECT IDENTIFIER ::= { pmOptMuxPhysicalCap 2 }

featureSpecificCap
    OBJECT IDENTIFIER ::= { advaFspR7Cap 7 }

fiberMapCap
    OBJECT IDENTIFIER ::= { featureSpecificCap 1 }

eciCap
    OBJECT IDENTIFIER ::= { featureSpecificCap 3 }

changeServiceCap
    OBJECT IDENTIFIER ::= { featureSpecificCap 5 }

protectionCap
    OBJECT IDENTIFIER ::= { featureSpecificCap 6 }

crossConnectionCapTable OBJECT-TYPE
    SYNTAX        SEQUENCE OF CrossConnectionCapEntry
    MAX-ACCESS    not-accessible
    STATUS        current
    DESCRIPTION   "crossConnectionCapTable"
    ::= { specificMgmtCap 6 }

crossConnectionCapEntry OBJECT-TYPE
    SYNTAX        CrossConnectionCapEntry
    MAX-ACCESS    not-accessible
    STATUS        current
    DESCRIPTION   "Entry of crossConnectionCapTable"
    INDEX       {
                  entityCrossConnFromShelfNo,
                  entityCrossConnFromSlotNo,
                  entityCrossConnFromPortNo,
                  entityCrossConnFromExtNo,
                  entityCrossConnFromClassName,
                  entityCrossConnToShelfNo,
                  entityCrossConnToSlotNo,
                  entityCrossConnToPortNo,
                  entityCrossConnToExtNo,
                  entityCrossConnToClassName,
                  entityCrossConnClassName
                }
    ::= { crossConnectionCapTable 1 }

CrossConnectionCapEntry ::= SEQUENCE
  {    crossConnectionCapRowStatus FspR7RowStatusCaps,
    crossConnectionCapAdmin FspR7AdminStateCaps,
    crossConnectionCapRedLineState FspR7YesNoCaps,
    crossConnectionCapConn FspR7ConnCaps,
    crossConnectionCapAlias Integer32,
    crossConnectionCapPathNode FspR7PathNodeCaps,
    crossConnectionCapTunnelAid Integer32,
    crossConnectionCapType FspR7InterfaceTypeCaps,
    crossConnectionCapCrsFunction FspR7FunctionCrsCaps,
    crossConnectionCapCrsFromAidTwo FspR7SnmpLongString,
    crossConnectionCapCrsToAidTwo FspR7SnmpLongString,
    crossConnectionCapCrsMcAidList FspR7SnmpLongString,
    crossConnectionCapCrsContAidList FspR7SnmpLongString,
    crossConnectionCapCrsContAidListTwo FspR7SnmpLongString }

crossConnectionCapRowStatus OBJECT-TYPE
    SYNTAX        FspR7RowStatusCaps
    MAX-ACCESS    read-only
    STATUS        current
    DESCRIPTION   "Cross Connection Capability RowStatus."
    ::= { crossConnectionCapEntry 1 }

crossConnectionCapAdmin OBJECT-TYPE
    SYNTAX        FspR7AdminStateCaps
    MAX-ACCESS    read-only
    STATUS        current
    DESCRIPTION   "Cross Connection Capability Adminstrative State."
    ::= { crossConnectionCapEntry 2 }

crossConnectionCapRedLineState OBJECT-TYPE
    SYNTAX        FspR7YesNoCaps
    MAX-ACCESS    read-only
    STATUS        current
    DESCRIPTION   "Cross Connection Capability Red Lined State."
    ::= { crossConnectionCapEntry 3 }

crossConnectionCapConn OBJECT-TYPE
    SYNTAX        FspR7ConnCaps
    MAX-ACCESS    read-only
    STATUS        current
    DESCRIPTION   "Cross Connection Capability Direction."
    ::= { crossConnectionCapEntry 4 }

crossConnectionCapAlias OBJECT-TYPE
    SYNTAX        Integer32
    MAX-ACCESS    read-only
    STATUS        current
    DESCRIPTION   "Cross Connection Capability Alias."
    ::= { crossConnectionCapEntry 5 }

crossConnectionCapPathNode OBJECT-TYPE
    SYNTAX        FspR7PathNodeCaps
    MAX-ACCESS    read-only
    STATUS        current
    DESCRIPTION   "Cross Connection Capability Path Node."
    ::= { crossConnectionCapEntry 6 }

crossConnectionCapTunnelAid OBJECT-TYPE
    SYNTAX        Integer32
    MAX-ACCESS    read-only
    STATUS        current
    DESCRIPTION   "Cross Connection Capability Tunnel AID."
    ::= { crossConnectionCapEntry 7 }

crossConnectionCapType OBJECT-TYPE
    SYNTAX        FspR7InterfaceTypeCaps
    MAX-ACCESS    read-only
    STATUS        current
    DESCRIPTION   "Cross Connection Capability Type Facility."
    ::= { crossConnectionCapEntry 8 }

crossConnectionCapCrsFunction OBJECT-TYPE
    SYNTAX        FspR7FunctionCrsCaps
    MAX-ACCESS    read-only
    STATUS        current
    DESCRIPTION   "Cross Connection Capability Crs Function."
    ::= { crossConnectionCapEntry 9 }

crossConnectionCapCrsFromAidTwo OBJECT-TYPE
    SYNTAX        FspR7SnmpLongString
    MAX-ACCESS    read-only
    STATUS        current
    DESCRIPTION   "Secondary source point (AID)"
    ::= { crossConnectionCapEntry 10 }

crossConnectionCapCrsToAidTwo OBJECT-TYPE
    SYNTAX        FspR7SnmpLongString
    MAX-ACCESS    read-only
    STATUS        current
    DESCRIPTION   "Secondary destination point (AID)"
    ::= { crossConnectionCapEntry 11 }

crossConnectionCapCrsMcAidList OBJECT-TYPE
    SYNTAX        FspR7SnmpLongString
    MAX-ACCESS    read-only
    STATUS        current
    DESCRIPTION   "Cross Connection destinations for multicast services (List of AIDs)"
    ::= { crossConnectionCapEntry 12 }

crossConnectionCapCrsContAidList OBJECT-TYPE
    SYNTAX        FspR7SnmpLongString
    MAX-ACCESS    read-only
    STATUS        current
    DESCRIPTION   "Cross connect destinations that continue on the network (List of AIDs)"
    ::= { crossConnectionCapEntry 13 }

crossConnectionCapCrsContAidListTwo OBJECT-TYPE
    SYNTAX        FspR7SnmpLongString
    MAX-ACCESS    read-only
    STATUS        current
    DESCRIPTION   "Cross Connection secondary destinations that continue on the network (List of AIDs)"
    ::= { crossConnectionCapEntry 14 }

crossOpticalLineCapTable OBJECT-TYPE
    SYNTAX        SEQUENCE OF CrossOpticalLineCapEntry
    MAX-ACCESS    not-accessible
    STATUS        current
    DESCRIPTION   "crossOpticalLineCapTable"
    ::= { specificMgmtCap 7 }

crossOpticalLineCapEntry OBJECT-TYPE
    SYNTAX        CrossOpticalLineCapEntry
    MAX-ACCESS    not-accessible
    STATUS        current
    DESCRIPTION   "Entry of crossOpticalLineCapTable"
    INDEX       {
                  entityCrsOptLineFromIndexNo1,
                  entityCrsOptLineFromIndexNo2,
                  entityCrsOptLineFromIndexNo3,
                  entityCrsOptLineFromIndexNo4,
                  entityCrsOptLineFromClassName,
                  entityCrsOptLineToIndexNo1,
                  entityCrsOptLineToIndexNo2,
                  entityCrsOptLineToIndexNo3,
                  entityCrsOptLineToIndexNo4,
                  entityCrsOptLineToClassName,
                  entityCrsOptLineClassName
                }
    ::= { crossOpticalLineCapTable 1 }

CrossOpticalLineCapEntry ::= SEQUENCE
  {    crossOpticalLineCapRowStatus FspR7RowStatusCaps,
    crossOpticalLineCapRedLineState FspR7YesNoCaps,
    crossOpticalLineCapConn FspR7ConnCaps,
    crossOpticalLineCapCrsType FspR7TypeCrsCaps,
    crossOpticalLineCapAlias Integer32,
    crossOpticalLineCapTunnelAid Integer32 }

crossOpticalLineCapRowStatus OBJECT-TYPE
    SYNTAX        FspR7RowStatusCaps
    MAX-ACCESS    read-only
    STATUS        current
    DESCRIPTION   "Cross Optical Line Capability RowStatus."
    ::= { crossOpticalLineCapEntry 1 }

crossOpticalLineCapRedLineState OBJECT-TYPE
    SYNTAX        FspR7YesNoCaps
    MAX-ACCESS    read-only
    STATUS        current
    DESCRIPTION   "Cross Optical Line Capability Red Lined State."
    ::= { crossOpticalLineCapEntry 2 }

crossOpticalLineCapConn OBJECT-TYPE
    SYNTAX        FspR7ConnCaps
    MAX-ACCESS    read-only
    STATUS        current
    DESCRIPTION   "Cross Optical Line Capability Direction."
    ::= { crossOpticalLineCapEntry 3 }

crossOpticalLineCapCrsType OBJECT-TYPE
    SYNTAX        FspR7TypeCrsCaps
    MAX-ACCESS    read-only
    STATUS        current
    DESCRIPTION   "Cross Optical Line Capability Type."
    ::= { crossOpticalLineCapEntry 4 }

crossOpticalLineCapAlias OBJECT-TYPE
    SYNTAX        Integer32
    MAX-ACCESS    read-only
    STATUS        current
    DESCRIPTION   "Cross Optical Line Capability Alias."
    ::= { crossOpticalLineCapEntry 5 }

crossOpticalLineCapTunnelAid OBJECT-TYPE
    SYNTAX        Integer32
    MAX-ACCESS    read-only
    STATUS        current
    DESCRIPTION   "Cross Optical Line Capability  Tunnel AID."
    ::= { crossOpticalLineCapEntry 6 }

endOfCrossOpticalLineCapTable OBJECT-TYPE
    SYNTAX        Integer32
    MAX-ACCESS    read-only
    STATUS        current
    DESCRIPTION   ""
    ::= { specificMgmtCap 8 }

crossDcnCapTable OBJECT-TYPE
    SYNTAX        SEQUENCE OF CrossDcnCapEntry
    MAX-ACCESS    not-accessible
    STATUS        current
    DESCRIPTION   "crossDcnCapTable"
    ::= { specificMgmtCap 9 }

crossDcnCapEntry OBJECT-TYPE
    SYNTAX        CrossDcnCapEntry
    MAX-ACCESS    not-accessible
    STATUS        current
    DESCRIPTION   "Entry of crossDcnCapTable"
    INDEX       {
                  entityCrossDcnShelfNo,
                  entityCrossDcnSlotNo,
                  entityCrossDcnPortNo,
                  entityCrossDcnExtNo,
                  entityCrossDcnClassName
                }
    ::= { crossDcnCapTable 1 }

CrossDcnCapEntry ::= SEQUENCE
  {    crossDcnCapRowStatus FspR7RowStatusCaps,
    crossDcnCapType FspR7TypeConnectionCaps,
    crossDcnCapLink SnmpAdminString,
    crossDcnCapEcc SnmpAdminString }

crossDcnCapRowStatus OBJECT-TYPE
    SYNTAX        FspR7RowStatusCaps
    MAX-ACCESS    read-only
    STATUS        current
    DESCRIPTION   "RowStatus object is used to create or delete a row in the table."
    ::= { crossDcnCapEntry 1 }

crossDcnCapType OBJECT-TYPE
    SYNTAX        FspR7TypeConnectionCaps
    MAX-ACCESS    read-only
    STATUS        current
    DESCRIPTION   "Type of Cross-Connect"
    ::= { crossDcnCapEntry 2 }

crossDcnCapLink OBJECT-TYPE
    SYNTAX        SnmpAdminString
    MAX-ACCESS    read-only
    STATUS        current
    DESCRIPTION   "Address Identifier of PPPIP LINK Entity."
    ::= { crossDcnCapEntry 3 }

crossDcnCapEcc OBJECT-TYPE
    SYNTAX        SnmpAdminString
    MAX-ACCESS    read-only
    STATUS        current
    DESCRIPTION   "Address Identifier of ECC Entity."
    ::= { crossDcnCapEntry 4 }

endOfCrossDcnCapTable OBJECT-TYPE
    SYNTAX        Integer32
    MAX-ACCESS    read-only
    STATUS        current
    DESCRIPTION   ""
    ::= { specificMgmtCap 10 }

endOfSpecificMgmtCap OBJECT-TYPE
    SYNTAX        Integer32
    MAX-ACCESS    read-only
    STATUS        current
    DESCRIPTION   ""
    ::= { specificMgmtCap 10000 }

shelfCapTable OBJECT-TYPE
    SYNTAX        SEQUENCE OF ShelfCapEntry
    MAX-ACCESS    not-accessible
    STATUS        current
    DESCRIPTION   "shelfCapTable"
    ::= { eqptMgmtCap 1 }

shelfCapEntry OBJECT-TYPE
    SYNTAX        ShelfCapEntry
    MAX-ACCESS    not-accessible
    STATUS        current
    DESCRIPTION   "Entry of shelfCapTable"
    INDEX       {
                  entityEqptShelfNo,
                  entityEqptSlotNo,
                  entityEqptPortNo,
                  entityEqptExtNo,
                  entityEqptClassName
                }
    ::= { shelfCapTable 1 }

ShelfCapEntry ::= SEQUENCE
  {    shelfCapRowStatus FspR7RowStatusCaps,
    shelfCapPsuOutputPower FspR7PsuOutputPowerCaps,
    shelfCapType FspR7EquipmentTypeCaps,
    shelfCapRack Integer32,
    shelfCapSupply FspR7SupplyTypeCaps,
    shelfCapBandProvision FspR7OpticalBandCaps,
    shelfCapAdmin FspR7AdminStateCaps,
    shelfCapRackNumber FspR7Unsigned32Caps,
    shelfCapRackOrder FspR7Unsigned32Caps,
    shelfCapAlias Integer32,
    shelfCapSlot FspR7Unsigned32Caps,
    shelfCapPowerSupplyProtection FspR7EnableDisableCaps,
    shelfCapAirFilterClear FspR7RlsActionCaps,
    shelfCapAirFilterCycle FspR7Unsigned32Caps }

shelfCapRowStatus OBJECT-TYPE
    SYNTAX        FspR7RowStatusCaps
    MAX-ACCESS    read-only
    STATUS        current
    DESCRIPTION   "RowStatus object is used to create or delete a row in the table."
    ::= { shelfCapEntry 1 }

shelfCapPsuOutputPower OBJECT-TYPE
    SYNTAX        FspR7PsuOutputPowerCaps
    MAX-ACCESS    read-only
    STATUS        current
    DESCRIPTION   "Maximum PSU Output Power"
    ::= { shelfCapEntry 2 }

shelfCapType OBJECT-TYPE
    SYNTAX        FspR7EquipmentTypeCaps
    MAX-ACCESS    read-only
    STATUS        current
    DESCRIPTION   "The TYPE of Equipment and the MODE setting determine uniquely
        the number and allowed TYPE's of the provisionable dependent
        entities (plugs, interfaces, modules)"
    ::= { shelfCapEntry 3 }

shelfCapRack OBJECT-TYPE
    SYNTAX        Integer32
    MAX-ACCESS    read-only
    STATUS        current
    DESCRIPTION   "Rack Containing Shelf"
    ::= { shelfCapEntry 4 }

shelfCapSupply OBJECT-TYPE
    SYNTAX        FspR7SupplyTypeCaps
    MAX-ACCESS    read-only
    STATUS        current
    DESCRIPTION   "The kind of power supply - provisioned value"
    ::= { shelfCapEntry 5 }

shelfCapBandProvision OBJECT-TYPE
    SYNTAX        FspR7OpticalBandCaps
    MAX-ACCESS    read-only
    STATUS        current
    DESCRIPTION   "Band Provision. Reference to BAND__INVENTORY."
    ::= { shelfCapEntry 6 }

shelfCapAdmin OBJECT-TYPE
    SYNTAX        FspR7AdminStateCaps
    MAX-ACCESS    read-only
    STATUS        current
    DESCRIPTION   "Administrative State is displayed in the GUI and Craft. Transition to Unassigend requires the entity to be deleted."
    ::= { shelfCapEntry 7 }

shelfCapRackNumber OBJECT-TYPE
    SYNTAX        FspR7Unsigned32Caps
    MAX-ACCESS    read-only
    STATUS        current
    DESCRIPTION   "Number of the Rack"
    ::= { shelfCapEntry 8 }

shelfCapRackOrder OBJECT-TYPE
    SYNTAX        FspR7Unsigned32Caps
    UNITS         "HU"
    MAX-ACCESS    read-only
    STATUS        current
    DESCRIPTION   "Defines the position of the shelf in a rack, starting from the top or bottom for the rack depending on Shelf Order (COUNT__ORDER). Shelf Position is used with Shelf Order for the graphical rack view."
    ::= { shelfCapEntry 9 }

shelfCapAlias OBJECT-TYPE
    SYNTAX        Integer32
    MAX-ACCESS    read-only
    STATUS        current
    DESCRIPTION   "User Applied Descriptor"
    ::= { shelfCapEntry 10 }

shelfCapSlot OBJECT-TYPE
    SYNTAX        FspR7Unsigned32Caps
    MAX-ACCESS    read-only
    STATUS        current
    DESCRIPTION   "Slot Position"
    ::= { shelfCapEntry 11 }

shelfCapPowerSupplyProtection OBJECT-TYPE
    SYNTAX        FspR7EnableDisableCaps
    MAX-ACCESS    read-only
    STATUS        current
    DESCRIPTION   "Power Supply Redundancy Configuration"
    ::= { shelfCapEntry 12 }

shelfCapAirFilterClear OBJECT-TYPE
    SYNTAX        FspR7RlsActionCaps
    MAX-ACCESS    read-only
    STATUS        current
    DESCRIPTION   "Operation to clear air filter replace condition and reset replacement count"
    ::= { shelfCapEntry 13 }

shelfCapAirFilterCycle OBJECT-TYPE
    SYNTAX        FspR7Unsigned32Caps
    UNITS         "month"
    MAX-ACCESS    read-only
    STATUS        current
    DESCRIPTION   "Sets the replacement duration for the air filter replace time setting in months; a setting of 0 prevents the replacement warning alram from being raised"
    ::= { shelfCapEntry 14 }

endOfShelfCapTable OBJECT-TYPE
    SYNTAX        Integer32
    MAX-ACCESS    read-only
    STATUS        current
    DESCRIPTION   ""
    ::= { eqptMgmtCap 2 }

fanCapTable OBJECT-TYPE
    SYNTAX        SEQUENCE OF FanCapEntry
    MAX-ACCESS    not-accessible
    STATUS        current
    DESCRIPTION   "fanCapTable"
    ::= { eqptMgmtCap 3 }

fanCapEntry OBJECT-TYPE
    SYNTAX        FanCapEntry
    MAX-ACCESS    not-accessible
    STATUS        current
    DESCRIPTION   "Entry of fanCapTable"
    INDEX       {
                  entityEqptShelfNo,
                  entityEqptSlotNo,
                  entityEqptPortNo,
                  entityEqptExtNo,
                  entityEqptClassName
                }
    ::= { fanCapTable 1 }

FanCapEntry ::= SEQUENCE
  {    fanCapRowStatus FspR7RowStatusCaps,
    fanCapForceDestroy FspR7ForcedStatusCaps,
    fanCapAdmin FspR7AdminStateCaps,
    fanCapType FspR7EquipmentTypeCaps,
    fanCapAlias Integer32,
    fanCapOutputReset FspR7RlsActionCaps }

fanCapRowStatus OBJECT-TYPE
    SYNTAX        FspR7RowStatusCaps
    MAX-ACCESS    read-only
    STATUS        current
    DESCRIPTION   "RowStatus object is used to create or delete a row in the table."
    ::= { fanCapEntry 1 }

fanCapForceDestroy OBJECT-TYPE
    SYNTAX        FspR7ForcedStatusCaps
    MAX-ACCESS    read-only
    STATUS        current
    DESCRIPTION   "Forced Destroy"
    ::= { fanCapEntry 2 }

fanCapAdmin OBJECT-TYPE
    SYNTAX        FspR7AdminStateCaps
    MAX-ACCESS    read-only
    STATUS        current
    DESCRIPTION   "Administrative State is displayed in the GUI and Craft. Transition to Unassigend requires the entity to be deleted."
    ::= { fanCapEntry 3 }

fanCapType OBJECT-TYPE
    SYNTAX        FspR7EquipmentTypeCaps
    MAX-ACCESS    read-only
    STATUS        current
    DESCRIPTION   "The TYPE of Equipment and the MODE setting determine uniquely
        the number and allowed TYPE's of the provisionable dependent
        entities (plugs, interfaces, modules)"
    ::= { fanCapEntry 4 }

fanCapAlias OBJECT-TYPE
    SYNTAX        Integer32
    MAX-ACCESS    read-only
    STATUS        current
    DESCRIPTION   "User Applied Descriptor"
    ::= { fanCapEntry 5 }

fanCapOutputReset OBJECT-TYPE
    SYNTAX        FspR7RlsActionCaps
    MAX-ACCESS    read-only
    STATUS        current
    DESCRIPTION   "Has the same function as the HW switch at the UTM board"
    ::= { fanCapEntry 6 }

endOfFanCapTable OBJECT-TYPE
    SYNTAX        Integer32
    MAX-ACCESS    read-only
    STATUS        current
    DESCRIPTION   ""
    ::= { eqptMgmtCap 4 }

plugCapTable OBJECT-TYPE
    SYNTAX        SEQUENCE OF PlugCapEntry
    MAX-ACCESS    not-accessible
    STATUS        current
    DESCRIPTION   "plugCapTable"
    ::= { eqptMgmtCap 5 }

plugCapEntry OBJECT-TYPE
    SYNTAX        PlugCapEntry
    MAX-ACCESS    not-accessible
    STATUS        current
    DESCRIPTION   "Entry of plugCapTable"
    INDEX       {
                  entityEqptShelfNo,
                  entityEqptSlotNo,
                  entityEqptPortNo,
                  entityEqptExtNo,
                  entityEqptClassName
                }
    ::= { plugCapTable 1 }

PlugCapEntry ::= SEQUENCE
  {    plugCapRowStatus FspR7RowStatusCaps,
    plugCapConnector FspR7ConnectorTypeCaps,
    plugCapType FspR7EquipmentTypeCaps,
    plugCapReach FspR7OpticalInterfaceReachCaps,
    plugCapLoopbackAttenuation FspR7Unsigned32Caps,
    plugCapTransmitChannel FspR7ChannelIdentifierCaps,
    plugCapAlias Integer32,
    plugCapLaneGroup FspR7LaneGroupInventoryCaps,
    plugCapMaxDataRate FspR7PlugDataRateCaps,
    plugCapThirdPartyUsage EnableStateCaps,
    plugCapAdmin FspR7AdminStateCaps,
    plugCapBidirectionalChannel FspR7BidirectionalChannelCaps,
    plugCapChannelSpacingProvision FspR7ChannelSpacingCaps,
    plugCapLength FspR7LengthCaps,
    plugCapPlugType FspR7PlugTypeCaps,
    plugCapPlugMode FspR7PlugModeCaps }

plugCapRowStatus OBJECT-TYPE
    SYNTAX        FspR7RowStatusCaps
    MAX-ACCESS    read-only
    STATUS        current
    DESCRIPTION   "RowStatus object is used to create or delete a row in the table."
    ::= { plugCapEntry 1 }

plugCapConnector OBJECT-TYPE
    SYNTAX        FspR7ConnectorTypeCaps
    MAX-ACCESS    read-only
    STATUS        current
    DESCRIPTION   "Connector"
    ::= { plugCapEntry 2 }

plugCapType OBJECT-TYPE
    SYNTAX        FspR7EquipmentTypeCaps
    MAX-ACCESS    read-only
    STATUS        current
    DESCRIPTION   "The TYPE of Equipment and the MODE setting determine uniquely
        the number and allowed TYPE's of the provisionable dependent
        entities (plugs, interfaces, modules)"
    ::= { plugCapEntry 3 }

plugCapReach OBJECT-TYPE
    SYNTAX        FspR7OpticalInterfaceReachCaps
    MAX-ACCESS    read-only
    STATUS        current
    DESCRIPTION   "Reach"
    ::= { plugCapEntry 4 }

plugCapLoopbackAttenuation OBJECT-TYPE
    SYNTAX        FspR7Unsigned32Caps
    UNITS         "0.1 dB"
    MAX-ACCESS    read-only
    STATUS        current
    DESCRIPTION   "Loop back attenuation used for Optojack SE plugs"
    ::= { plugCapEntry 5 }

plugCapTransmitChannel OBJECT-TYPE
    SYNTAX        FspR7ChannelIdentifierCaps
    MAX-ACCESS    read-only
    STATUS        current
    DESCRIPTION   "Channel"
    ::= { plugCapEntry 6 }

plugCapAlias OBJECT-TYPE
    SYNTAX        Integer32
    MAX-ACCESS    read-only
    STATUS        current
    DESCRIPTION   "User Applied Descriptor"
    ::= { plugCapEntry 7 }

plugCapLaneGroup OBJECT-TYPE
    SYNTAX        FspR7LaneGroupInventoryCaps
    MAX-ACCESS    read-only
    STATUS        current
    DESCRIPTION   "Lane group to provision"
    ::= { plugCapEntry 8 }

plugCapMaxDataRate OBJECT-TYPE
    SYNTAX        FspR7PlugDataRateCaps
    MAX-ACCESS    read-only
    STATUS        current
    DESCRIPTION   "Rate"
    ::= { plugCapEntry 9 }

plugCapThirdPartyUsage OBJECT-TYPE
    SYNTAX        EnableStateCaps
    MAX-ACCESS    read-only
    STATUS        current
    DESCRIPTION   "Usage of 3rd Party Plugs"
    ::= { plugCapEntry 10 }

plugCapAdmin OBJECT-TYPE
    SYNTAX        FspR7AdminStateCaps
    MAX-ACCESS    read-only
    STATUS        current
    DESCRIPTION   "Administrative State is displayed in the GUI and Craft. Transition to Unassigend requires the entity to be deleted."
    ::= { plugCapEntry 11 }

plugCapBidirectionalChannel OBJECT-TYPE
    SYNTAX        FspR7BidirectionalChannelCaps
    MAX-ACCESS    read-only
    STATUS        current
    DESCRIPTION   "Bidirectional Channel Rates from Provisioning"
    ::= { plugCapEntry 12 }

plugCapChannelSpacingProvision OBJECT-TYPE
    SYNTAX        FspR7ChannelSpacingCaps
    MAX-ACCESS    read-only
    STATUS        current
    DESCRIPTION   "Channel Space Provision, reference to CHA-SPC__INVENTORY"
    ::= { plugCapEntry 13 }

plugCapLength OBJECT-TYPE
    SYNTAX        FspR7LengthCaps
    MAX-ACCESS    read-only
    STATUS        current
    DESCRIPTION   "Length"
    ::= { plugCapEntry 14 }

plugCapPlugType OBJECT-TYPE
    SYNTAX        FspR7PlugTypeCaps
    MAX-ACCESS    read-only
    STATUS        current
    DESCRIPTION   "Plug Type"
    ::= { plugCapEntry 15 }

plugCapPlugMode OBJECT-TYPE
    SYNTAX        FspR7PlugModeCaps
    MAX-ACCESS    read-only
    STATUS        current
    DESCRIPTION   "Plug Mode"
    ::= { plugCapEntry 16 }

endOfPlugCapTable OBJECT-TYPE
    SYNTAX        Integer32
    MAX-ACCESS    read-only
    STATUS        current
    DESCRIPTION   ""
    ::= { eqptMgmtCap 6 }

moduleCapTable OBJECT-TYPE
    SYNTAX        SEQUENCE OF ModuleCapEntry
    MAX-ACCESS    not-accessible
    STATUS        current
    DESCRIPTION   "moduleCapTable"
    ::= { eqptMgmtCap 7 }

moduleCapEntry OBJECT-TYPE
    SYNTAX        ModuleCapEntry
    MAX-ACCESS    not-accessible
    STATUS        current
    DESCRIPTION   "Entry of moduleCapTable"
    INDEX       {
                  entityEqptShelfNo,
                  entityEqptSlotNo,
                  entityEqptPortNo,
                  entityEqptExtNo,
                  entityEqptClassName
                }
    ::= { moduleCapTable 1 }

ModuleCapEntry ::= SEQUENCE
  {    moduleCapRowStatus FspR7RowStatusCaps,
    moduleCapForceDestroy FspR7ForcedStatusCaps,
    moduleCapPsuOutputPower FspR7PsuOutputPowerCaps,
    moduleCapPower FspR7EdfaOutputPowerRatingCaps,
    moduleCapReach FspR7OpticalInterfaceReachCaps,
    moduleCapInitEqlz FspR7RlsActionCaps,
    moduleCapLanAid SnmpAdminString,
    moduleCapType FspR7EquipmentTypeCaps,
    moduleCapMapping FspR7MappingCaps,
    moduleCapGainRange FspR7GainRangeCaps,
    moduleCapSfProvision FspR7SingleFiberLocationCaps,
    moduleCapCapabilityLevelProvision FspR7CapInventoryCaps,
    moduleCapDCFiberType FspR7DCFiberTypeCaps,
    moduleCapChannelsProvision FspR7NumberOfChannelsCaps,
    moduleCapFiberDetect FspR7EnableDisableCaps,
    moduleCapSupply FspR7SupplyTypeCaps,
    moduleCapGroup FspR7OpticalGroupCaps,
    moduleCapDeploy FspR7DeploymentScenarioCaps,
    moduleCapLagSysPrio FspR7Unsigned32Caps,
    moduleCapTransmitChannel FspR7ChannelIdentifierCaps,
    moduleCapBand FspR7OpticalBandCaps,
    moduleCapTrafficDirection FspR7TrafficDirectionCaps,
    moduleCapIpAddr FspR7YesNo,
    moduleCapDispersionCompensation FspR7DispersionCompensationCaps,
    moduleCapActivateDetect FspR7YesNoCaps,
    moduleCapOscUsage FspR7OscUsageCaps,
    moduleCapAdmin FspR7AdminStateCaps,
    moduleCapScrambling FspR7EnableDisableCaps,
    moduleCapChannelsNumber FspR7NumberOfChannelsCaps,
    moduleCapChannelSpacingProvision FspR7ChannelSpacingCaps,
    moduleCapMode FspR7TransmissionModeCaps,
    moduleCapSubBandProvision FspR7OpticalSubBandCaps,
    moduleCapAlias Integer32,
    moduleCapFiberType FspR7OpticalFiberTypeCaps,
    moduleCapChannelSpacing FspR7ChannelSpacingCaps,
    moduleCapOutputReset FspR7RlsActionCaps,
    moduleCapRoadmNumber FspR7RoadmNumberCaps,
    moduleCapTopology FspR7TopologyCaps,
    moduleCapForceConfig FspR7RlsActionCaps,
    moduleCapMuxMethod FspR7MuxMethodCaps,
    moduleCapNdpCleanup FspR7RlsActionCaps,
    moduleCapRstp FspR7EnableDisableCaps,
    moduleCapRemoteReset FspR7RlsActionCaps,
    moduleCapPartner1 SnmpAdminString,
    moduleCapPartner2 SnmpAdminString,
    moduleCapPartner3 SnmpAdminString,
    moduleCapPartner4 SnmpAdminString,
    moduleCapAcp FspR7AcpCaps }

moduleCapRowStatus OBJECT-TYPE
    SYNTAX        FspR7RowStatusCaps
    MAX-ACCESS    read-only
    STATUS        current
    DESCRIPTION   "RowStatus object is used to create or delete a row in the table."
    ::= { moduleCapEntry 1 }

moduleCapForceDestroy OBJECT-TYPE
    SYNTAX        FspR7ForcedStatusCaps
    MAX-ACCESS    read-only
    STATUS        current
    DESCRIPTION   "Forced Destroy"
    ::= { moduleCapEntry 2 }

moduleCapPsuOutputPower OBJECT-TYPE
    SYNTAX        FspR7PsuOutputPowerCaps
    MAX-ACCESS    read-only
    STATUS        current
    DESCRIPTION   "Maximum PSU Output Power"
    ::= { moduleCapEntry 3 }

moduleCapPower OBJECT-TYPE
    SYNTAX        FspR7EdfaOutputPowerRatingCaps
    MAX-ACCESS    read-only
    STATUS        current
    DESCRIPTION   "Optical Output Power Rating - Provision"
    ::= { moduleCapEntry 4 }

moduleCapReach OBJECT-TYPE
    SYNTAX        FspR7OpticalInterfaceReachCaps
    MAX-ACCESS    read-only
    STATUS        current
    DESCRIPTION   "Reach"
    ::= { moduleCapEntry 5 }

moduleCapInitEqlz OBJECT-TYPE
    SYNTAX        FspR7RlsActionCaps
    MAX-ACCESS    read-only
    STATUS        current
    DESCRIPTION   "Initiate Equalization"
    ::= { moduleCapEntry 6 }

moduleCapLanAid OBJECT-TYPE
    SYNTAX        SnmpAdminString
    MAX-ACCESS    read-only
    STATUS        current
    DESCRIPTION   "AID of LAN"
    ::= { moduleCapEntry 7 }

moduleCapType OBJECT-TYPE
    SYNTAX        FspR7EquipmentTypeCaps
    MAX-ACCESS    read-only
    STATUS        current
    DESCRIPTION   "The TYPE of Equipment and the MODE setting determine uniquely
        the number and allowed TYPE's of the provisionable dependent
        entities (plugs, interfaces, modules)"
    ::= { moduleCapEntry 8 }

moduleCapMapping OBJECT-TYPE
    SYNTAX        FspR7MappingCaps
    MAX-ACCESS    read-only
    STATUS        current
    DESCRIPTION   "Type of mapping; transparent or framing"
    ::= { moduleCapEntry 9 }

moduleCapGainRange OBJECT-TYPE
    SYNTAX        FspR7GainRangeCaps
    MAX-ACCESS    read-only
    STATUS        current
    DESCRIPTION   "EDFA gain range to provision"
    ::= { moduleCapEntry 10 }

moduleCapSfProvision OBJECT-TYPE
    SYNTAX        FspR7SingleFiberLocationCaps
    MAX-ACCESS    read-only
    STATUS        current
    DESCRIPTION   "determines the location (A or B) for Single Fiber applications"
    ::= { moduleCapEntry 11 }

moduleCapCapabilityLevelProvision OBJECT-TYPE
    SYNTAX        FspR7CapInventoryCaps
    MAX-ACCESS    read-only
    STATUS        current
    DESCRIPTION   "Capability level provisioned"
    ::= { moduleCapEntry 12 }

moduleCapDCFiberType OBJECT-TYPE
    SYNTAX        FspR7DCFiberTypeCaps
    MAX-ACCESS    read-only
    STATUS        current
    DESCRIPTION   "Dispersion Compensation Fibertype"
    ::= { moduleCapEntry 13 }

moduleCapChannelsProvision OBJECT-TYPE
    SYNTAX        FspR7NumberOfChannelsCaps
    MAX-ACCESS    read-only
    STATUS        current
    DESCRIPTION   "Number of channels supported by an entity"
    ::= { moduleCapEntry 14 }

moduleCapFiberDetect OBJECT-TYPE
    SYNTAX        FspR7EnableDisableCaps
    MAX-ACCESS    read-only
    STATUS        current
    DESCRIPTION   "Fiber Detect"
    ::= { moduleCapEntry 15 }

moduleCapSupply OBJECT-TYPE
    SYNTAX        FspR7SupplyTypeCaps
    MAX-ACCESS    read-only
    STATUS        current
    DESCRIPTION   "The kind of power supply - provisioned value"
    ::= { moduleCapEntry 16 }

moduleCapGroup OBJECT-TYPE
    SYNTAX        FspR7OpticalGroupCaps
    MAX-ACCESS    read-only
    STATUS        current
    DESCRIPTION   "The Group of 4 DWDM channels or the Group of 4 CWDM channels"
    ::= { moduleCapEntry 17 }

moduleCapDeploy OBJECT-TYPE
    SYNTAX        FspR7DeploymentScenarioCaps
    MAX-ACCESS    read-only
    STATUS        current
    DESCRIPTION   "Describes how the card is applied related to a network scenario"
    ::= { moduleCapEntry 18 }

moduleCapLagSysPrio OBJECT-TYPE
    SYNTAX        FspR7Unsigned32Caps
    MAX-ACCESS    read-only
    STATUS        current
    DESCRIPTION   "Link Aggregation Group Actor System Priority Part of LAG ID"
    ::= { moduleCapEntry 19 }

moduleCapTransmitChannel OBJECT-TYPE
    SYNTAX        FspR7ChannelIdentifierCaps
    MAX-ACCESS    read-only
    STATUS        current
    DESCRIPTION   "Channel"
    ::= { moduleCapEntry 20 }

moduleCapBand OBJECT-TYPE
    SYNTAX        FspR7OpticalBandCaps
    MAX-ACCESS    read-only
    STATUS        current
    DESCRIPTION   "The optical band of the module."
    ::= { moduleCapEntry 21 }

moduleCapTrafficDirection OBJECT-TYPE
    SYNTAX        FspR7TrafficDirectionCaps
    MAX-ACCESS    read-only
    STATUS        current
    DESCRIPTION   "Traffic Direction"
    ::= { moduleCapEntry 22 }

moduleCapIpAddr OBJECT-TYPE
    SYNTAX        FspR7YesNo
    MAX-ACCESS    read-only
    STATUS        current
    DESCRIPTION   "IP Address assigned to LAN IP Interface"
    ::= { moduleCapEntry 23 }

moduleCapDispersionCompensation OBJECT-TYPE
    SYNTAX        FspR7DispersionCompensationCaps
    MAX-ACCESS    read-only
    STATUS        current
    DESCRIPTION   "Dispersion Compensation Value in km of SSMF fiber"
    ::= { moduleCapEntry 24 }

moduleCapActivateDetect OBJECT-TYPE
    SYNTAX        FspR7YesNoCaps
    MAX-ACCESS    read-only
    STATUS        current
    DESCRIPTION   "Initialize Topology Detection"
    ::= { moduleCapEntry 25 }

moduleCapOscUsage OBJECT-TYPE
    SYNTAX        FspR7OscUsageCaps
    MAX-ACCESS    read-only
    STATUS        current
    DESCRIPTION   "Select if and how the OSC is to be used on an amplifier"
    ::= { moduleCapEntry 26 }

moduleCapAdmin OBJECT-TYPE
    SYNTAX        FspR7AdminStateCaps
    MAX-ACCESS    read-only
    STATUS        current
    DESCRIPTION   "Administrative State is displayed in the GUI and Craft. Transition to Unassigend requires the entity to be deleted."
    ::= { moduleCapEntry 27 }

moduleCapScrambling OBJECT-TYPE
    SYNTAX        FspR7EnableDisableCaps
    MAX-ACCESS    read-only
    STATUS        current
    DESCRIPTION   "Configuration of scrambling functionality for Virtual Facilities"
    ::= { moduleCapEntry 28 }

moduleCapChannelsNumber OBJECT-TYPE
    SYNTAX        FspR7NumberOfChannelsCaps
    MAX-ACCESS    read-only
    STATUS        current
    DESCRIPTION   "Number of channels supported by an entity"
    ::= { moduleCapEntry 29 }

moduleCapChannelSpacingProvision OBJECT-TYPE
    SYNTAX        FspR7ChannelSpacingCaps
    MAX-ACCESS    read-only
    STATUS        current
    DESCRIPTION   "Channel Space Provision, reference to CHA-SPC__INVENTORY"
    ::= { moduleCapEntry 30 }

moduleCapMode OBJECT-TYPE
    SYNTAX        FspR7TransmissionModeCaps
    MAX-ACCESS    read-only
    STATUS        current
    DESCRIPTION   "Mode of the module, determine operation or functionality"
    ::= { moduleCapEntry 31 }

moduleCapSubBandProvision OBJECT-TYPE
    SYNTAX        FspR7OpticalSubBandCaps
    MAX-ACCESS    read-only
    STATUS        current
    DESCRIPTION   "Subband - Provision"
    ::= { moduleCapEntry 32 }

moduleCapAlias OBJECT-TYPE
    SYNTAX        Integer32
    MAX-ACCESS    read-only
    STATUS        current
    DESCRIPTION   "User Applied Descriptor"
    ::= { moduleCapEntry 33 }

moduleCapFiberType OBJECT-TYPE
    SYNTAX        FspR7OpticalFiberTypeCaps
    MAX-ACCESS    read-only
    STATUS        current
    DESCRIPTION   "Fiber of Optical Interface - Provision, Reference to FIBER__INVENTORY"
    ::= { moduleCapEntry 34 }

moduleCapChannelSpacing OBJECT-TYPE
    SYNTAX        FspR7ChannelSpacingCaps
    MAX-ACCESS    read-only
    STATUS        current
    DESCRIPTION   "ITU Grid channel spacing"
    ::= { moduleCapEntry 35 }

moduleCapOutputReset OBJECT-TYPE
    SYNTAX        FspR7RlsActionCaps
    MAX-ACCESS    read-only
    STATUS        current
    DESCRIPTION   "Has the same function as the HW switch at the UTM board"
    ::= { moduleCapEntry 36 }

moduleCapRoadmNumber OBJECT-TYPE
    SYNTAX        FspR7RoadmNumberCaps
    MAX-ACCESS    read-only
    STATUS        current
    DESCRIPTION   "Number for ROADM module typically associated with a Network Fiber or Degree"
    ::= { moduleCapEntry 37 }

moduleCapTopology OBJECT-TYPE
    SYNTAX        FspR7TopologyCaps
    MAX-ACCESS    read-only
    STATUS        current
    DESCRIPTION   "Shows the card topology in the NE"
    ::= { moduleCapEntry 38 }

moduleCapForceConfig OBJECT-TYPE
    SYNTAX        FspR7RlsActionCaps
    MAX-ACCESS    read-only
    STATUS        current
    DESCRIPTION   "Force cserver to send down configuration to module"
    ::= { moduleCapEntry 39 }

moduleCapMuxMethod OBJECT-TYPE
    SYNTAX        FspR7MuxMethodCaps
    MAX-ACCESS    read-only
    STATUS        current
    DESCRIPTION   "Selection of mux method"
    ::= { moduleCapEntry 40 }

moduleCapNdpCleanup OBJECT-TYPE
    SYNTAX        FspR7RlsActionCaps
    MAX-ACCESS    read-only
    STATUS        current
    DESCRIPTION   "Cleanup Network Data Path allocation"
    ::= { moduleCapEntry 41 }

moduleCapRstp OBJECT-TYPE
    SYNTAX        FspR7EnableDisableCaps
    MAX-ACCESS    read-only
    STATUS        current
    DESCRIPTION   "Rapid spanning tree protocol"
    ::= { moduleCapEntry 42 }

moduleCapRemoteReset OBJECT-TYPE
    SYNTAX        FspR7RlsActionCaps
    MAX-ACCESS    read-only
    STATUS        current
    DESCRIPTION   "Remote reset of module. This parameter will be available only on SH9HU and SH1HUPF shelves."
    ::= { moduleCapEntry 43 }

moduleCapPartner1 OBJECT-TYPE
    SYNTAX        SnmpAdminString
    MAX-ACCESS    read-only
    STATUS        current
    DESCRIPTION   "External Protection Trigger Entity AID #1"
    ::= { moduleCapEntry 44 }

moduleCapPartner2 OBJECT-TYPE
    SYNTAX        SnmpAdminString
    MAX-ACCESS    read-only
    STATUS        current
    DESCRIPTION   "External Protection Trigger Entity AID #2"
    ::= { moduleCapEntry 45 }

moduleCapPartner3 OBJECT-TYPE
    SYNTAX        SnmpAdminString
    MAX-ACCESS    read-only
    STATUS        current
    DESCRIPTION   "External Protection Trigger Entity AID #3"
    ::= { moduleCapEntry 46 }

moduleCapPartner4 OBJECT-TYPE
    SYNTAX        SnmpAdminString
    MAX-ACCESS    read-only
    STATUS        current
    DESCRIPTION   "External Protection Trigger Entity AID #4"
    ::= { moduleCapEntry 47 }

moduleCapAcp OBJECT-TYPE
    SYNTAX        FspR7AcpCaps
    MAX-ACCESS    read-only
    STATUS        current
    DESCRIPTION   "APS communication partner"
    ::= { moduleCapEntry 48 }

endOfModuleCap OBJECT-TYPE
    SYNTAX        Integer32
    MAX-ACCESS    read-only
    STATUS        current
    DESCRIPTION   ""
    ::= { eqptMgmtCap 8 }

protectionCableCapTable OBJECT-TYPE
    SYNTAX        SEQUENCE OF ProtectionCableCapEntry
    MAX-ACCESS    not-accessible
    STATUS        current
    DESCRIPTION   "protectionCableCapTable"
    ::= { eqptMgmtCap 9 }

protectionCableCapEntry OBJECT-TYPE
    SYNTAX        ProtectionCableCapEntry
    MAX-ACCESS    not-accessible
    STATUS        current
    DESCRIPTION   "Entry of protectionCableCapTable"
    INDEX       {
                  entityProtectionCableIndex1,
                  entityProtectionCableIndex2,
                  entityProtectionCableIndex3,
                  entityProtectionCableIndex4,
                  entityProtectionCableClassName
                }
    ::= { protectionCableCapTable 1 }

ProtectionCableCapEntry ::= SEQUENCE
  {    protectionCableCapRowStatus FspR7RowStatusCaps,
    protectionCableCapType FspR7YcableTypeCaps }

protectionCableCapRowStatus OBJECT-TYPE
    SYNTAX        FspR7RowStatusCaps
    MAX-ACCESS    read-only
    STATUS        current
    DESCRIPTION   "RowStatus object is used to create or delete a row in the table."
    ::= { protectionCableCapEntry 1 }

protectionCableCapType OBJECT-TYPE
    SYNTAX        FspR7YcableTypeCaps
    MAX-ACCESS    read-only
    STATUS        current
    DESCRIPTION   "Type of Y-cable"
    ::= { protectionCableCapEntry 2 }

endOfProtectionCableCap OBJECT-TYPE
    SYNTAX        Integer32
    MAX-ACCESS    read-only
    STATUS        current
    DESCRIPTION   ""
    ::= { eqptMgmtCap 10 }

filterCableCapTable OBJECT-TYPE
    SYNTAX        SEQUENCE OF FilterCableCapEntry
    MAX-ACCESS    not-accessible
    STATUS        current
    DESCRIPTION   "filterCableCapTable"
    ::= { eqptMgmtCap 11 }

filterCableCapEntry OBJECT-TYPE
    SYNTAX        FilterCableCapEntry
    MAX-ACCESS    not-accessible
    STATUS        current
    DESCRIPTION   "Entry of filterCableCapTable"
    INDEX       {
                  entityFilterCableIndex1,
                  entityFilterCableIndex2,
                  entityFilterCableIndex3,
                  entityFilterCableIndex4,
                  entityFilterCableClassName
                }
    ::= { filterCableCapTable 1 }

FilterCableCapEntry ::= SEQUENCE
  {    filterCableCapRowStatus FspR7RowStatusCaps,
    filterCableCapType FspR7FltrCableTypeCaps }

filterCableCapRowStatus OBJECT-TYPE
    SYNTAX        FspR7RowStatusCaps
    MAX-ACCESS    read-only
    STATUS        current
    DESCRIPTION   "RowStatus object is used to create or delete a row in the table."
    ::= { filterCableCapEntry 1 }

filterCableCapType OBJECT-TYPE
    SYNTAX        FspR7FltrCableTypeCaps
    MAX-ACCESS    read-only
    STATUS        current
    DESCRIPTION   "Filter Cable"
    ::= { filterCableCapEntry 2 }

endOfFilterCableCap OBJECT-TYPE
    SYNTAX        Integer32
    MAX-ACCESS    read-only
    STATUS        current
    DESCRIPTION   ""
    ::= { eqptMgmtCap 12 }

endOfEqptMgmCap OBJECT-TYPE
    SYNTAX        Integer32
    MAX-ACCESS    read-only
    STATUS        current
    DESCRIPTION   ""
    ::= { eqptMgmtCap 10000 }

physicalPortCapTable OBJECT-TYPE
    SYNTAX        SEQUENCE OF PhysicalPortCapEntry
    MAX-ACCESS    not-accessible
    STATUS        current
    DESCRIPTION   "physicalPortCapTable"
    ::= { facilityMgmtCap 1 }

physicalPortCapEntry OBJECT-TYPE
    SYNTAX        PhysicalPortCapEntry
    MAX-ACCESS    not-accessible
    STATUS        current
    DESCRIPTION   "Entry of physicalPortCapTable"
    INDEX       {
                  entityFacilityShelfNo,
                  entityFacilitySlotNo,
                  entityFacilityPortNo,
                  entityFacilityExtNo,
                  entityFacilityClassName
                }
    ::= { physicalPortCapTable 1 }

PhysicalPortCapEntry ::= SEQUENCE
  {    physicalPortCapRowStatus FspR7RowStatusCaps,
    physicalPortCapType FspR7InterfaceTypeCaps,
    physicalPortCapAdmin FspR7AdminStateCaps,
    physicalPortCapAlias Integer32,
    physicalPortCapAlsMode FspR7AlsModeCaps,
    physicalPortCapAutoThresReset FspR7RlsActionCaps,
    physicalPortCapAutonegotiation EnableStateCaps,
    physicalPortCapBehaviour FspR7PortBehaviourCaps,
    physicalPortCapDispertionConfig FspR7RlsActionCaps,
    physicalPortCapDispersionSetting FspR7Integer32Caps,
    physicalPortCapDispersionMode FspR7DispersionModesCaps,
    physicalPortCapChannelProv FspR7ChannelIdentifierCaps,
    physicalPortCapWdmRxChannel FspR7ChannelIdentifierCaps,
    physicalPortCapCodeGain FspR7CodeGainCaps,
    physicalPortCapXfpDecisionThres FspR7XfpDecisionThresCaps,
    physicalPortCapDisparityCorrection EnableStateCaps,
    physicalPortCapEqlzAdmin FspR7EnableDisableCaps,
    physicalPortCapErrorForwarding FspR7ErrorFwdModeCaps,
    physicalPortCapFecType FspR7FecTypeCaps,
    physicalPortCapFarEndCommunication FspR7YesNoCaps,
    physicalPortCapFlowControl FspR7FlowControlModeCaps,
    physicalPortCapForceLaserOn FspR7RlsActionCaps,
    physicalPortCapInhibitSwitchToProt FspR7YesNoCaps,
    physicalPortCapInhibitSwitchToWork FspR7YesNoCaps,
    physicalPortCapLaneChannelSetting FspR7ChannelIdentifierCaps,
    physicalPortCapLoopConfig LoopConfigCaps,
    physicalPortCapLaserDelayTimer FspR7LaserDelayTimerCaps,
    physicalPortCapLaserOffTimer FspR7Unsigned32Caps,
    physicalPortCapLaserOnTimer FspR7Unsigned32Caps,
    physicalPortCapLaserOffDelayFunction EnableStateCaps,
    physicalPortCapAutoPTassignment FspR7ManualAutoCaps,
    physicalPortCapTributarySlotMethod FspR7ManualAutoCaps,
    physicalPortCapInitiateEqualization FspR7RlsActionCaps,
    physicalPortCapLossAttenuation FspR7RlsActionCaps,
    physicalPortCapOpticalSetPoint FspR7Integer32Caps,
    physicalPortCapDataLayerPmReset FspR7PmResetCaps,
    physicalPortCapPrbsPmReset FspR7PmResetCaps,
    physicalPortCapTestPrbsRcvMode FspR7RlsActionCaps,
    physicalPortCapTestPrbsTrmtMode FspR7RlsActionCaps,
    physicalPortCapSwitchCommand FspR7APSCommandCaps,
    physicalPortCapOpuPayloadType FspR7OpuPayloadTypeCaps,
    physicalPortCapSigDegThresSonetLine FspR7BERThresholdCaps,
    physicalPortCapSigDegThresSdhMs FspR7Unsigned32Caps,
    physicalPortCapSigDegThresOtu FspR7Integer32Caps,
    physicalPortCapSigDegThresOdu FspR7Integer32Caps,
    physicalPortCapSigDegThreshold FspR7Unsigned32Caps,
    physicalPortCapSigDegPcslThreshold FspR7Unsigned32Caps,
    physicalPortCapSigDegThresSonetSection FspR7BERThresholdCaps,
    physicalPortCapSigDegThresSdhSection FspR7Unsigned32Caps,
    physicalPortCapSigDegThresOduTcmA FspR7Integer32Caps,
    physicalPortCapSigDegThresOduTcmB FspR7Integer32Caps,
    physicalPortCapSigDegThresOduTcmC FspR7Integer32Caps,
    physicalPortCapSignalDegradePeriod FspR7Unsigned32Caps,
    physicalPortCapSigDegPeriodOdu FspR7Unsigned32Caps,
    physicalPortCapSigDegPeriodOtu FspR7Unsigned32Caps,
    physicalPortCapSigDegPeriodIntegration FspR7Unsigned32Caps,
    physicalPortCapSigDegPeriodSdhSection FspR7Unsigned32Caps,
    physicalPortCapSigDegPeriodOduTcmA FspR7Unsigned32Caps,
    physicalPortCapSigDegPeriodOduTcmB FspR7Unsigned32Caps,
    physicalPortCapSigDegPeriodOduTcmC FspR7Unsigned32Caps,
    physicalPortCapOtnStuffing FspR7YesNoCaps,
    physicalPortCapTcmALevel OtnTcmLevelCaps,
    physicalPortCapTcmBLevel OtnTcmLevelCaps,
    physicalPortCapTcmCLevel OtnTcmLevelCaps,
    physicalPortCapTerminationLevel OhTerminationLevelCaps,
    physicalPortCapTimingSource SonetTimingSourceCaps,
    physicalPortCapTimModeOdu TimModeCaps,
    physicalPortCapTimModeOtu TimModeCaps,
    physicalPortCapTimModeSonetSection TimModeCaps,
    physicalPortCapTimModeOduTcmA TimModeCaps,
    physicalPortCapTimModeOduTcmB TimModeCaps,
    physicalPortCapTimModeOduTcmC TimModeCaps,
    physicalPortCapTraceFormSonetSection SonetTraceFormCaps,
    physicalPortCapTraceExpectedSonetSection Integer32,
    physicalPortCapTraceTransmitSonetSection Integer32,
    physicalPortCapTraceExpectedOtu Integer32,
    physicalPortCapTraceTransmitSapiOtu Integer32,
    physicalPortCapTraceTransmitDapiOtu Integer32,
    physicalPortCapTraceTransmitOpspOtu Integer32,
    physicalPortCapTraceExpectedOdu Integer32,
    physicalPortCapTraceTransmitSapiOdu Integer32,
    physicalPortCapTraceTransmitDapiOdu Integer32,
    physicalPortCapTraceTransmitOpspOdu Integer32,
    physicalPortCapTraceExpectedOduTcmA Integer32,
    physicalPortCapTraceTransmitSapiOduTcmA Integer32,
    physicalPortCapTraceTransmitDapiOduTcmA Integer32,
    physicalPortCapTraceTransmitOpspOduTcmA Integer32,
    physicalPortCapTraceExpectedOduTcmB Integer32,
    physicalPortCapTraceTransmitSapiOduTcmB Integer32,
    physicalPortCapTraceTransmitDapiOduTcmB Integer32,
    physicalPortCapTraceTransmitOpspOduTcmB Integer32,
    physicalPortCapTraceExpectedOduTcmC Integer32,
    physicalPortCapTraceTransmitSapiOduTcmC Integer32,
    physicalPortCapTraceTransmitDapiOduTcmC Integer32,
    physicalPortCapTraceTransmitOpspOduTcmC Integer32,
    physicalPortCapTurnupConfig FspR7RlsActionCaps,
    physicalPortCapTxOffDelay FspR7EnableDisableCaps,
    physicalPortCapVoaMode FspR7VoaModeCaps,
    physicalPortCapVoaSetpoint FspR7Unsigned32Caps,
    physicalPortCapLagPrio FspR7Unsigned32Caps,
    physicalPortCapMaxFrameSize FspR7Unsigned32Caps,
    physicalPortCapPayload OtnPayloadTypeCaps,
    physicalPortCapPortMode FspR7PortModeCaps,
    physicalPortCapPortRole FspR7PortRoleCaps,
    physicalPortCapPriority FspR7Unsigned32Caps,
    physicalPortCapPvid FspR7Unsigned32Caps,
    physicalPortCapStagType Integer32,
    physicalPortCapUtag FspR7UntaggedFramesCaps,
    physicalPortCapVethAid SnmpAdminString,
    physicalPortCapRedLineState FspR7YesNoCaps,
    physicalPortCapTunnelAid Integer32,
    physicalPortCapRateLimit FspR7DisableEnableCaps,
    physicalPortCapTxOffOnTm FspR7TxOffOnTmCaps,
    physicalPortCapTxOffTimer FspR7Unsigned32Caps,
    physicalPortCapTxOnTimer FspR7Unsigned32Caps,
    physicalPortCapMode FspR7TransmissionModeCaps,
    physicalPortCapMonLevel FspR7MonLevelCaps,
    physicalPortCapChannelPlan FspR7ChannelRangeInventoryCaps,
    physicalPortCapOptimize FspR7OptimizeCaps,
    physicalPortCapEncryptionChannel CryptoFspR7EncryptionCommunicationCaps,
    physicalPortCapLinkSetup FspR7DisableEnableCaps,
    physicalPortCapCdCompensationRange FspR7CdCompensationRangeCaps,
    physicalPortCapChannelSpacing FspR7ChannelSpacingCaps,
    physicalPortCapLLDPNeighborsRx FspR7LLDPNeighborsCaps,
    physicalPortCapLLDPNeighborsTx FspR7LLDPNeighborsCaps,
    physicalPortCapCdPostCompensationRange FspR7CdPostCompensationRangeCaps,
    physicalPortCapLaneChannel1 FspR7ChannelIdentifierCaps,
    physicalPortCapLaneChannel2 FspR7ChannelIdentifierCaps,
    physicalPortCapOpticalSetPointLane1 FspR7Integer32Caps,
    physicalPortCapOpticalSetPointLane2 FspR7Integer32Caps,
    physicalPortCapTerminationMode FspR7TerminationModeCaps,
    physicalPortCapTimDetModeOtu FspR7TimDetModeCaps,
    physicalPortCapTimActionOtu FspR7YesNoCaps,
    physicalPortCapTraceExpectedDapiOtu Integer32,
    physicalPortCapTraceExpectedOpspOtu Integer32,
    physicalPortCapTimDetModeOdu FspR7TimDetModeCaps,
    physicalPortCapTimActionOdu FspR7YesNoCaps,
    physicalPortCapTraceExpectedDapiOdu Integer32,
    physicalPortCapTraceExpectedOpspOdu Integer32,
    physicalPortCapReportAisLine FspR7YesNoCaps,
    physicalPortCapReportSsfLine FspR7YesNoCaps,
    physicalPortCapReportSsfSection FspR7YesNoCaps,
    physicalPortCapDelayMeasurementOperation FspR7DmsrmtOperationCaps }

physicalPortCapRowStatus OBJECT-TYPE
    SYNTAX        FspR7RowStatusCaps
    MAX-ACCESS    read-only
    STATUS        current
    DESCRIPTION   "Physical Port Capability RowStatus."
    ::= { physicalPortCapEntry 1 }

physicalPortCapType OBJECT-TYPE
    SYNTAX        FspR7InterfaceTypeCaps
    MAX-ACCESS    read-only
    STATUS        current
    DESCRIPTION   "Physical Port Capability Facility Type."
    ::= { physicalPortCapEntry 2 }

physicalPortCapAdmin OBJECT-TYPE
    SYNTAX        FspR7AdminStateCaps
    MAX-ACCESS    read-only
    STATUS        current
    DESCRIPTION   "Physical Port Capability Adminstrative State."
    ::= { physicalPortCapEntry 3 }

physicalPortCapAlias OBJECT-TYPE
    SYNTAX        Integer32
    MAX-ACCESS    read-only
    STATUS        current
    DESCRIPTION   "User Applied Descriptor"
    ::= { physicalPortCapEntry 4 }

physicalPortCapAlsMode OBJECT-TYPE
    SYNTAX        FspR7AlsModeCaps
    MAX-ACCESS    read-only
    STATUS        current
    DESCRIPTION   "Determines the reaction in backward direction in response to a LOS
        on the same Interface: on a Network Interface connected to the DWDM
        this is a matter of laser safety"
    ::= { physicalPortCapEntry 5 }

physicalPortCapAutoThresReset OBJECT-TYPE
    SYNTAX        FspR7RlsActionCaps
    MAX-ACCESS    read-only
    STATUS        current
    DESCRIPTION   "Adaptive Threshold Control Reset"
    ::= { physicalPortCapEntry 6 }

physicalPortCapAutonegotiation OBJECT-TYPE
    SYNTAX        EnableStateCaps
    MAX-ACCESS    read-only
    STATUS        current
    DESCRIPTION   "Auto Negotiation for the data rate"
    ::= { physicalPortCapEntry 7 }

physicalPortCapBehaviour OBJECT-TYPE
    SYNTAX        FspR7PortBehaviourCaps
    MAX-ACCESS    read-only
    STATUS        current
    DESCRIPTION   "Behavior or Port usage based on configuration/usage in the system regardless of faceplate designation"
    ::= { physicalPortCapEntry 8 }

physicalPortCapDispertionConfig OBJECT-TYPE
    SYNTAX        FspR7RlsActionCaps
    MAX-ACCESS    read-only
    STATUS        current
    DESCRIPTION   "Chromatic Dispersion Compensation"
    ::= { physicalPortCapEntry 9 }

physicalPortCapDispersionSetting OBJECT-TYPE
    SYNTAX        FspR7Integer32Caps
    UNITS         "ps/nm"
    MAX-ACCESS    read-only
    STATUS        current
    DESCRIPTION   "Chromatic Dispersion Compensation setting on module"
    ::= { physicalPortCapEntry 10 }

physicalPortCapDispersionMode OBJECT-TYPE
    SYNTAX        FspR7DispersionModesCaps
    MAX-ACCESS    read-only
    STATUS        current
    DESCRIPTION   "Chromatic Dispersion Compensation Mode"
    ::= { physicalPortCapEntry 11 }

physicalPortCapChannelProv OBJECT-TYPE
    SYNTAX        FspR7ChannelIdentifierCaps
    MAX-ACCESS    read-only
    STATUS        current
    DESCRIPTION   "Channel"
    ::= { physicalPortCapEntry 12 }

physicalPortCapWdmRxChannel OBJECT-TYPE
    SYNTAX        FspR7ChannelIdentifierCaps
    MAX-ACCESS    read-only
    STATUS        current
    DESCRIPTION   "Channel Number for the Receive Interface"
    ::= { physicalPortCapEntry 13 }

physicalPortCapCodeGain OBJECT-TYPE
    SYNTAX        FspR7CodeGainCaps
    MAX-ACCESS    read-only
    STATUS        current
    DESCRIPTION   "Forward Error Correction Coding gain"
    ::= { physicalPortCapEntry 14 }

physicalPortCapXfpDecisionThres OBJECT-TYPE
    SYNTAX        FspR7XfpDecisionThresCaps
    MAX-ACCESS    read-only
    STATUS        current
    DESCRIPTION   "XFP Decision threshold setting"
    ::= { physicalPortCapEntry 15 }

physicalPortCapDisparityCorrection OBJECT-TYPE
    SYNTAX        EnableStateCaps
    MAX-ACCESS    read-only
    STATUS        current
    DESCRIPTION   "Disparity correction"
    ::= { physicalPortCapEntry 16 }

physicalPortCapEqlzAdmin OBJECT-TYPE
    SYNTAX        FspR7EnableDisableCaps
    MAX-ACCESS    read-only
    STATUS        current
    DESCRIPTION   "Scheduled Equalization Administration"
    ::= { physicalPortCapEntry 17 }

physicalPortCapErrorForwarding OBJECT-TYPE
    SYNTAX        FspR7ErrorFwdModeCaps
    MAX-ACCESS    read-only
    STATUS        current
    DESCRIPTION   "Determines the reaction in forward direction in response to a LOS on
        the interface on the opposite side of the module: may override
        this behaviour in the interests of laser safety."
    ::= { physicalPortCapEntry 18 }

physicalPortCapFecType OBJECT-TYPE
    SYNTAX        FspR7FecTypeCaps
    MAX-ACCESS    read-only
    STATUS        current
    DESCRIPTION   "Forward Error Correction (Only relevant where TYPE = OTU#)"
    ::= { physicalPortCapEntry 19 }

physicalPortCapFarEndCommunication OBJECT-TYPE
    SYNTAX        FspR7YesNoCaps
    MAX-ACCESS    read-only
    STATUS        current
    DESCRIPTION   "Used for Optojack plugs; Communication to Far End Plug is observed"
    ::= { physicalPortCapEntry 20 }

physicalPortCapFlowControl OBJECT-TYPE
    SYNTAX        FspR7FlowControlModeCaps
    MAX-ACCESS    read-only
    STATUS        current
    DESCRIPTION   "Flow Control mechanism"
    ::= { physicalPortCapEntry 21 }

physicalPortCapForceLaserOn OBJECT-TYPE
    SYNTAX        FspR7RlsActionCaps
    MAX-ACCESS    read-only
    STATUS        current
    DESCRIPTION   "Laser Forced On"
    ::= { physicalPortCapEntry 22 }

physicalPortCapInhibitSwitchToProt OBJECT-TYPE
    SYNTAX        FspR7YesNoCaps
    MAX-ACCESS    read-only
    STATUS        current
    DESCRIPTION   "Inhibit Switch to protection facility. Inhibition blocks an automatic switch
        to the protection facility. Valid only for the working facility."
    ::= { physicalPortCapEntry 23 }

physicalPortCapInhibitSwitchToWork OBJECT-TYPE
    SYNTAX        FspR7YesNoCaps
    MAX-ACCESS    read-only
    STATUS        current
    DESCRIPTION   "Inhibit Switch to working facility. Inhibition blocks an automatic switch to the
        working facility. Valid only for the protection facility."
    ::= { physicalPortCapEntry 24 }

physicalPortCapLaneChannelSetting OBJECT-TYPE
    SYNTAX        FspR7ChannelIdentifierCaps
    MAX-ACCESS    read-only
    STATUS        current
    DESCRIPTION   "Lane Channel Setting"
    ::= { physicalPortCapEntry 25 }

physicalPortCapLoopConfig OBJECT-TYPE
    SYNTAX        LoopConfigCaps
    MAX-ACCESS    read-only
    STATUS        current
    DESCRIPTION   "The configuration of the loopback function.
        - noLoop:   no loop configuration on the interface.
        - lineLoop: the incoming signal is looped to the outgoing
        line on the interface. The incoming signal is sent in the
        downstream direction and processed as normal.
        - inwardLoop: the output signal is looped to the incoming line
        on the interface. The looped signal is transmitted unchanged on
        the optical output."
    ::= { physicalPortCapEntry 26 }

physicalPortCapLaserDelayTimer OBJECT-TYPE
    SYNTAX        FspR7LaserDelayTimerCaps
    MAX-ACCESS    read-only
    STATUS        current
    DESCRIPTION   "Relevant only when ERRFWD=LSROFF. Enables/disables the
        possibility to delay turning off and on the laser.
        This applies to the case when turning off the laser
        is done  as an error forwarding mechanism."
    ::= { physicalPortCapEntry 27 }

physicalPortCapLaserOffTimer OBJECT-TYPE
    SYNTAX        FspR7Unsigned32Caps
    UNITS         "ms"
    MAX-ACCESS    read-only
    STATUS        current
    DESCRIPTION   "Delay before laser is swiched off"
    ::= { physicalPortCapEntry 28 }

physicalPortCapLaserOnTimer OBJECT-TYPE
    SYNTAX        FspR7Unsigned32Caps
    UNITS         "ms"
    MAX-ACCESS    read-only
    STATUS        current
    DESCRIPTION   "Delay before laser is switched on"
    ::= { physicalPortCapEntry 29 }

physicalPortCapLaserOffDelayFunction OBJECT-TYPE
    SYNTAX        EnableStateCaps
    MAX-ACCESS    read-only
    STATUS        current
    DESCRIPTION   "A configuration request for the Laser Off Delay function. This function
        delays turning off the laser as a consequent action to a defect."
    ::= { physicalPortCapEntry 30 }

physicalPortCapAutoPTassignment OBJECT-TYPE
    SYNTAX        FspR7ManualAutoCaps
    MAX-ACCESS    read-only
    STATUS        current
    DESCRIPTION   "Auto assignment of ODU PT"
    ::= { physicalPortCapEntry 31 }

physicalPortCapTributarySlotMethod OBJECT-TYPE
    SYNTAX        FspR7ManualAutoCaps
    MAX-ACCESS    read-only
    STATUS        current
    DESCRIPTION   "Tributary Slot assignment method"
    ::= { physicalPortCapEntry 32 }

physicalPortCapInitiateEqualization OBJECT-TYPE
    SYNTAX        FspR7RlsActionCaps
    MAX-ACCESS    read-only
    STATUS        current
    DESCRIPTION   "Initiate Equalization"
    ::= { physicalPortCapEntry 33 }

physicalPortCapLossAttenuation OBJECT-TYPE
    SYNTAX        FspR7RlsActionCaps
    MAX-ACCESS    read-only
    STATUS        current
    DESCRIPTION   "LOS Attenuation Finding in progress"
    ::= { physicalPortCapEntry 34 }

physicalPortCapOpticalSetPoint OBJECT-TYPE
    SYNTAX        FspR7Integer32Caps
    UNITS         "0.1 dBm"
    MAX-ACCESS    read-only
    STATUS        current
    DESCRIPTION   "Sets the optical power for power equalization in ROADM or for channel power control in OPCM"
    ::= { physicalPortCapEntry 35 }

physicalPortCapDataLayerPmReset OBJECT-TYPE
    SYNTAX        FspR7PmResetCaps
    MAX-ACCESS    read-only
    STATUS        current
    DESCRIPTION   "Reset data-layer Performance registers"
    ::= { physicalPortCapEntry 36 }

physicalPortCapPrbsPmReset OBJECT-TYPE
    SYNTAX        FspR7PmResetCaps
    MAX-ACCESS    read-only
    STATUS        current
    DESCRIPTION   "Reset PRBS PM counters"
    ::= { physicalPortCapEntry 37 }

physicalPortCapTestPrbsRcvMode OBJECT-TYPE
    SYNTAX        FspR7RlsActionCaps
    MAX-ACCESS    read-only
    STATUS        current
    DESCRIPTION   "PRBS test pattern received"
    ::= { physicalPortCapEntry 38 }

physicalPortCapTestPrbsTrmtMode OBJECT-TYPE
    SYNTAX        FspR7RlsActionCaps
    MAX-ACCESS    read-only
    STATUS        current
    DESCRIPTION   "PRBS test pattern transmitted"
    ::= { physicalPortCapEntry 39 }

physicalPortCapSwitchCommand OBJECT-TYPE
    SYNTAX        FspR7APSCommandCaps
    MAX-ACCESS    read-only
    STATUS        current
    DESCRIPTION   "The switch command action for this facility. A command resulting
        in a switch event will also cause a change of the facility secondary state
        and a corresponding condition. Addressed by this command is the active port,
        the port to switch away from. Since this is a manual switch command, it will
        not switch if other port suffers from a signalfailure or a signal degrade."
    ::= { physicalPortCapEntry 40 }

physicalPortCapOpuPayloadType OBJECT-TYPE
    SYNTAX        FspR7OpuPayloadTypeCaps
    MAX-ACCESS    read-only
    STATUS        current
    DESCRIPTION   "OPU Payload Type Indicator"
    ::= { physicalPortCapEntry 41 }

physicalPortCapSigDegThresSonetLine OBJECT-TYPE
    SYNTAX        FspR7BERThresholdCaps
    MAX-ACCESS    read-only
    STATUS        current
    DESCRIPTION   "Bit-Error-Based Degradation Definition for SONET (standard integration period)"
    ::= { physicalPortCapEntry 42 }

physicalPortCapSigDegThresSdhMs OBJECT-TYPE
    SYNTAX        FspR7Unsigned32Caps
    UNITS         "%"
    MAX-ACCESS    read-only
    STATUS        current
    DESCRIPTION   "Block-Error-Based Degradation Definition for SDH (standard integration period).
        Defined as percentage Background Block Errors (30% default) evaluated
        over a defined period (SDPER-RS)."
    ::= { physicalPortCapEntry 43 }

physicalPortCapSigDegThresOtu OBJECT-TYPE
    SYNTAX        FspR7Integer32Caps
    UNITS         "%"
    MAX-ACCESS    read-only
    STATUS        current
    DESCRIPTION   "Background-Block-Error-Based Signal Degradation Definition for OTU"
    ::= { physicalPortCapEntry 44 }

physicalPortCapSigDegThresOdu OBJECT-TYPE
    SYNTAX        FspR7Integer32Caps
    UNITS         "%"
    MAX-ACCESS    read-only
    STATUS        current
    DESCRIPTION   "Background-Block-Error-Based Signal Degradation Definition for ODU"
    ::= { physicalPortCapEntry 45 }

physicalPortCapSigDegThreshold OBJECT-TYPE
    SYNTAX        FspR7Unsigned32Caps
    MAX-ACCESS    read-only
    STATUS        current
    DESCRIPTION   "Threshold for number of errors (CV or CV+DE) in one second"
    ::= { physicalPortCapEntry 46 }

physicalPortCapSigDegPcslThreshold OBJECT-TYPE
    SYNTAX        FspR7Unsigned32Caps
    UNITS         "%"
    MAX-ACCESS    read-only
    STATUS        current
    DESCRIPTION   "Block-Error-Based Degradation Definition for Physical Coding Sublayer"
    ::= { physicalPortCapEntry 47 }

physicalPortCapSigDegThresSonetSection OBJECT-TYPE
    SYNTAX        FspR7BERThresholdCaps
    MAX-ACCESS    read-only
    STATUS        current
    DESCRIPTION   "Bit-Error-Based Degradation Definition for SONET (standard integration period)"
    ::= { physicalPortCapEntry 48 }

physicalPortCapSigDegThresSdhSection OBJECT-TYPE
    SYNTAX        FspR7Unsigned32Caps
    UNITS         "%"
    MAX-ACCESS    read-only
    STATUS        current
    DESCRIPTION   "Block-Error-Based Degradation Definition for SDH (standard integration period).
        Defined as percentage Background Block Errors (30% default) evaluated
        over a defined period (SDPER-RS)."
    ::= { physicalPortCapEntry 49 }

physicalPortCapSigDegThresOduTcmA OBJECT-TYPE
    SYNTAX        FspR7Integer32Caps
    UNITS         "%"
    MAX-ACCESS    read-only
    STATUS        current
    DESCRIPTION   "Background-Block-Error-Based Signal Degradation Definition for TCM-A"
    ::= { physicalPortCapEntry 50 }

physicalPortCapSigDegThresOduTcmB OBJECT-TYPE
    SYNTAX        FspR7Integer32Caps
    UNITS         "%"
    MAX-ACCESS    read-only
    STATUS        current
    DESCRIPTION   "Background-Block-Error-Based Signal Degradation Definition for TCM-B"
    ::= { physicalPortCapEntry 51 }

physicalPortCapSigDegThresOduTcmC OBJECT-TYPE
    SYNTAX        FspR7Integer32Caps
    UNITS         "%"
    MAX-ACCESS    read-only
    STATUS        current
    DESCRIPTION   "Background-Block-Error-Based Signal Degradation Definition for TCM-C"
    ::= { physicalPortCapEntry 52 }

physicalPortCapSignalDegradePeriod OBJECT-TYPE
    SYNTAX        FspR7Unsigned32Caps
    UNITS         "s"
    MAX-ACCESS    read-only
    STATUS        current
    DESCRIPTION   "The measurement period in seconds used together with
        the deployProvIfSigDegThresSdhRegSect based on the block error counting method.
        The valid range is 2..10,
        The default being 7."
    ::= { physicalPortCapEntry 53 }

physicalPortCapSigDegPeriodOdu OBJECT-TYPE
    SYNTAX        FspR7Unsigned32Caps
    UNITS         "s"
    MAX-ACCESS    read-only
    STATUS        current
    DESCRIPTION   "Integration Period for Signal degrade"
    ::= { physicalPortCapEntry 54 }

physicalPortCapSigDegPeriodOtu OBJECT-TYPE
    SYNTAX        FspR7Unsigned32Caps
    UNITS         "s"
    MAX-ACCESS    read-only
    STATUS        current
    DESCRIPTION   "Integration Period for Signal degrade"
    ::= { physicalPortCapEntry 55 }

physicalPortCapSigDegPeriodIntegration OBJECT-TYPE
    SYNTAX        FspR7Unsigned32Caps
    UNITS         "s"
    MAX-ACCESS    read-only
    STATUS        current
    DESCRIPTION   "Integration Period for Signal degrade"
    ::= { physicalPortCapEntry 56 }

physicalPortCapSigDegPeriodSdhSection OBJECT-TYPE
    SYNTAX        FspR7Unsigned32Caps
    UNITS         "s"
    MAX-ACCESS    read-only
    STATUS        current
    DESCRIPTION   "Provisionable Signal Degrade Integration Period for SDH"
    ::= { physicalPortCapEntry 57 }

physicalPortCapSigDegPeriodOduTcmA OBJECT-TYPE
    SYNTAX        FspR7Unsigned32Caps
    UNITS         "s"
    MAX-ACCESS    read-only
    STATUS        current
    DESCRIPTION   "Integration Period for Signal degrade"
    ::= { physicalPortCapEntry 58 }

physicalPortCapSigDegPeriodOduTcmB OBJECT-TYPE
    SYNTAX        FspR7Unsigned32Caps
    UNITS         "s"
    MAX-ACCESS    read-only
    STATUS        current
    DESCRIPTION   "Integration Period of TCMB Signal Segrade"
    ::= { physicalPortCapEntry 59 }

physicalPortCapSigDegPeriodOduTcmC OBJECT-TYPE
    SYNTAX        FspR7Unsigned32Caps
    UNITS         "s"
    MAX-ACCESS    read-only
    STATUS        current
    DESCRIPTION   "Integration Period of TCMC Signal Segrade"
    ::= { physicalPortCapEntry 60 }

physicalPortCapOtnStuffing OBJECT-TYPE
    SYNTAX        FspR7YesNoCaps
    MAX-ACCESS    read-only
    STATUS        current
    DESCRIPTION   "Indicates if bit/byte stuffing is used in the transport signal."
    ::= { physicalPortCapEntry 61 }

physicalPortCapTcmALevel OBJECT-TYPE
    SYNTAX        OtnTcmLevelCaps
    MAX-ACCESS    read-only
    STATUS        current
    DESCRIPTION   "Activation of Tandem Connection Monitoring Instance A"
    ::= { physicalPortCapEntry 62 }

physicalPortCapTcmBLevel OBJECT-TYPE
    SYNTAX        OtnTcmLevelCaps
    MAX-ACCESS    read-only
    STATUS        current
    DESCRIPTION   "Activation of Tandem Connection Monitoring Instance B"
    ::= { physicalPortCapEntry 63 }

physicalPortCapTcmCLevel OBJECT-TYPE
    SYNTAX        OtnTcmLevelCaps
    MAX-ACCESS    read-only
    STATUS        current
    DESCRIPTION   "Activation of Tandem Connection Monitoring Instance C"
    ::= { physicalPortCapEntry 64 }

physicalPortCapTerminationLevel OBJECT-TYPE
    SYNTAX        OhTerminationLevelCaps
    MAX-ACCESS    read-only
    STATUS        current
    DESCRIPTION   "Highest signal level hardware removes then generates for transmission."
    ::= { physicalPortCapEntry 65 }

physicalPortCapTimingSource OBJECT-TYPE
    SYNTAX        SonetTimingSourceCaps
    MAX-ACCESS    read-only
    STATUS        current
    DESCRIPTION   "The timing source for this interface.
        - internal: used in stand-alone, point-to-point topologies stand-alone (dedicated fiber operation).
        - loopTiming: e.g. used in point-to-point via SONET network and feeder topologies. The default is
        internal(1)."
    ::= { physicalPortCapEntry 66 }

physicalPortCapTimModeOdu OBJECT-TYPE
    SYNTAX        TimModeCaps
    MAX-ACCESS    read-only
    STATUS        current
    DESCRIPTION   "Detection of TIM-ODU Condition can be configured"
    ::= { physicalPortCapEntry 67 }

physicalPortCapTimModeOtu OBJECT-TYPE
    SYNTAX        TimModeCaps
    MAX-ACCESS    read-only
    STATUS        current
    DESCRIPTION   "OTU Trace Identifier Mismatch (TIM) detection/action for TIM defect."
    ::= { physicalPortCapEntry 68 }

physicalPortCapTimModeSonetSection OBJECT-TYPE
    SYNTAX        TimModeCaps
    MAX-ACCESS    read-only
    STATUS        current
    DESCRIPTION   "SONET Section  Trace Identifier Mismatch (TIM) detection/action for TIM defect."
    ::= { physicalPortCapEntry 69 }

physicalPortCapTimModeOduTcmA OBJECT-TYPE
    SYNTAX        TimModeCaps
    MAX-ACCESS    read-only
    STATUS        current
    DESCRIPTION   "TCM_A Trace Identifier Mismatch (TIM) detection/action for TIM defect."
    ::= { physicalPortCapEntry 70 }

physicalPortCapTimModeOduTcmB OBJECT-TYPE
    SYNTAX        TimModeCaps
    MAX-ACCESS    read-only
    STATUS        current
    DESCRIPTION   "TCM_B Trace Identifier Mismatch (TIM) detection/action for TIM defect."
    ::= { physicalPortCapEntry 71 }

physicalPortCapTimModeOduTcmC OBJECT-TYPE
    SYNTAX        TimModeCaps
    MAX-ACCESS    read-only
    STATUS        current
    DESCRIPTION   "TCM_C Trace Identifier Mismatch (TIM) detection/action for TIM defect."
    ::= { physicalPortCapEntry 72 }

physicalPortCapTraceFormSonetSection OBJECT-TYPE
    SYNTAX        SonetTraceFormCaps
    MAX-ACCESS    read-only
    STATUS        current
    DESCRIPTION   "Byte-Length of Trace Compared to Expected"
    ::= { physicalPortCapEntry 73 }

physicalPortCapTraceExpectedSonetSection OBJECT-TYPE
    SYNTAX        Integer32
    MAX-ACCESS    read-only
    STATUS        current
    DESCRIPTION   "Expected Sec/RS trace. NULL TRACE implies that no trace comparison is made."
    ::= { physicalPortCapEntry 74 }

physicalPortCapTraceTransmitSonetSection OBJECT-TYPE
    SYNTAX        Integer32
    MAX-ACCESS    read-only
    STATUS        current
    DESCRIPTION   "Sec/RS Trace to be Transmitted"
    ::= { physicalPortCapEntry 75 }

physicalPortCapTraceExpectedOtu OBJECT-TYPE
    SYNTAX        Integer32
    MAX-ACCESS    read-only
    STATUS        current
    DESCRIPTION   "Expected SAPI part of the OTU trace (15 character). NULL TRACE implies that no trace comparison is made."
    ::= { physicalPortCapEntry 76 }

physicalPortCapTraceTransmitSapiOtu OBJECT-TYPE
    SYNTAX        Integer32
    MAX-ACCESS    read-only
    STATUS        current
    DESCRIPTION   "The transmitted SAPI part of the OTU trace (15 character)"
    ::= { physicalPortCapEntry 77 }

physicalPortCapTraceTransmitDapiOtu OBJECT-TYPE
    SYNTAX        Integer32
    MAX-ACCESS    read-only
    STATUS        current
    DESCRIPTION   "The transmitted DAPI part of the OTU trace (15 character)"
    ::= { physicalPortCapEntry 78 }

physicalPortCapTraceTransmitOpspOtu OBJECT-TYPE
    SYNTAX        Integer32
    MAX-ACCESS    read-only
    STATUS        current
    DESCRIPTION   "The transmitted Operator Specific part of the OTU trace (32 character)"
    ::= { physicalPortCapEntry 79 }

physicalPortCapTraceExpectedOdu OBJECT-TYPE
    SYNTAX        Integer32
    MAX-ACCESS    read-only
    STATUS        current
    DESCRIPTION   "Expected SAPI part of the ODU trace (15 character). NULL TRACE implies that no trace comparison is made."
    ::= { physicalPortCapEntry 80 }

physicalPortCapTraceTransmitSapiOdu OBJECT-TYPE
    SYNTAX        Integer32
    MAX-ACCESS    read-only
    STATUS        current
    DESCRIPTION   "The transmitted SAPI part of the ODU trace (15 character)"
    ::= { physicalPortCapEntry 81 }

physicalPortCapTraceTransmitDapiOdu OBJECT-TYPE
    SYNTAX        Integer32
    MAX-ACCESS    read-only
    STATUS        current
    DESCRIPTION   "The transmitted DAPI part of the ODU trace (15 character)"
    ::= { physicalPortCapEntry 82 }

physicalPortCapTraceTransmitOpspOdu OBJECT-TYPE
    SYNTAX        Integer32
    MAX-ACCESS    read-only
    STATUS        current
    DESCRIPTION   "The transmitted Operator Specific part of the ODU trace (32 character)"
    ::= { physicalPortCapEntry 83 }

physicalPortCapTraceExpectedOduTcmA OBJECT-TYPE
    SYNTAX        Integer32
    MAX-ACCESS    read-only
    STATUS        current
    DESCRIPTION   "Expected SAPI part of the TCMA trace (15 character). NULL TRACE-TCM implies that no trace comparison is made."
    ::= { physicalPortCapEntry 84 }

physicalPortCapTraceTransmitSapiOduTcmA OBJECT-TYPE
    SYNTAX        Integer32
    MAX-ACCESS    read-only
    STATUS        current
    DESCRIPTION   "The transmitted SAPI part of the TCMA trace (15 character)"
    ::= { physicalPortCapEntry 85 }

physicalPortCapTraceTransmitDapiOduTcmA OBJECT-TYPE
    SYNTAX        Integer32
    MAX-ACCESS    read-only
    STATUS        current
    DESCRIPTION   "The transmitted DAPI part of the TCMA trace (15 character)"
    ::= { physicalPortCapEntry 86 }

physicalPortCapTraceTransmitOpspOduTcmA OBJECT-TYPE
    SYNTAX        Integer32
    MAX-ACCESS    read-only
    STATUS        current
    DESCRIPTION   "The transmitted Operator Specific part of the TCMA trace (32 character)"
    ::= { physicalPortCapEntry 87 }

physicalPortCapTraceExpectedOduTcmB OBJECT-TYPE
    SYNTAX        Integer32
    MAX-ACCESS    read-only
    STATUS        current
    DESCRIPTION   "Expected SAPI part of the TCMB trace (15 character). NULL TRACE-TCM implies that no trace comparison is made."
    ::= { physicalPortCapEntry 88 }

physicalPortCapTraceTransmitSapiOduTcmB OBJECT-TYPE
    SYNTAX        Integer32
    MAX-ACCESS    read-only
    STATUS        current
    DESCRIPTION   "The transmitted SAPI part of the TCMB trace (15 character)"
    ::= { physicalPortCapEntry 89 }

physicalPortCapTraceTransmitDapiOduTcmB OBJECT-TYPE
    SYNTAX        Integer32
    MAX-ACCESS    read-only
    STATUS        current
    DESCRIPTION   "The transmitted DAPI part of the TCMB trace (15 character)"
    ::= { physicalPortCapEntry 90 }

physicalPortCapTraceTransmitOpspOduTcmB OBJECT-TYPE
    SYNTAX        Integer32
    MAX-ACCESS    read-only
    STATUS        current
    DESCRIPTION   "The transmitted Operator Specific part of the TCMB trace (32 character)"
    ::= { physicalPortCapEntry 91 }

physicalPortCapTraceExpectedOduTcmC OBJECT-TYPE
    SYNTAX        Integer32
    MAX-ACCESS    read-only
    STATUS        current
    DESCRIPTION   "Expected SAPI part of the TCMC trace (15 character). NULL TRACE-TCM implies that no trace comparison is made."
    ::= { physicalPortCapEntry 92 }

physicalPortCapTraceTransmitSapiOduTcmC OBJECT-TYPE
    SYNTAX        Integer32
    MAX-ACCESS    read-only
    STATUS        current
    DESCRIPTION   "The transmitted SAPI part of the TCMC trace (15 character)"
    ::= { physicalPortCapEntry 93 }

physicalPortCapTraceTransmitDapiOduTcmC OBJECT-TYPE
    SYNTAX        Integer32
    MAX-ACCESS    read-only
    STATUS        current
    DESCRIPTION   "The transmitted DAPI part of the TCMC trace (15 character)"
    ::= { physicalPortCapEntry 94 }

physicalPortCapTraceTransmitOpspOduTcmC OBJECT-TYPE
    SYNTAX        Integer32
    MAX-ACCESS    read-only
    STATUS        current
    DESCRIPTION   "The transmitted Operator Specific part of the TCMC trace (32 character)"
    ::= { physicalPortCapEntry 95 }

physicalPortCapTurnupConfig OBJECT-TYPE
    SYNTAX        FspR7RlsActionCaps
    MAX-ACCESS    read-only
    STATUS        current
    DESCRIPTION   "Turnup Operation"
    ::= { physicalPortCapEntry 96 }

physicalPortCapTxOffDelay OBJECT-TYPE
    SYNTAX        FspR7EnableDisableCaps
    MAX-ACCESS    read-only
    STATUS        current
    DESCRIPTION   "Enable or disable TXOFFHOLD Period for Error Forwarding and LKDO-OFF Consequent Action."
    ::= { physicalPortCapEntry 97 }

physicalPortCapVoaMode OBJECT-TYPE
    SYNTAX        FspR7VoaModeCaps
    MAX-ACCESS    read-only
    STATUS        current
    DESCRIPTION   "VOA operating mode"
    ::= { physicalPortCapEntry 98 }

physicalPortCapVoaSetpoint OBJECT-TYPE
    SYNTAX        FspR7Unsigned32Caps
    UNITS         "0.1 dB"
    MAX-ACCESS    read-only
    STATUS        current
    DESCRIPTION   "Sets the optical attenuation of VOA"
    ::= { physicalPortCapEntry 99 }

physicalPortCapLagPrio OBJECT-TYPE
    SYNTAX        FspR7Unsigned32Caps
    MAX-ACCESS    read-only
    STATUS        current
    DESCRIPTION   "Part of ID. Port pri that defines standby."
    ::= { physicalPortCapEntry 100 }

physicalPortCapMaxFrameSize OBJECT-TYPE
    SYNTAX        FspR7Unsigned32Caps
    MAX-ACCESS    read-only
    STATUS        current
    DESCRIPTION   "Max Frame Size"
    ::= { physicalPortCapEntry 101 }

physicalPortCapPayload OBJECT-TYPE
    SYNTAX        OtnPayloadTypeCaps
    MAX-ACCESS    read-only
    STATUS        current
    DESCRIPTION   "The PAYLOAD defines the transport service type of the payload"
    ::= { physicalPortCapEntry 102 }

physicalPortCapPortMode OBJECT-TYPE
    SYNTAX        FspR7PortModeCaps
    MAX-ACCESS    read-only
    STATUS        current
    DESCRIPTION   "Port Mode"
    ::= { physicalPortCapEntry 103 }

physicalPortCapPortRole OBJECT-TYPE
    SYNTAX        FspR7PortRoleCaps
    MAX-ACCESS    read-only
    STATUS        current
    DESCRIPTION   "ADVA cloud Port Roles"
    ::= { physicalPortCapEntry 104 }

physicalPortCapPriority OBJECT-TYPE
    SYNTAX        FspR7Unsigned32Caps
    MAX-ACCESS    read-only
    STATUS        current
    DESCRIPTION   "Default PCP in case UTAG is Enabled. The Prio may be remapped in the EVC."
    ::= { physicalPortCapEntry 105 }

physicalPortCapPvid OBJECT-TYPE
    SYNTAX        FspR7Unsigned32Caps
    MAX-ACCESS    read-only
    STATUS        current
    DESCRIPTION   "Default VLAN ID (both STAG/CTAG mode) in case UTAG is enabled"
    ::= { physicalPortCapEntry 106 }

physicalPortCapStagType OBJECT-TYPE
    SYNTAX        Integer32
    MAX-ACCESS    read-only
    STATUS        current
    DESCRIPTION   "TAG type field"
    ::= { physicalPortCapEntry 107 }

physicalPortCapUtag OBJECT-TYPE
    SYNTAX        FspR7UntaggedFramesCaps
    MAX-ACCESS    read-only
    STATUS        current
    DESCRIPTION   "If untagged frames shall be enabled on this port or not."
    ::= { physicalPortCapEntry 108 }

physicalPortCapVethAid OBJECT-TYPE
    SYNTAX        SnmpAdminString
    MAX-ACCESS    read-only
    STATUS        current
    DESCRIPTION   "Shows if PORT is a member in the LAG with the VETH AID"
    ::= { physicalPortCapEntry 109 }

physicalPortCapRedLineState OBJECT-TYPE
    SYNTAX        FspR7YesNoCaps
    MAX-ACCESS    read-only
    STATUS        current
    DESCRIPTION   "will be set by higher level software to act as a barrier to deletion"
    ::= { physicalPortCapEntry 110 }

physicalPortCapTunnelAid OBJECT-TYPE
    SYNTAX        Integer32
    MAX-ACCESS    read-only
    STATUS        current
    DESCRIPTION   "Tunnel AID"
    ::= { physicalPortCapEntry 111 }

physicalPortCapRateLimit OBJECT-TYPE
    SYNTAX        FspR7DisableEnableCaps
    MAX-ACCESS    read-only
    STATUS        current
    DESCRIPTION   "Selection to apply rate limit feature or not."
    ::= { physicalPortCapEntry 112 }

physicalPortCapTxOffOnTm OBJECT-TYPE
    SYNTAX        FspR7TxOffOnTmCaps
    MAX-ACCESS    read-only
    STATUS        current
    DESCRIPTION   "Relevant only when ERRFWD=TXOFF. Enables/disables the
        possibility to delay turning off and on the the transmitter.
        This applies to the case when turning off the transmitter
        is done  as an error forwarding mechanism."
    ::= { physicalPortCapEntry 113 }

physicalPortCapTxOffTimer OBJECT-TYPE
    SYNTAX        FspR7Unsigned32Caps
    UNITS         "ms"
    MAX-ACCESS    read-only
    STATUS        current
    DESCRIPTION   "Delay before transmitter is swiched off"
    ::= { physicalPortCapEntry 114 }

physicalPortCapTxOnTimer OBJECT-TYPE
    SYNTAX        FspR7Unsigned32Caps
    UNITS         "ms"
    MAX-ACCESS    read-only
    STATUS        current
    DESCRIPTION   "Delay before transmitter is switched on"
    ::= { physicalPortCapEntry 115 }

physicalPortCapMode OBJECT-TYPE
    SYNTAX        FspR7TransmissionModeCaps
    MAX-ACCESS    read-only
    STATUS        current
    DESCRIPTION   "Mode of the module, determine operation or functionality"
    ::= { physicalPortCapEntry 116 }

physicalPortCapMonLevel OBJECT-TYPE
    SYNTAX        FspR7MonLevelCaps
    MAX-ACCESS    read-only
    STATUS        current
    DESCRIPTION   "Highest signal level of intrusive or non-intrusive monitoring. Hardware may monitor the signal one layer higher than Termination Level (TERM)."
    ::= { physicalPortCapEntry 117 }

physicalPortCapChannelPlan OBJECT-TYPE
    SYNTAX        FspR7ChannelRangeInventoryCaps
    MAX-ACCESS    read-only
    STATUS        current
    DESCRIPTION   "Channel Range"
    ::= { physicalPortCapEntry 118 }

physicalPortCapOptimize OBJECT-TYPE
    SYNTAX        FspR7OptimizeCaps
    MAX-ACCESS    read-only
    STATUS        current
    DESCRIPTION   "Optimizes port for either protection switch time or traffic regeneration operation"
    ::= { physicalPortCapEntry 119 }

physicalPortCapEncryptionChannel OBJECT-TYPE
    SYNTAX        CryptoFspR7EncryptionCommunicationCaps
    MAX-ACCESS    read-only
    STATUS        current
    DESCRIPTION   "Embedded Communication Channel used to support Encryption"
    ::= { physicalPortCapEntry 120 }

physicalPortCapLinkSetup OBJECT-TYPE
    SYNTAX        FspR7DisableEnableCaps
    MAX-ACCESS    read-only
    STATUS        current
    DESCRIPTION   "Support RDMA over Converged Ethernet (RoCE)"
    ::= { physicalPortCapEntry 121 }

physicalPortCapCdCompensationRange OBJECT-TYPE
    SYNTAX        FspR7CdCompensationRangeCaps
    MAX-ACCESS    read-only
    STATUS        current
    DESCRIPTION   "Chromatic Dispersion Compensation Goal"
    ::= { physicalPortCapEntry 122 }

physicalPortCapChannelSpacing OBJECT-TYPE
    SYNTAX        FspR7ChannelSpacingCaps
    MAX-ACCESS    read-only
    STATUS        current
    DESCRIPTION   "ITU Grid channel spacing"
    ::= { physicalPortCapEntry 123 }

physicalPortCapLLDPNeighborsRx OBJECT-TYPE
    SYNTAX        FspR7LLDPNeighborsCaps
    MAX-ACCESS    read-only
    STATUS        current
    DESCRIPTION   "LLDP Neighbors in Rx Direction"
    ::= { physicalPortCapEntry 124 }

physicalPortCapLLDPNeighborsTx OBJECT-TYPE
    SYNTAX        FspR7LLDPNeighborsCaps
    MAX-ACCESS    read-only
    STATUS        current
    DESCRIPTION   "LLDP Neighbors in Tx Direction"
    ::= { physicalPortCapEntry 125 }

physicalPortCapCdPostCompensationRange OBJECT-TYPE
    SYNTAX        FspR7CdPostCompensationRangeCaps
    MAX-ACCESS    read-only
    STATUS        current
    DESCRIPTION   "CD Post Compensation Range
        Range 1: [-22 ns/nm   to +6 ns/nm] or [-20 ns/nm to +2 ns/nm]
        Range 2: [-72 ns/nm   to +6 ns/nm] or [-45 ns/nm to +5 ns/nm]
        Range 3: [-120 ns/nm to +6 ns/nm]
        Range 4: [-280 ns/nm to +6 ns/nm]"
    ::= { physicalPortCapEntry 126 }

physicalPortCapLaneChannel1 OBJECT-TYPE
    SYNTAX        FspR7ChannelIdentifierCaps
    MAX-ACCESS    read-only
    STATUS        current
    DESCRIPTION   "Lane Channel"
    ::= { physicalPortCapEntry 127 }

physicalPortCapLaneChannel2 OBJECT-TYPE
    SYNTAX        FspR7ChannelIdentifierCaps
    MAX-ACCESS    read-only
    STATUS        current
    DESCRIPTION   "Lane Channel"
    ::= { physicalPortCapEntry 128 }

physicalPortCapOpticalSetPointLane1 OBJECT-TYPE
    SYNTAX        FspR7Integer32Caps
    UNITS         "0.1 dBm"
    MAX-ACCESS    read-only
    STATUS        current
    DESCRIPTION   "Optical Power Setpoint for Optical Transport Lane 1"
    ::= { physicalPortCapEntry 129 }

physicalPortCapOpticalSetPointLane2 OBJECT-TYPE
    SYNTAX        FspR7Integer32Caps
    UNITS         "0.1 dBm"
    MAX-ACCESS    read-only
    STATUS        current
    DESCRIPTION   "Optical Power Setpoint for Optical Transport Lane 2"
    ::= { physicalPortCapEntry 130 }

physicalPortCapTerminationMode OBJECT-TYPE
    SYNTAX        FspR7TerminationModeCaps
    MAX-ACCESS    read-only
    STATUS        current
    DESCRIPTION   "FSP 3000 C Signal Termination Modes
        Monitor or Terminate 	describes general signal handling at layer
        Mux		indicates if signal is multiplexed or demultiplexed at layer
        Connect		indicates support for Sub Network Connection (SNC), cross-connect"
    ::= { physicalPortCapEntry 131 }

physicalPortCapTimDetModeOtu OBJECT-TYPE
    SYNTAX        FspR7TimDetModeCaps
    MAX-ACCESS    read-only
    STATUS        current
    DESCRIPTION   "OTU Trace Identifier Mismatch (TIM) strings compared to generate TIM defect."
    ::= { physicalPortCapEntry 132 }

physicalPortCapTimActionOtu OBJECT-TYPE
    SYNTAX        FspR7YesNoCaps
    MAX-ACCESS    read-only
    STATUS        current
    DESCRIPTION   "Trace Identifier Mismatch (TIM) is reported as an alarm when detected. User selection allow traffic or AIS to be sent while the mismatch is present."
    ::= { physicalPortCapEntry 133 }

physicalPortCapTraceExpectedDapiOtu OBJECT-TYPE
    SYNTAX        Integer32
    MAX-ACCESS    read-only
    STATUS        current
    DESCRIPTION   "Expected DAPI part of the OTU trace (15 character). NULL TRACE implies that no trace comparison is made."
    ::= { physicalPortCapEntry 134 }

physicalPortCapTraceExpectedOpspOtu OBJECT-TYPE
    SYNTAX        Integer32
    MAX-ACCESS    read-only
    STATUS        current
    DESCRIPTION   "Expected OPSP part of the OTU trace (32 character). NULL TRACE implies that no trace comparison is made."
    ::= { physicalPortCapEntry 135 }

physicalPortCapTimDetModeOdu OBJECT-TYPE
    SYNTAX        FspR7TimDetModeCaps
    MAX-ACCESS    read-only
    STATUS        current
    DESCRIPTION   "ODU Trace Identifier Mismatch (TIM) strings compared to generate TIM defect."
    ::= { physicalPortCapEntry 136 }

physicalPortCapTimActionOdu OBJECT-TYPE
    SYNTAX        FspR7YesNoCaps
    MAX-ACCESS    read-only
    STATUS        current
    DESCRIPTION   "Trace Identifier Mismatch (TIM) is reported as an alarm when detected. User selection allow traffic or AIS to be sent while the mismatch is present."
    ::= { physicalPortCapEntry 137 }

physicalPortCapTraceExpectedDapiOdu OBJECT-TYPE
    SYNTAX        Integer32
    MAX-ACCESS    read-only
    STATUS        current
    DESCRIPTION   "Expected DAPI part of the ODU trace (15 character). NULL TRACE implies that no trace comparison is made."
    ::= { physicalPortCapEntry 138 }

physicalPortCapTraceExpectedOpspOdu OBJECT-TYPE
    SYNTAX        Integer32
    MAX-ACCESS    read-only
    STATUS        current
    DESCRIPTION   "Expected OPSP part of the ODU trace (32 character). NULL TRACE implies that no trace comparison is made."
    ::= { physicalPortCapEntry 139 }

physicalPortCapReportAisLine OBJECT-TYPE
    SYNTAX        FspR7YesNoCaps
    MAX-ACCESS    read-only
    STATUS        current
    DESCRIPTION   "Whether AIS alarm (Line/MS) is reported or not."
    ::= { physicalPortCapEntry 140 }

physicalPortCapReportSsfLine OBJECT-TYPE
    SYNTAX        FspR7YesNoCaps
    MAX-ACCESS    read-only
    STATUS        current
    DESCRIPTION   "Whether SSF alarm (Line/MS) is reported or not."
    ::= { physicalPortCapEntry 141 }

physicalPortCapReportSsfSection OBJECT-TYPE
    SYNTAX        FspR7YesNoCaps
    MAX-ACCESS    read-only
    STATUS        current
    DESCRIPTION   "Whether SSF alarm (Section/RS) is reported or not."
    ::= { physicalPortCapEntry 142 }

physicalPortCapDelayMeasurementOperation OBJECT-TYPE
    SYNTAX        FspR7DmsrmtOperationCaps
    MAX-ACCESS    read-only
    STATUS        current
    DESCRIPTION   "Delay Measurement start"
    ::= { physicalPortCapEntry 143 }

virtualPortCapTable OBJECT-TYPE
    SYNTAX        SEQUENCE OF VirtualPortCapEntry
    MAX-ACCESS    not-accessible
    STATUS        current
    DESCRIPTION   "virtualPortCapTable"
    ::= { facilityMgmtCap 2 }

virtualPortCapEntry OBJECT-TYPE
    SYNTAX        VirtualPortCapEntry
    MAX-ACCESS    not-accessible
    STATUS        current
    DESCRIPTION   "Entry of virtualPortCapTable"
    INDEX       {
                  entityFacilityShelfNo,
                  entityFacilitySlotNo,
                  entityFacilityPortNo,
                  entityFacilityExtNo,
                  entityFacilityClassName
                }
    ::= { virtualPortCapTable 1 }

VirtualPortCapEntry ::= SEQUENCE
  {    virtualPortCapRowStatus FspR7RowStatusCaps,
    virtualPortCapChannelBand FspR7ChannelBandwidthCaps,
    virtualPortCapType FspR7InterfaceTypeCaps,
    virtualPortCapAlias Integer32,
    virtualPortCapAdmin FspR7AdminStateCaps,
    virtualPortCapEqlzAdmin FspR7EnableDisableCaps,
    virtualPortCapInitEqlz FspR7RlsActionCaps,
    virtualPortCapLacpMode FspR7LacpModeCaps,
    virtualPortCapLacpTimeout FspR7LacpTimeoutCaps,
    virtualPortCapLagActivePorts FspR7Unsigned32Caps,
    virtualPortCapMaxFrameSize FspR7Unsigned32Caps,
    virtualPortCapPortMode FspR7PortModeCaps,
    virtualPortCapDataLayerPmReset FspR7PmResetCaps,
    virtualPortCapPortRole FspR7PortRoleCaps,
    virtualPortCapLagPortType FspR7LagPortTypeCaps,
    virtualPortCapPriority FspR7Unsigned32Caps,
    virtualPortCapPvid FspR7Unsigned32Caps,
    virtualPortCapRevertiveMode ApsRevertModeCaps,
    virtualPortCapStagType Integer32,
    virtualPortCapUtag FspR7UntaggedFramesCaps,
    virtualPortCapBundle FspR7SnmpLongString,
    virtualPortCapSwitchCommand FspR7APSCommandCaps,
    virtualPortCapInhibitSwitchToWork FspR7YesNoCaps,
    virtualPortCapInhibitSwitchToProt FspR7YesNoCaps,
    virtualPortCapOduTribPortNo SnmpAdminString,
    virtualPortCapOduTribTimeSlottNo SnmpAdminString,
    virtualPortCapSigDegThresOdu FspR7Integer32Caps,
    virtualPortCapSigDegPeriodOdu FspR7Unsigned32Caps,
    virtualPortCapTraceExpectedOdu Integer32,
    virtualPortCapTraceTransmitSapiOdu Integer32,
    virtualPortCapTraceTransmitDapiOdu Integer32,
    virtualPortCapTraceTransmitOpspOdu Integer32,
    virtualPortCapTimModeOdu TimModeCaps,
    virtualPortCapSigDegThresOduTcmA FspR7Integer32Caps,
    virtualPortCapSigDegPeriodOduTcmA FspR7Unsigned32Caps,
    virtualPortCapSigDegThresOduTcmB FspR7Integer32Caps,
    virtualPortCapSigDegPeriodOduTcmB FspR7Unsigned32Caps,
    virtualPortCapSigDegThresOduTcmC FspR7Integer32Caps,
    virtualPortCapSigDegPeriodOduTcmC FspR7Unsigned32Caps,
    virtualPortCapTcmALevel OtnTcmLevelCaps,
    virtualPortCapTcmBLevel OtnTcmLevelCaps,
    virtualPortCapTcmCLevel OtnTcmLevelCaps,
    virtualPortCapTraceTransmitSapiOduTcmA Integer32,
    virtualPortCapTraceTransmitDapiOduTcmA Integer32,
    virtualPortCapTraceTransmitOpspOduTcmA Integer32,
    virtualPortCapTraceExpectedOduTcmA Integer32,
    virtualPortCapTimModeOduTcmA TimModeCaps,
    virtualPortCapTraceExpectedOduTcmB Integer32,
    virtualPortCapTraceTransmitSapiOduTcmB Integer32,
    virtualPortCapTraceTransmitDapiOduTcmB Integer32,
    virtualPortCapTraceTransmitOpspOduTcmB Integer32,
    virtualPortCapTimModeOduTcmB TimModeCaps,
    virtualPortCapTraceExpectedOduTcmC Integer32,
    virtualPortCapTraceTransmitSapiOduTcmC Integer32,
    virtualPortCapTraceTransmitDapiOduTcmC Integer32,
    virtualPortCapTraceTransmitOpspOduTcmC Integer32,
    virtualPortCapTimModeOduTcmC TimModeCaps,
    virtualPortCapTerminationLevel OhTerminationLevelCaps,
    virtualPortCapLoopConfig LoopConfigCaps,
    virtualPortCapVcType VirtualContainerTypeCaps,
    virtualPortCapCir FspR7Unsigned32Caps,
    virtualPortCapOpuPayloadType FspR7OpuPayloadTypeCaps,
    virtualPortCapOtnStuffing FspR7YesNoCaps,
    virtualPortCapRedLineState FspR7YesNoCaps,
    virtualPortCapTunnelAid Integer32,
    virtualPortCapTrafficDirection FspR7TrafficDirectionCaps,
    virtualPortCapChannelId FspR7SnmpLongString,
    virtualPortCapOptSetDeviation FspR7Integer32Caps,
    virtualPortCapPayload OtnPayloadTypeCaps,
    virtualPortCapPrbsPmReset FspR7PmResetCaps,
    virtualPortCapTestPrbsRcvMode FspR7RlsActionCaps,
    virtualPortCapTestPrbsTrmtMode FspR7RlsActionCaps,
    virtualPortCapTimDetModeOdu FspR7TimDetModeCaps,
    virtualPortCapTimActionOdu FspR7YesNoCaps,
    virtualPortCapTraceExpectedDapiOdu Integer32,
    virtualPortCapTraceExpectedOpspOdu Integer32 }

virtualPortCapRowStatus OBJECT-TYPE
    SYNTAX        FspR7RowStatusCaps
    MAX-ACCESS    read-only
    STATUS        current
    DESCRIPTION   "Virtual Port Capability RowStatus."
    ::= { virtualPortCapEntry 1 }

virtualPortCapChannelBand OBJECT-TYPE
    SYNTAX        FspR7ChannelBandwidthCaps
    MAX-ACCESS    read-only
    STATUS        current
    DESCRIPTION   "Virtual Port Capability Channel Bandwidth."
    ::= { virtualPortCapEntry 2 }

virtualPortCapType OBJECT-TYPE
    SYNTAX        FspR7InterfaceTypeCaps
    MAX-ACCESS    read-only
    STATUS        current
    DESCRIPTION   "Virtual Port Capability Facility Type."
    ::= { virtualPortCapEntry 3 }

virtualPortCapAlias OBJECT-TYPE
    SYNTAX        Integer32
    MAX-ACCESS    read-only
    STATUS        current
    DESCRIPTION   "Virtual Port Capability Alias."
    ::= { virtualPortCapEntry 4 }

virtualPortCapAdmin OBJECT-TYPE
    SYNTAX        FspR7AdminStateCaps
    MAX-ACCESS    read-only
    STATUS        current
    DESCRIPTION   "Virtual Port Capability Adminstrative State."
    ::= { virtualPortCapEntry 5 }

virtualPortCapEqlzAdmin OBJECT-TYPE
    SYNTAX        FspR7EnableDisableCaps
    MAX-ACCESS    read-only
    STATUS        current
    DESCRIPTION   "Virtual Port Capability Fiber Connection Attenuation."
    ::= { virtualPortCapEntry 6 }

virtualPortCapInitEqlz OBJECT-TYPE
    SYNTAX        FspR7RlsActionCaps
    MAX-ACCESS    read-only
    STATUS        current
    DESCRIPTION   "Virtual Port Capability Initiate Equalization."
    ::= { virtualPortCapEntry 7 }

virtualPortCapLacpMode OBJECT-TYPE
    SYNTAX        FspR7LacpModeCaps
    MAX-ACCESS    read-only
    STATUS        current
    DESCRIPTION   "Enable of LACP state machine"
    ::= { virtualPortCapEntry 8 }

virtualPortCapLacpTimeout OBJECT-TYPE
    SYNTAX        FspR7LacpTimeoutCaps
    MAX-ACCESS    read-only
    STATUS        current
    DESCRIPTION   "Timeout of the LACP"
    ::= { virtualPortCapEntry 9 }

virtualPortCapLagActivePorts OBJECT-TYPE
    SYNTAX        FspR7Unsigned32Caps
    MAX-ACCESS    read-only
    STATUS        current
    DESCRIPTION   "Number of active ports in the Link Aggregation Group"
    ::= { virtualPortCapEntry 10 }

virtualPortCapMaxFrameSize OBJECT-TYPE
    SYNTAX        FspR7Unsigned32Caps
    MAX-ACCESS    read-only
    STATUS        current
    DESCRIPTION   "Max Frame Size"
    ::= { virtualPortCapEntry 11 }

virtualPortCapPortMode OBJECT-TYPE
    SYNTAX        FspR7PortModeCaps
    MAX-ACCESS    read-only
    STATUS        current
    DESCRIPTION   "Port Mode"
    ::= { virtualPortCapEntry 12 }

virtualPortCapDataLayerPmReset OBJECT-TYPE
    SYNTAX        FspR7PmResetCaps
    MAX-ACCESS    read-only
    STATUS        current
    DESCRIPTION   "Reset data-layer Performance registers"
    ::= { virtualPortCapEntry 13 }

virtualPortCapPortRole OBJECT-TYPE
    SYNTAX        FspR7PortRoleCaps
    MAX-ACCESS    read-only
    STATUS        current
    DESCRIPTION   "ADVA cloud Port Roles"
    ::= { virtualPortCapEntry 14 }

virtualPortCapLagPortType OBJECT-TYPE
    SYNTAX        FspR7LagPortTypeCaps
    MAX-ACCESS    read-only
    STATUS        current
    DESCRIPTION   "Type/Speed of connected ports in the Link Aggregation Group"
    ::= { virtualPortCapEntry 15 }

virtualPortCapPriority OBJECT-TYPE
    SYNTAX        FspR7Unsigned32Caps
    MAX-ACCESS    read-only
    STATUS        current
    DESCRIPTION   "Default PCP in case UTAG is Enabled. The Prio may be remapped in the EVC."
    ::= { virtualPortCapEntry 16 }

virtualPortCapPvid OBJECT-TYPE
    SYNTAX        FspR7Unsigned32Caps
    MAX-ACCESS    read-only
    STATUS        current
    DESCRIPTION   "Default VLAN ID (both STAG/CTAG mode) in case UTAG is enabled"
    ::= { virtualPortCapEntry 17 }

virtualPortCapRevertiveMode OBJECT-TYPE
    SYNTAX        ApsRevertModeCaps
    MAX-ACCESS    read-only
    STATUS        current
    DESCRIPTION   "Revertive Protection Switching"
    ::= { virtualPortCapEntry 18 }

virtualPortCapStagType OBJECT-TYPE
    SYNTAX        Integer32
    MAX-ACCESS    read-only
    STATUS        current
    DESCRIPTION   "TAG type field"
    ::= { virtualPortCapEntry 19 }

virtualPortCapUtag OBJECT-TYPE
    SYNTAX        FspR7UntaggedFramesCaps
    MAX-ACCESS    read-only
    STATUS        current
    DESCRIPTION   "If untagged frames shall be enabled on this port or not."
    ::= { virtualPortCapEntry 20 }

virtualPortCapBundle OBJECT-TYPE
    SYNTAX        FspR7SnmpLongString
    MAX-ACCESS    read-only
    STATUS        current
    DESCRIPTION   "List of VC4/VC3/STS1/STS3c/STS24c/STS48c containers used in the BUNDLE"
    ::= { virtualPortCapEntry 21 }

virtualPortCapSwitchCommand OBJECT-TYPE
    SYNTAX        FspR7APSCommandCaps
    MAX-ACCESS    read-only
    STATUS        current
    DESCRIPTION   "The switch command action for this facility. A command resulting
        in a switch event will also cause a change of the facility secondary state
        and a corresponding condition. Addressed by this command is the active port,
        the port to switch away from. Since this is a manual switch command, it will
        not switch if other port suffers from a signalfailure or a signal degrade."
    ::= { virtualPortCapEntry 22 }

virtualPortCapInhibitSwitchToWork OBJECT-TYPE
    SYNTAX        FspR7YesNoCaps
    MAX-ACCESS    read-only
    STATUS        current
    DESCRIPTION   "Inhibit Switch to working facility. Inhibition blocks an automatic switch to the
        working facility. Valid only for the protection facility."
    ::= { virtualPortCapEntry 23 }

virtualPortCapInhibitSwitchToProt OBJECT-TYPE
    SYNTAX        FspR7YesNoCaps
    MAX-ACCESS    read-only
    STATUS        current
    DESCRIPTION   "Inhibit Switch to protection facility. Inhibition blocks an automatic switch
        to the protection facility. Valid only for the working facility."
    ::= { virtualPortCapEntry 24 }

virtualPortCapOduTribPortNo OBJECT-TYPE
    SYNTAX        SnmpAdminString
    MAX-ACCESS    read-only
    STATUS        current
    DESCRIPTION   "ODU Tributary Port Number"
    ::= { virtualPortCapEntry 25 }

virtualPortCapOduTribTimeSlottNo OBJECT-TYPE
    SYNTAX        SnmpAdminString
    MAX-ACCESS    read-only
    STATUS        current
    DESCRIPTION   "ODU Tributary slot number. Multiple values can be entered as a string, separated by commas or given as a range.
        For capabilities objects possible number of slots and valid range are displayed in a form:
        [1,2,3,8][count: 1-1]
        In first brackets valid slots are shown and in the second possible number of slots."
    ::= { virtualPortCapEntry 26 }

virtualPortCapSigDegThresOdu OBJECT-TYPE
    SYNTAX        FspR7Integer32Caps
    UNITS         "%"
    MAX-ACCESS    read-only
    STATUS        current
    DESCRIPTION   "Background-Block-Error-Based Signal Degradation Definition for ODU"
    ::= { virtualPortCapEntry 27 }

virtualPortCapSigDegPeriodOdu OBJECT-TYPE
    SYNTAX        FspR7Unsigned32Caps
    UNITS         "s"
    MAX-ACCESS    read-only
    STATUS        current
    DESCRIPTION   "Integration Period for Signal degrade"
    ::= { virtualPortCapEntry 28 }

virtualPortCapTraceExpectedOdu OBJECT-TYPE
    SYNTAX        Integer32
    MAX-ACCESS    read-only
    STATUS        current
    DESCRIPTION   "Expected SAPI part of the ODU trace (15 character). NULL TRACE implies that no trace comparison is made."
    ::= { virtualPortCapEntry 29 }

virtualPortCapTraceTransmitSapiOdu OBJECT-TYPE
    SYNTAX        Integer32
    MAX-ACCESS    read-only
    STATUS        current
    DESCRIPTION   "The transmitted SAPI part of the ODU trace (15 character)"
    ::= { virtualPortCapEntry 30 }

virtualPortCapTraceTransmitDapiOdu OBJECT-TYPE
    SYNTAX        Integer32
    MAX-ACCESS    read-only
    STATUS        current
    DESCRIPTION   "The transmitted DAPI part of the ODU trace (15 character)"
    ::= { virtualPortCapEntry 31 }

virtualPortCapTraceTransmitOpspOdu OBJECT-TYPE
    SYNTAX        Integer32
    MAX-ACCESS    read-only
    STATUS        current
    DESCRIPTION   "The transmitted Operator Specific part of the ODU trace (32 character)"
    ::= { virtualPortCapEntry 32 }

virtualPortCapTimModeOdu OBJECT-TYPE
    SYNTAX        TimModeCaps
    MAX-ACCESS    read-only
    STATUS        current
    DESCRIPTION   "Detection of TIM-ODU Condition can be configured"
    ::= { virtualPortCapEntry 33 }

virtualPortCapSigDegThresOduTcmA OBJECT-TYPE
    SYNTAX        FspR7Integer32Caps
    UNITS         "%"
    MAX-ACCESS    read-only
    STATUS        current
    DESCRIPTION   "Background-Block-Error-Based Signal Degradation Definition for TCM-A"
    ::= { virtualPortCapEntry 34 }

virtualPortCapSigDegPeriodOduTcmA OBJECT-TYPE
    SYNTAX        FspR7Unsigned32Caps
    UNITS         "s"
    MAX-ACCESS    read-only
    STATUS        current
    DESCRIPTION   "Integration Period for Signal degrade"
    ::= { virtualPortCapEntry 35 }

virtualPortCapSigDegThresOduTcmB OBJECT-TYPE
    SYNTAX        FspR7Integer32Caps
    UNITS         "%"
    MAX-ACCESS    read-only
    STATUS        current
    DESCRIPTION   "Background-Block-Error-Based Signal Degradation Definition for TCM-B"
    ::= { virtualPortCapEntry 36 }

virtualPortCapSigDegPeriodOduTcmB OBJECT-TYPE
    SYNTAX        FspR7Unsigned32Caps
    UNITS         "s"
    MAX-ACCESS    read-only
    STATUS        current
    DESCRIPTION   "Integration Period of TCMB Signal Segrade"
    ::= { virtualPortCapEntry 37 }

virtualPortCapSigDegThresOduTcmC OBJECT-TYPE
    SYNTAX        FspR7Integer32Caps
    UNITS         "%"
    MAX-ACCESS    read-only
    STATUS        current
    DESCRIPTION   "Background-Block-Error-Based Signal Degradation Definition for TCM-C"
    ::= { virtualPortCapEntry 38 }

virtualPortCapSigDegPeriodOduTcmC OBJECT-TYPE
    SYNTAX        FspR7Unsigned32Caps
    UNITS         "s"
    MAX-ACCESS    read-only
    STATUS        current
    DESCRIPTION   "Integration Period of TCMC Signal Segrade"
    ::= { virtualPortCapEntry 39 }

virtualPortCapTcmALevel OBJECT-TYPE
    SYNTAX        OtnTcmLevelCaps
    MAX-ACCESS    read-only
    STATUS        current
    DESCRIPTION   "Activation of Tandem Connection Monitoring Instance A"
    ::= { virtualPortCapEntry 40 }

virtualPortCapTcmBLevel OBJECT-TYPE
    SYNTAX        OtnTcmLevelCaps
    MAX-ACCESS    read-only
    STATUS        current
    DESCRIPTION   "Activation of Tandem Connection Monitoring Instance B"
    ::= { virtualPortCapEntry 41 }

virtualPortCapTcmCLevel OBJECT-TYPE
    SYNTAX        OtnTcmLevelCaps
    MAX-ACCESS    read-only
    STATUS        current
    DESCRIPTION   "Activation of Tandem Connection Monitoring Instance C"
    ::= { virtualPortCapEntry 42 }

virtualPortCapTraceTransmitSapiOduTcmA OBJECT-TYPE
    SYNTAX        Integer32
    MAX-ACCESS    read-only
    STATUS        current
    DESCRIPTION   "The transmitted SAPI part of the TCMA trace (15 character)"
    ::= { virtualPortCapEntry 43 }

virtualPortCapTraceTransmitDapiOduTcmA OBJECT-TYPE
    SYNTAX        Integer32
    MAX-ACCESS    read-only
    STATUS        current
    DESCRIPTION   "The transmitted DAPI part of the TCMA trace (15 character)"
    ::= { virtualPortCapEntry 44 }

virtualPortCapTraceTransmitOpspOduTcmA OBJECT-TYPE
    SYNTAX        Integer32
    MAX-ACCESS    read-only
    STATUS        current
    DESCRIPTION   "The transmitted Operator Specific part of the TCMA trace (32 character)"
    ::= { virtualPortCapEntry 45 }

virtualPortCapTraceExpectedOduTcmA OBJECT-TYPE
    SYNTAX        Integer32
    MAX-ACCESS    read-only
    STATUS        current
    DESCRIPTION   "Expected SAPI part of the TCMA trace (15 character). NULL TRACE-TCM implies that no trace comparison is made."
    ::= { virtualPortCapEntry 46 }

virtualPortCapTimModeOduTcmA OBJECT-TYPE
    SYNTAX        TimModeCaps
    MAX-ACCESS    read-only
    STATUS        current
    DESCRIPTION   "TCM_A Trace Identifier Mismatch (TIM) detection/action for TIM defect."
    ::= { virtualPortCapEntry 47 }

virtualPortCapTraceExpectedOduTcmB OBJECT-TYPE
    SYNTAX        Integer32
    MAX-ACCESS    read-only
    STATUS        current
    DESCRIPTION   "Expected SAPI part of the TCMB trace (15 character). NULL TRACE-TCM implies that no trace comparison is made."
    ::= { virtualPortCapEntry 48 }

virtualPortCapTraceTransmitSapiOduTcmB OBJECT-TYPE
    SYNTAX        Integer32
    MAX-ACCESS    read-only
    STATUS        current
    DESCRIPTION   "The transmitted SAPI part of the TCMB trace (15 character)"
    ::= { virtualPortCapEntry 49 }

virtualPortCapTraceTransmitDapiOduTcmB OBJECT-TYPE
    SYNTAX        Integer32
    MAX-ACCESS    read-only
    STATUS        current
    DESCRIPTION   "The transmitted DAPI part of the TCMB trace (15 character)"
    ::= { virtualPortCapEntry 50 }

virtualPortCapTraceTransmitOpspOduTcmB OBJECT-TYPE
    SYNTAX        Integer32
    MAX-ACCESS    read-only
    STATUS        current
    DESCRIPTION   "The transmitted Operator Specific part of the TCMB trace (32 character)"
    ::= { virtualPortCapEntry 51 }

virtualPortCapTimModeOduTcmB OBJECT-TYPE
    SYNTAX        TimModeCaps
    MAX-ACCESS    read-only
    STATUS        current
    DESCRIPTION   "TCM_B Trace Identifier Mismatch (TIM) detection/action for TIM defect."
    ::= { virtualPortCapEntry 52 }

virtualPortCapTraceExpectedOduTcmC OBJECT-TYPE
    SYNTAX        Integer32
    MAX-ACCESS    read-only
    STATUS        current
    DESCRIPTION   "Expected SAPI part of the TCMC trace (15 character). NULL TRACE-TCM implies that no trace comparison is made."
    ::= { virtualPortCapEntry 53 }

virtualPortCapTraceTransmitSapiOduTcmC OBJECT-TYPE
    SYNTAX        Integer32
    MAX-ACCESS    read-only
    STATUS        current
    DESCRIPTION   "The transmitted SAPI part of the TCMC trace (15 character)"
    ::= { virtualPortCapEntry 54 }

virtualPortCapTraceTransmitDapiOduTcmC OBJECT-TYPE
    SYNTAX        Integer32
    MAX-ACCESS    read-only
    STATUS        current
    DESCRIPTION   "The transmitted DAPI part of the TCMC trace (15 character)"
    ::= { virtualPortCapEntry 55 }

virtualPortCapTraceTransmitOpspOduTcmC OBJECT-TYPE
    SYNTAX        Integer32
    MAX-ACCESS    read-only
    STATUS        current
    DESCRIPTION   "The transmitted Operator Specific part of the TCMC trace (32 character)"
    ::= { virtualPortCapEntry 56 }

virtualPortCapTimModeOduTcmC OBJECT-TYPE
    SYNTAX        TimModeCaps
    MAX-ACCESS    read-only
    STATUS        current
    DESCRIPTION   "TCM_C Trace Identifier Mismatch (TIM) detection/action for TIM defect."
    ::= { virtualPortCapEntry 57 }

virtualPortCapTerminationLevel OBJECT-TYPE
    SYNTAX        OhTerminationLevelCaps
    MAX-ACCESS    read-only
    STATUS        current
    DESCRIPTION   "Highest signal level hardware removes then generates for transmission."
    ::= { virtualPortCapEntry 58 }

virtualPortCapLoopConfig OBJECT-TYPE
    SYNTAX        LoopConfigCaps
    MAX-ACCESS    read-only
    STATUS        current
    DESCRIPTION   "External or Facility Loopback"
    ::= { virtualPortCapEntry 59 }

virtualPortCapVcType OBJECT-TYPE
    SYNTAX        VirtualContainerTypeCaps
    MAX-ACCESS    read-only
    STATUS        current
    DESCRIPTION   "Virtual Container Group Type"
    ::= { virtualPortCapEntry 60 }

virtualPortCapCir OBJECT-TYPE
    SYNTAX        FspR7Unsigned32Caps
    UNITS         "Mbps"
    MAX-ACCESS    read-only
    STATUS        current
    DESCRIPTION   "CIR (Committed Information Rate ) is used on Ethernet Interfaces with a policing function"
    ::= { virtualPortCapEntry 61 }

virtualPortCapOpuPayloadType OBJECT-TYPE
    SYNTAX        FspR7OpuPayloadTypeCaps
    MAX-ACCESS    read-only
    STATUS        current
    DESCRIPTION   "OPU Payload Type Indicator"
    ::= { virtualPortCapEntry 62 }

virtualPortCapOtnStuffing OBJECT-TYPE
    SYNTAX        FspR7YesNoCaps
    MAX-ACCESS    read-only
    STATUS        current
    DESCRIPTION   "Indicates if bit/byte stuffing is used in the transport signal."
    ::= { virtualPortCapEntry 63 }

virtualPortCapRedLineState OBJECT-TYPE
    SYNTAX        FspR7YesNoCaps
    MAX-ACCESS    read-only
    STATUS        current
    DESCRIPTION   "will be set by higher level software to act as a barrier to deletion"
    ::= { virtualPortCapEntry 64 }

virtualPortCapTunnelAid OBJECT-TYPE
    SYNTAX        Integer32
    MAX-ACCESS    read-only
    STATUS        current
    DESCRIPTION   "Tunnel AID"
    ::= { virtualPortCapEntry 65 }

virtualPortCapTrafficDirection OBJECT-TYPE
    SYNTAX        FspR7TrafficDirectionCaps
    MAX-ACCESS    read-only
    STATUS        current
    DESCRIPTION   "Traffic Direction"
    ::= { virtualPortCapEntry 66 }

virtualPortCapChannelId OBJECT-TYPE
    SYNTAX        FspR7SnmpLongString
    MAX-ACCESS    read-only
    STATUS        current
    DESCRIPTION   "Channel ID [1 ..256]"
    ::= { virtualPortCapEntry 67 }

virtualPortCapOptSetDeviation OBJECT-TYPE
    SYNTAX        FspR7Integer32Caps
    UNITS         "0.1 dB"
    MAX-ACCESS    read-only
    STATUS        current
    DESCRIPTION   "Channel optical power delta from the port optical power set-point used for equalization (use is optional)."
    ::= { virtualPortCapEntry 68 }

virtualPortCapPayload OBJECT-TYPE
    SYNTAX        OtnPayloadTypeCaps
    MAX-ACCESS    read-only
    STATUS        current
    DESCRIPTION   "The PAYLOAD defines the transport service type of the payload"
    ::= { virtualPortCapEntry 69 }

virtualPortCapPrbsPmReset OBJECT-TYPE
    SYNTAX        FspR7PmResetCaps
    MAX-ACCESS    read-only
    STATUS        current
    DESCRIPTION   "Reset PRBS PM counters"
    ::= { virtualPortCapEntry 70 }

virtualPortCapTestPrbsRcvMode OBJECT-TYPE
    SYNTAX        FspR7RlsActionCaps
    MAX-ACCESS    read-only
    STATUS        current
    DESCRIPTION   "PRBS test pattern received"
    ::= { virtualPortCapEntry 71 }

virtualPortCapTestPrbsTrmtMode OBJECT-TYPE
    SYNTAX        FspR7RlsActionCaps
    MAX-ACCESS    read-only
    STATUS        current
    DESCRIPTION   "PRBS test pattern transmitted"
    ::= { virtualPortCapEntry 72 }

virtualPortCapTimDetModeOdu OBJECT-TYPE
    SYNTAX        FspR7TimDetModeCaps
    MAX-ACCESS    read-only
    STATUS        current
    DESCRIPTION   "ODU Trace Identifier Mismatch (TIM) strings compared to generate TIM defect."
    ::= { virtualPortCapEntry 73 }

virtualPortCapTimActionOdu OBJECT-TYPE
    SYNTAX        FspR7YesNoCaps
    MAX-ACCESS    read-only
    STATUS        current
    DESCRIPTION   "Trace Identifier Mismatch (TIM) is reported as an alarm when detected. User selection allow traffic or AIS to be sent while the mismatch is present."
    ::= { virtualPortCapEntry 74 }

virtualPortCapTraceExpectedDapiOdu OBJECT-TYPE
    SYNTAX        Integer32
    MAX-ACCESS    read-only
    STATUS        current
    DESCRIPTION   "Expected DAPI part of the ODU trace (15 character). NULL TRACE implies that no trace comparison is made."
    ::= { virtualPortCapEntry 75 }

virtualPortCapTraceExpectedOpspOdu OBJECT-TYPE
    SYNTAX        Integer32
    MAX-ACCESS    read-only
    STATUS        current
    DESCRIPTION   "Expected OPSP part of the ODU trace (32 character). NULL TRACE implies that no trace comparison is made."
    ::= { virtualPortCapEntry 76 }

endOfVirtualPortCapTable OBJECT-TYPE
    SYNTAX        Integer32
    MAX-ACCESS    read-only
    STATUS        current
    DESCRIPTION   ""
    ::= { facilityMgmtCap 3 }

lldpCapTable OBJECT-TYPE
    SYNTAX        SEQUENCE OF LldpCapEntry
    MAX-ACCESS    not-accessible
    STATUS        current
    DESCRIPTION   "lldpCapTable"
    ::= { facilityMgmtCap 4 }

lldpCapEntry OBJECT-TYPE
    SYNTAX        LldpCapEntry
    MAX-ACCESS    not-accessible
    STATUS        current
    DESCRIPTION   "Entry of lldpCapTable"
    INDEX       {
                  entityFacilityShelfNo,
                  entityFacilitySlotNo,
                  entityFacilityPortNo,
                  entityFacilityExtNo,
                  entityFacilityClassName
                }
    ::= { lldpCapTable 1 }

LldpCapEntry ::= SEQUENCE
  {    lldpCapRowStatus FspR7RowStatusCaps,
    lldpCapType FspR7InterfaceTypeCaps,
    lldpCapAlias Integer32,
    lldpCapDataLayerPmReset FspR7PmResetCaps,
    lldpCapAdmin FspR7AdminStateCaps,
    lldpCapLLDPScope FspR7LLDPScopeCaps }

lldpCapRowStatus OBJECT-TYPE
    SYNTAX        FspR7RowStatusCaps
    MAX-ACCESS    read-only
    STATUS        current
    DESCRIPTION   "LLDP Capability RowStatus."
    ::= { lldpCapEntry 1 }

lldpCapType OBJECT-TYPE
    SYNTAX        FspR7InterfaceTypeCaps
    MAX-ACCESS    read-only
    STATUS        current
    DESCRIPTION   "LLDP Capability Facility Type."
    ::= { lldpCapEntry 2 }

lldpCapAlias OBJECT-TYPE
    SYNTAX        Integer32
    MAX-ACCESS    read-only
    STATUS        current
    DESCRIPTION   "LLDP Capability Alias."
    ::= { lldpCapEntry 3 }

lldpCapDataLayerPmReset OBJECT-TYPE
    SYNTAX        FspR7PmResetCaps
    MAX-ACCESS    read-only
    STATUS        current
    DESCRIPTION   "Reset data-layer Performance registers"
    ::= { lldpCapEntry 4 }

lldpCapAdmin OBJECT-TYPE
    SYNTAX        FspR7AdminStateCaps
    MAX-ACCESS    read-only
    STATUS        current
    DESCRIPTION   "LLDP Capability Adminstrative State."
    ::= { lldpCapEntry 5 }

lldpCapLLDPScope OBJECT-TYPE
    SYNTAX        FspR7LLDPScopeCaps
    MAX-ACCESS    read-only
    STATUS        current
    DESCRIPTION   "Scope of LLDP propogation based on standard group MAC Addresses"
    ::= { lldpCapEntry 6 }

endOfLldpCapTable OBJECT-TYPE
    SYNTAX        Integer32
    MAX-ACCESS    read-only
    STATUS        current
    DESCRIPTION   ""
    ::= { facilityMgmtCap 5 }

endOfFacilityMgmtCap OBJECT-TYPE
    SYNTAX        Integer32
    MAX-ACCESS    read-only
    STATUS        current
    DESCRIPTION   ""
    ::= { facilityMgmtCap 10000 }

linkCapTable OBJECT-TYPE
    SYNTAX        SEQUENCE OF LinkCapEntry
    MAX-ACCESS    not-accessible
    STATUS        current
    DESCRIPTION   "linkCapTable"
    ::= { dcnMgmtCap 1 }

linkCapEntry OBJECT-TYPE
    SYNTAX        LinkCapEntry
    MAX-ACCESS    not-accessible
    STATUS        current
    DESCRIPTION   "Entry of linkCapTable"
    INDEX       {
                  entityDcnShelfNo,
                  entityDcnSlotNo,
                  entityDcnPortNo,
                  entityDcnExtNo,
                  entityDcnClassName
                }
    ::= { linkCapTable 1 }

LinkCapEntry ::= SEQUENCE
  {    linkCapRowStatus FspR7RowStatusCaps,
    linkCapType FspR7InterfaceTypeCaps,
    linkCapAdmin FspR7AdminStateCaps,
    linkCapAlias Integer32,
    linkCapAuthString Integer32,
    linkCapProxyArp FspR7NoYesCaps,
    linkCapOspf FspR7OspfModeCaps,
    linkCapBaud FspR7BaundCaps,
    linkCapAuthType FspR7CpAuthTypeCaps,
    linkCapIpType FspR7IpTypeCaps,
    linkCapMetric FspR7Unsigned32Caps,
    linkCapAreaAid SnmpAdminString,
    linkCapNearEndIp FspR7YesNo,
    linkCapBitrate FspR7Unsigned32Caps,
    linkCapIPv6Type FspR7IPv6TypeCaps,
    linkCapNendIPv6 FspR7YesNo,
    linkCapMtu FspR7Unsigned32Caps,
    linkCapHelloInterval FspR7Unsigned32Caps,
    linkCapDeadInterval FspR7Unsigned32Caps,
    linkCapRetransmitInterval FspR7Unsigned32Caps,
    linkCapFarEndIp FspR7YesNo,
    linkCapFendLogicalIpAddr FspR7YesNo }

linkCapRowStatus OBJECT-TYPE
    SYNTAX        FspR7RowStatusCaps
    MAX-ACCESS    read-only
    STATUS        current
    DESCRIPTION   "RowStatus object is used to create or delete a row in the table."
    ::= { linkCapEntry 1 }

linkCapType OBJECT-TYPE
    SYNTAX        FspR7InterfaceTypeCaps
    MAX-ACCESS    read-only
    STATUS        current
    DESCRIPTION   "The TYPE defines the transport service type as wrapper with wrapper layer termination OR else as payload"
    ::= { linkCapEntry 2 }

linkCapAdmin OBJECT-TYPE
    SYNTAX        FspR7AdminStateCaps
    MAX-ACCESS    read-only
    STATUS        current
    DESCRIPTION   "Administrative State is displayed in the GUI and Craft. Transition to Unassigend requires the entity to be deleted."
    ::= { linkCapEntry 3 }

linkCapAlias OBJECT-TYPE
    SYNTAX        Integer32
    MAX-ACCESS    read-only
    STATUS        current
    DESCRIPTION   "User Applied Descriptor"
    ::= { linkCapEntry 4 }

linkCapAuthString OBJECT-TYPE
    SYNTAX        Integer32
    MAX-ACCESS    read-only
    STATUS        current
    DESCRIPTION   "OSPF Authentication Key/String depending on Authentication Type"
    ::= { linkCapEntry 5 }

linkCapProxyArp OBJECT-TYPE
    SYNTAX        FspR7NoYesCaps
    MAX-ACCESS    read-only
    STATUS        current
    DESCRIPTION   "If enabled then ARP requests for FENDIP (coming in on another interface in the same subnet as FENDIP) will be replied too."
    ::= { linkCapEntry 6 }

linkCapOspf OBJECT-TYPE
    SYNTAX        FspR7OspfModeCaps
    MAX-ACCESS    read-only
    STATUS        current
    DESCRIPTION   "OSPF Routing (Dynamic)"
    ::= { linkCapEntry 7 }

linkCapBaud OBJECT-TYPE
    SYNTAX        FspR7BaundCaps
    MAX-ACCESS    read-only
    STATUS        current
    DESCRIPTION   "Baud rate of the serial interface"
    ::= { linkCapEntry 8 }

linkCapAuthType OBJECT-TYPE
    SYNTAX        FspR7CpAuthTypeCaps
    MAX-ACCESS    read-only
    STATUS        current
    DESCRIPTION   "OSPF Authentication Type"
    ::= { linkCapEntry 9 }

linkCapIpType OBJECT-TYPE
    SYNTAX        FspR7IpTypeCaps
    MAX-ACCESS    read-only
    STATUS        current
    DESCRIPTION   "Type of IP configuration"
    ::= { linkCapEntry 10 }

linkCapMetric OBJECT-TYPE
    SYNTAX        FspR7Unsigned32Caps
    MAX-ACCESS    read-only
    STATUS        current
    DESCRIPTION   "Routing Metric"
    ::= { linkCapEntry 11 }

linkCapAreaAid OBJECT-TYPE
    SYNTAX        SnmpAdminString
    MAX-ACCESS    read-only
    STATUS        current
    DESCRIPTION   "OSPF Area AID"
    ::= { linkCapEntry 12 }

linkCapNearEndIp OBJECT-TYPE
    SYNTAX        FspR7YesNo
    MAX-ACCESS    read-only
    STATUS        current
    DESCRIPTION   "IP Address assigned to PPP Termination Point on Near-End NE. Defaults to System IP address"
    ::= { linkCapEntry 13 }

linkCapBitrate OBJECT-TYPE
    SYNTAX        FspR7Unsigned32Caps
    UNITS         "kbps"
    MAX-ACCESS    read-only
    STATUS        current
    DESCRIPTION   "Maximum provisioned bit rate for PPP/IP Link of transmitter for an ECC"
    ::= { linkCapEntry 14 }

linkCapIPv6Type OBJECT-TYPE
    SYNTAX        FspR7IPv6TypeCaps
    MAX-ACCESS    read-only
    STATUS        current
    DESCRIPTION   "Type of IPv6 configuration"
    ::= { linkCapEntry 15 }

linkCapNendIPv6 OBJECT-TYPE
    SYNTAX        FspR7YesNo
    MAX-ACCESS    read-only
    STATUS        current
    DESCRIPTION   "IPv6 Address assigned to PPP Termination Point on Near-End NE."
    ::= { linkCapEntry 16 }

linkCapMtu OBJECT-TYPE
    SYNTAX        FspR7Unsigned32Caps
    UNITS         "Byte"
    MAX-ACCESS    read-only
    STATUS        current
    DESCRIPTION   "Maximum Transmission Unit"
    ::= { linkCapEntry 17 }

linkCapHelloInterval OBJECT-TYPE
    SYNTAX        FspR7Unsigned32Caps
    UNITS         "s"
    MAX-ACCESS    read-only
    STATUS        current
    DESCRIPTION   "Hello Interval"
    ::= { linkCapEntry 18 }

linkCapDeadInterval OBJECT-TYPE
    SYNTAX        FspR7Unsigned32Caps
    UNITS         "s"
    MAX-ACCESS    read-only
    STATUS        current
    DESCRIPTION   "Dead Interval"
    ::= { linkCapEntry 19 }

linkCapRetransmitInterval OBJECT-TYPE
    SYNTAX        FspR7Unsigned32Caps
    UNITS         "s"
    MAX-ACCESS    read-only
    STATUS        current
    DESCRIPTION   "Retransmit Interval"
    ::= { linkCapEntry 20 }

linkCapFarEndIp OBJECT-TYPE
    SYNTAX        FspR7YesNo
    MAX-ACCESS    read-only
    STATUS        current
    DESCRIPTION   "IP Address assigned to PPP Termination Point on Far-End NE. Default is set by NE System on LINK establishment if FENDIPACPT = Y"
    ::= { linkCapEntry 21 }

linkCapFendLogicalIpAddr OBJECT-TYPE
    SYNTAX        FspR7YesNo
    MAX-ACCESS    read-only
    STATUS        current
    DESCRIPTION   "Far End Logical Interface IP"
    ::= { linkCapEntry 22 }

endOfLinkCapTable OBJECT-TYPE
    SYNTAX        Integer32
    MAX-ACCESS    read-only
    STATUS        current
    DESCRIPTION   ""
    ::= { dcnMgmtCap 2 }

scCapTable OBJECT-TYPE
    SYNTAX        SEQUENCE OF ScCapEntry
    MAX-ACCESS    not-accessible
    STATUS        current
    DESCRIPTION   "scCapTable"
    ::= { dcnMgmtCap 3 }

scCapEntry OBJECT-TYPE
    SYNTAX        ScCapEntry
    MAX-ACCESS    not-accessible
    STATUS        current
    DESCRIPTION   "Entry of scCapTable"
    INDEX       {
                  entityDcnShelfNo,
                  entityDcnSlotNo,
                  entityDcnPortNo,
                  entityDcnExtNo,
                  entityDcnClassName
                }
    ::= { scCapTable 1 }

ScCapEntry ::= SEQUENCE
  {    scCapRowStatus FspR7RowStatusCaps,
    scCapType FspR7InterfaceTypeCaps,
    scCapAdmin FspR7AdminStateCaps,
    scCapAlias Integer32,
    scCapAuthString Integer32,
    scCapOspf FspR7OspfModeCaps,
    scCapAuthType FspR7CpAuthTypeCaps,
    scCapIpType FspR7IpTypeCaps,
    scCapMetric FspR7Unsigned32Caps,
    scCapAreaAid SnmpAdminString,
    scCapAlsMode FspR7AlsModeCaps,
    scCapSigDegThresReceiver FspR7Unsigned32Caps,
    scCapAutonegotiation EnableStateCaps,
    scCapBitrate FspR7BitrateCaps,
    scCapDuplex EthDuplexModeCaps,
    scCapAttGradientTh FspR7Unsigned32Caps,
    scCapIpAddr FspR7YesNo,
    scCapLanAid SnmpAdminString,
    scCapIpMask FspR7YesNo,
    scCapDataLayerPmReset FspR7PmResetCaps,
    scCapPriority FspR7Unsigned32Caps,
    scCapIPv6 FspR7YesNo,
    scCapIPv6PrefixLen FspR7Unsigned32Caps,
    scCapIpMode FspR7IpModeCaps,
    scCapGatewayProxyArp FspR7EnableDisableCaps,
    scCapMtu FspR7Unsigned32Caps,
    scCapHelloInterval FspR7Unsigned32Caps,
    scCapDeadInterval FspR7Unsigned32Caps,
    scCapRetransmitInterval FspR7Unsigned32Caps,
    scCapDhcpServer FspR7DhcpServerCaps,
    scCapDhcpStartAddr FspR7YesNo,
    scCapDhcpStopAddr FspR7YesNo,
    scCapDhcpMask FspR7YesNo,
    scCapFrcdLogin FspR7EnableDisableCaps,
    scCapMdix FspR7InterfaceCrossoverCaps }

scCapRowStatus OBJECT-TYPE
    SYNTAX        FspR7RowStatusCaps
    MAX-ACCESS    read-only
    STATUS        current
    DESCRIPTION   "RowStatus object is used to create or delete a row in the table."
    ::= { scCapEntry 1 }

scCapType OBJECT-TYPE
    SYNTAX        FspR7InterfaceTypeCaps
    MAX-ACCESS    read-only
    STATUS        current
    DESCRIPTION   "The TYPE defines the transport service type as wrapper with wrapper layer termination OR else as payload"
    ::= { scCapEntry 2 }

scCapAdmin OBJECT-TYPE
    SYNTAX        FspR7AdminStateCaps
    MAX-ACCESS    read-only
    STATUS        current
    DESCRIPTION   "Administrative State is displayed in the GUI and Craft. Transition to Unassigend requires the entity to be deleted."
    ::= { scCapEntry 3 }

scCapAlias OBJECT-TYPE
    SYNTAX        Integer32
    MAX-ACCESS    read-only
    STATUS        current
    DESCRIPTION   "User Applied Descriptor"
    ::= { scCapEntry 4 }

scCapAuthString OBJECT-TYPE
    SYNTAX        Integer32
    MAX-ACCESS    read-only
    STATUS        current
    DESCRIPTION   "OSPF Authentication Key/String depending on Authentication Type"
    ::= { scCapEntry 5 }

scCapOspf OBJECT-TYPE
    SYNTAX        FspR7OspfModeCaps
    MAX-ACCESS    read-only
    STATUS        current
    DESCRIPTION   "OSPF Routing (Dynamic)"
    ::= { scCapEntry 6 }

scCapAuthType OBJECT-TYPE
    SYNTAX        FspR7CpAuthTypeCaps
    MAX-ACCESS    read-only
    STATUS        current
    DESCRIPTION   "OSPF Authentication Type"
    ::= { scCapEntry 7 }

scCapIpType OBJECT-TYPE
    SYNTAX        FspR7IpTypeCaps
    MAX-ACCESS    read-only
    STATUS        current
    DESCRIPTION   "Type of IP configuration"
    ::= { scCapEntry 8 }

scCapMetric OBJECT-TYPE
    SYNTAX        FspR7Unsigned32Caps
    MAX-ACCESS    read-only
    STATUS        current
    DESCRIPTION   "Routing Metric"
    ::= { scCapEntry 9 }

scCapAreaAid OBJECT-TYPE
    SYNTAX        SnmpAdminString
    MAX-ACCESS    read-only
    STATUS        current
    DESCRIPTION   "OSPF Area AID"
    ::= { scCapEntry 10 }

scCapAlsMode OBJECT-TYPE
    SYNTAX        FspR7AlsModeCaps
    MAX-ACCESS    read-only
    STATUS        current
    DESCRIPTION   "Determines the reaction in backward direction in response to a LOS
        on the same Interface: on a Network Interface connected to the DWDM
        this is a matter of laser safety"
    ::= { scCapEntry 11 }

scCapSigDegThresReceiver OBJECT-TYPE
    SYNTAX        FspR7Unsigned32Caps
    UNITS         "0.1 dB"
    MAX-ACCESS    read-only
    STATUS        current
    DESCRIPTION   "Signal Degrade Threshold on Receiver. Reported as ATTRMT-SDHT to far end."
    ::= { scCapEntry 12 }

scCapAutonegotiation OBJECT-TYPE
    SYNTAX        EnableStateCaps
    MAX-ACCESS    read-only
    STATUS        current
    DESCRIPTION   "Auto Negotiation for the data rate"
    ::= { scCapEntry 13 }

scCapBitrate OBJECT-TYPE
    SYNTAX        FspR7BitrateCaps
    MAX-ACCESS    read-only
    STATUS        current
    DESCRIPTION   "Provisioned data rate"
    ::= { scCapEntry 14 }

scCapDuplex OBJECT-TYPE
    SYNTAX        EthDuplexModeCaps
    MAX-ACCESS    read-only
    STATUS        current
    DESCRIPTION   "Duplex Mode (provision), available when Auto Negoiation is Disable (AUTONEG=DISABLE)"
    ::= { scCapEntry 15 }

scCapAttGradientTh OBJECT-TYPE
    SYNTAX        FspR7Unsigned32Caps
    UNITS         "0.1 dB/min"
    MAX-ACCESS    read-only
    STATUS        current
    DESCRIPTION   "Attenuation Gradient Threshold on Receive Fiber. Applies to both
        TRMT and RCV directions; but threshold violation is reported for
        each direction separately by the 'tapping' alarms: INTRUDE-RCV
        and INTRUDE-TRMT."
    ::= { scCapEntry 16 }

scCapIpAddr OBJECT-TYPE
    SYNTAX        FspR7YesNo
    MAX-ACCESS    read-only
    STATUS        current
    DESCRIPTION   "IP Address assigned to LAN IP Interface"
    ::= { scCapEntry 17 }

scCapLanAid OBJECT-TYPE
    SYNTAX        SnmpAdminString
    MAX-ACCESS    read-only
    STATUS        current
    DESCRIPTION   "AID of LAN"
    ::= { scCapEntry 18 }

scCapIpMask OBJECT-TYPE
    SYNTAX        FspR7YesNo
    MAX-ACCESS    read-only
    STATUS        current
    DESCRIPTION   "IP MASK assigned to LAN IP Interface"
    ::= { scCapEntry 19 }

scCapDataLayerPmReset OBJECT-TYPE
    SYNTAX        FspR7PmResetCaps
    MAX-ACCESS    read-only
    STATUS        current
    DESCRIPTION   "Reset data-layer Performance registers"
    ::= { scCapEntry 20 }

scCapPriority OBJECT-TYPE
    SYNTAX        FspR7Unsigned32Caps
    MAX-ACCESS    read-only
    STATUS        current
    DESCRIPTION   "Priority"
    ::= { scCapEntry 21 }

scCapIPv6 OBJECT-TYPE
    SYNTAX        FspR7YesNo
    MAX-ACCESS    read-only
    STATUS        current
    DESCRIPTION   "IPv6 Address"
    ::= { scCapEntry 22 }

scCapIPv6PrefixLen OBJECT-TYPE
    SYNTAX        FspR7Unsigned32Caps
    MAX-ACCESS    read-only
    STATUS        current
    DESCRIPTION   "IPv6 Subnet Prefix Length"
    ::= { scCapEntry 23 }

scCapIpMode OBJECT-TYPE
    SYNTAX        FspR7IpModeCaps
    MAX-ACCESS    read-only
    STATUS        current
    DESCRIPTION   "IP Mode of Operation either IPv4 only or IPv4 and IPv6. When operation supports IPv6, it is used for addresses external to the network."
    ::= { scCapEntry 24 }

scCapGatewayProxyArp OBJECT-TYPE
    SYNTAX        FspR7EnableDisableCaps
    MAX-ACCESS    read-only
    STATUS        current
    DESCRIPTION   "Gateway node serves as an ARP proxy"
    ::= { scCapEntry 25 }

scCapMtu OBJECT-TYPE
    SYNTAX        FspR7Unsigned32Caps
    UNITS         "Byte"
    MAX-ACCESS    read-only
    STATUS        current
    DESCRIPTION   "Maximum Transmission Unit"
    ::= { scCapEntry 26 }

scCapHelloInterval OBJECT-TYPE
    SYNTAX        FspR7Unsigned32Caps
    UNITS         "s"
    MAX-ACCESS    read-only
    STATUS        current
    DESCRIPTION   "Hello Interval"
    ::= { scCapEntry 27 }

scCapDeadInterval OBJECT-TYPE
    SYNTAX        FspR7Unsigned32Caps
    UNITS         "s"
    MAX-ACCESS    read-only
    STATUS        current
    DESCRIPTION   "Dead Interval"
    ::= { scCapEntry 28 }

scCapRetransmitInterval OBJECT-TYPE
    SYNTAX        FspR7Unsigned32Caps
    UNITS         "s"
    MAX-ACCESS    read-only
    STATUS        current
    DESCRIPTION   "Retransmit Interval"
    ::= { scCapEntry 29 }

scCapDhcpServer OBJECT-TYPE
    SYNTAX        FspR7DhcpServerCaps
    MAX-ACCESS    read-only
    STATUS        current
    DESCRIPTION   "Determines DHCP Server/Client mode of the NCU"
    ::= { scCapEntry 30 }

scCapDhcpStartAddr OBJECT-TYPE
    SYNTAX        FspR7YesNo
    MAX-ACCESS    read-only
    STATUS        current
    DESCRIPTION   "DHCP Start Address"
    ::= { scCapEntry 31 }

scCapDhcpStopAddr OBJECT-TYPE
    SYNTAX        FspR7YesNo
    MAX-ACCESS    read-only
    STATUS        current
    DESCRIPTION   "DHCP Stop Address"
    ::= { scCapEntry 32 }

scCapDhcpMask OBJECT-TYPE
    SYNTAX        FspR7YesNo
    MAX-ACCESS    read-only
    STATUS        current
    DESCRIPTION   "DHCP Mask"
    ::= { scCapEntry 33 }

scCapFrcdLogin OBJECT-TYPE
    SYNTAX        FspR7EnableDisableCaps
    MAX-ACCESS    read-only
    STATUS        current
    DESCRIPTION   "Directs web browser to the NED login page when enabled and user is not currently logged in."
    ::= { scCapEntry 34 }

scCapMdix OBJECT-TYPE
    SYNTAX        FspR7InterfaceCrossoverCaps
    MAX-ACCESS    read-only
    STATUS        current
    DESCRIPTION   "Medium-dependent interface crossover"
    ::= { scCapEntry 35 }

endOfScCapTable OBJECT-TYPE
    SYNTAX        Integer32
    MAX-ACCESS    read-only
    STATUS        current
    DESCRIPTION   ""
    ::= { dcnMgmtCap 4 }

lanCapTable OBJECT-TYPE
    SYNTAX        SEQUENCE OF LanCapEntry
    MAX-ACCESS    not-accessible
    STATUS        current
    DESCRIPTION   "lanCapTable"
    ::= { dcnMgmtCap 5 }

lanCapEntry OBJECT-TYPE
    SYNTAX        LanCapEntry
    MAX-ACCESS    not-accessible
    STATUS        current
    DESCRIPTION   "Entry of lanCapTable"
    INDEX       {
                  entityDcnShelfNo,
                  entityDcnSlotNo,
                  entityDcnPortNo,
                  entityDcnExtNo,
                  entityDcnClassName
                }
    ::= { lanCapTable 1 }

LanCapEntry ::= SEQUENCE
  {    lanCapRowStatus FspR7RowStatusCaps,
    lanCapType FspR7InterfaceTypeCaps,
    lanCapAdmin FspR7AdminStateCaps,
    lanCapAlias Integer32,
    lanCapAuthString Integer32,
    lanCapOspf FspR7OspfModeCaps,
    lanCapAuthType FspR7CpAuthTypeCaps,
    lanCapIpType FspR7IpTypeCaps,
    lanCapMetric FspR7Unsigned32Caps,
    lanCapAreaAid SnmpAdminString,
    lanCapIpAddr FspR7YesNo,
    lanCapIpMask FspR7YesNo,
    lanCapPriority FspR7Unsigned32Caps,
    lanCapIPv6 FspR7YesNo,
    lanCapIPv6PrefixLen FspR7Unsigned32Caps,
    lanCapIpMode FspR7IpModeCaps,
    lanCapMtu FspR7Unsigned32Caps,
    lanCapHelloInterval FspR7Unsigned32Caps,
    lanCapDeadInterval FspR7Unsigned32Caps,
    lanCapRetransmitInterval FspR7Unsigned32Caps,
    lanCapDhcpServer FspR7DhcpServerCaps,
    lanCapDhcpStartAddr FspR7YesNo,
    lanCapDhcpStopAddr FspR7YesNo,
    lanCapDhcpMask FspR7YesNo,
    lanCapFrcdLogin FspR7EnableDisableCaps }

lanCapRowStatus OBJECT-TYPE
    SYNTAX        FspR7RowStatusCaps
    MAX-ACCESS    read-only
    STATUS        current
    DESCRIPTION   "RowStatus object is used to create or delete a row in the table."
    ::= { lanCapEntry 1 }

lanCapType OBJECT-TYPE
    SYNTAX        FspR7InterfaceTypeCaps
    MAX-ACCESS    read-only
    STATUS        current
    DESCRIPTION   "The TYPE defines the transport service type as wrapper with wrapper layer termination OR else as payload"
    ::= { lanCapEntry 2 }

lanCapAdmin OBJECT-TYPE
    SYNTAX        FspR7AdminStateCaps
    MAX-ACCESS    read-only
    STATUS        current
    DESCRIPTION   "Administrative State is displayed in the GUI and Craft. Transition to Unassigend requires the entity to be deleted."
    ::= { lanCapEntry 3 }

lanCapAlias OBJECT-TYPE
    SYNTAX        Integer32
    MAX-ACCESS    read-only
    STATUS        current
    DESCRIPTION   "User Applied Descriptor"
    ::= { lanCapEntry 4 }

lanCapAuthString OBJECT-TYPE
    SYNTAX        Integer32
    MAX-ACCESS    read-only
    STATUS        current
    DESCRIPTION   "OSPF Authentication Key/String depending on Authentication Type"
    ::= { lanCapEntry 5 }

lanCapOspf OBJECT-TYPE
    SYNTAX        FspR7OspfModeCaps
    MAX-ACCESS    read-only
    STATUS        current
    DESCRIPTION   "OSPF Routing (Dynamic)"
    ::= { lanCapEntry 6 }

lanCapAuthType OBJECT-TYPE
    SYNTAX        FspR7CpAuthTypeCaps
    MAX-ACCESS    read-only
    STATUS        current
    DESCRIPTION   "OSPF Authentication Type"
    ::= { lanCapEntry 7 }

lanCapIpType OBJECT-TYPE
    SYNTAX        FspR7IpTypeCaps
    MAX-ACCESS    read-only
    STATUS        current
    DESCRIPTION   "Type of IP configuration"
    ::= { lanCapEntry 8 }

lanCapMetric OBJECT-TYPE
    SYNTAX        FspR7Unsigned32Caps
    MAX-ACCESS    read-only
    STATUS        current
    DESCRIPTION   "Routing Metric"
    ::= { lanCapEntry 9 }

lanCapAreaAid OBJECT-TYPE
    SYNTAX        SnmpAdminString
    MAX-ACCESS    read-only
    STATUS        current
    DESCRIPTION   "OSPF Area AID"
    ::= { lanCapEntry 10 }

lanCapIpAddr OBJECT-TYPE
    SYNTAX        FspR7YesNo
    MAX-ACCESS    read-only
    STATUS        current
    DESCRIPTION   "IP Address assigned to LAN IP Interface"
    ::= { lanCapEntry 11 }

lanCapIpMask OBJECT-TYPE
    SYNTAX        FspR7YesNo
    MAX-ACCESS    read-only
    STATUS        current
    DESCRIPTION   "IP MASK assigned to LAN IP Interface"
    ::= { lanCapEntry 12 }

lanCapPriority OBJECT-TYPE
    SYNTAX        FspR7Unsigned32Caps
    MAX-ACCESS    read-only
    STATUS        current
    DESCRIPTION   "Priority"
    ::= { lanCapEntry 13 }

lanCapIPv6 OBJECT-TYPE
    SYNTAX        FspR7YesNo
    MAX-ACCESS    read-only
    STATUS        current
    DESCRIPTION   "IPv6 Address"
    ::= { lanCapEntry 14 }

lanCapIPv6PrefixLen OBJECT-TYPE
    SYNTAX        FspR7Unsigned32Caps
    MAX-ACCESS    read-only
    STATUS        current
    DESCRIPTION   "IPv6 Subnet Prefix Length"
    ::= { lanCapEntry 15 }

lanCapIpMode OBJECT-TYPE
    SYNTAX        FspR7IpModeCaps
    MAX-ACCESS    read-only
    STATUS        current
    DESCRIPTION   "IP Mode of Operation either IPv4 only or IPv4 and IPv6. When operation supports IPv6, it is used for addresses external to the network."
    ::= { lanCapEntry 16 }

lanCapMtu OBJECT-TYPE
    SYNTAX        FspR7Unsigned32Caps
    UNITS         "Byte"
    MAX-ACCESS    read-only
    STATUS        current
    DESCRIPTION   "Maximum Transmission Unit"
    ::= { lanCapEntry 17 }

lanCapHelloInterval OBJECT-TYPE
    SYNTAX        FspR7Unsigned32Caps
    UNITS         "s"
    MAX-ACCESS    read-only
    STATUS        current
    DESCRIPTION   "Hello Interval"
    ::= { lanCapEntry 18 }

lanCapDeadInterval OBJECT-TYPE
    SYNTAX        FspR7Unsigned32Caps
    UNITS         "s"
    MAX-ACCESS    read-only
    STATUS        current
    DESCRIPTION   "Dead Interval"
    ::= { lanCapEntry 19 }

lanCapRetransmitInterval OBJECT-TYPE
    SYNTAX        FspR7Unsigned32Caps
    UNITS         "s"
    MAX-ACCESS    read-only
    STATUS        current
    DESCRIPTION   "Retransmit Interval"
    ::= { lanCapEntry 20 }

lanCapDhcpServer OBJECT-TYPE
    SYNTAX        FspR7DhcpServerCaps
    MAX-ACCESS    read-only
    STATUS        current
    DESCRIPTION   "Determines DHCP Server/Client mode of the NCU"
    ::= { lanCapEntry 21 }

lanCapDhcpStartAddr OBJECT-TYPE
    SYNTAX        FspR7YesNo
    MAX-ACCESS    read-only
    STATUS        current
    DESCRIPTION   "DHCP Start Address"
    ::= { lanCapEntry 22 }

lanCapDhcpStopAddr OBJECT-TYPE
    SYNTAX        FspR7YesNo
    MAX-ACCESS    read-only
    STATUS        current
    DESCRIPTION   "DHCP Stop Address"
    ::= { lanCapEntry 23 }

lanCapDhcpMask OBJECT-TYPE
    SYNTAX        FspR7YesNo
    MAX-ACCESS    read-only
    STATUS        current
    DESCRIPTION   "DHCP Mask"
    ::= { lanCapEntry 24 }

lanCapFrcdLogin OBJECT-TYPE
    SYNTAX        FspR7EnableDisableCaps
    MAX-ACCESS    read-only
    STATUS        current
    DESCRIPTION   "Directs web browser to the NED login page when enabled and user is not currently logged in."
    ::= { lanCapEntry 25 }

endOfLanCapTable OBJECT-TYPE
    SYNTAX        Integer32
    MAX-ACCESS    read-only
    STATUS        current
    DESCRIPTION   ""
    ::= { dcnMgmtCap 6 }

eccCapTable OBJECT-TYPE
    SYNTAX        SEQUENCE OF EccCapEntry
    MAX-ACCESS    not-accessible
    STATUS        current
    DESCRIPTION   "eccCapTable (Embedded Communication Channel)"
    ::= { dcnMgmtCap 7 }

eccCapEntry OBJECT-TYPE
    SYNTAX        EccCapEntry
    MAX-ACCESS    not-accessible
    STATUS        current
    DESCRIPTION   "Entry of eccCapTable"
    INDEX       {
                  entityDcnShelfNo,
                  entityDcnSlotNo,
                  entityDcnPortNo,
                  entityDcnExtNo,
                  entityDcnClassName
                }
    ::= { eccCapTable 1 }

EccCapEntry ::= SEQUENCE
  {    eccCapRowStatus FspR7RowStatusCaps,
    eccCapType FspR7InterfaceTypeCaps,
    eccCapAdmin FspR7AdminStateCaps,
    eccCapAlias Integer32,
    eccCapLanAid SnmpAdminString,
    eccCapExternalVid Unsigned32,
    eccCapGccUsage FspR7GccUsageCaps }

eccCapRowStatus OBJECT-TYPE
    SYNTAX        FspR7RowStatusCaps
    MAX-ACCESS    read-only
    STATUS        current
    DESCRIPTION   "RowStatus object is used to create or delete a row in the table."
    ::= { eccCapEntry 1 }

eccCapType OBJECT-TYPE
    SYNTAX        FspR7InterfaceTypeCaps
    MAX-ACCESS    read-only
    STATUS        current
    DESCRIPTION   "The TYPE defines the transport service type as wrapper with wrapper layer termination OR else as payload"
    ::= { eccCapEntry 2 }

eccCapAdmin OBJECT-TYPE
    SYNTAX        FspR7AdminStateCaps
    MAX-ACCESS    read-only
    STATUS        current
    DESCRIPTION   "Administrative State is displayed in the GUI and Craft. Transition to Unassigend requires the entity to be deleted."
    ::= { eccCapEntry 3 }

eccCapAlias OBJECT-TYPE
    SYNTAX        Integer32
    MAX-ACCESS    read-only
    STATUS        current
    DESCRIPTION   "User Applied Descriptor"
    ::= { eccCapEntry 4 }

eccCapLanAid OBJECT-TYPE
    SYNTAX        SnmpAdminString
    MAX-ACCESS    read-only
    STATUS        current
    DESCRIPTION   "AID of LAN"
    ::= { eccCapEntry 5 }

eccCapExternalVid OBJECT-TYPE
    SYNTAX        Unsigned32
    MAX-ACCESS    read-only
    STATUS        current
    DESCRIPTION   "External VID"
    ::= { eccCapEntry 6 }

eccCapGccUsage OBJECT-TYPE
    SYNTAX        FspR7GccUsageCaps
    MAX-ACCESS    read-only
    STATUS        current
    DESCRIPTION   "GCC Usage"
    ::= { eccCapEntry 7 }

endOfEccCapTable OBJECT-TYPE
    SYNTAX        Integer32
    MAX-ACCESS    read-only
    STATUS        current
    DESCRIPTION   ""
    ::= { dcnMgmtCap 8 }

endOfDcnMgmtCap OBJECT-TYPE
    SYNTAX        Integer32
    MAX-ACCESS    read-only
    STATUS        current
    DESCRIPTION   ""
    ::= { dcnMgmtCap 10000 }

opticalMuxCapTable OBJECT-TYPE
    SYNTAX        SEQUENCE OF OpticalMuxCapEntry
    MAX-ACCESS    not-accessible
    STATUS        current
    DESCRIPTION   "opticalCapTable"
    ::= { opticalMuxMgmtCap 1 }

opticalMuxCapEntry OBJECT-TYPE
    SYNTAX        OpticalMuxCapEntry
    MAX-ACCESS    not-accessible
    STATUS        current
    DESCRIPTION   "Entry of opticalCapTable"
    INDEX       {
                  entityOpticalMuxShelfNo,
                  entityOpticalMuxSlotNo,
                  entityOpticalMuxPortNo,
                  entityOpticalMuxExtNo,
                  entityOpticalMuxClassName
                }
    ::= { opticalMuxCapTable 1 }

OpticalMuxCapEntry ::= SEQUENCE
  {    opticalMuxCapRowStatus FspR7RowStatusCaps,
    opticalMuxCapPumpPower FspR7Integer32Caps,
    opticalMuxCapInhibitSwitchToWork FspR7YesNoCaps,
    opticalMuxCapForceLaserOn FspR7RlsActionCaps,
    opticalMuxCapAseTabCreation FspR7RlsActionCaps,
    opticalMuxCapOpticalSetPoint FspR7Integer32Caps,
    opticalMuxCapInitiateEqualization FspR7RlsActionCaps,
    opticalMuxCapTilt FspR7Integer32Caps,
    opticalMuxCapOscOpticalSetpoint FspR7Integer32Caps,
    opticalMuxCapOffset FspR7Integer32Caps,
    opticalMuxCapSwitchCommand FspR7APSCommandCaps,
    opticalMuxCapAlsMode FspR7AlsModeCaps,
    opticalMuxCapType FspR7InterfaceTypeCaps,
    opticalMuxCapAttenuationGradient FspR7Unsigned32Caps,
    opticalMuxCapInhibitSwitchToProt FspR7YesNoCaps,
    opticalMuxCapVariableGain FspR7Unsigned32Caps,
    opticalMuxCapAdmin FspR7AdminStateCaps,
    opticalMuxCapTimePeriod FspR7OtdrPeriodCaps,
    opticalMuxCapSigDegThresReceiver FspR7Unsigned32Caps,
    opticalMuxCapAlias Integer32,
    opticalMuxCapDataLayerPmReset FspR7PmResetCaps,
    opticalMuxCapGain FspR7GainCaps,
    opticalMuxCapEdfaPwrOut FspR7EdfaOutputPowerRatingCaps,
    opticalMuxCapVoaSetpoint FspR7Unsigned32Caps,
    opticalMuxCapFiberBrand FspR7FiberBrandCaps,
    opticalMuxCapTiltSet FspR7TiltSetCaps,
    opticalMuxCapForceFwdAsePilotOn FspR7RlsActionCaps,
    opticalMuxCapBandProvision FspR7OpticalBandCaps,
    opticalMuxCapOffsetHigh FspR7Integer32Caps,
    opticalMuxCapOffsetLow FspR7Integer32Caps,
    opticalMuxCapOptUpdate FspR7RlsActionCaps,
    opticalMuxCapVariableGainNtoR FspR7Unsigned32Caps,
    opticalMuxCapVariableGainRtoN FspR7Unsigned32Caps }

opticalMuxCapRowStatus OBJECT-TYPE
    SYNTAX        FspR7RowStatusCaps
    MAX-ACCESS    read-only
    STATUS        current
    DESCRIPTION   "RowStatus object is used to create or delete a row in the table."
    ::= { opticalMuxCapEntry 1 }

opticalMuxCapPumpPower OBJECT-TYPE
    SYNTAX        FspR7Integer32Caps
    UNITS         "0.2 dBm"
    MAX-ACCESS    read-only
    STATUS        current
    DESCRIPTION   "Total raman pump power"
    ::= { opticalMuxCapEntry 2 }

opticalMuxCapInhibitSwitchToWork OBJECT-TYPE
    SYNTAX        FspR7YesNoCaps
    MAX-ACCESS    read-only
    STATUS        current
    DESCRIPTION   "Inhibit Switch to Working. Inhibition blocks a switchInhibit Switch to Protection facility. Inhibition blocksInhibit Switch to Working. Inhibition blocks a switch
        switch to the Protection facility (protection path).Inhibit Switch to Protection facility. Inhibition blocks
        switch to the Protection facility (protection path).
        to the Working facility (working path).
        to the Working facility (working path).
        Applicable only for the Working facility in ACT state.
        Applicable only for the Working facility in ACT state.
        Applicable for the Protection facility in ACT state.
        Applicable for the Protection facility in ACT state."
    ::= { opticalMuxCapEntry 3 }

opticalMuxCapForceLaserOn OBJECT-TYPE
    SYNTAX        FspR7RlsActionCaps
    MAX-ACCESS    read-only
    STATUS        current
    DESCRIPTION   "Laser Forced On"
    ::= { opticalMuxCapEntry 4 }

opticalMuxCapAseTabCreation OBJECT-TYPE
    SYNTAX        FspR7RlsActionCaps
    MAX-ACCESS    read-only
    STATUS        current
    DESCRIPTION   "ASE Table creation in process"
    ::= { opticalMuxCapEntry 5 }

opticalMuxCapOpticalSetPoint OBJECT-TYPE
    SYNTAX        FspR7Integer32Caps
    UNITS         "0.1 dBm"
    MAX-ACCESS    read-only
    STATUS        current
    DESCRIPTION   "Sets the optical power for power equalization in ROADM or for channel power control in OPCM"
    ::= { opticalMuxCapEntry 6 }

opticalMuxCapInitiateEqualization OBJECT-TYPE
    SYNTAX        FspR7RlsActionCaps
    MAX-ACCESS    read-only
    STATUS        current
    DESCRIPTION   "Initiate Equalization"
    ::= { opticalMuxCapEntry 7 }

opticalMuxCapTilt OBJECT-TYPE
    SYNTAX        FspR7Integer32Caps
    UNITS         "0.1 dB"
    MAX-ACCESS    read-only
    STATUS        current
    DESCRIPTION   "Change of optical channel power in dB over the complete transmission band"
    ::= { opticalMuxCapEntry 8 }

opticalMuxCapOscOpticalSetpoint OBJECT-TYPE
    SYNTAX        FspR7Integer32Caps
    UNITS         "0.1 dBm"
    MAX-ACCESS    read-only
    STATUS        current
    DESCRIPTION   "Sets the OSC optical power"
    ::= { opticalMuxCapEntry 9 }

opticalMuxCapOffset OBJECT-TYPE
    SYNTAX        FspR7Integer32Caps
    UNITS         "0.1 dB"
    MAX-ACCESS    read-only
    STATUS        current
    DESCRIPTION   "Sets the offset for the mean optical power for power equalization in ROADM"
    ::= { opticalMuxCapEntry 10 }

opticalMuxCapSwitchCommand OBJECT-TYPE
    SYNTAX        FspR7APSCommandCaps
    MAX-ACCESS    read-only
    STATUS        current
    DESCRIPTION   "The switch command action for this facility. A command resulting
        in a switch event will also cause a change of the facility secondary state
        and a corresponding condition. Addressed by this command is the active port,
        the port to switch away from. Since this is a manual switch command, it will
        not switch if other port suffers from a signalfailure or a signal degrade."
    ::= { opticalMuxCapEntry 11 }

opticalMuxCapAlsMode OBJECT-TYPE
    SYNTAX        FspR7AlsModeCaps
    MAX-ACCESS    read-only
    STATUS        current
    DESCRIPTION   "Determines the reaction in backward direction in response to a LOS
        on the same Interface: on a Network Interface connected to the DWDM
        this is a matter of laser safety"
    ::= { opticalMuxCapEntry 12 }

opticalMuxCapType OBJECT-TYPE
    SYNTAX        FspR7InterfaceTypeCaps
    MAX-ACCESS    read-only
    STATUS        current
    DESCRIPTION   "The TYPE defines the transport service type as wrapper with wrapper layer termination OR else as payload"
    ::= { opticalMuxCapEntry 13 }

opticalMuxCapAttenuationGradient OBJECT-TYPE
    SYNTAX        FspR7Unsigned32Caps
    UNITS         "0.1 dB/min"
    MAX-ACCESS    read-only
    STATUS        current
    DESCRIPTION   "Attenuation Gradient Threshold on Receive Fiber. Applies to both TRMT and RCV directions; but threshold violation is reported for each direction separately by the 'tapping' alarms: INTRUDE-RCV and INTRUDE-TRMT."
    ::= { opticalMuxCapEntry 14 }

opticalMuxCapInhibitSwitchToProt OBJECT-TYPE
    SYNTAX        FspR7YesNoCaps
    MAX-ACCESS    read-only
    STATUS        current
    DESCRIPTION   "Inhibit Switch to Working. Inhibition blocks a switchInhibit Switch to Protection facility. Inhibition blocksInhibit Switch to Working. Inhibition blocks a switch"
    ::= { opticalMuxCapEntry 15 }

opticalMuxCapVariableGain OBJECT-TYPE
    SYNTAX        FspR7Unsigned32Caps
    UNITS         "0.1 dB"
    MAX-ACCESS    read-only
    STATUS        current
    DESCRIPTION   "Variable Gain of EDFA"
    ::= { opticalMuxCapEntry 16 }

opticalMuxCapAdmin OBJECT-TYPE
    SYNTAX        FspR7AdminStateCaps
    MAX-ACCESS    read-only
    STATUS        current
    DESCRIPTION   "Administrative State is displayed in the GUI and Craft. Transition to Unassigend requires the entity to be deleted."
    ::= { opticalMuxCapEntry 17 }

opticalMuxCapTimePeriod OBJECT-TYPE
    SYNTAX        FspR7OtdrPeriodCaps
    MAX-ACCESS    read-only
    STATUS        current
    DESCRIPTION   "NONE - OTDR measurement disabled otherwise the OTDR duration in minutes."
    ::= { opticalMuxCapEntry 18 }

opticalMuxCapSigDegThresReceiver OBJECT-TYPE
    SYNTAX        FspR7Unsigned32Caps
    UNITS         "0.1 dB"
    MAX-ACCESS    read-only
    STATUS        current
    DESCRIPTION   "Signal Degrade Threshold on Receiver. Reported as ATTRMT-SDHT to far end."
    ::= { opticalMuxCapEntry 19 }

opticalMuxCapAlias OBJECT-TYPE
    SYNTAX        Integer32
    MAX-ACCESS    read-only
    STATUS        current
    DESCRIPTION   "User Applied Descriptor"
    ::= { opticalMuxCapEntry 20 }

opticalMuxCapDataLayerPmReset OBJECT-TYPE
    SYNTAX        FspR7PmResetCaps
    MAX-ACCESS    read-only
    STATUS        current
    DESCRIPTION   "Reset data-layer Performance registers"
    ::= { opticalMuxCapEntry 21 }

opticalMuxCapGain OBJECT-TYPE
    SYNTAX        FspR7GainCaps
    MAX-ACCESS    read-only
    STATUS        current
    DESCRIPTION   "Gain"
    ::= { opticalMuxCapEntry 22 }

opticalMuxCapEdfaPwrOut OBJECT-TYPE
    SYNTAX        FspR7EdfaOutputPowerRatingCaps
    MAX-ACCESS    read-only
    STATUS        current
    DESCRIPTION   "Optical Output Power Rating - Provision"
    ::= { opticalMuxCapEntry 23 }

opticalMuxCapVoaSetpoint OBJECT-TYPE
    SYNTAX        FspR7Unsigned32Caps
    UNITS         "0.1 dB"
    MAX-ACCESS    read-only
    STATUS        current
    DESCRIPTION   "Sets the optical attenuation of VOA"
    ::= { opticalMuxCapEntry 24 }

opticalMuxCapFiberBrand OBJECT-TYPE
    SYNTAX        FspR7FiberBrandCaps
    MAX-ACCESS    read-only
    STATUS        current
    DESCRIPTION   "Brand of fiber present in the fiber plant"
    ::= { opticalMuxCapEntry 25 }

opticalMuxCapTiltSet OBJECT-TYPE
    SYNTAX        FspR7TiltSetCaps
    MAX-ACCESS    read-only
    STATUS        current
    DESCRIPTION   "Tilt setting as discrete values versus a range"
    ::= { opticalMuxCapEntry 26 }

opticalMuxCapForceFwdAsePilotOn OBJECT-TYPE
    SYNTAX        FspR7RlsActionCaps
    MAX-ACCESS    read-only
    STATUS        current
    DESCRIPTION   "Force the BWD Raman pilot on to allow building of FWD Raman ASE Table"
    ::= { opticalMuxCapEntry 27 }

opticalMuxCapBandProvision OBJECT-TYPE
    SYNTAX        FspR7OpticalBandCaps
    MAX-ACCESS    read-only
    STATUS        current
    DESCRIPTION   "Band Provision. Reference to BAND__INVENTORY."
    ::= { opticalMuxCapEntry 28 }

opticalMuxCapOffsetHigh OBJECT-TYPE
    SYNTAX        FspR7Integer32Caps
    UNITS         "0.1 dBm"
    MAX-ACCESS    read-only
    STATUS        current
    DESCRIPTION   "Sets the high level offset for power equalization in CCM"
    ::= { opticalMuxCapEntry 29 }

opticalMuxCapOffsetLow OBJECT-TYPE
    SYNTAX        FspR7Integer32Caps
    UNITS         "0.1 dBm"
    MAX-ACCESS    read-only
    STATUS        current
    DESCRIPTION   "Sets the low level offset for power equalization in CCM"
    ::= { opticalMuxCapEntry 30 }

opticalMuxCapOptUpdate OBJECT-TYPE
    SYNTAX        FspR7RlsActionCaps
    MAX-ACCESS    read-only
    STATUS        current
    DESCRIPTION   "This parameter is used to operate/trigger OPT PM update; it triggers the entity to update its current OPT PM value, which can be retrieved via GET function."
    ::= { opticalMuxCapEntry 31 }

opticalMuxCapVariableGainNtoR OBJECT-TYPE
    SYNTAX        FspR7Unsigned32Caps
    UNITS         "0.1 dB"
    MAX-ACCESS    read-only
    STATUS        current
    DESCRIPTION   "Variable Gain of EDFA (N to R)"
    ::= { opticalMuxCapEntry 32 }

opticalMuxCapVariableGainRtoN OBJECT-TYPE
    SYNTAX        FspR7Unsigned32Caps
    UNITS         "0.1 dB"
    MAX-ACCESS    read-only
    STATUS        current
    DESCRIPTION   "Variable Gain of EDFA (R to N)"
    ::= { opticalMuxCapEntry 33 }

endOfOpticalMuxCapTable OBJECT-TYPE
    SYNTAX        Integer32
    MAX-ACCESS    read-only
    STATUS        current
    DESCRIPTION   ""
    ::= { opticalMuxMgmtCap 2 }

endOfOpticalMuxMgmtCap OBJECT-TYPE
    SYNTAX        Integer32
    MAX-ACCESS    read-only
    STATUS        current
    DESCRIPTION   ""
    ::= { opticalMuxMgmtCap 10000 }

shelfConnCapTable OBJECT-TYPE
    SYNTAX        SEQUENCE OF ShelfConnCapEntry
    MAX-ACCESS    not-accessible
    STATUS        current
    DESCRIPTION   "shelfConnCapTable"
    ::= { shelfConnMgmtCap 1 }

shelfConnCapEntry OBJECT-TYPE
    SYNTAX        ShelfConnCapEntry
    MAX-ACCESS    not-accessible
    STATUS        current
    DESCRIPTION   "Entry of shelfConnCapTable"
    INDEX       {
                  entityShelfConnShelfNo,
                  entityShelfConnSlotNo,
                  entityShelfConnPortNo,
                  entityShelfConnExtNo,
                  entityShelfConnClassName
                }
    ::= { shelfConnCapTable 1 }

ShelfConnCapEntry ::= SEQUENCE
  {    shelfConnCapRowStatus FspR7RowStatusCaps,
    shelfConnCapAdmin FspR7AdminStateCaps,
    shelfConnCapAlias Integer32,
    shelfConnCapFacilityType FspR7InterfaceTypeCaps,
    shelfConnCapDataLayerPmReset FspR7PmResetCaps,
    shelfConnCapAutonegotiation EnableStateCaps,
    shelfConnCapBitrate FspR7BitrateCaps,
    shelfConnCapDuplex EthDuplexModeCaps,
    shelfConnCapMdix FspR7InterfaceCrossoverCaps }

shelfConnCapRowStatus OBJECT-TYPE
    SYNTAX        FspR7RowStatusCaps
    MAX-ACCESS    read-only
    STATUS        current
    DESCRIPTION   "RowStatus object is used to create or delete a row in the table."
    ::= { shelfConnCapEntry 1 }

shelfConnCapAdmin OBJECT-TYPE
    SYNTAX        FspR7AdminStateCaps
    MAX-ACCESS    read-only
    STATUS        current
    DESCRIPTION   "Administrative State is displayed in the GUI and Craft. Transition to Unassigend requires the entity to be deleted."
    ::= { shelfConnCapEntry 2 }

shelfConnCapAlias OBJECT-TYPE
    SYNTAX        Integer32
    MAX-ACCESS    read-only
    STATUS        current
    DESCRIPTION   "User Applied Descriptor"
    ::= { shelfConnCapEntry 3 }

shelfConnCapFacilityType OBJECT-TYPE
    SYNTAX        FspR7InterfaceTypeCaps
    MAX-ACCESS    read-only
    STATUS        current
    DESCRIPTION   "The TYPE defines the transport service type as wrapper with wrapper layer termination OR else as payload"
    ::= { shelfConnCapEntry 4 }

shelfConnCapDataLayerPmReset OBJECT-TYPE
    SYNTAX        FspR7PmResetCaps
    MAX-ACCESS    read-only
    STATUS        current
    DESCRIPTION   "Reset data-layer Performance registers"
    ::= { shelfConnCapEntry 5 }

shelfConnCapAutonegotiation OBJECT-TYPE
    SYNTAX        EnableStateCaps
    MAX-ACCESS    read-only
    STATUS        current
    DESCRIPTION   "Auto Negotiation for the data rate"
    ::= { shelfConnCapEntry 6 }

shelfConnCapBitrate OBJECT-TYPE
    SYNTAX        FspR7BitrateCaps
    MAX-ACCESS    read-only
    STATUS        current
    DESCRIPTION   "Provisioned data rate"
    ::= { shelfConnCapEntry 7 }

shelfConnCapDuplex OBJECT-TYPE
    SYNTAX        EthDuplexModeCaps
    MAX-ACCESS    read-only
    STATUS        current
    DESCRIPTION   "Duplex Mode (provision), available when Auto Negoiation is Disable (AUTONEG=DISABLE)"
    ::= { shelfConnCapEntry 8 }

shelfConnCapMdix OBJECT-TYPE
    SYNTAX        FspR7InterfaceCrossoverCaps
    MAX-ACCESS    read-only
    STATUS        current
    DESCRIPTION   "Medium-dependent interface crossover"
    ::= { shelfConnCapEntry 9 }

endOfShelfConnCapTable OBJECT-TYPE
    SYNTAX        Integer32
    MAX-ACCESS    read-only
    STATUS        current
    DESCRIPTION   ""
    ::= { shelfConnMgmtCap 2 }

endOfShelfConnMgmtCap OBJECT-TYPE
    SYNTAX        Integer32
    MAX-ACCESS    read-only
    STATUS        current
    DESCRIPTION   ""
    ::= { shelfConnMgmtCap 10000 }

envPortCapTable OBJECT-TYPE
    SYNTAX        SEQUENCE OF EnvPortCapEntry
    MAX-ACCESS    not-accessible
    STATUS        current
    DESCRIPTION   "envPortCapTable"
    ::= { envMgmtCap 1 }

envPortCapEntry OBJECT-TYPE
    SYNTAX        EnvPortCapEntry
    MAX-ACCESS    not-accessible
    STATUS        current
    DESCRIPTION   "Entry of envPortCapTable"
    INDEX       {
                  entityEqptShelfNo,
                  entityEqptSlotNo,
                  entityEqptPortNo,
                  entityEqptExtNo,
                  entityEqptClassName
                }
    ::= { envPortCapTable 1 }

EnvPortCapEntry ::= SEQUENCE
  {    envPortCapRowStatus FspR7RowStatusCaps,
    envPortCapTelemetry FspR7TelemetryOutputCaps,
    envPortCapFacilityType FspR7InterfaceTypeCaps,
    envPortCapTifAlarmType Integer32,
    envPortCapTifAlarmMessage Integer32,
    envPortCapInvertTifInputLogic FspR7InvertTelemetryInputLogicCaps }

envPortCapRowStatus OBJECT-TYPE
    SYNTAX        FspR7RowStatusCaps
    MAX-ACCESS    read-only
    STATUS        current
    DESCRIPTION   "RowStatus object is used to create or delete a row in the table."
    ::= { envPortCapEntry 1 }

envPortCapTelemetry OBJECT-TYPE
    SYNTAX        FspR7TelemetryOutputCaps
    MAX-ACCESS    read-only
    STATUS        current
    DESCRIPTION   "Telemetry interface output provision"
    ::= { envPortCapEntry 2 }

envPortCapFacilityType OBJECT-TYPE
    SYNTAX        FspR7InterfaceTypeCaps
    MAX-ACCESS    read-only
    STATUS        current
    DESCRIPTION   "The TYPE defines the transport service type as wrapper with wrapper layer termination OR else as payload"
    ::= { envPortCapEntry 3 }

envPortCapTifAlarmType OBJECT-TYPE
    SYNTAX        Integer32
    MAX-ACCESS    read-only
    STATUS        current
    DESCRIPTION   "Telemetry interface alarm type"
    ::= { envPortCapEntry 4 }

envPortCapTifAlarmMessage OBJECT-TYPE
    SYNTAX        Integer32
    MAX-ACCESS    read-only
    STATUS        current
    DESCRIPTION   "Telemetry interface alarm message"
    ::= { envPortCapEntry 5 }

envPortCapInvertTifInputLogic OBJECT-TYPE
    SYNTAX        FspR7InvertTelemetryInputLogicCaps
    MAX-ACCESS    read-only
    STATUS        current
    DESCRIPTION   "Change telemetry interface input logic"
    ::= { envPortCapEntry 6 }

endOfEnvPortCapTable OBJECT-TYPE
    SYNTAX        Integer32
    MAX-ACCESS    read-only
    STATUS        current
    DESCRIPTION   ""
    ::= { envMgmtCap 2 }

endOfEnvMgmtCap OBJECT-TYPE
    SYNTAX        Integer32
    MAX-ACCESS    read-only
    STATUS        current
    DESCRIPTION   ""
    ::= { envMgmtCap 10000 }

containerCapTable OBJECT-TYPE
    SYNTAX        SEQUENCE OF ContainerCapEntry
    MAX-ACCESS    not-accessible
    STATUS        current
    DESCRIPTION   "containerCapTable"
    ::= { containerMgmtCap 1 }

containerCapEntry OBJECT-TYPE
    SYNTAX        ContainerCapEntry
    MAX-ACCESS    not-accessible
    STATUS        current
    DESCRIPTION   "Entry of containerCapTable"
    INDEX       {
                  entityContainerShelfNo,
                  entityContainerSlotNo,
                  entityContainerPortNo,
                  entityContainerExtNo,
                  entityContainerClassName
                }
    ::= { containerCapTable 1 }

ContainerCapEntry ::= SEQUENCE
  {    containerCapRowStatus FspR7RowStatusCaps,
    containerCapFacilityType FspR7InterfaceTypeCaps }

containerCapRowStatus OBJECT-TYPE
    SYNTAX        FspR7RowStatusCaps
    MAX-ACCESS    read-only
    STATUS        current
    DESCRIPTION   "RowStatus object is used to create or delete a row in the table."
    ::= { containerCapEntry 1 }

containerCapFacilityType OBJECT-TYPE
    SYNTAX        FspR7InterfaceTypeCaps
    MAX-ACCESS    read-only
    STATUS        current
    DESCRIPTION   "The TYPE defines the transport service type as wrapper with wrapper layer termination OR else as payload"
    ::= { containerCapEntry 2 }

endOfContainerCapTable OBJECT-TYPE
    SYNTAX        Integer32
    MAX-ACCESS    read-only
    STATUS        current
    DESCRIPTION   ""
    ::= { containerMgmtCap 2 }

endOfContainerMgmtCap OBJECT-TYPE
    SYNTAX        Integer32
    MAX-ACCESS    read-only
    STATUS        current
    DESCRIPTION   ""
    ::= { containerMgmtCap 10000 }

opticalLineCapTable OBJECT-TYPE
    SYNTAX        SEQUENCE OF OpticalLineCapEntry
    MAX-ACCESS    not-accessible
    STATUS        current
    DESCRIPTION   "opticalLineCapTable"
    ::= { opticalLineMgmtCap 1 }

opticalLineCapEntry OBJECT-TYPE
    SYNTAX        OpticalLineCapEntry
    MAX-ACCESS    not-accessible
    STATUS        current
    DESCRIPTION   "Entry of opticalLineCapTable"
    INDEX       {
                  entityOptLineIndexNo1,
                  entityOptLineIndexNo1,
                  entityOptLineIndexNo1,
                  entityOptLineIndexNo1,
                  entityOptLineClassName
                }
    ::= { opticalLineCapTable 1 }

OpticalLineCapEntry ::= SEQUENCE
  {    opticalLineCapRowStatus FspR7RowStatusCaps,
    opticalLineCapTxLineAttenuation FspR7Integer32Caps,
    opticalLineCapRxLineAttenuation FspR7Integer32Caps,
    opticalLineCapAlias Integer32,
    opticalLineCapFarEndLocation Integer32,
    opticalLineCapFiberLength FspR7Unsigned32Caps,
    opticalLineCapChannelBandwith FspR7ChannelBandwidthCaps }

opticalLineCapRowStatus OBJECT-TYPE
    SYNTAX        FspR7RowStatusCaps
    MAX-ACCESS    read-only
    STATUS        current
    DESCRIPTION   "RowStatus object is used to create or delete a row in the table."
    ::= { opticalLineCapEntry 1 }

opticalLineCapTxLineAttenuation OBJECT-TYPE
    SYNTAX        FspR7Integer32Caps
    UNITS         "0.1 dB"
    MAX-ACCESS    read-only
    STATUS        current
    DESCRIPTION   "The Attenuation (in 0.1 dB) on line connected to
        transmitter of this interface. If there is loss of signal
        then line attenuation is -65535. The value -255 will be
        returned if the value isn't available."
    ::= { opticalLineCapEntry 2 }

opticalLineCapRxLineAttenuation OBJECT-TYPE
    SYNTAX        FspR7Integer32Caps
    UNITS         "0.1 dB"
    MAX-ACCESS    read-only
    STATUS        current
    DESCRIPTION   "The Attenuation (in 0.1 dB) on line connected to receiver
        of this interface. If there is loss of signal then ine
        attenuation is -65535. The value -255 will be returned if
        the value isn't available."
    ::= { opticalLineCapEntry 3 }

opticalLineCapAlias OBJECT-TYPE
    SYNTAX        Integer32
    MAX-ACCESS    read-only
    STATUS        current
    DESCRIPTION   "User Applied Descriptor"
    ::= { opticalLineCapEntry 4 }

opticalLineCapFarEndLocation OBJECT-TYPE
    SYNTAX        Integer32
    MAX-ACCESS    read-only
    STATUS        current
    DESCRIPTION   "FEND Location"
    ::= { opticalLineCapEntry 5 }

opticalLineCapFiberLength OBJECT-TYPE
    SYNTAX        FspR7Unsigned32Caps
    UNITS         "km"
    MAX-ACCESS    read-only
    STATUS        current
    DESCRIPTION   "Fiber length between 2 remote NEs"
    ::= { opticalLineCapEntry 6 }

opticalLineCapChannelBandwith OBJECT-TYPE
    SYNTAX        FspR7ChannelBandwidthCaps
    MAX-ACCESS    read-only
    STATUS        current
    DESCRIPTION   "Channel Bandwidth"
    ::= { opticalLineCapEntry 7 }

endOfOpticalLineCapTable OBJECT-TYPE
    SYNTAX        Integer32
    MAX-ACCESS    read-only
    STATUS        current
    DESCRIPTION   ""
    ::= { opticalLineMgmtCap 2 }

endOfOpticalLineMgmtCap OBJECT-TYPE
    SYNTAX        Integer32
    MAX-ACCESS    read-only
    STATUS        current
    DESCRIPTION   ""
    ::= { opticalLineMgmtCap 10000 }

endOfManagementCap OBJECT-TYPE
    SYNTAX        Integer32
    MAX-ACCESS    read-only
    STATUS        current
    DESCRIPTION   ""
    ::= { managementCap 10000 }

optThresholdConfigCapTable OBJECT-TYPE
    SYNTAX        SEQUENCE OF OptThresholdConfigCapEntry
    MAX-ACCESS    not-accessible
    STATUS        current
    DESCRIPTION   "optThresholdConfigCapTable"
    ::= { performanceFacilityThresholdCap 1 }

optThresholdConfigCapEntry OBJECT-TYPE
    SYNTAX        OptThresholdConfigCapEntry
    MAX-ACCESS    not-accessible
    STATUS        current
    DESCRIPTION   "Entry of optThresholdConfigCapTable"
    INDEX       {
                  entityFacilityShelfNo,
                  entityFacilitySlotNo,
                  entityFacilityPortNo,
                  entityFacilityExtNo,
                  entityFacilityClassName
                }
    ::= { optThresholdConfigCapTable 1 }

OptThresholdConfigCapEntry ::= SEQUENCE
  {    optThresholdConfigCapLowConfig FspR7Integer32Caps,
    optThresholdConfigCapHighConfig FspR7Integer32Caps }

optThresholdConfigCapLowConfig OBJECT-TYPE
    SYNTAX        FspR7Integer32Caps
    UNITS         "0.1 dBm"
    MAX-ACCESS    read-only
    STATUS        current
    DESCRIPTION   "Configurable threshold of the Optical Power Transmitted (output)"
    ::= { optThresholdConfigCapEntry 1 }

optThresholdConfigCapHighConfig OBJECT-TYPE
    SYNTAX        FspR7Integer32Caps
    UNITS         "0.1 dBm"
    MAX-ACCESS    read-only
    STATUS        current
    DESCRIPTION   "Configurable high threshold of the Optical Power Transmitted (output)"
    ::= { optThresholdConfigCapEntry 2 }

oprThresholdConfigCapTable OBJECT-TYPE
    SYNTAX        SEQUENCE OF OprThresholdConfigCapEntry
    MAX-ACCESS    not-accessible
    STATUS        current
    DESCRIPTION   "oprThresholdConfigCapTable"
    ::= { performanceFacilityThresholdCap 2 }

oprThresholdConfigCapEntry OBJECT-TYPE
    SYNTAX        OprThresholdConfigCapEntry
    MAX-ACCESS    not-accessible
    STATUS        current
    DESCRIPTION   "Entry of oprThresholdConfigCapTable"
    INDEX       {
                  entityFacilityShelfNo,
                  entityFacilitySlotNo,
                  entityFacilityPortNo,
                  entityFacilityExtNo,
                  entityFacilityClassName
                }
    ::= { oprThresholdConfigCapTable 1 }

OprThresholdConfigCapEntry ::= SEQUENCE
  {    oprThresholdConfigCapLowConfig FspR7Integer32Caps,
    oprThresholdConfigCapHighConfig FspR7Integer32Caps }

oprThresholdConfigCapLowConfig OBJECT-TYPE
    SYNTAX        FspR7Integer32Caps
    UNITS         "0.1 dBm"
    MAX-ACCESS    read-only
    STATUS        current
    DESCRIPTION   "Optical Input Power Received"
    ::= { oprThresholdConfigCapEntry 1 }

oprThresholdConfigCapHighConfig OBJECT-TYPE
    SYNTAX        FspR7Integer32Caps
    UNITS         "0.1 dBm"
    MAX-ACCESS    read-only
    STATUS        current
    DESCRIPTION   "Optical Input Power Received"
    ::= { oprThresholdConfigCapEntry 2 }

endOfOprThresholdConfigCapTable OBJECT-TYPE
    SYNTAX        Integer32
    MAX-ACCESS    read-only
    STATUS        current
    DESCRIPTION   ""
    ::= { performanceFacilityThresholdCap 3 }

endOfPerformanceFacilityThresholdCap OBJECT-TYPE
    SYNTAX        Integer32
    MAX-ACCESS    read-only
    STATUS        current
    DESCRIPTION   ""
    ::= { performanceFacilityThresholdCap 10000 }

endOfPerformanceFacilityCap OBJECT-TYPE
    SYNTAX        Integer32
    MAX-ACCESS    read-only
    STATUS        current
    DESCRIPTION   ""
    ::= { performanceFacilityCap 10000 }

dcnPhysThresholdCapTable OBJECT-TYPE
    SYNTAX        SEQUENCE OF DcnPhysThresholdCapEntry
    MAX-ACCESS    not-accessible
    STATUS        current
    DESCRIPTION   ""
    ::= { pmDcnPhysThresholdCap 1 }

dcnPhysThresholdCapEntry OBJECT-TYPE
    SYNTAX        DcnPhysThresholdCapEntry
    MAX-ACCESS    not-accessible
    STATUS        current
    DESCRIPTION   ""
    INDEX       {
                  entityDcnShelfNo,
                  entityDcnSlotNo,
                  entityDcnPortNo,
                  entityDcnExtNo,
                  entityDcnClassName
                }
    ::= { dcnPhysThresholdCapTable 1 }

DcnPhysThresholdCapEntry ::= SEQUENCE
  {    dcnPhysThresholdCapOprLow FspR7Integer32Caps,
    dcnPhysThresholdCapOprHigh FspR7Integer32Caps,
    dcnPhysThresholdCapAttRcvLow FspR7Integer32Caps,
    dcnPhysThresholdCapAttRcvHigh FspR7Integer32Caps }

dcnPhysThresholdCapOprLow OBJECT-TYPE
    SYNTAX        FspR7Integer32Caps
    UNITS         "0.1 dBm"
    MAX-ACCESS    read-only
    STATUS        current
    DESCRIPTION   "Optical Input Power Received"
    ::= { dcnPhysThresholdCapEntry 1 }

dcnPhysThresholdCapOprHigh OBJECT-TYPE
    SYNTAX        FspR7Integer32Caps
    UNITS         "0.1 dBm"
    MAX-ACCESS    read-only
    STATUS        current
    DESCRIPTION   "Optical Input Power Received"
    ::= { dcnPhysThresholdCapEntry 2 }

dcnPhysThresholdCapAttRcvLow OBJECT-TYPE
    SYNTAX        FspR7Integer32Caps
    UNITS         "0.1 dB"
    MAX-ACCESS    read-only
    STATUS        current
    DESCRIPTION   "Low Threshold for Attenuation on Receive Fiber."
    ::= { dcnPhysThresholdCapEntry 3 }

dcnPhysThresholdCapAttRcvHigh OBJECT-TYPE
    SYNTAX        FspR7Integer32Caps
    UNITS         "0.1 dB"
    MAX-ACCESS    read-only
    STATUS        current
    DESCRIPTION   "High Threshold for Attenuation on Receive Fiber"
    ::= { dcnPhysThresholdCapEntry 4 }

endOfDcnPhysThresholdCapTable OBJECT-TYPE
    SYNTAX        Integer32
    MAX-ACCESS    read-only
    STATUS        current
    DESCRIPTION   ""
    ::= { pmDcnPhysThresholdCap 2 }

endOfPmDcnPhysThresholdCap OBJECT-TYPE
    SYNTAX        Integer32
    MAX-ACCESS    read-only
    STATUS        current
    DESCRIPTION   ""
    ::= { pmDcnPhysThresholdCap 10000 }

endOfPmDcnPhysicalCap OBJECT-TYPE
    SYNTAX        Integer32
    MAX-ACCESS    read-only
    STATUS        current
    DESCRIPTION   ""
    ::= { pmDcnPhysicalCap 10000 }

endOfPmDcnCap OBJECT-TYPE
    SYNTAX        Integer32
    MAX-ACCESS    read-only
    STATUS        current
    DESCRIPTION   ""
    ::= { pmDcnCap 10000 }

oduFacilityDataThresholdCapTable OBJECT-TYPE
    SYNTAX        SEQUENCE OF OduFacilityDataThresholdCapEntry
    MAX-ACCESS    not-accessible
    STATUS        current
    DESCRIPTION   ""
    ::= { pmFacilityDataThresholdCap 1 }

oduFacilityDataThresholdCapEntry OBJECT-TYPE
    SYNTAX        OduFacilityDataThresholdCapEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { oduFacilityDataThresholdCapTable 1 }

OduFacilityDataThresholdCapEntry ::= SEQUENCE
  {    oduFacilityDataThresholdCapESHighThres15min FspR7Unsigned32Caps,
    oduFacilityDataThresholdCapESHighThres1day FspR7Unsigned32Caps,
    oduFacilityDataThresholdCapSESHighThres15min FspR7Unsigned32Caps,
    oduFacilityDataThresholdCapSESHighThres1day FspR7Unsigned32Caps,
    oduFacilityDataThresholdCapBbeHighThres15min Counter64StringCaps,
    oduFacilityDataThresholdCapBbeHighThres1day Counter64StringCaps,
    oduFacilityDataThresholdCapUASHighThres15min FspR7Unsigned32Caps,
    oduFacilityDataThresholdCapUASHighThres1day FspR7Unsigned32Caps }

oduFacilityDataThresholdCapESHighThres15min OBJECT-TYPE
    SYNTAX        FspR7Unsigned32Caps
    MAX-ACCESS    read-only
    STATUS        current
    DESCRIPTION   "ODU Errored Seconds 15 Minute Threshold"
    ::= { oduFacilityDataThresholdCapEntry 1 }

oduFacilityDataThresholdCapESHighThres1day OBJECT-TYPE
    SYNTAX        FspR7Unsigned32Caps
    MAX-ACCESS    read-only
    STATUS        current
    DESCRIPTION   "ODU Errored Seconds 1 Day Threshold"
    ::= { oduFacilityDataThresholdCapEntry 2 }

oduFacilityDataThresholdCapSESHighThres15min OBJECT-TYPE
    SYNTAX        FspR7Unsigned32Caps
    MAX-ACCESS    read-only
    STATUS        current
    DESCRIPTION   "ODU Severely Errored Seconds 15 Minute Threshold"
    ::= { oduFacilityDataThresholdCapEntry 3 }

oduFacilityDataThresholdCapSESHighThres1day OBJECT-TYPE
    SYNTAX        FspR7Unsigned32Caps
    MAX-ACCESS    read-only
    STATUS        current
    DESCRIPTION   "ODU Severely Errored Seconds 1 Day Threshold"
    ::= { oduFacilityDataThresholdCapEntry 4 }

oduFacilityDataThresholdCapBbeHighThres15min OBJECT-TYPE
    SYNTAX        Counter64StringCaps
    MAX-ACCESS    read-only
    STATUS        current
    DESCRIPTION   "ODU Background Block Errors 15 Minute Threshold"
    ::= { oduFacilityDataThresholdCapEntry 5 }

oduFacilityDataThresholdCapBbeHighThres1day OBJECT-TYPE
    SYNTAX        Counter64StringCaps
    MAX-ACCESS    read-only
    STATUS        current
    DESCRIPTION   "ODU Background Block Errors 1 Day Threshold"
    ::= { oduFacilityDataThresholdCapEntry 6 }

oduFacilityDataThresholdCapUASHighThres15min OBJECT-TYPE
    SYNTAX        FspR7Unsigned32Caps
    MAX-ACCESS    read-only
    STATUS        current
    DESCRIPTION   "ODU Unavailable Seconds 15 Minute Threshold"
    ::= { oduFacilityDataThresholdCapEntry 7 }

oduFacilityDataThresholdCapUASHighThres1day OBJECT-TYPE
    SYNTAX        FspR7Unsigned32Caps
    MAX-ACCESS    read-only
    STATUS        current
    DESCRIPTION   "ODU Unavailable Seconds 1 Day Threshold"
    ::= { oduFacilityDataThresholdCapEntry 8 }

endOfOduFacilityDataThresholdCapTable OBJECT-TYPE
    SYNTAX        Integer32
    MAX-ACCESS    read-only
    STATUS        current
    DESCRIPTION   ""
    ::= { pmFacilityDataThresholdCap 2 }

tcmAFacilityDataThresholdCapTable OBJECT-TYPE
    SYNTAX        SEQUENCE OF TcmAFacilityDataThresholdCapEntry
    MAX-ACCESS    not-accessible
    STATUS        current
    DESCRIPTION   ""
    ::= { pmFacilityDataThresholdCap 3 }

tcmAFacilityDataThresholdCapEntry OBJECT-TYPE
    SYNTAX        TcmAFacilityDataThresholdCapEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { tcmAFacilityDataThresholdCapTable 1 }

TcmAFacilityDataThresholdCapEntry ::= SEQUENCE
  {    tcmAFacilityDataThresholdCapESHighThres15min FspR7Unsigned32Caps,
    tcmAFacilityDataThresholdCapESHighThres1day FspR7Unsigned32Caps,
    tcmAFacilityDataThresholdCapSESHighThres15min FspR7Unsigned32Caps,
    tcmAFacilityDataThresholdCapSESHighThres1day FspR7Unsigned32Caps,
    tcmAFacilityDataThresholdCapBbeHighThres15min Counter64StringCaps,
    tcmAFacilityDataThresholdCapBbeHighThres1day Counter64StringCaps,
    tcmAFacilityDataThresholdCapUASHighThres15min FspR7Unsigned32Caps,
    tcmAFacilityDataThresholdCapUASHighThres1day FspR7Unsigned32Caps }

tcmAFacilityDataThresholdCapESHighThres15min OBJECT-TYPE
    SYNTAX        FspR7Unsigned32Caps
    MAX-ACCESS    read-only
    STATUS        current
    DESCRIPTION   "ODU Tandem Connection Monitoring A Errored Seconds 15 Minute Threshold"
    ::= { tcmAFacilityDataThresholdCapEntry 1 }

tcmAFacilityDataThresholdCapESHighThres1day OBJECT-TYPE
    SYNTAX        FspR7Unsigned32Caps
    MAX-ACCESS    read-only
    STATUS        current
    DESCRIPTION   "ODU Tandem Connection Monitoring A Errored Seconds 1 Day Threshold"
    ::= { tcmAFacilityDataThresholdCapEntry 2 }

tcmAFacilityDataThresholdCapSESHighThres15min OBJECT-TYPE
    SYNTAX        FspR7Unsigned32Caps
    MAX-ACCESS    read-only
    STATUS        current
    DESCRIPTION   "Tandem Connection Monitor A Section Severely Errored Seconds 15 Minute Threshold"
    ::= { tcmAFacilityDataThresholdCapEntry 3 }

tcmAFacilityDataThresholdCapSESHighThres1day OBJECT-TYPE
    SYNTAX        FspR7Unsigned32Caps
    MAX-ACCESS    read-only
    STATUS        current
    DESCRIPTION   "Tandem Connection Monitor A Section Severely Errored Seconds 1 Day Threshold"
    ::= { tcmAFacilityDataThresholdCapEntry 4 }

tcmAFacilityDataThresholdCapBbeHighThres15min OBJECT-TYPE
    SYNTAX        Counter64StringCaps
    MAX-ACCESS    read-only
    STATUS        current
    DESCRIPTION   "ODU Tandem Connection A Background Block Errors 15 Minute Threshold"
    ::= { tcmAFacilityDataThresholdCapEntry 5 }

tcmAFacilityDataThresholdCapBbeHighThres1day OBJECT-TYPE
    SYNTAX        Counter64StringCaps
    MAX-ACCESS    read-only
    STATUS        current
    DESCRIPTION   "ODU Tandem Connection A Background Block Errors 1 Day Minute Threshold"
    ::= { tcmAFacilityDataThresholdCapEntry 6 }

tcmAFacilityDataThresholdCapUASHighThres15min OBJECT-TYPE
    SYNTAX        FspR7Unsigned32Caps
    MAX-ACCESS    read-only
    STATUS        current
    DESCRIPTION   "ODU Tandem Connection Monitoring A Unavailable Seconds 15 Minute Threshold"
    ::= { tcmAFacilityDataThresholdCapEntry 7 }

tcmAFacilityDataThresholdCapUASHighThres1day OBJECT-TYPE
    SYNTAX        FspR7Unsigned32Caps
    MAX-ACCESS    read-only
    STATUS        current
    DESCRIPTION   "ODU Tandem Connection Monitoring A Unavailable Seconds 1 Day Threshold"
    ::= { tcmAFacilityDataThresholdCapEntry 8 }

endOfTcmAFacilityDataThresholdCapTable OBJECT-TYPE
    SYNTAX        Integer32
    MAX-ACCESS    read-only
    STATUS        current
    DESCRIPTION   ""
    ::= { pmFacilityDataThresholdCap 4 }

tcmBFacilityDataThresholdCapTable OBJECT-TYPE
    SYNTAX        SEQUENCE OF TcmBFacilityDataThresholdCapEntry
    MAX-ACCESS    not-accessible
    STATUS        current
    DESCRIPTION   ""
    ::= { pmFacilityDataThresholdCap 5 }

tcmBFacilityDataThresholdCapEntry OBJECT-TYPE
    SYNTAX        TcmBFacilityDataThresholdCapEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { tcmBFacilityDataThresholdCapTable 1 }

TcmBFacilityDataThresholdCapEntry ::= SEQUENCE
  {    tcmBFacilityDataThresholdCapBESHighThres15min FspR7Unsigned32Caps,
    tcmBFacilityDataThresholdCapESHighThres1day FspR7Unsigned32Caps,
    tcmBFacilityDataThresholdCapSESHighThres15min FspR7Unsigned32Caps,
    tcmBFacilityDataThresholdCapSESHighThres1day FspR7Unsigned32Caps,
    tcmBFacilityDataThresholdCapOduTcmBBbeHighThres15min Counter64StringCaps,
    tcmBFacilityDataThresholdCapOduTcmBBbeHighThres1day Counter64StringCaps,
    tcmBFacilityDataThresholdCapUASHighThres15min FspR7Unsigned32Caps,
    tcmBFacilityDataThresholdCapUASHighThres1day FspR7Unsigned32Caps }

tcmBFacilityDataThresholdCapBESHighThres15min OBJECT-TYPE
    SYNTAX        FspR7Unsigned32Caps
    MAX-ACCESS    read-only
    STATUS        current
    DESCRIPTION   "ODU Tandem Connection Monitoring B Errored Seconds 15 Minute Threshold"
    ::= { tcmBFacilityDataThresholdCapEntry 1 }

tcmBFacilityDataThresholdCapESHighThres1day OBJECT-TYPE
    SYNTAX        FspR7Unsigned32Caps
    MAX-ACCESS    read-only
    STATUS        current
    DESCRIPTION   "ODU Tandem Connection Monitoring B Errored Seconds 1 Day Threshold"
    ::= { tcmBFacilityDataThresholdCapEntry 2 }

tcmBFacilityDataThresholdCapSESHighThres15min OBJECT-TYPE
    SYNTAX        FspR7Unsigned32Caps
    MAX-ACCESS    read-only
    STATUS        current
    DESCRIPTION   "Tandem Connection Monitor B Section Severely Errored Seconds 15 Minute Threshold"
    ::= { tcmBFacilityDataThresholdCapEntry 3 }

tcmBFacilityDataThresholdCapSESHighThres1day OBJECT-TYPE
    SYNTAX        FspR7Unsigned32Caps
    MAX-ACCESS    read-only
    STATUS        current
    DESCRIPTION   "Tandem Connection Monitor B Section Severely Errored Seconds 1 Day Threshold"
    ::= { tcmBFacilityDataThresholdCapEntry 4 }

tcmBFacilityDataThresholdCapOduTcmBBbeHighThres15min OBJECT-TYPE
    SYNTAX        Counter64StringCaps
    MAX-ACCESS    read-only
    STATUS        current
    DESCRIPTION   "ODU Tandem Connection B Background Block Errors 15 Minute Threshold"
    ::= { tcmBFacilityDataThresholdCapEntry 5 }

tcmBFacilityDataThresholdCapOduTcmBBbeHighThres1day OBJECT-TYPE
    SYNTAX        Counter64StringCaps
    MAX-ACCESS    read-only
    STATUS        current
    DESCRIPTION   "ODU Tandem Connection B Background Block Errors 1 Day Threshold"
    ::= { tcmBFacilityDataThresholdCapEntry 6 }

tcmBFacilityDataThresholdCapUASHighThres15min OBJECT-TYPE
    SYNTAX        FspR7Unsigned32Caps
    MAX-ACCESS    read-only
    STATUS        current
    DESCRIPTION   "ODU Tandem Connection Monitoring B Unavailable Seconds 15 Minute Threshold"
    ::= { tcmBFacilityDataThresholdCapEntry 7 }

tcmBFacilityDataThresholdCapUASHighThres1day OBJECT-TYPE
    SYNTAX        FspR7Unsigned32Caps
    MAX-ACCESS    read-only
    STATUS        current
    DESCRIPTION   "ODU Tandem Connection Monitoring B Unavailable Seconds 1 Day Threshold"
    ::= { tcmBFacilityDataThresholdCapEntry 8 }

endOfTcmBFacilityDataThresholdCapTable OBJECT-TYPE
    SYNTAX        Integer32
    MAX-ACCESS    read-only
    STATUS        current
    DESCRIPTION   ""
    ::= { pmFacilityDataThresholdCap 6 }

tcmCFacilityDataThresholdCapTable OBJECT-TYPE
    SYNTAX        SEQUENCE OF TcmCFacilityDataThresholdCapEntry
    MAX-ACCESS    not-accessible
    STATUS        current
    DESCRIPTION   ""
    ::= { pmFacilityDataThresholdCap 7 }

tcmCFacilityDataThresholdCapEntry OBJECT-TYPE
    SYNTAX        TcmCFacilityDataThresholdCapEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { tcmCFacilityDataThresholdCapTable 1 }

TcmCFacilityDataThresholdCapEntry ::= SEQUENCE
  {    tcmCFacilityDataThresholdCapBESHighThres15min FspR7Unsigned32Caps,
    tcmCFacilityDataThresholdCapESHighThres1day FspR7Unsigned32Caps,
    tcmCFacilityDataThresholdCapSESHighThres15min FspR7Unsigned32Caps,
    tcmCFacilityDataThresholdCapSESHighThres1day FspR7Unsigned32Caps,
    tcmCFacilityDataThresholdCapOduTcmCBbeHighThres15min Counter64StringCaps,
    tcmCFacilityDataThresholdCapOduTcmCBbeHighThres1day Counter64StringCaps,
    tcmCFacilityDataThresholdCapUASHighThres15min FspR7Unsigned32Caps,
    tcmCFacilityDataThresholdCapUASHighThres1day FspR7Unsigned32Caps }

tcmCFacilityDataThresholdCapBESHighThres15min OBJECT-TYPE
    SYNTAX        FspR7Unsigned32Caps
    MAX-ACCESS    read-only
    STATUS        current
    DESCRIPTION   "ODU Tandem Connection Monitoring C Errored Seconds 15 Minute Threshold"
    ::= { tcmCFacilityDataThresholdCapEntry 1 }

tcmCFacilityDataThresholdCapESHighThres1day OBJECT-TYPE
    SYNTAX        FspR7Unsigned32Caps
    MAX-ACCESS    read-only
    STATUS        current
    DESCRIPTION   "ODU Tandem Connection Monitoring C Errored Seconds 1 Day Threshold"
    ::= { tcmCFacilityDataThresholdCapEntry 2 }

tcmCFacilityDataThresholdCapSESHighThres15min OBJECT-TYPE
    SYNTAX        FspR7Unsigned32Caps
    MAX-ACCESS    read-only
    STATUS        current
    DESCRIPTION   "Tandem Connection Monitor C Section Severely Errored Seconds 15 Minute Threshold"
    ::= { tcmCFacilityDataThresholdCapEntry 3 }

tcmCFacilityDataThresholdCapSESHighThres1day OBJECT-TYPE
    SYNTAX        FspR7Unsigned32Caps
    MAX-ACCESS    read-only
    STATUS        current
    DESCRIPTION   "Tandem Connection Monitor C Section Severely Errored Seconds 1 Day Threshold"
    ::= { tcmCFacilityDataThresholdCapEntry 4 }

tcmCFacilityDataThresholdCapOduTcmCBbeHighThres15min OBJECT-TYPE
    SYNTAX        Counter64StringCaps
    MAX-ACCESS    read-only
    STATUS        current
    DESCRIPTION   "ODU Tandem Connection C Background Block Errors 15 Minute Threshold"
    ::= { tcmCFacilityDataThresholdCapEntry 5 }

tcmCFacilityDataThresholdCapOduTcmCBbeHighThres1day OBJECT-TYPE
    SYNTAX        Counter64StringCaps
    MAX-ACCESS    read-only
    STATUS        current
    DESCRIPTION   "ODU Tandem Connection C Background Block Errors 1 Day Threshold"
    ::= { tcmCFacilityDataThresholdCapEntry 6 }

tcmCFacilityDataThresholdCapUASHighThres15min OBJECT-TYPE
    SYNTAX        FspR7Unsigned32Caps
    MAX-ACCESS    read-only
    STATUS        current
    DESCRIPTION   "ODU Tandem Connection Monitoring C Unavailable Seconds 15 Minute Threshold"
    ::= { tcmCFacilityDataThresholdCapEntry 7 }

tcmCFacilityDataThresholdCapUASHighThres1day OBJECT-TYPE
    SYNTAX        FspR7Unsigned32Caps
    MAX-ACCESS    read-only
    STATUS        current
    DESCRIPTION   "ODU Tandem Connection Monitoring C Unavailable Seconds 1 Day Threshold"
    ::= { tcmCFacilityDataThresholdCapEntry 8 }

endOfTcmCFacilityDataThresholdCapTable OBJECT-TYPE
    SYNTAX        Integer32
    MAX-ACCESS    read-only
    STATUS        current
    DESCRIPTION   ""
    ::= { pmFacilityDataThresholdCap 8 }

otuFacilityDataThresholdCapTable OBJECT-TYPE
    SYNTAX        SEQUENCE OF OtuFacilityDataThresholdCapEntry
    MAX-ACCESS    not-accessible
    STATUS        current
    DESCRIPTION   ""
    ::= { pmFacilityDataThresholdCap 9 }

otuFacilityDataThresholdCapEntry OBJECT-TYPE
    SYNTAX        OtuFacilityDataThresholdCapEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { otuFacilityDataThresholdCapTable 1 }

OtuFacilityDataThresholdCapEntry ::= SEQUENCE
  {    otuFacilityDataThresholdCapESHighThres15min FspR7Unsigned32Caps,
    otuFacilityDataThresholdCapESHighThres1day FspR7Unsigned32Caps,
    otuFacilityDataThresholdCapSESHighThres15min FspR7Unsigned32Caps,
    otuFacilityDataThresholdCapSESHighThres1day FspR7Unsigned32Caps,
    otuFacilityDataThresholdCapBbeHighThres15min Counter64StringCaps,
    otuFacilityDataThresholdCapBbeHighThres1day Counter64StringCaps,
    otuFacilityDataThresholdCapUASHighThres15min FspR7Unsigned32Caps,
    otuFacilityDataThresholdCapUASHighThres1day FspR7Unsigned32Caps }

otuFacilityDataThresholdCapESHighThres15min OBJECT-TYPE
    SYNTAX        FspR7Unsigned32Caps
    MAX-ACCESS    read-only
    STATUS        current
    DESCRIPTION   "OTU Errored Seconds 15 Minute Threshold"
    ::= { otuFacilityDataThresholdCapEntry 1 }

otuFacilityDataThresholdCapESHighThres1day OBJECT-TYPE
    SYNTAX        FspR7Unsigned32Caps
    MAX-ACCESS    read-only
    STATUS        current
    DESCRIPTION   "OTU Errored Seconds 1 Day Threshold"
    ::= { otuFacilityDataThresholdCapEntry 2 }

otuFacilityDataThresholdCapSESHighThres15min OBJECT-TYPE
    SYNTAX        FspR7Unsigned32Caps
    MAX-ACCESS    read-only
    STATUS        current
    DESCRIPTION   "OTU Severely Errored Seconds 15 Minute Threshold"
    ::= { otuFacilityDataThresholdCapEntry 3 }

otuFacilityDataThresholdCapSESHighThres1day OBJECT-TYPE
    SYNTAX        FspR7Unsigned32Caps
    MAX-ACCESS    read-only
    STATUS        current
    DESCRIPTION   "OTU Severely Errored Seconds 1 Day Threshold"
    ::= { otuFacilityDataThresholdCapEntry 4 }

otuFacilityDataThresholdCapBbeHighThres15min OBJECT-TYPE
    SYNTAX        Counter64StringCaps
    MAX-ACCESS    read-only
    STATUS        current
    DESCRIPTION   "OTU Background Block Errors 15 Minute Threshold"
    ::= { otuFacilityDataThresholdCapEntry 5 }

otuFacilityDataThresholdCapBbeHighThres1day OBJECT-TYPE
    SYNTAX        Counter64StringCaps
    MAX-ACCESS    read-only
    STATUS        current
    DESCRIPTION   "OTU Background Block Errors 1 Day Threshold"
    ::= { otuFacilityDataThresholdCapEntry 6 }

otuFacilityDataThresholdCapUASHighThres15min OBJECT-TYPE
    SYNTAX        FspR7Unsigned32Caps
    MAX-ACCESS    read-only
    STATUS        current
    DESCRIPTION   "OTU Unavailable Seconds 15 Minute Threshold"
    ::= { otuFacilityDataThresholdCapEntry 7 }

otuFacilityDataThresholdCapUASHighThres1day OBJECT-TYPE
    SYNTAX        FspR7Unsigned32Caps
    MAX-ACCESS    read-only
    STATUS        current
    DESCRIPTION   "OTU Unavailable Seconds 1 Day Threshold"
    ::= { otuFacilityDataThresholdCapEntry 8 }

endOfOtuFacilityDataThresholdCapTable OBJECT-TYPE
    SYNTAX        Integer32
    MAX-ACCESS    read-only
    STATUS        current
    DESCRIPTION   ""
    ::= { pmFacilityDataThresholdCap 10 }

otuFecFacilityDataThresholdCapTable OBJECT-TYPE
    SYNTAX        SEQUENCE OF OtuFecFacilityDataThresholdCapEntry
    MAX-ACCESS    not-accessible
    STATUS        current
    DESCRIPTION   ""
    ::= { pmFacilityDataThresholdCap 11 }

otuFecFacilityDataThresholdCapEntry OBJECT-TYPE
    SYNTAX        OtuFecFacilityDataThresholdCapEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { otuFecFacilityDataThresholdCapTable 1 }

OtuFecFacilityDataThresholdCapEntry ::= SEQUENCE
  {    otuFecFacilityDataThresholdCapESHighThres15min FspR7Unsigned32Caps,
    otuFecFacilityDataThresholdCapESHighThres1day FspR7Unsigned32Caps,
    otuFecFacilityDataThresholdCapSESHighThres15min FspR7Unsigned32Caps,
    otuFecFacilityDataThresholdCapSESHighThres1day FspR7Unsigned32Caps,
    otuFecFacilityDataThresholdCapUBEHighThres15min Counter64StringCaps,
    otuFecFacilityDataThresholdCapUBEHighThres1day Counter64StringCaps,
    otuFecFacilityDataThresholdCapCErrHighThres15min Counter64StringCaps,
    otuFecFacilityDataThresholdCapCErrHighThres1day Counter64StringCaps,
    otuFecFacilityDataThresholdCapBERCErrHighThres15min Counter64StringCaps,
    otuFecFacilityDataThresholdCapBERCErrHighThres1day Counter64StringCaps }

otuFecFacilityDataThresholdCapESHighThres15min OBJECT-TYPE
    SYNTAX        FspR7Unsigned32Caps
    MAX-ACCESS    read-only
    STATUS        current
    DESCRIPTION   "OTU FEC Errored Seconds 15 Minute Threshold"
    ::= { otuFecFacilityDataThresholdCapEntry 1 }

otuFecFacilityDataThresholdCapESHighThres1day OBJECT-TYPE
    SYNTAX        FspR7Unsigned32Caps
    MAX-ACCESS    read-only
    STATUS        current
    DESCRIPTION   "OTU FEC Errored Seconds Day Threshold"
    ::= { otuFecFacilityDataThresholdCapEntry 2 }

otuFecFacilityDataThresholdCapSESHighThres15min OBJECT-TYPE
    SYNTAX        FspR7Unsigned32Caps
    MAX-ACCESS    read-only
    STATUS        current
    DESCRIPTION   "OTU FEC Severely Errored Seconds 15 Minute Threshold"
    ::= { otuFecFacilityDataThresholdCapEntry 3 }

otuFecFacilityDataThresholdCapSESHighThres1day OBJECT-TYPE
    SYNTAX        FspR7Unsigned32Caps
    MAX-ACCESS    read-only
    STATUS        current
    DESCRIPTION   "OTU FEC Severely Errored Seconds 1 Day Threshold"
    ::= { otuFecFacilityDataThresholdCapEntry 4 }

otuFecFacilityDataThresholdCapUBEHighThres15min OBJECT-TYPE
    SYNTAX        Counter64StringCaps
    MAX-ACCESS    read-only
    STATUS        current
    DESCRIPTION   "Uncorrected Block Errors 15 Minute Threshold"
    ::= { otuFecFacilityDataThresholdCapEntry 5 }

otuFecFacilityDataThresholdCapUBEHighThres1day OBJECT-TYPE
    SYNTAX        Counter64StringCaps
    MAX-ACCESS    read-only
    STATUS        current
    DESCRIPTION   "Uncorrected Block Errors 1 Day Threshold"
    ::= { otuFecFacilityDataThresholdCapEntry 6 }

otuFecFacilityDataThresholdCapCErrHighThres15min OBJECT-TYPE
    SYNTAX        Counter64StringCaps
    MAX-ACCESS    read-only
    STATUS        current
    DESCRIPTION   "FEC Corrected Errors 15 Minute Threshold"
    ::= { otuFecFacilityDataThresholdCapEntry 7 }

otuFecFacilityDataThresholdCapCErrHighThres1day OBJECT-TYPE
    SYNTAX        Counter64StringCaps
    MAX-ACCESS    read-only
    STATUS        current
    DESCRIPTION   "FEC Corrected Errors 1 Day Threshold"
    ::= { otuFecFacilityDataThresholdCapEntry 8 }

otuFecFacilityDataThresholdCapBERCErrHighThres15min OBJECT-TYPE
    SYNTAX        Counter64StringCaps
    UNITS         "1.0E-18"
    MAX-ACCESS    read-only
    STATUS        current
    DESCRIPTION   "Bit Error Rate before FEC 15 Minute Threshold"
    ::= { otuFecFacilityDataThresholdCapEntry 9 }

otuFecFacilityDataThresholdCapBERCErrHighThres1day OBJECT-TYPE
    SYNTAX        Counter64StringCaps
    UNITS         "1.0E-18"
    MAX-ACCESS    read-only
    STATUS        current
    DESCRIPTION   "Bit Error Rate before FEC 1 Day Threshold"
    ::= { otuFecFacilityDataThresholdCapEntry 10 }

endOfOtuFecFacilityDataThresholdCapTable OBJECT-TYPE
    SYNTAX        Integer32
    MAX-ACCESS    read-only
    STATUS        current
    DESCRIPTION   ""
    ::= { pmFacilityDataThresholdCap 12 }

fecFacilityDataThresholdCapTable OBJECT-TYPE
    SYNTAX        SEQUENCE OF FecFacilityDataThresholdCapEntry
    MAX-ACCESS    not-accessible
    STATUS        current
    DESCRIPTION   ""
    ::= { pmFacilityDataThresholdCap 13 }

fecFacilityDataThresholdCapEntry OBJECT-TYPE
    SYNTAX        FecFacilityDataThresholdCapEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { fecFacilityDataThresholdCapTable 1 }

FecFacilityDataThresholdCapEntry ::= SEQUENCE
  {    fecFacilityDataThresholdCapCEHighThres15min Counter64StringCaps,
    fecFacilityDataThresholdCapCEHighThres1day Counter64StringCaps,
    fecFacilityDataThresholdCapUBEHighThres15min Counter64StringCaps,
    fecFacilityDataThresholdCapUBEHighThres1day Counter64StringCaps }

fecFacilityDataThresholdCapCEHighThres15min OBJECT-TYPE
    SYNTAX        Counter64StringCaps
    MAX-ACCESS    read-only
    STATUS        current
    DESCRIPTION   "FEC Corrected Errors 15 Minute Threshold"
    ::= { fecFacilityDataThresholdCapEntry 1 }

fecFacilityDataThresholdCapCEHighThres1day OBJECT-TYPE
    SYNTAX        Counter64StringCaps
    MAX-ACCESS    read-only
    STATUS        current
    DESCRIPTION   "FEC Corrected Errors 1 Day Threshold"
    ::= { fecFacilityDataThresholdCapEntry 2 }

fecFacilityDataThresholdCapUBEHighThres15min OBJECT-TYPE
    SYNTAX        Counter64StringCaps
    MAX-ACCESS    read-only
    STATUS        current
    DESCRIPTION   "Uncorrected Block Errors 15 Minute Threshold"
    ::= { fecFacilityDataThresholdCapEntry 3 }

fecFacilityDataThresholdCapUBEHighThres1day OBJECT-TYPE
    SYNTAX        Counter64StringCaps
    MAX-ACCESS    read-only
    STATUS        current
    DESCRIPTION   "Uncorrected Block Errors 1 Day Threshold"
    ::= { fecFacilityDataThresholdCapEntry 4 }

endOfFecFacilityDataThresholdCapTable OBJECT-TYPE
    SYNTAX        Integer32
    MAX-ACCESS    read-only
    STATUS        current
    DESCRIPTION   ""
    ::= { pmFacilityDataThresholdCap 14 }

pcs2FacilityDataThresholdCapTable OBJECT-TYPE
    SYNTAX        SEQUENCE OF Pcs2FacilityDataThresholdCapEntry
    MAX-ACCESS    not-accessible
    STATUS        current
    DESCRIPTION   ""
    ::= { pmFacilityDataThresholdCap 15 }

pcs2FacilityDataThresholdCapEntry OBJECT-TYPE
    SYNTAX        Pcs2FacilityDataThresholdCapEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { pcs2FacilityDataThresholdCapTable 1 }

Pcs2FacilityDataThresholdCapEntry ::= SEQUENCE
  {    pcs2FacilityDataThresholdCapESHighThres15min FspR7Unsigned32Caps,
    pcs2FacilityDataThresholdCapESHighThres1day FspR7Unsigned32Caps,
    pcs2FacilityDataThresholdCapDEHighThres15min FspR7Unsigned32Caps,
    pcs2FacilityDataThresholdCapDEHighThres1day FspR7Unsigned32Caps,
    pcs2FacilityDataThresholdCapCVHighThres15min Counter64StringCaps,
    pcs2FacilityDataThresholdCapCVHighThres1day Counter64StringCaps }

pcs2FacilityDataThresholdCapESHighThres15min OBJECT-TYPE
    SYNTAX        FspR7Unsigned32Caps
    MAX-ACCESS    read-only
    STATUS        current
    DESCRIPTION   "Physical Coding Layer Errored Seconds 15 Minute Threshold"
    ::= { pcs2FacilityDataThresholdCapEntry 1 }

pcs2FacilityDataThresholdCapESHighThres1day OBJECT-TYPE
    SYNTAX        FspR7Unsigned32Caps
    MAX-ACCESS    read-only
    STATUS        current
    DESCRIPTION   "Physical Coding Layer Errored Seconds 1 Day Threshold"
    ::= { pcs2FacilityDataThresholdCapEntry 2 }

pcs2FacilityDataThresholdCapDEHighThres15min OBJECT-TYPE
    SYNTAX        FspR7Unsigned32Caps
    MAX-ACCESS    read-only
    STATUS        current
    DESCRIPTION   "Physical Coding Layer Disparity Errors 15 Minute Threshold"
    ::= { pcs2FacilityDataThresholdCapEntry 3 }

pcs2FacilityDataThresholdCapDEHighThres1day OBJECT-TYPE
    SYNTAX        FspR7Unsigned32Caps
    MAX-ACCESS    read-only
    STATUS        current
    DESCRIPTION   "Physical Coding Layer Disparity Errors 1 Day Threshold"
    ::= { pcs2FacilityDataThresholdCapEntry 4 }

pcs2FacilityDataThresholdCapCVHighThres15min OBJECT-TYPE
    SYNTAX        Counter64StringCaps
    MAX-ACCESS    read-only
    STATUS        current
    DESCRIPTION   "Physical Coding Layer 15 Minute Threshold"
    ::= { pcs2FacilityDataThresholdCapEntry 5 }

pcs2FacilityDataThresholdCapCVHighThres1day OBJECT-TYPE
    SYNTAX        Counter64StringCaps
    MAX-ACCESS    read-only
    STATUS        current
    DESCRIPTION   "Physical Coding Layer Coding Violations 1 Day Threshold"
    ::= { pcs2FacilityDataThresholdCapEntry 6 }

endOfPcs2FacilityDataThresholdCapTable OBJECT-TYPE
    SYNTAX        Integer32
    MAX-ACCESS    read-only
    STATUS        current
    DESCRIPTION   ""
    ::= { pmFacilityDataThresholdCap 16 }

lFacilityDataThresholdCapTable OBJECT-TYPE
    SYNTAX        SEQUENCE OF LFacilityDataThresholdCapEntry
    MAX-ACCESS    not-accessible
    STATUS        current
    DESCRIPTION   ""
    ::= { pmFacilityDataThresholdCap 17 }

lFacilityDataThresholdCapEntry OBJECT-TYPE
    SYNTAX        LFacilityDataThresholdCapEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { lFacilityDataThresholdCapTable 1 }

LFacilityDataThresholdCapEntry ::= SEQUENCE
  {    lFacilityDataThresholdCapESHighThres15min FspR7Unsigned32Caps,
    lFacilityDataThresholdCapESHighThres1day FspR7Unsigned32Caps,
    lFacilityDataThresholdCapSESHighThres15min FspR7Unsigned32Caps,
    lFacilityDataThresholdCapSESHighThres1day FspR7Unsigned32Caps,
    lFacilityDataThresholdCapUASHighThres15min FspR7Unsigned32Caps,
    lFacilityDataThresholdCapUASSHighThres1day FspR7Unsigned32Caps,
    lFacilityDataThresholdCapCVHighThres15min Counter64StringCaps,
    lFacilityDataThresholdCapCVSHighThres1day Counter64StringCaps }

lFacilityDataThresholdCapESHighThres15min OBJECT-TYPE
    SYNTAX        FspR7Unsigned32Caps
    MAX-ACCESS    read-only
    STATUS        current
    DESCRIPTION   "Line / Multiplex Section Errored Seconds 15 Minute Threshold"
    ::= { lFacilityDataThresholdCapEntry 1 }

lFacilityDataThresholdCapESHighThres1day OBJECT-TYPE
    SYNTAX        FspR7Unsigned32Caps
    MAX-ACCESS    read-only
    STATUS        current
    DESCRIPTION   "Line / Multiplex Section Errored Seconds 1 Day Threshold"
    ::= { lFacilityDataThresholdCapEntry 2 }

lFacilityDataThresholdCapSESHighThres15min OBJECT-TYPE
    SYNTAX        FspR7Unsigned32Caps
    MAX-ACCESS    read-only
    STATUS        current
    DESCRIPTION   "Line / Multiplex Section Severely Errored Seconds 15 Minute Threshold"
    ::= { lFacilityDataThresholdCapEntry 3 }

lFacilityDataThresholdCapSESHighThres1day OBJECT-TYPE
    SYNTAX        FspR7Unsigned32Caps
    MAX-ACCESS    read-only
    STATUS        current
    DESCRIPTION   "Line / Multiplex Section Severely Errored Seconds 1 Day Threshold"
    ::= { lFacilityDataThresholdCapEntry 4 }

lFacilityDataThresholdCapUASHighThres15min OBJECT-TYPE
    SYNTAX        FspR7Unsigned32Caps
    MAX-ACCESS    read-only
    STATUS        current
    DESCRIPTION   "Line / Multiplex Section Unavailable Seconds 15 Minute Threshold"
    ::= { lFacilityDataThresholdCapEntry 5 }

lFacilityDataThresholdCapUASSHighThres1day OBJECT-TYPE
    SYNTAX        FspR7Unsigned32Caps
    MAX-ACCESS    read-only
    STATUS        current
    DESCRIPTION   "Line / Multiplex Section Unavailable Seconds 1 Day Threshold"
    ::= { lFacilityDataThresholdCapEntry 6 }

lFacilityDataThresholdCapCVHighThres15min OBJECT-TYPE
    SYNTAX        Counter64StringCaps
    MAX-ACCESS    read-only
    STATUS        current
    DESCRIPTION   "Line / Multiplex Section Coding Violations 15 Minute Threshold"
    ::= { lFacilityDataThresholdCapEntry 7 }

lFacilityDataThresholdCapCVSHighThres1day OBJECT-TYPE
    SYNTAX        Counter64StringCaps
    MAX-ACCESS    read-only
    STATUS        current
    DESCRIPTION   "Line / Multiplex Section Coding Violations 1 Day Threshold"
    ::= { lFacilityDataThresholdCapEntry 8 }

endOfLFacilityDataThresholdCapTable OBJECT-TYPE
    SYNTAX        Integer32
    MAX-ACCESS    read-only
    STATUS        current
    DESCRIPTION   ""
    ::= { pmFacilityDataThresholdCap 18 }

sFacilityDataThresholdCapTable OBJECT-TYPE
    SYNTAX        SEQUENCE OF SFacilityDataThresholdCapEntry
    MAX-ACCESS    not-accessible
    STATUS        current
    DESCRIPTION   ""
    ::= { pmFacilityDataThresholdCap 19 }

sFacilityDataThresholdCapEntry OBJECT-TYPE
    SYNTAX        SFacilityDataThresholdCapEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { sFacilityDataThresholdCapTable 1 }

SFacilityDataThresholdCapEntry ::= SEQUENCE
  {    sFacilityDataThresholdCapESHighThres15min FspR7Unsigned32Caps,
    sFacilityDataThresholdCapESHighThres1day FspR7Unsigned32Caps,
    sFacilityDataThresholdCapSESHighThres15min FspR7Unsigned32Caps,
    sFacilityDataThresholdCapSESHighThres1day FspR7Unsigned32Caps,
    sFacilityDataThresholdCapSEFSHighThres15min FspR7Unsigned32Caps,
    sFacilityDataThresholdCapSEFSHighThres1day FspR7Unsigned32Caps,
    sFacilityDataThresholdCapCVHighThres15min Counter64StringCaps,
    sFacilityDataThresholdCapCVHighThres1day Counter64StringCaps }

sFacilityDataThresholdCapESHighThres15min OBJECT-TYPE
    SYNTAX        FspR7Unsigned32Caps
    MAX-ACCESS    read-only
    STATUS        current
    DESCRIPTION   "Section / Regeneration Section Errored Seconds 15 Minute Threshold"
    ::= { sFacilityDataThresholdCapEntry 1 }

sFacilityDataThresholdCapESHighThres1day OBJECT-TYPE
    SYNTAX        FspR7Unsigned32Caps
    MAX-ACCESS    read-only
    STATUS        current
    DESCRIPTION   "Section / Regeneration Section Errored Seconds 1 Day Threshold"
    ::= { sFacilityDataThresholdCapEntry 2 }

sFacilityDataThresholdCapSESHighThres15min OBJECT-TYPE
    SYNTAX        FspR7Unsigned32Caps
    MAX-ACCESS    read-only
    STATUS        current
    DESCRIPTION   "Section / Regenerator Section Severely Errored Seconds 15 Minute Threshold"
    ::= { sFacilityDataThresholdCapEntry 3 }

sFacilityDataThresholdCapSESHighThres1day OBJECT-TYPE
    SYNTAX        FspR7Unsigned32Caps
    MAX-ACCESS    read-only
    STATUS        current
    DESCRIPTION   "Section / Regenerator Section Severely Errored Seconds 1 Day Threshold"
    ::= { sFacilityDataThresholdCapEntry 4 }

sFacilityDataThresholdCapSEFSHighThres15min OBJECT-TYPE
    SYNTAX        FspR7Unsigned32Caps
    MAX-ACCESS    read-only
    STATUS        current
    DESCRIPTION   "Section Severely Errored Frame Seconds 15 Minute Threshold"
    ::= { sFacilityDataThresholdCapEntry 5 }

sFacilityDataThresholdCapSEFSHighThres1day OBJECT-TYPE
    SYNTAX        FspR7Unsigned32Caps
    MAX-ACCESS    read-only
    STATUS        current
    DESCRIPTION   "Section Severely Errored Frame Seconds 1 Day Threshold"
    ::= { sFacilityDataThresholdCapEntry 6 }

sFacilityDataThresholdCapCVHighThres15min OBJECT-TYPE
    SYNTAX        Counter64StringCaps
    MAX-ACCESS    read-only
    STATUS        current
    DESCRIPTION   "Section / Regenerator Section Coding Violations 15 Minute Threshold"
    ::= { sFacilityDataThresholdCapEntry 7 }

sFacilityDataThresholdCapCVHighThres1day OBJECT-TYPE
    SYNTAX        Counter64StringCaps
    MAX-ACCESS    read-only
    STATUS        current
    DESCRIPTION   "Section / Regenerator Section Coding Violations 1 Day Threshold"
    ::= { sFacilityDataThresholdCapEntry 8 }

endOfSFacilityDataThresholdCapTable OBJECT-TYPE
    SYNTAX        Integer32
    MAX-ACCESS    read-only
    STATUS        current
    DESCRIPTION   ""
    ::= { pmFacilityDataThresholdCap 20 }

endOfPmFacilityDataThresholdCap OBJECT-TYPE
    SYNTAX        Integer32
    MAX-ACCESS    read-only
    STATUS        current
    DESCRIPTION   ""
    ::= { pmFacilityDataThresholdCap 10000 }

endOfPmFacilityDataCap OBJECT-TYPE
    SYNTAX        Integer32
    MAX-ACCESS    read-only
    STATUS        current
    DESCRIPTION   ""
    ::= { pmFacilityDataCap 10000 }

facilityPhysThresholdCapTable OBJECT-TYPE
    SYNTAX        SEQUENCE OF FacilityPhysThresholdCapEntry
    MAX-ACCESS    not-accessible
    STATUS        current
    DESCRIPTION   ""
    ::= { pmFacilityPhysThresholdCap 1 }

facilityPhysThresholdCapEntry OBJECT-TYPE
    SYNTAX        FacilityPhysThresholdCapEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { facilityPhysThresholdCapTable 1 }

FacilityPhysThresholdCapEntry ::= SEQUENCE
  {    facilityPhysThresholdCapOpticalInputPwrLow FspR7Integer32Caps,
    facilityPhysThresholdCapOpticalInputPwrHigh FspR7Integer32Caps,
    facilityPhysThresholdCapConfigurableOpticalOutputPwrLow FspR7Integer32Caps,
    facilityPhysThresholdCapConfigurableOpticalOutputPwrHigh FspR7Integer32Caps,
    facilityPhysThresholdCapRoundTripDelayLowThres FspR7Integer32Caps,
    facilityPhysThresholdCapRoundTripDelayHighThres FspR7Integer32Caps,
    facilityPhysThresholdCapLatencyLowThres FspR7Integer32Caps,
    facilityPhysThresholdCapLatencyHighThres FspR7Integer32Caps,
    facilityPhysThresholdCapChromaticDispersionHigh FspR7Integer32Caps,
    facilityPhysThresholdCapChromaticDispersionLow FspR7Integer32Caps,
    facilityPhysThresholdCapCarrierFreqOffsetLow FspR7Integer32Caps,
    facilityPhysThresholdCapCarrierFreqOffsetHigh FspR7Integer32Caps,
    facilityPhysThresholdCapLogicalLanesSkewHigh FspR7Integer32Caps,
    facilityPhysThresholdCapDispersionCompensationLowThres FspR7Integer32Caps,
    facilityPhysThresholdCapDispersionCompensationHighThres FspR7Integer32Caps,
    facilityPhysThresholdCapSignalToNoiseRatioLow FspR7Integer32Caps,
    facilityPhysThresholdCapDifferentialGroupDelayHigh FspR7Integer32Caps,
    facilityPhysThresholdCapQualityFactorLowThres FspR7Integer32Caps }

facilityPhysThresholdCapOpticalInputPwrLow OBJECT-TYPE
    SYNTAX        FspR7Integer32Caps
    UNITS         "0.1 dBm"
    MAX-ACCESS    read-only
    STATUS        current
    DESCRIPTION   "Optical Input Power Received"
    ::= { facilityPhysThresholdCapEntry 1 }

facilityPhysThresholdCapOpticalInputPwrHigh OBJECT-TYPE
    SYNTAX        FspR7Integer32Caps
    UNITS         "0.1 dBm"
    MAX-ACCESS    read-only
    STATUS        current
    DESCRIPTION   "Optical Input Power Received"
    ::= { facilityPhysThresholdCapEntry 2 }

facilityPhysThresholdCapConfigurableOpticalOutputPwrLow OBJECT-TYPE
    SYNTAX        FspR7Integer32Caps
    UNITS         "0.1 dBm"
    MAX-ACCESS    read-only
    STATUS        current
    DESCRIPTION   "Configurable threshold of the Optical Power Transmitted (output)"
    ::= { facilityPhysThresholdCapEntry 3 }

facilityPhysThresholdCapConfigurableOpticalOutputPwrHigh OBJECT-TYPE
    SYNTAX        FspR7Integer32Caps
    UNITS         "0.1 dBm"
    MAX-ACCESS    read-only
    STATUS        current
    DESCRIPTION   "Configurable high threshold of the Optical Power Transmitted (output)"
    ::= { facilityPhysThresholdCapEntry 4 }

facilityPhysThresholdCapRoundTripDelayLowThres OBJECT-TYPE
    SYNTAX        FspR7Integer32Caps
    UNITS         "ns"
    MAX-ACCESS    read-only
    STATUS        current
    DESCRIPTION   "Configurable low threshold for round trip delay"
    ::= { facilityPhysThresholdCapEntry 5 }

facilityPhysThresholdCapRoundTripDelayHighThres OBJECT-TYPE
    SYNTAX        FspR7Integer32Caps
    UNITS         "ns"
    MAX-ACCESS    read-only
    STATUS        current
    DESCRIPTION   "Configurable high threshold for round trip delay"
    ::= { facilityPhysThresholdCapEntry 6 }

facilityPhysThresholdCapLatencyLowThres OBJECT-TYPE
    SYNTAX        FspR7Integer32Caps
    UNITS         "0.1 us"
    MAX-ACCESS    read-only
    STATUS        current
    DESCRIPTION   "Configurable low threshold round trip delay"
    ::= { facilityPhysThresholdCapEntry 7 }

facilityPhysThresholdCapLatencyHighThres OBJECT-TYPE
    SYNTAX        FspR7Integer32Caps
    UNITS         "0.1 us"
    MAX-ACCESS    read-only
    STATUS        current
    DESCRIPTION   "Configurable high threshold for round trip delay"
    ::= { facilityPhysThresholdCapEntry 8 }

facilityPhysThresholdCapChromaticDispersionHigh OBJECT-TYPE
    SYNTAX        FspR7Integer32Caps
    UNITS         "ps/nm"
    MAX-ACCESS    read-only
    STATUS        current
    DESCRIPTION   "Chromatic Dispersion Compensation High Threshold"
    ::= { facilityPhysThresholdCapEntry 9 }

facilityPhysThresholdCapChromaticDispersionLow OBJECT-TYPE
    SYNTAX        FspR7Integer32Caps
    UNITS         "ps/nm"
    MAX-ACCESS    read-only
    STATUS        current
    DESCRIPTION   "Chromatic Dispersion Compensation Low Threshold"
    ::= { facilityPhysThresholdCapEntry 10 }

facilityPhysThresholdCapCarrierFreqOffsetLow OBJECT-TYPE
    SYNTAX        FspR7Integer32Caps
    UNITS         "0.001 GHz"
    MAX-ACCESS    read-only
    STATUS        current
    DESCRIPTION   "Carrier Frequency Offset Low TH"
    ::= { facilityPhysThresholdCapEntry 11 }

facilityPhysThresholdCapCarrierFreqOffsetHigh OBJECT-TYPE
    SYNTAX        FspR7Integer32Caps
    UNITS         "0.001 GHz"
    MAX-ACCESS    read-only
    STATUS        current
    DESCRIPTION   "Carrier Frequency Offset High TH"
    ::= { facilityPhysThresholdCapEntry 12 }

facilityPhysThresholdCapLogicalLanesSkewHigh OBJECT-TYPE
    SYNTAX        FspR7Integer32Caps
    UNITS         "ns"
    MAX-ACCESS    read-only
    STATUS        current
    DESCRIPTION   "Skew between logical lanes farthest apart high threshold"
    ::= { facilityPhysThresholdCapEntry 13 }

facilityPhysThresholdCapDispersionCompensationLowThres OBJECT-TYPE
    SYNTAX        FspR7Integer32Caps
    UNITS         "ps/nm"
    MAX-ACCESS    read-only
    STATUS        current
    DESCRIPTION   "Chromatic Dispersion Compensation Low Threshold"
    ::= { facilityPhysThresholdCapEntry 14 }

facilityPhysThresholdCapDispersionCompensationHighThres OBJECT-TYPE
    SYNTAX        FspR7Integer32Caps
    UNITS         "ps/nm"
    MAX-ACCESS    read-only
    STATUS        current
    DESCRIPTION   "Chromatic Dispersion Compensation High Threshold"
    ::= { facilityPhysThresholdCapEntry 15 }

facilityPhysThresholdCapSignalToNoiseRatioLow OBJECT-TYPE
    SYNTAX        FspR7Integer32Caps
    UNITS         "0.1 dB"
    MAX-ACCESS    read-only
    STATUS        current
    DESCRIPTION   "Signal-to-Noise Ratio Low TH"
    ::= { facilityPhysThresholdCapEntry 16 }

facilityPhysThresholdCapDifferentialGroupDelayHigh OBJECT-TYPE
    SYNTAX        FspR7Integer32Caps
    UNITS         "ps"
    MAX-ACCESS    read-only
    STATUS        current
    DESCRIPTION   "Differential Group Delay High TH"
    ::= { facilityPhysThresholdCapEntry 17 }

facilityPhysThresholdCapQualityFactorLowThres OBJECT-TYPE
    SYNTAX        FspR7Integer32Caps
    UNITS         "0.1 dB"
    MAX-ACCESS    read-only
    STATUS        current
    DESCRIPTION   "Quality Factor Low TH"
    ::= { facilityPhysThresholdCapEntry 18 }

endOfFacilityPhysThresholdCapTable OBJECT-TYPE
    SYNTAX        Integer32
    MAX-ACCESS    read-only
    STATUS        current
    DESCRIPTION   ""
    ::= { pmFacilityPhysThresholdCap 2 }

endOfPmFacilityPhysThresholdCap OBJECT-TYPE
    SYNTAX        Integer32
    MAX-ACCESS    read-only
    STATUS        current
    DESCRIPTION   ""
    ::= { pmFacilityPhysThresholdCap 10000 }

endOfPmFacilityPhysicalCap OBJECT-TYPE
    SYNTAX        Integer32
    MAX-ACCESS    read-only
    STATUS        current
    DESCRIPTION   ""
    ::= { pmFacilityPhysicalCap 10000 }

endOfPmFacilityCap OBJECT-TYPE
    SYNTAX        Integer32
    MAX-ACCESS    read-only
    STATUS        current
    DESCRIPTION   ""
    ::= { pmFacilityCap 10000 }

optMuxPhysThresholdCapTable OBJECT-TYPE
    SYNTAX        SEQUENCE OF OptMuxPhysThresholdCapEntry
    MAX-ACCESS    not-accessible
    STATUS        current
    DESCRIPTION   ""
    ::= { pmOptMuxPhysThresholdCap 2 }

optMuxPhysThresholdCapEntry OBJECT-TYPE
    SYNTAX        OptMuxPhysThresholdCapEntry
    MAX-ACCESS    not-accessible
    STATUS        current
    DESCRIPTION   ""
    INDEX       {
                  entityOpticalMuxShelfNo,
                  entityOpticalMuxSlotNo,
                  entityOpticalMuxPortNo,
                  entityOpticalMuxExtNo,
                  entityOpticalMuxClassName
                }
    ::= { optMuxPhysThresholdCapTable 1 }

OptMuxPhysThresholdCapEntry ::= SEQUENCE
  {    optMuxPhysThresholdCapBrtxHighConfig FspR7Integer32Caps,
    optMuxPhysThresholdCapBrPwrReceivedHighThres FspR7Integer32Caps,
    optMuxPhysThresholdCapConfigurableOpticalOutputPwrHigh FspR7Integer32Caps,
    optMuxPhysThresholdCapConfigurableOpticalOutputPwrLow FspR7Integer32Caps,
    optMuxPhysThresholdCapOscPwrRcvHighThres FspR7Integer32Caps,
    optMuxPhysThresholdCapOscPwrRcvLowThres FspR7Integer32Caps,
    optMuxPhysThresholdCapOpticalInputPwrHigh FspR7Integer32Caps,
    optMuxPhysThresholdCapOpticalInputPwrLow FspR7Integer32Caps,
    optMuxPhysThresholdCapAttRxHigh FspR7Integer32Caps,
    optMuxPhysThresholdCapAttRxLow FspR7Integer32Caps,
    optMuxPhysThresholdCapAttTxHigh FspR7Integer32Caps,
    optMuxPhysThresholdCapAttTxLow FspR7Integer32Caps }

optMuxPhysThresholdCapBrtxHighConfig OBJECT-TYPE
    SYNTAX        FspR7Integer32Caps
    UNITS         "0.1 dB"
    MAX-ACCESS    read-only
    STATUS        current
    DESCRIPTION   "Backreflection power High Threshold, at Tx Port"
    ::= { optMuxPhysThresholdCapEntry 1 }

optMuxPhysThresholdCapBrPwrReceivedHighThres OBJECT-TYPE
    SYNTAX        FspR7Integer32Caps
    UNITS         "0.1 dB"
    MAX-ACCESS    read-only
    STATUS        current
    DESCRIPTION   "Backreflection Input Received High Threshold"
    ::= { optMuxPhysThresholdCapEntry 2 }

optMuxPhysThresholdCapConfigurableOpticalOutputPwrHigh OBJECT-TYPE
    SYNTAX        FspR7Integer32Caps
    UNITS         "0.1 dBm"
    MAX-ACCESS    read-only
    STATUS        current
    DESCRIPTION   "Configurable high threshold of the Optical Power Transmitted (output)"
    ::= { optMuxPhysThresholdCapEntry 3 }

optMuxPhysThresholdCapConfigurableOpticalOutputPwrLow OBJECT-TYPE
    SYNTAX        FspR7Integer32Caps
    UNITS         "0.1 dBm"
    MAX-ACCESS    read-only
    STATUS        current
    DESCRIPTION   "Configurable threshold of the Optical Power Transmitted (output)"
    ::= { optMuxPhysThresholdCapEntry 4 }

optMuxPhysThresholdCapOscPwrRcvHighThres OBJECT-TYPE
    SYNTAX        FspR7Integer32Caps
    UNITS         "0.1 dBm"
    MAX-ACCESS    read-only
    STATUS        current
    DESCRIPTION   "Optical Supervisory Channel Input Power Received High Threshold"
    ::= { optMuxPhysThresholdCapEntry 5 }

optMuxPhysThresholdCapOscPwrRcvLowThres OBJECT-TYPE
    SYNTAX        FspR7Integer32Caps
    UNITS         "0.1 dBm"
    MAX-ACCESS    read-only
    STATUS        current
    DESCRIPTION   "Optical Supervisory Channel Input Power Received Low Threshold"
    ::= { optMuxPhysThresholdCapEntry 6 }

optMuxPhysThresholdCapOpticalInputPwrHigh OBJECT-TYPE
    SYNTAX        FspR7Integer32Caps
    UNITS         "0.1 dBm"
    MAX-ACCESS    read-only
    STATUS        current
    DESCRIPTION   "Optical Input Power Received"
    ::= { optMuxPhysThresholdCapEntry 7 }

optMuxPhysThresholdCapOpticalInputPwrLow OBJECT-TYPE
    SYNTAX        FspR7Integer32Caps
    UNITS         "0.1 dBm"
    MAX-ACCESS    read-only
    STATUS        current
    DESCRIPTION   "Optical Input Power Received"
    ::= { optMuxPhysThresholdCapEntry 8 }

optMuxPhysThresholdCapAttRxHigh OBJECT-TYPE
    SYNTAX        FspR7Integer32Caps
    UNITS         "0.1 dB"
    MAX-ACCESS    read-only
    STATUS        current
    DESCRIPTION   "High Threshold for Attenuation on Receive Fiber"
    ::= { optMuxPhysThresholdCapEntry 9 }

optMuxPhysThresholdCapAttRxLow OBJECT-TYPE
    SYNTAX        FspR7Integer32Caps
    UNITS         "0.1 dB"
    MAX-ACCESS    read-only
    STATUS        current
    DESCRIPTION   "Low Threshold for Attenuation on Receive Fiber."
    ::= { optMuxPhysThresholdCapEntry 10 }

optMuxPhysThresholdCapAttTxHigh OBJECT-TYPE
    SYNTAX        FspR7Integer32Caps
    UNITS         "0.1 dB"
    MAX-ACCESS    read-only
    STATUS        current
    DESCRIPTION   "High Threshold of Attenuation on Transmit Fiber"
    ::= { optMuxPhysThresholdCapEntry 11 }

optMuxPhysThresholdCapAttTxLow OBJECT-TYPE
    SYNTAX        FspR7Integer32Caps
    UNITS         "0.1 dB"
    MAX-ACCESS    read-only
    STATUS        current
    DESCRIPTION   "Low Threshold Attenuation on Transmit Fiber"
    ::= { optMuxPhysThresholdCapEntry 12 }

endOfOptMuxPhysThresholdCapTable OBJECT-TYPE
    SYNTAX        Integer32
    MAX-ACCESS    read-only
    STATUS        current
    DESCRIPTION   ""
    ::= { pmOptMuxPhysThresholdCap 3 }

endOfPmOptMuxPhysThresholdCap OBJECT-TYPE
    SYNTAX        Integer32
    MAX-ACCESS    read-only
    STATUS        current
    DESCRIPTION   ""
    ::= { pmOptMuxPhysThresholdCap 10000 }

terminationPointCapTable OBJECT-TYPE
    SYNTAX        SEQUENCE OF TerminationPointCapEntry
    MAX-ACCESS    not-accessible
    STATUS        current
    DESCRIPTION   "terminationPointCapTable"
    ::= { fiberMapCap 1 }

terminationPointCapEntry OBJECT-TYPE
    SYNTAX        TerminationPointCapEntry
    MAX-ACCESS    not-accessible
    STATUS        current
    DESCRIPTION   "Entry of terminationPointCapTable"
    INDEX       {
                  entityTerminPointIndexNo1,
                  entityTerminPointIndexNo2,
                  entityTerminPointIndexNo3,
                  entityTerminPointIndexNo4,
                  entityTerminPointClassName
                }
    ::= { terminationPointCapTable 1 }

TerminationPointCapEntry ::= SEQUENCE
  {    terminationPointCapRowStatus FspR7RowStatusCaps,
    terminationPointCapAdmin FspR7AdminStateCaps,
    terminationPointCapFiberDetect FspR7EnableDisableCaps,
    terminationPointCapAlias Integer32 }

terminationPointCapRowStatus OBJECT-TYPE
    SYNTAX        FspR7RowStatusCaps
    MAX-ACCESS    read-only
    STATUS        current
    DESCRIPTION   "Physical Termination Point Capability RowStatus."
    ::= { terminationPointCapEntry 1 }

terminationPointCapAdmin OBJECT-TYPE
    SYNTAX        FspR7AdminStateCaps
    MAX-ACCESS    read-only
    STATUS        current
    DESCRIPTION   "Physical Termination Point Capability Adminstrative State."
    ::= { terminationPointCapEntry 2 }

terminationPointCapFiberDetect OBJECT-TYPE
    SYNTAX        FspR7EnableDisableCaps
    MAX-ACCESS    read-only
    STATUS        current
    DESCRIPTION   "Physical Termination Point Capability Fiber Detect."
    ::= { terminationPointCapEntry 3 }

terminationPointCapAlias OBJECT-TYPE
    SYNTAX        Integer32
    MAX-ACCESS    read-only
    STATUS        current
    DESCRIPTION   "Physical Termination Point Capabillity Alias."
    ::= { terminationPointCapEntry 4 }

connectionCapTable OBJECT-TYPE
    SYNTAX        SEQUENCE OF ConnectionCapEntry
    MAX-ACCESS    not-accessible
    STATUS        current
    DESCRIPTION   "connectionCapTable"
    ::= { fiberMapCap 2 }

connectionCapEntry OBJECT-TYPE
    SYNTAX        ConnectionCapEntry
    MAX-ACCESS    not-accessible
    STATUS        current
    DESCRIPTION   "Entry of connectionCapTable"
    INDEX       {
                  entityTerminPointIndexNo1,
                  entityTerminPointIndexNo2,
                  entityTerminPointIndexNo3,
                  entityTerminPointIndexNo4,
                  entityTerminPointClassName,
                  entityTerminPointIndexNo1,
                  entityTerminPointIndexNo2,
                  entityTerminPointIndexNo3,
                  entityTerminPointIndexNo4,
                  entityTerminPointClassName,
                  entityConnectionClassName
                }
    ::= { connectionCapTable 1 }

ConnectionCapEntry ::= SEQUENCE
  {    connectionCapRowStatus FspR7RowStatusCaps,
    connectionCapType FspR7TypeConnectionCaps }

connectionCapRowStatus OBJECT-TYPE
    SYNTAX        FspR7RowStatusCaps
    MAX-ACCESS    read-only
    STATUS        current
    DESCRIPTION   "Physical Connection Capability RowStatus."
    ::= { connectionCapEntry 1 }

connectionCapType OBJECT-TYPE
    SYNTAX        FspR7TypeConnectionCaps
    MAX-ACCESS    read-only
    STATUS        current
    DESCRIPTION   "Physical Connection Capability Type."
    ::= { connectionCapEntry 2 }

endOfConnectionCapTable OBJECT-TYPE
    SYNTAX        Integer32
    MAX-ACCESS    read-only
    STATUS        current
    DESCRIPTION   ""
    ::= { fiberMapCap 3 }

endOfFiberMapCap OBJECT-TYPE
    SYNTAX        Integer32
    MAX-ACCESS    read-only
    STATUS        current
    DESCRIPTION   ""
    ::= { fiberMapCap 10000 }

externalPortCapTable OBJECT-TYPE
    SYNTAX        SEQUENCE OF ExternalPortCapEntry
    MAX-ACCESS    not-accessible
    STATUS        current
    DESCRIPTION   "externalPortCap"
    ::= { eciCap 1 }

externalPortCapEntry OBJECT-TYPE
    SYNTAX        ExternalPortCapEntry
    MAX-ACCESS    not-accessible
    STATUS        current
    DESCRIPTION   "Entry of externalPortCap"
    INDEX       {
                  entityExternalPortShelfNo,
                  entityExternalPortSlotNo,
                  entityExternalPortPortNo,
                  entityExternalPortExtNo,
                  entityExternalPortClassName
                }
    ::= { externalPortCapTable 1 }

ExternalPortCapEntry ::= SEQUENCE
  {    externalPortCapRowStatus FspR7RowStatusCaps,
    externalPortCapType FspR7InterfaceTypeCaps,
    externalPortCapTransmitChannel FspR7ChannelIdentifierCaps,
    externalPortCapChannelBandwith FspR7ChannelBandwidthCaps,
    externalPortCapAlias Integer32,
    externalPortCapFarEndLocation Integer32,
    externalPortCapBitrate FspR7Unsigned32Caps,
    externalPortCapFecType FspR7FecTypeCaps,
    externalPortCapLineCoding FspR7LineCodingCaps,
    externalPortCapFrameFormat FspR7FrameFormatCaps,
    externalPortCapOpticalPowerTx FspR7Integer32Caps,
    externalPortCapOsnrTransmit FspR7Unsigned32Caps,
    externalPortCapPmdTransmit FspR7Unsigned32Caps,
    externalPortCapChromDisperTx FspR7Integer32Caps,
    externalPortCapMinOsnrRcv FspR7Unsigned32Caps,
    externalPortCapMinOptPowerRcv FspR7Integer32Caps,
    externalPortCapMaxOptPowerRcv FspR7Integer32Caps,
    externalPortCapMaxPmdRcv FspR7Unsigned32Caps,
    externalPortCapMinChromDisperRcv FspR7Integer32Caps,
    externalPortCapMaxChromDisperRcv FspR7Integer32Caps,
    externalPortCapMaxBitErrorRate FspR7MaxBitErrorRateCaps,
    externalPortCapSourceProfile Integer32 }

externalPortCapRowStatus OBJECT-TYPE
    SYNTAX        FspR7RowStatusCaps
    MAX-ACCESS    read-only
    STATUS        current
    DESCRIPTION   "Object is used to create or delete a row in the table."
    ::= { externalPortCapEntry 1 }

externalPortCapType OBJECT-TYPE
    SYNTAX        FspR7InterfaceTypeCaps
    MAX-ACCESS    read-only
    STATUS        current
    DESCRIPTION   "."
    ::= { externalPortCapEntry 2 }

externalPortCapTransmitChannel OBJECT-TYPE
    SYNTAX        FspR7ChannelIdentifierCaps
    MAX-ACCESS    read-only
    STATUS        current
    DESCRIPTION   "."
    ::= { externalPortCapEntry 3 }

externalPortCapChannelBandwith OBJECT-TYPE
    SYNTAX        FspR7ChannelBandwidthCaps
    MAX-ACCESS    read-only
    STATUS        current
    DESCRIPTION   "."
    ::= { externalPortCapEntry 4 }

externalPortCapAlias OBJECT-TYPE
    SYNTAX        Integer32
    MAX-ACCESS    read-only
    STATUS        current
    DESCRIPTION   "."
    ::= { externalPortCapEntry 5 }

externalPortCapFarEndLocation OBJECT-TYPE
    SYNTAX        Integer32
    MAX-ACCESS    read-only
    STATUS        current
    DESCRIPTION   "."
    ::= { externalPortCapEntry 6 }

externalPortCapBitrate OBJECT-TYPE
    SYNTAX        FspR7Unsigned32Caps
    UNITS         "Mbps"
    MAX-ACCESS    read-only
    STATUS        current
    DESCRIPTION   "."
    ::= { externalPortCapEntry 7 }

externalPortCapFecType OBJECT-TYPE
    SYNTAX        FspR7FecTypeCaps
    MAX-ACCESS    read-only
    STATUS        current
    DESCRIPTION   "."
    ::= { externalPortCapEntry 8 }

externalPortCapLineCoding OBJECT-TYPE
    SYNTAX        FspR7LineCodingCaps
    MAX-ACCESS    read-only
    STATUS        current
    DESCRIPTION   "."
    ::= { externalPortCapEntry 9 }

externalPortCapFrameFormat OBJECT-TYPE
    SYNTAX        FspR7FrameFormatCaps
    MAX-ACCESS    read-only
    STATUS        current
    DESCRIPTION   "."
    ::= { externalPortCapEntry 10 }

externalPortCapOpticalPowerTx OBJECT-TYPE
    SYNTAX        FspR7Integer32Caps
    UNITS         "0.1 dBm"
    MAX-ACCESS    read-only
    STATUS        current
    DESCRIPTION   "."
    ::= { externalPortCapEntry 11 }

externalPortCapOsnrTransmit OBJECT-TYPE
    SYNTAX        FspR7Unsigned32Caps
    UNITS         "dB"
    MAX-ACCESS    read-only
    STATUS        current
    DESCRIPTION   "."
    ::= { externalPortCapEntry 12 }

externalPortCapPmdTransmit OBJECT-TYPE
    SYNTAX        FspR7Unsigned32Caps
    UNITS         "ps"
    MAX-ACCESS    read-only
    STATUS        current
    DESCRIPTION   "."
    ::= { externalPortCapEntry 13 }

externalPortCapChromDisperTx OBJECT-TYPE
    SYNTAX        FspR7Integer32Caps
    UNITS         "ps/nm"
    MAX-ACCESS    read-only
    STATUS        current
    DESCRIPTION   "."
    ::= { externalPortCapEntry 14 }

externalPortCapMinOsnrRcv OBJECT-TYPE
    SYNTAX        FspR7Unsigned32Caps
    UNITS         "dB"
    MAX-ACCESS    read-only
    STATUS        current
    DESCRIPTION   "."
    ::= { externalPortCapEntry 15 }

externalPortCapMinOptPowerRcv OBJECT-TYPE
    SYNTAX        FspR7Integer32Caps
    UNITS         "0.1 dBm"
    MAX-ACCESS    read-only
    STATUS        current
    DESCRIPTION   "."
    ::= { externalPortCapEntry 16 }

externalPortCapMaxOptPowerRcv OBJECT-TYPE
    SYNTAX        FspR7Integer32Caps
    UNITS         "0.1 dBm"
    MAX-ACCESS    read-only
    STATUS        current
    DESCRIPTION   "."
    ::= { externalPortCapEntry 17 }

externalPortCapMaxPmdRcv OBJECT-TYPE
    SYNTAX        FspR7Unsigned32Caps
    UNITS         "ps"
    MAX-ACCESS    read-only
    STATUS        current
    DESCRIPTION   "."
    ::= { externalPortCapEntry 18 }

externalPortCapMinChromDisperRcv OBJECT-TYPE
    SYNTAX        FspR7Integer32Caps
    UNITS         "ps/nm"
    MAX-ACCESS    read-only
    STATUS        current
    DESCRIPTION   "."
    ::= { externalPortCapEntry 19 }

externalPortCapMaxChromDisperRcv OBJECT-TYPE
    SYNTAX        FspR7Integer32Caps
    UNITS         "ps/nm"
    MAX-ACCESS    read-only
    STATUS        current
    DESCRIPTION   "."
    ::= { externalPortCapEntry 20 }

externalPortCapMaxBitErrorRate OBJECT-TYPE
    SYNTAX        FspR7MaxBitErrorRateCaps
    MAX-ACCESS    read-only
    STATUS        current
    DESCRIPTION   "."
    ::= { externalPortCapEntry 21 }

externalPortCapSourceProfile OBJECT-TYPE
    SYNTAX        Integer32
    MAX-ACCESS    read-only
    STATUS        current
    DESCRIPTION   "."
    ::= { externalPortCapEntry 22 }

endOfExternalPortCapTable OBJECT-TYPE
    SYNTAX        Integer32
    MAX-ACCESS    read-only
    STATUS        current
    DESCRIPTION   ""
    ::= { eciCap 2 }

externalOmCapTable OBJECT-TYPE
    SYNTAX        SEQUENCE OF ExternalOmCapEntry
    MAX-ACCESS    not-accessible
    STATUS        current
    DESCRIPTION   "externalOmCap"
    ::= { eciCap 3 }

externalOmCapEntry OBJECT-TYPE
    SYNTAX        ExternalOmCapEntry
    MAX-ACCESS    not-accessible
    STATUS        current
    DESCRIPTION   "Entry of externalOmCap"
    INDEX       {
                  entityExternalPortShelfNo,
                  entityExternalPortSlotNo,
                  entityExternalPortPortNo,
                  entityExternalPortExtNo,
                  entityExternalPortClassName
                }
    ::= { externalOmCapTable 1 }

ExternalOmCapEntry ::= SEQUENCE
  {    externalOmCapRowStatus FspR7RowStatusCaps,
    externalOmCapType FspR7InterfaceTypeCaps,
    externalOmCapHostName Integer32 }

externalOmCapRowStatus OBJECT-TYPE
    SYNTAX        FspR7RowStatusCaps
    MAX-ACCESS    read-only
    STATUS        current
    DESCRIPTION   "Object is used to create or delete a row in the table."
    ::= { externalOmCapEntry 1 }

externalOmCapType OBJECT-TYPE
    SYNTAX        FspR7InterfaceTypeCaps
    MAX-ACCESS    read-only
    STATUS        current
    DESCRIPTION   "The TYPE defines the transport service type as wrapper with wrapper layer termination OR else as payload"
    ::= { externalOmCapEntry 2 }

externalOmCapHostName OBJECT-TYPE
    SYNTAX        Integer32
    MAX-ACCESS    read-only
    STATUS        current
    DESCRIPTION   "Host Device Name"
    ::= { externalOmCapEntry 3 }

externalVchCapTable OBJECT-TYPE
    SYNTAX        SEQUENCE OF ExternalVchCapEntry
    MAX-ACCESS    not-accessible
    STATUS        current
    DESCRIPTION   "externalVchCap"
    ::= { eciCap 5 }

externalVchCapEntry OBJECT-TYPE
    SYNTAX        ExternalVchCapEntry
    MAX-ACCESS    not-accessible
    STATUS        current
    DESCRIPTION   "Entry of externalVchCap"
    INDEX       {
                  entityExternalPortShelfNo,
                  entityExternalPortSlotNo,
                  entityExternalPortPortNo,
                  entityExternalPortExtNo,
                  entityExternalPortClassName
                }
    ::= { externalVchCapTable 1 }

ExternalVchCapEntry ::= SEQUENCE
  {    externalVchCapRowStatus FspR7RowStatusCaps,
    externalVchCapType FspR7InterfaceTypeCaps,
    externalVchCapTransmitChannel FspR7ChannelIdentifierCaps,
    externalVchCapChannelBandwith FspR7ChannelBandwidthCaps,
    externalVchCapAlias Integer32,
    externalVchCapFarEndLocation Integer32,
    externalVchCapBitrate FspR7Unsigned32Caps,
    externalVchCapFecType FspR7FecTypeCaps,
    externalVchCapLineCoding FspR7LineCodingCaps,
    externalVchCapFrameFormat FspR7FrameFormatCaps,
    externalVchCapOpticalPowerTx FspR7Integer32Caps,
    externalVchCapOsnrTransmit FspR7Unsigned32Caps,
    externalVchCapPmdTransmit FspR7Unsigned32Caps,
    externalVchCapChromDisperTx FspR7Integer32Caps,
    externalVchCapMinOsnrRcv FspR7Unsigned32Caps,
    externalVchCapMinOptPowerRcv FspR7Integer32Caps,
    externalVchCapMaxOptPowerRcv FspR7Integer32Caps,
    externalVchCapMaxPmdRcv FspR7Unsigned32Caps,
    externalVchCapMinChromDisperRcv FspR7Integer32Caps,
    externalVchCapMaxChromDisperRcv FspR7Integer32Caps,
    externalVchCapMaxBitErrorRate FspR7MaxBitErrorRateCaps,
    externalVchCapSourceProfile Integer32 }

externalVchCapRowStatus OBJECT-TYPE
    SYNTAX        FspR7RowStatusCaps
    MAX-ACCESS    read-only
    STATUS        current
    DESCRIPTION   "Object is used to create or delete a row in the table."
    ::= { externalVchCapEntry 1 }

externalVchCapType OBJECT-TYPE
    SYNTAX        FspR7InterfaceTypeCaps
    MAX-ACCESS    read-only
    STATUS        current
    DESCRIPTION   "."
    ::= { externalVchCapEntry 2 }

externalVchCapTransmitChannel OBJECT-TYPE
    SYNTAX        FspR7ChannelIdentifierCaps
    MAX-ACCESS    read-only
    STATUS        current
    DESCRIPTION   "."
    ::= { externalVchCapEntry 3 }

externalVchCapChannelBandwith OBJECT-TYPE
    SYNTAX        FspR7ChannelBandwidthCaps
    MAX-ACCESS    read-only
    STATUS        current
    DESCRIPTION   "."
    ::= { externalVchCapEntry 4 }

externalVchCapAlias OBJECT-TYPE
    SYNTAX        Integer32
    MAX-ACCESS    read-only
    STATUS        current
    DESCRIPTION   "."
    ::= { externalVchCapEntry 5 }

externalVchCapFarEndLocation OBJECT-TYPE
    SYNTAX        Integer32
    MAX-ACCESS    read-only
    STATUS        current
    DESCRIPTION   "."
    ::= { externalVchCapEntry 6 }

externalVchCapBitrate OBJECT-TYPE
    SYNTAX        FspR7Unsigned32Caps
    UNITS         "Mbps"
    MAX-ACCESS    read-only
    STATUS        current
    DESCRIPTION   "."
    ::= { externalVchCapEntry 7 }

externalVchCapFecType OBJECT-TYPE
    SYNTAX        FspR7FecTypeCaps
    MAX-ACCESS    read-only
    STATUS        current
    DESCRIPTION   "."
    ::= { externalVchCapEntry 8 }

externalVchCapLineCoding OBJECT-TYPE
    SYNTAX        FspR7LineCodingCaps
    MAX-ACCESS    read-only
    STATUS        current
    DESCRIPTION   "."
    ::= { externalVchCapEntry 9 }

externalVchCapFrameFormat OBJECT-TYPE
    SYNTAX        FspR7FrameFormatCaps
    MAX-ACCESS    read-only
    STATUS        current
    DESCRIPTION   "."
    ::= { externalVchCapEntry 10 }

externalVchCapOpticalPowerTx OBJECT-TYPE
    SYNTAX        FspR7Integer32Caps
    UNITS         "0.1 dBm"
    MAX-ACCESS    read-only
    STATUS        current
    DESCRIPTION   "."
    ::= { externalVchCapEntry 11 }

externalVchCapOsnrTransmit OBJECT-TYPE
    SYNTAX        FspR7Unsigned32Caps
    UNITS         "dB"
    MAX-ACCESS    read-only
    STATUS        current
    DESCRIPTION   "."
    ::= { externalVchCapEntry 12 }

externalVchCapPmdTransmit OBJECT-TYPE
    SYNTAX        FspR7Unsigned32Caps
    UNITS         "ps"
    MAX-ACCESS    read-only
    STATUS        current
    DESCRIPTION   "."
    ::= { externalVchCapEntry 13 }

externalVchCapChromDisperTx OBJECT-TYPE
    SYNTAX        FspR7Integer32Caps
    UNITS         "ps/nm"
    MAX-ACCESS    read-only
    STATUS        current
    DESCRIPTION   "."
    ::= { externalVchCapEntry 14 }

externalVchCapMinOsnrRcv OBJECT-TYPE
    SYNTAX        FspR7Unsigned32Caps
    UNITS         "dB"
    MAX-ACCESS    read-only
    STATUS        current
    DESCRIPTION   "."
    ::= { externalVchCapEntry 15 }

externalVchCapMinOptPowerRcv OBJECT-TYPE
    SYNTAX        FspR7Integer32Caps
    UNITS         "0.1 dBm"
    MAX-ACCESS    read-only
    STATUS        current
    DESCRIPTION   "."
    ::= { externalVchCapEntry 16 }

externalVchCapMaxOptPowerRcv OBJECT-TYPE
    SYNTAX        FspR7Integer32Caps
    UNITS         "0.1 dBm"
    MAX-ACCESS    read-only
    STATUS        current
    DESCRIPTION   "."
    ::= { externalVchCapEntry 17 }

externalVchCapMaxPmdRcv OBJECT-TYPE
    SYNTAX        FspR7Unsigned32Caps
    UNITS         "ps"
    MAX-ACCESS    read-only
    STATUS        current
    DESCRIPTION   "."
    ::= { externalVchCapEntry 18 }

externalVchCapMinChromDisperRcv OBJECT-TYPE
    SYNTAX        FspR7Integer32Caps
    UNITS         "ps/nm"
    MAX-ACCESS    read-only
    STATUS        current
    DESCRIPTION   "."
    ::= { externalVchCapEntry 19 }

externalVchCapMaxChromDisperRcv OBJECT-TYPE
    SYNTAX        FspR7Integer32Caps
    UNITS         "ps/nm"
    MAX-ACCESS    read-only
    STATUS        current
    DESCRIPTION   "."
    ::= { externalVchCapEntry 20 }

externalVchCapMaxBitErrorRate OBJECT-TYPE
    SYNTAX        FspR7MaxBitErrorRateCaps
    MAX-ACCESS    read-only
    STATUS        current
    DESCRIPTION   "."
    ::= { externalVchCapEntry 21 }

externalVchCapSourceProfile OBJECT-TYPE
    SYNTAX        Integer32
    MAX-ACCESS    read-only
    STATUS        current
    DESCRIPTION   "."
    ::= { externalVchCapEntry 22 }

endOfEciCap OBJECT-TYPE
    SYNTAX        Integer32
    MAX-ACCESS    read-only
    STATUS        current
    DESCRIPTION   ""
    ::= { eciCap 10000 }

changePhysicalPortServiceCapTable OBJECT-TYPE
    SYNTAX        SEQUENCE OF ChangePhysicalPortServiceCapEntry
    MAX-ACCESS    not-accessible
    STATUS        current
    DESCRIPTION   ""
    ::= { changeServiceCap 1 }

changePhysicalPortServiceCapEntry OBJECT-TYPE
    SYNTAX        ChangePhysicalPortServiceCapEntry
    MAX-ACCESS    not-accessible
    STATUS        current
    DESCRIPTION   ""
    INDEX       {
                  entityFacilityShelfNo,
                  entityFacilitySlotNo,
                  entityFacilityPortNo,
                  entityFacilityExtNo,
                  entityFacilityClassName
                }
    ::= { changePhysicalPortServiceCapTable 1 }

ChangePhysicalPortServiceCapEntry ::= SEQUENCE
  {    changePhysicalPortServiceCapRowStatus FspR7RowStatusCaps,
    changePhysicalPortServiceCapType FspR7InterfaceTypeCaps,
    changePhysicalPortServiceCapAdmin FspR7AdminStateCaps,
    changePhysicalPortServiceCapAlias Integer32,
    changePhysicalPortServiceCapAlsMode FspR7AlsModeCaps,
    changePhysicalPortServiceCapBehaviour FspR7PortBehaviourCaps,
    changePhysicalPortServiceCapDispersionSetting FspR7Integer32Caps,
    changePhysicalPortServiceCapDispersionMode FspR7DispersionModesCaps,
    changePhysicalPortServiceCapChannelProv FspR7ChannelIdentifierCaps,
    changePhysicalPortServiceCapWdmRxChannel FspR7ChannelIdentifierCaps,
    changePhysicalPortServiceCapCodeGain FspR7CodeGainCaps,
    changePhysicalPortServiceCapXfpDecisionThres FspR7XfpDecisionThresCaps,
    changePhysicalPortServiceCapDisparityCorrection EnableStateCaps,
    changePhysicalPortServiceCapEqlzAdmin FspR7EnableDisableCaps,
    changePhysicalPortServiceCapErrorForwarding FspR7ErrorFwdModeCaps,
    changePhysicalPortServiceCapFecType FspR7FecTypeCaps,
    changePhysicalPortServiceCapFarEndCommunication FspR7YesNoCaps,
    changePhysicalPortServiceCapFlowControl FspR7FlowControlModeCaps,
    changePhysicalPortServiceCapLaneChannelSetting FspR7ChannelIdentifierCaps,
    changePhysicalPortServiceCapLaserDelayTimer FspR7LaserDelayTimerCaps,
    changePhysicalPortServiceCapLaserOffTimer FspR7Unsigned32Caps,
    changePhysicalPortServiceCapLaserOnTimer FspR7Unsigned32Caps,
    changePhysicalPortServiceCapLaserOffDelayFunction EnableStateCaps,
    changePhysicalPortServiceCapAutoPTassignment FspR7ManualAutoCaps,
    changePhysicalPortServiceCapTributarySlotMethod FspR7ManualAutoCaps,
    changePhysicalPortServiceCapOpticalSetPoint FspR7Integer32Caps,
    changePhysicalPortServiceCapOpuPayloadType FspR7OpuPayloadTypeCaps,
    changePhysicalPortServiceCapSigDegThresSonetLine FspR7BERThresholdCaps,
    changePhysicalPortServiceCapSigDegThresSdhMs FspR7Unsigned32Caps,
    changePhysicalPortServiceCapSigDegThresOtu FspR7Integer32Caps,
    changePhysicalPortServiceCapSigDegThresOdu FspR7Integer32Caps,
    changePhysicalPortServiceCapSigDegThreshold FspR7Unsigned32Caps,
    changePhysicalPortServiceCapSigDegPcslThreshold FspR7Unsigned32Caps,
    changePhysicalPortServiceCapSigDegThresSonetSection FspR7BERThresholdCaps,
    changePhysicalPortServiceCapSigDegThresSdhSection FspR7Unsigned32Caps,
    changePhysicalPortServiceCapSigDegThresOduTcmA FspR7Integer32Caps,
    changePhysicalPortServiceCapSigDegThresOduTcmB FspR7Integer32Caps,
    changePhysicalPortServiceCapSigDegThresOduTcmC FspR7Integer32Caps,
    changePhysicalPortServiceCapSignalDegradePeriod FspR7Unsigned32Caps,
    changePhysicalPortServiceCapSigDegPeriodOdu FspR7Unsigned32Caps,
    changePhysicalPortServiceCapSigDegPeriodOtu FspR7Unsigned32Caps,
    changePhysicalPortServiceCapSigDegPeriodIntegration FspR7Unsigned32Caps,
    changePhysicalPortServiceCapSigDegPeriodSdhSection FspR7Unsigned32Caps,
    changePhysicalPortServiceCapSigDegPeriodOduTcmA FspR7Unsigned32Caps,
    changePhysicalPortServiceCapSigDegPeriodOduTcmB FspR7Unsigned32Caps,
    changePhysicalPortServiceCapSigDegPeriodOduTcmC FspR7Unsigned32Caps,
    changePhysicalPortServiceCapOtnStuffing FspR7YesNoCaps,
    changePhysicalPortServiceCapTcmALevel OtnTcmLevelCaps,
    changePhysicalPortServiceCapTcmBLevel OtnTcmLevelCaps,
    changePhysicalPortServiceCapTcmCLevel OtnTcmLevelCaps,
    changePhysicalPortServiceCapTerminationLevel OhTerminationLevelCaps,
    changePhysicalPortServiceCapTimingSource SonetTimingSourceCaps,
    changePhysicalPortServiceCapTimModeOdu TimModeCaps,
    changePhysicalPortServiceCapTimModeOtu TimModeCaps,
    changePhysicalPortServiceCapTimModeSonetSection TimModeCaps,
    changePhysicalPortServiceCapTimModeOduTcmA TimModeCaps,
    changePhysicalPortServiceCapTimModeOduTcmB TimModeCaps,
    changePhysicalPortServiceCapTimModeOduTcmC TimModeCaps,
    changePhysicalPortServiceCapTraceFormSonetSection SonetTraceFormCaps,
    changePhysicalPortServiceCapTraceExpectedSonetSection Integer32,
    changePhysicalPortServiceCapTraceTransmitSonetSection Integer32,
    changePhysicalPortServiceCapTraceExpectedOtu Integer32,
    changePhysicalPortServiceCapTraceTransmitSapiOtu Integer32,
    changePhysicalPortServiceCapTraceTransmitDapiOtu Integer32,
    changePhysicalPortServiceCapTraceTransmitOpspOtu Integer32,
    changePhysicalPortServiceCapTraceExpectedOdu Integer32,
    changePhysicalPortServiceCapTraceTransmitSapiOdu Integer32,
    changePhysicalPortServiceCapTraceTransmitDapiOdu Integer32,
    changePhysicalPortServiceCapTraceTransmitOpspOdu Integer32,
    changePhysicalPortServiceCapTraceExpectedOduTcmA Integer32,
    changePhysicalPortServiceCapTraceTransmitSapiOduTcmA Integer32,
    changePhysicalPortServiceCapTraceTransmitDapiOduTcmA Integer32,
    changePhysicalPortServiceCapTraceTransmitOpspOduTcmA Integer32,
    changePhysicalPortServiceCapTraceExpectedOduTcmB Integer32,
    changePhysicalPortServiceCapTraceTransmitSapiOduTcmB Integer32,
    changePhysicalPortServiceCapTraceTransmitDapiOduTcmB Integer32,
    changePhysicalPortServiceCapTraceTransmitOpspOduTcmB Integer32,
    changePhysicalPortServiceCapTraceExpectedOduTcmC Integer32,
    changePhysicalPortServiceCapTraceTransmitSapiOduTcmC Integer32,
    changePhysicalPortServiceCapTraceTransmitDapiOduTcmC Integer32,
    changePhysicalPortServiceCapTraceTransmitOpspOduTcmC Integer32,
    changePhysicalPortServiceCapTxOffDelay FspR7EnableDisableCaps,
    changePhysicalPortServiceCapVoaMode FspR7VoaModeCaps,
    changePhysicalPortServiceCapVoaSetpoint FspR7Unsigned32Caps,
    changePhysicalPortServiceCapTxOffOnTm FspR7TxOffOnTmCaps,
    changePhysicalPortServiceCapTxOffTimer FspR7Unsigned32Caps,
    changePhysicalPortServiceCapTxOnTimer FspR7Unsigned32Caps,
    changePhysicalPortServiceCapMode FspR7TransmissionModeCaps,
    changePhysicalPortServiceCapMonLevel FspR7MonLevelCaps,
    changePhysicalPortServiceCapOptimize FspR7OptimizeCaps,
    changePhysicalPortServiceCapLinkSetup FspR7DisableEnableCaps,
    changePhysicalPortServiceCapChannelSpacing FspR7ChannelSpacingCaps }

changePhysicalPortServiceCapRowStatus OBJECT-TYPE
    SYNTAX        FspR7RowStatusCaps
    MAX-ACCESS    read-only
    STATUS        current
    DESCRIPTION   "RowStatus object is used to create or delete a row in the table."
    ::= { changePhysicalPortServiceCapEntry 1 }

changePhysicalPortServiceCapType OBJECT-TYPE
    SYNTAX        FspR7InterfaceTypeCaps
    MAX-ACCESS    read-only
    STATUS        current
    DESCRIPTION   "The TYPE defines the transport service type as wrapper with wrapper layer termination OR else as payload"
    ::= { changePhysicalPortServiceCapEntry 2 }

changePhysicalPortServiceCapAdmin OBJECT-TYPE
    SYNTAX        FspR7AdminStateCaps
    MAX-ACCESS    read-only
    STATUS        current
    DESCRIPTION   "Administrative State is displayed in the GUI and Craft. Transition to Unassigend requires the entity to be deleted."
    ::= { changePhysicalPortServiceCapEntry 3 }

changePhysicalPortServiceCapAlias OBJECT-TYPE
    SYNTAX        Integer32
    MAX-ACCESS    read-only
    STATUS        current
    DESCRIPTION   "User Applied Descriptor"
    ::= { changePhysicalPortServiceCapEntry 4 }

changePhysicalPortServiceCapAlsMode OBJECT-TYPE
    SYNTAX        FspR7AlsModeCaps
    MAX-ACCESS    read-only
    STATUS        current
    DESCRIPTION   "Determines the reaction in backward direction in response to a LOS
        on the same Interface: on a Network Interface connected to the DWDM
        this is a matter of laser safety"
    ::= { changePhysicalPortServiceCapEntry 5 }

changePhysicalPortServiceCapBehaviour OBJECT-TYPE
    SYNTAX        FspR7PortBehaviourCaps
    MAX-ACCESS    read-only
    STATUS        current
    DESCRIPTION   "Behavior or Port usage based on configuration/usage in the system regardless of faceplate designation"
    ::= { changePhysicalPortServiceCapEntry 6 }

changePhysicalPortServiceCapDispersionSetting OBJECT-TYPE
    SYNTAX        FspR7Integer32Caps
    UNITS         "ps/nm"
    MAX-ACCESS    read-only
    STATUS        current
    DESCRIPTION   "Chromatic Dispersion Compensation setting on module"
    ::= { changePhysicalPortServiceCapEntry 7 }

changePhysicalPortServiceCapDispersionMode OBJECT-TYPE
    SYNTAX        FspR7DispersionModesCaps
    MAX-ACCESS    read-only
    STATUS        current
    DESCRIPTION   "Chromatic Dispersion Compensation Mode"
    ::= { changePhysicalPortServiceCapEntry 8 }

changePhysicalPortServiceCapChannelProv OBJECT-TYPE
    SYNTAX        FspR7ChannelIdentifierCaps
    MAX-ACCESS    read-only
    STATUS        current
    DESCRIPTION   "Channel"
    ::= { changePhysicalPortServiceCapEntry 9 }

changePhysicalPortServiceCapWdmRxChannel OBJECT-TYPE
    SYNTAX        FspR7ChannelIdentifierCaps
    MAX-ACCESS    read-only
    STATUS        current
    DESCRIPTION   "Channel Number for the Receive Interface"
    ::= { changePhysicalPortServiceCapEntry 10 }

changePhysicalPortServiceCapCodeGain OBJECT-TYPE
    SYNTAX        FspR7CodeGainCaps
    MAX-ACCESS    read-only
    STATUS        current
    DESCRIPTION   "Forward Error Correction Coding gain"
    ::= { changePhysicalPortServiceCapEntry 11 }

changePhysicalPortServiceCapXfpDecisionThres OBJECT-TYPE
    SYNTAX        FspR7XfpDecisionThresCaps
    MAX-ACCESS    read-only
    STATUS        current
    DESCRIPTION   "XFP Decision threshold setting"
    ::= { changePhysicalPortServiceCapEntry 12 }

changePhysicalPortServiceCapDisparityCorrection OBJECT-TYPE
    SYNTAX        EnableStateCaps
    MAX-ACCESS    read-only
    STATUS        current
    DESCRIPTION   "Disparity correction"
    ::= { changePhysicalPortServiceCapEntry 13 }

changePhysicalPortServiceCapEqlzAdmin OBJECT-TYPE
    SYNTAX        FspR7EnableDisableCaps
    MAX-ACCESS    read-only
    STATUS        current
    DESCRIPTION   "Scheduled Equalization Administration"
    ::= { changePhysicalPortServiceCapEntry 14 }

changePhysicalPortServiceCapErrorForwarding OBJECT-TYPE
    SYNTAX        FspR7ErrorFwdModeCaps
    MAX-ACCESS    read-only
    STATUS        current
    DESCRIPTION   "Determines the reaction in forward direction in response to a LOS on
        the interface on the opposite side of the module: may override
        this behaviour in the interests of laser safety."
    ::= { changePhysicalPortServiceCapEntry 15 }

changePhysicalPortServiceCapFecType OBJECT-TYPE
    SYNTAX        FspR7FecTypeCaps
    MAX-ACCESS    read-only
    STATUS        current
    DESCRIPTION   "Forward Error Correction (Only relevant where TYPE = OTU#)"
    ::= { changePhysicalPortServiceCapEntry 16 }

changePhysicalPortServiceCapFarEndCommunication OBJECT-TYPE
    SYNTAX        FspR7YesNoCaps
    MAX-ACCESS    read-only
    STATUS        current
    DESCRIPTION   "Used for Optojack plugs; Communication to Far End Plug is observed"
    ::= { changePhysicalPortServiceCapEntry 17 }

changePhysicalPortServiceCapFlowControl OBJECT-TYPE
    SYNTAX        FspR7FlowControlModeCaps
    MAX-ACCESS    read-only
    STATUS        current
    DESCRIPTION   "Flow Control mechanism"
    ::= { changePhysicalPortServiceCapEntry 18 }

changePhysicalPortServiceCapLaneChannelSetting OBJECT-TYPE
    SYNTAX        FspR7ChannelIdentifierCaps
    MAX-ACCESS    read-only
    STATUS        current
    DESCRIPTION   "Lane Channel Setting"
    ::= { changePhysicalPortServiceCapEntry 19 }

changePhysicalPortServiceCapLaserDelayTimer OBJECT-TYPE
    SYNTAX        FspR7LaserDelayTimerCaps
    MAX-ACCESS    read-only
    STATUS        current
    DESCRIPTION   "Relevant only when ERRFWD=LSROFF. Enables/disables the
        possibility to delay turning off and on the laser.
        This applies to the case when turning off the laser
        is done  as an error forwarding mechanism."
    ::= { changePhysicalPortServiceCapEntry 20 }

changePhysicalPortServiceCapLaserOffTimer OBJECT-TYPE
    SYNTAX        FspR7Unsigned32Caps
    UNITS         "ms"
    MAX-ACCESS    read-only
    STATUS        current
    DESCRIPTION   "Delay before laser is swiched off"
    ::= { changePhysicalPortServiceCapEntry 21 }

changePhysicalPortServiceCapLaserOnTimer OBJECT-TYPE
    SYNTAX        FspR7Unsigned32Caps
    UNITS         "ms"
    MAX-ACCESS    read-only
    STATUS        current
    DESCRIPTION   "Delay before laser is switched on"
    ::= { changePhysicalPortServiceCapEntry 22 }

changePhysicalPortServiceCapLaserOffDelayFunction OBJECT-TYPE
    SYNTAX        EnableStateCaps
    MAX-ACCESS    read-only
    STATUS        current
    DESCRIPTION   "A configuration request for the Laser Off Delay function. This function
        delays turning off the laser as a consequent action to a defect."
    ::= { changePhysicalPortServiceCapEntry 23 }

changePhysicalPortServiceCapAutoPTassignment OBJECT-TYPE
    SYNTAX        FspR7ManualAutoCaps
    MAX-ACCESS    read-only
    STATUS        current
    DESCRIPTION   "Auto assignment of ODU PT"
    ::= { changePhysicalPortServiceCapEntry 24 }

changePhysicalPortServiceCapTributarySlotMethod OBJECT-TYPE
    SYNTAX        FspR7ManualAutoCaps
    MAX-ACCESS    read-only
    STATUS        current
    DESCRIPTION   "Tributary Slot assignment method"
    ::= { changePhysicalPortServiceCapEntry 25 }

changePhysicalPortServiceCapOpticalSetPoint OBJECT-TYPE
    SYNTAX        FspR7Integer32Caps
    UNITS         "0.1 dBm"
    MAX-ACCESS    read-only
    STATUS        current
    DESCRIPTION   "Sets the optical power for power equalization in ROADM or for channel power control in OPCM"
    ::= { changePhysicalPortServiceCapEntry 26 }

changePhysicalPortServiceCapOpuPayloadType OBJECT-TYPE
    SYNTAX        FspR7OpuPayloadTypeCaps
    MAX-ACCESS    read-only
    STATUS        current
    DESCRIPTION   "OPU Payload Type Indicator"
    ::= { changePhysicalPortServiceCapEntry 27 }

changePhysicalPortServiceCapSigDegThresSonetLine OBJECT-TYPE
    SYNTAX        FspR7BERThresholdCaps
    MAX-ACCESS    read-only
    STATUS        current
    DESCRIPTION   "Bit-Error-Based Degradation Definition for SONET (standard integration period)"
    ::= { changePhysicalPortServiceCapEntry 28 }

changePhysicalPortServiceCapSigDegThresSdhMs OBJECT-TYPE
    SYNTAX        FspR7Unsigned32Caps
    UNITS         "%"
    MAX-ACCESS    read-only
    STATUS        current
    DESCRIPTION   "Block-Error-Based Degradation Definition for SDH (standard integration period).
        Defined as percentage Background Block Errors (30% default) evaluated
        over a defined period (SDPER-RS)."
    ::= { changePhysicalPortServiceCapEntry 29 }

changePhysicalPortServiceCapSigDegThresOtu OBJECT-TYPE
    SYNTAX        FspR7Integer32Caps
    UNITS         "%"
    MAX-ACCESS    read-only
    STATUS        current
    DESCRIPTION   "Background-Block-Error-Based Signal Degradation Definition for OTU"
    ::= { changePhysicalPortServiceCapEntry 30 }

changePhysicalPortServiceCapSigDegThresOdu OBJECT-TYPE
    SYNTAX        FspR7Integer32Caps
    UNITS         "%"
    MAX-ACCESS    read-only
    STATUS        current
    DESCRIPTION   "Background-Block-Error-Based Signal Degradation Definition for ODU"
    ::= { changePhysicalPortServiceCapEntry 31 }

changePhysicalPortServiceCapSigDegThreshold OBJECT-TYPE
    SYNTAX        FspR7Unsigned32Caps
    MAX-ACCESS    read-only
    STATUS        current
    DESCRIPTION   "Threshold for number of errors (CV or CV+DE) in one second"
    ::= { changePhysicalPortServiceCapEntry 32 }

changePhysicalPortServiceCapSigDegPcslThreshold OBJECT-TYPE
    SYNTAX        FspR7Unsigned32Caps
    UNITS         "%"
    MAX-ACCESS    read-only
    STATUS        current
    DESCRIPTION   "Block-Error-Based Degradation Definition for Physical Coding Sublayer"
    ::= { changePhysicalPortServiceCapEntry 33 }

changePhysicalPortServiceCapSigDegThresSonetSection OBJECT-TYPE
    SYNTAX        FspR7BERThresholdCaps
    MAX-ACCESS    read-only
    STATUS        current
    DESCRIPTION   "Bit-Error-Based Degradation Definition for SONET (standard integration period)"
    ::= { changePhysicalPortServiceCapEntry 34 }

changePhysicalPortServiceCapSigDegThresSdhSection OBJECT-TYPE
    SYNTAX        FspR7Unsigned32Caps
    UNITS         "%"
    MAX-ACCESS    read-only
    STATUS        current
    DESCRIPTION   "Block-Error-Based Degradation Definition for SDH (standard integration period).
        Defined as percentage Background Block Errors (30% default) evaluated
        over a defined period (SDPER-RS)."
    ::= { changePhysicalPortServiceCapEntry 35 }

changePhysicalPortServiceCapSigDegThresOduTcmA OBJECT-TYPE
    SYNTAX        FspR7Integer32Caps
    UNITS         "%"
    MAX-ACCESS    read-only
    STATUS        current
    DESCRIPTION   "Background-Block-Error-Based Signal Degradation Definition for TCM-A"
    ::= { changePhysicalPortServiceCapEntry 36 }

changePhysicalPortServiceCapSigDegThresOduTcmB OBJECT-TYPE
    SYNTAX        FspR7Integer32Caps
    UNITS         "%"
    MAX-ACCESS    read-only
    STATUS        current
    DESCRIPTION   "Background-Block-Error-Based Signal Degradation Definition for TCM-B"
    ::= { changePhysicalPortServiceCapEntry 37 }

changePhysicalPortServiceCapSigDegThresOduTcmC OBJECT-TYPE
    SYNTAX        FspR7Integer32Caps
    UNITS         "%"
    MAX-ACCESS    read-only
    STATUS        current
    DESCRIPTION   "Background-Block-Error-Based Signal Degradation Definition for TCM-C"
    ::= { changePhysicalPortServiceCapEntry 38 }

changePhysicalPortServiceCapSignalDegradePeriod OBJECT-TYPE
    SYNTAX        FspR7Unsigned32Caps
    UNITS         "s"
    MAX-ACCESS    read-only
    STATUS        current
    DESCRIPTION   "The measurement period in seconds used together with
        the deployProvIfSigDegThresSdhRegSect based on the block error counting method.
        The valid range is 2..10,
        The default being 7."
    ::= { changePhysicalPortServiceCapEntry 39 }

changePhysicalPortServiceCapSigDegPeriodOdu OBJECT-TYPE
    SYNTAX        FspR7Unsigned32Caps
    UNITS         "s"
    MAX-ACCESS    read-only
    STATUS        current
    DESCRIPTION   "Integration Period for Signal degrade"
    ::= { changePhysicalPortServiceCapEntry 40 }

changePhysicalPortServiceCapSigDegPeriodOtu OBJECT-TYPE
    SYNTAX        FspR7Unsigned32Caps
    UNITS         "s"
    MAX-ACCESS    read-only
    STATUS        current
    DESCRIPTION   "Integration Period for Signal degrade"
    ::= { changePhysicalPortServiceCapEntry 41 }

changePhysicalPortServiceCapSigDegPeriodIntegration OBJECT-TYPE
    SYNTAX        FspR7Unsigned32Caps
    UNITS         "s"
    MAX-ACCESS    read-only
    STATUS        current
    DESCRIPTION   "Integration Period for Signal degrade"
    ::= { changePhysicalPortServiceCapEntry 42 }

changePhysicalPortServiceCapSigDegPeriodSdhSection OBJECT-TYPE
    SYNTAX        FspR7Unsigned32Caps
    UNITS         "s"
    MAX-ACCESS    read-only
    STATUS        current
    DESCRIPTION   "Provisionable Signal Degrade Integration Period for SDH"
    ::= { changePhysicalPortServiceCapEntry 43 }

changePhysicalPortServiceCapSigDegPeriodOduTcmA OBJECT-TYPE
    SYNTAX        FspR7Unsigned32Caps
    UNITS         "s"
    MAX-ACCESS    read-only
    STATUS        current
    DESCRIPTION   "Integration Period for Signal degrade"
    ::= { changePhysicalPortServiceCapEntry 44 }

changePhysicalPortServiceCapSigDegPeriodOduTcmB OBJECT-TYPE
    SYNTAX        FspR7Unsigned32Caps
    UNITS         "s"
    MAX-ACCESS    read-only
    STATUS        current
    DESCRIPTION   "Integration Period of TCMB Signal Segrade"
    ::= { changePhysicalPortServiceCapEntry 45 }

changePhysicalPortServiceCapSigDegPeriodOduTcmC OBJECT-TYPE
    SYNTAX        FspR7Unsigned32Caps
    UNITS         "s"
    MAX-ACCESS    read-only
    STATUS        current
    DESCRIPTION   "Integration Period of TCMC Signal Segrade"
    ::= { changePhysicalPortServiceCapEntry 46 }

changePhysicalPortServiceCapOtnStuffing OBJECT-TYPE
    SYNTAX        FspR7YesNoCaps
    MAX-ACCESS    read-only
    STATUS        current
    DESCRIPTION   "Indicates if bit/byte stuffing is used in the transport signal."
    ::= { changePhysicalPortServiceCapEntry 47 }

changePhysicalPortServiceCapTcmALevel OBJECT-TYPE
    SYNTAX        OtnTcmLevelCaps
    MAX-ACCESS    read-only
    STATUS        current
    DESCRIPTION   "Activation of Tandem Connection Monitoring Instance A"
    ::= { changePhysicalPortServiceCapEntry 48 }

changePhysicalPortServiceCapTcmBLevel OBJECT-TYPE
    SYNTAX        OtnTcmLevelCaps
    MAX-ACCESS    read-only
    STATUS        current
    DESCRIPTION   "Activation of Tandem Connection Monitoring Instance B"
    ::= { changePhysicalPortServiceCapEntry 49 }

changePhysicalPortServiceCapTcmCLevel OBJECT-TYPE
    SYNTAX        OtnTcmLevelCaps
    MAX-ACCESS    read-only
    STATUS        current
    DESCRIPTION   "Activation of Tandem Connection Monitoring Instance C"
    ::= { changePhysicalPortServiceCapEntry 50 }

changePhysicalPortServiceCapTerminationLevel OBJECT-TYPE
    SYNTAX        OhTerminationLevelCaps
    MAX-ACCESS    read-only
    STATUS        current
    DESCRIPTION   "Highest signal level hardware removes then generates for transmission."
    ::= { changePhysicalPortServiceCapEntry 51 }

changePhysicalPortServiceCapTimingSource OBJECT-TYPE
    SYNTAX        SonetTimingSourceCaps
    MAX-ACCESS    read-only
    STATUS        current
    DESCRIPTION   "The timing source for this interface.
        - internal: used in stand-alone, point-to-point topologies stand-alone (dedicated fiber operation).
        - loopTiming: e.g. used in point-to-point via SONET network and feeder topologies. The default is
        internal(1)."
    ::= { changePhysicalPortServiceCapEntry 52 }

changePhysicalPortServiceCapTimModeOdu OBJECT-TYPE
    SYNTAX        TimModeCaps
    MAX-ACCESS    read-only
    STATUS        current
    DESCRIPTION   "Detection of TIM-ODU Condition can be configured"
    ::= { changePhysicalPortServiceCapEntry 53 }

changePhysicalPortServiceCapTimModeOtu OBJECT-TYPE
    SYNTAX        TimModeCaps
    MAX-ACCESS    read-only
    STATUS        current
    DESCRIPTION   "OTU Trace Identifier Mismatch (TIM) detection/action for TIM defect."
    ::= { changePhysicalPortServiceCapEntry 54 }

changePhysicalPortServiceCapTimModeSonetSection OBJECT-TYPE
    SYNTAX        TimModeCaps
    MAX-ACCESS    read-only
    STATUS        current
    DESCRIPTION   "SONET Section  Trace Identifier Mismatch (TIM) detection/action for TIM defect."
    ::= { changePhysicalPortServiceCapEntry 55 }

changePhysicalPortServiceCapTimModeOduTcmA OBJECT-TYPE
    SYNTAX        TimModeCaps
    MAX-ACCESS    read-only
    STATUS        current
    DESCRIPTION   "TCM_A Trace Identifier Mismatch (TIM) detection/action for TIM defect."
    ::= { changePhysicalPortServiceCapEntry 56 }

changePhysicalPortServiceCapTimModeOduTcmB OBJECT-TYPE
    SYNTAX        TimModeCaps
    MAX-ACCESS    read-only
    STATUS        current
    DESCRIPTION   "TCM_B Trace Identifier Mismatch (TIM) detection/action for TIM defect."
    ::= { changePhysicalPortServiceCapEntry 57 }

changePhysicalPortServiceCapTimModeOduTcmC OBJECT-TYPE
    SYNTAX        TimModeCaps
    MAX-ACCESS    read-only
    STATUS        current
    DESCRIPTION   "TCM_C Trace Identifier Mismatch (TIM) detection/action for TIM defect."
    ::= { changePhysicalPortServiceCapEntry 58 }

changePhysicalPortServiceCapTraceFormSonetSection OBJECT-TYPE
    SYNTAX        SonetTraceFormCaps
    MAX-ACCESS    read-only
    STATUS        current
    DESCRIPTION   "Byte-Length of Trace Compared to Expected"
    ::= { changePhysicalPortServiceCapEntry 59 }

changePhysicalPortServiceCapTraceExpectedSonetSection OBJECT-TYPE
    SYNTAX        Integer32
    MAX-ACCESS    read-only
    STATUS        current
    DESCRIPTION   "Expected Sec/RS trace. NULL TRACE implies that no trace comparison is made."
    ::= { changePhysicalPortServiceCapEntry 60 }

changePhysicalPortServiceCapTraceTransmitSonetSection OBJECT-TYPE
    SYNTAX        Integer32
    MAX-ACCESS    read-only
    STATUS        current
    DESCRIPTION   "Sec/RS Trace to be Transmitted"
    ::= { changePhysicalPortServiceCapEntry 61 }

changePhysicalPortServiceCapTraceExpectedOtu OBJECT-TYPE
    SYNTAX        Integer32
    MAX-ACCESS    read-only
    STATUS        current
    DESCRIPTION   "Expected SAPI part of the OTU trace (15 character). NULL TRACE implies that no trace comparison is made."
    ::= { changePhysicalPortServiceCapEntry 62 }

changePhysicalPortServiceCapTraceTransmitSapiOtu OBJECT-TYPE
    SYNTAX        Integer32
    MAX-ACCESS    read-only
    STATUS        current
    DESCRIPTION   "The transmitted SAPI part of the OTU trace (15 character)"
    ::= { changePhysicalPortServiceCapEntry 63 }

changePhysicalPortServiceCapTraceTransmitDapiOtu OBJECT-TYPE
    SYNTAX        Integer32
    MAX-ACCESS    read-only
    STATUS        current
    DESCRIPTION   "The transmitted DAPI part of the OTU trace (15 character)"
    ::= { changePhysicalPortServiceCapEntry 64 }

changePhysicalPortServiceCapTraceTransmitOpspOtu OBJECT-TYPE
    SYNTAX        Integer32
    MAX-ACCESS    read-only
    STATUS        current
    DESCRIPTION   "The transmitted Operator Specific part of the OTU trace (32 character)"
    ::= { changePhysicalPortServiceCapEntry 65 }

changePhysicalPortServiceCapTraceExpectedOdu OBJECT-TYPE
    SYNTAX        Integer32
    MAX-ACCESS    read-only
    STATUS        current
    DESCRIPTION   "Expected SAPI part of the ODU trace (15 character). NULL TRACE implies that no trace comparison is made."
    ::= { changePhysicalPortServiceCapEntry 66 }

changePhysicalPortServiceCapTraceTransmitSapiOdu OBJECT-TYPE
    SYNTAX        Integer32
    MAX-ACCESS    read-only
    STATUS        current
    DESCRIPTION   "The transmitted SAPI part of the ODU trace (15 character)"
    ::= { changePhysicalPortServiceCapEntry 67 }

changePhysicalPortServiceCapTraceTransmitDapiOdu OBJECT-TYPE
    SYNTAX        Integer32
    MAX-ACCESS    read-only
    STATUS        current
    DESCRIPTION   "The transmitted DAPI part of the ODU trace (15 character)"
    ::= { changePhysicalPortServiceCapEntry 68 }

changePhysicalPortServiceCapTraceTransmitOpspOdu OBJECT-TYPE
    SYNTAX        Integer32
    MAX-ACCESS    read-only
    STATUS        current
    DESCRIPTION   "The transmitted Operator Specific part of the ODU trace (32 character)"
    ::= { changePhysicalPortServiceCapEntry 69 }

changePhysicalPortServiceCapTraceExpectedOduTcmA OBJECT-TYPE
    SYNTAX        Integer32
    MAX-ACCESS    read-only
    STATUS        current
    DESCRIPTION   "Expected SAPI part of the TCMA trace (15 character). NULL TRACE-TCM implies that no trace comparison is made."
    ::= { changePhysicalPortServiceCapEntry 70 }

changePhysicalPortServiceCapTraceTransmitSapiOduTcmA OBJECT-TYPE
    SYNTAX        Integer32
    MAX-ACCESS    read-only
    STATUS        current
    DESCRIPTION   "The transmitted SAPI part of the TCMA trace (15 character)"
    ::= { changePhysicalPortServiceCapEntry 71 }

changePhysicalPortServiceCapTraceTransmitDapiOduTcmA OBJECT-TYPE
    SYNTAX        Integer32
    MAX-ACCESS    read-only
    STATUS        current
    DESCRIPTION   "The transmitted DAPI part of the TCMA trace (15 character)"
    ::= { changePhysicalPortServiceCapEntry 72 }

changePhysicalPortServiceCapTraceTransmitOpspOduTcmA OBJECT-TYPE
    SYNTAX        Integer32
    MAX-ACCESS    read-only
    STATUS        current
    DESCRIPTION   "The transmitted Operator Specific part of the TCMA trace (32 character)"
    ::= { changePhysicalPortServiceCapEntry 73 }

changePhysicalPortServiceCapTraceExpectedOduTcmB OBJECT-TYPE
    SYNTAX        Integer32
    MAX-ACCESS    read-only
    STATUS        current
    DESCRIPTION   "Expected SAPI part of the TCMB trace (15 character). NULL TRACE-TCM implies that no trace comparison is made."
    ::= { changePhysicalPortServiceCapEntry 74 }

changePhysicalPortServiceCapTraceTransmitSapiOduTcmB OBJECT-TYPE
    SYNTAX        Integer32
    MAX-ACCESS    read-only
    STATUS        current
    DESCRIPTION   "The transmitted SAPI part of the TCMB trace (15 character)"
    ::= { changePhysicalPortServiceCapEntry 75 }

changePhysicalPortServiceCapTraceTransmitDapiOduTcmB OBJECT-TYPE
    SYNTAX        Integer32
    MAX-ACCESS    read-only
    STATUS        current
    DESCRIPTION   "The transmitted DAPI part of the TCMB trace (15 character)"
    ::= { changePhysicalPortServiceCapEntry 76 }

changePhysicalPortServiceCapTraceTransmitOpspOduTcmB OBJECT-TYPE
    SYNTAX        Integer32
    MAX-ACCESS    read-only
    STATUS        current
    DESCRIPTION   "The transmitted Operator Specific part of the TCMB trace (32 character)"
    ::= { changePhysicalPortServiceCapEntry 77 }

changePhysicalPortServiceCapTraceExpectedOduTcmC OBJECT-TYPE
    SYNTAX        Integer32
    MAX-ACCESS    read-only
    STATUS        current
    DESCRIPTION   "Expected SAPI part of the TCMC trace (15 character). NULL TRACE-TCM implies that no trace comparison is made."
    ::= { changePhysicalPortServiceCapEntry 78 }

changePhysicalPortServiceCapTraceTransmitSapiOduTcmC OBJECT-TYPE
    SYNTAX        Integer32
    MAX-ACCESS    read-only
    STATUS        current
    DESCRIPTION   "The transmitted SAPI part of the TCMC trace (15 character)"
    ::= { changePhysicalPortServiceCapEntry 79 }

changePhysicalPortServiceCapTraceTransmitDapiOduTcmC OBJECT-TYPE
    SYNTAX        Integer32
    MAX-ACCESS    read-only
    STATUS        current
    DESCRIPTION   "The transmitted DAPI part of the TCMC trace (15 character)"
    ::= { changePhysicalPortServiceCapEntry 80 }

changePhysicalPortServiceCapTraceTransmitOpspOduTcmC OBJECT-TYPE
    SYNTAX        Integer32
    MAX-ACCESS    read-only
    STATUS        current
    DESCRIPTION   "The transmitted Operator Specific part of the TCMC trace (32 character)"
    ::= { changePhysicalPortServiceCapEntry 81 }

changePhysicalPortServiceCapTxOffDelay OBJECT-TYPE
    SYNTAX        FspR7EnableDisableCaps
    MAX-ACCESS    read-only
    STATUS        current
    DESCRIPTION   "Enable or disable TXOFFHOLD Period for Error Forwarding and LKDO-OFF Consequent Action."
    ::= { changePhysicalPortServiceCapEntry 82 }

changePhysicalPortServiceCapVoaMode OBJECT-TYPE
    SYNTAX        FspR7VoaModeCaps
    MAX-ACCESS    read-only
    STATUS        current
    DESCRIPTION   "VOA operating mode"
    ::= { changePhysicalPortServiceCapEntry 83 }

changePhysicalPortServiceCapVoaSetpoint OBJECT-TYPE
    SYNTAX        FspR7Unsigned32Caps
    UNITS         "0.1 dB"
    MAX-ACCESS    read-only
    STATUS        current
    DESCRIPTION   "Sets the optical attenuation of VOA"
    ::= { changePhysicalPortServiceCapEntry 84 }

changePhysicalPortServiceCapTxOffOnTm OBJECT-TYPE
    SYNTAX        FspR7TxOffOnTmCaps
    MAX-ACCESS    read-only
    STATUS        current
    DESCRIPTION   "Relevant only when ERRFWD=TXOFF. Enables/disables the
        possibility to delay turning off and on the the transmitter.
        This applies to the case when turning off the transmitter
        is done  as an error forwarding mechanism."
    ::= { changePhysicalPortServiceCapEntry 85 }

changePhysicalPortServiceCapTxOffTimer OBJECT-TYPE
    SYNTAX        FspR7Unsigned32Caps
    UNITS         "ms"
    MAX-ACCESS    read-only
    STATUS        current
    DESCRIPTION   "Delay before transmitter is swiched off"
    ::= { changePhysicalPortServiceCapEntry 86 }

changePhysicalPortServiceCapTxOnTimer OBJECT-TYPE
    SYNTAX        FspR7Unsigned32Caps
    UNITS         "ms"
    MAX-ACCESS    read-only
    STATUS        current
    DESCRIPTION   "Delay before transmitter is switched on"
    ::= { changePhysicalPortServiceCapEntry 87 }

changePhysicalPortServiceCapMode OBJECT-TYPE
    SYNTAX        FspR7TransmissionModeCaps
    MAX-ACCESS    read-only
    STATUS        current
    DESCRIPTION   "Mode of the module, determine operation or functionality"
    ::= { changePhysicalPortServiceCapEntry 88 }

changePhysicalPortServiceCapMonLevel OBJECT-TYPE
    SYNTAX        FspR7MonLevelCaps
    MAX-ACCESS    read-only
    STATUS        current
    DESCRIPTION   "Highest signal level of intrusive or non-intrusive monitoring. Hardware may monitor the signal one layer higher than Termination Level (TERM)."
    ::= { changePhysicalPortServiceCapEntry 89 }

changePhysicalPortServiceCapOptimize OBJECT-TYPE
    SYNTAX        FspR7OptimizeCaps
    MAX-ACCESS    read-only
    STATUS        current
    DESCRIPTION   "Optimizes port for either protection switch time or traffic regeneration operation"
    ::= { changePhysicalPortServiceCapEntry 90 }

changePhysicalPortServiceCapLinkSetup OBJECT-TYPE
    SYNTAX        FspR7DisableEnableCaps
    MAX-ACCESS    read-only
    STATUS        current
    DESCRIPTION   "Support RDMA over Converged Ethernet (RoCE)"
    ::= { changePhysicalPortServiceCapEntry 91 }

changePhysicalPortServiceCapChannelSpacing OBJECT-TYPE
    SYNTAX        FspR7ChannelSpacingCaps
    MAX-ACCESS    read-only
    STATUS        current
    DESCRIPTION   "ITU Grid channel spacing"
    ::= { changePhysicalPortServiceCapEntry 92 }

endOfChangePhysicalPortServiceCapTable OBJECT-TYPE
    SYNTAX        Integer32
    MAX-ACCESS    read-only
    STATUS        current
    DESCRIPTION   ""
    ::= { changeServiceCap 2 }

endOfChangeServiceCap OBJECT-TYPE
    SYNTAX        Integer32
    MAX-ACCESS    read-only
    STATUS        current
    DESCRIPTION   ""
    ::= { changeServiceCap 10000 }

ffpCapTable OBJECT-TYPE
    SYNTAX        SEQUENCE OF FfpCapEntry
    MAX-ACCESS    not-accessible
    STATUS        current
    DESCRIPTION   "FfpCapTable"
    ::= { protectionCap 2 }

ffpCapEntry OBJECT-TYPE
    SYNTAX        FfpCapEntry
    MAX-ACCESS    not-accessible
    STATUS        current
    DESCRIPTION   "Entry of FfpCapTable"
    INDEX       {
                  entityFfpShelfNo,
                  entityFfpSlotNo,
                  entityFfpPortNo,
                  entityFfpExtNo,
                  entityFfpClassName
                }
    ::= { ffpCapTable 1 }

FfpCapEntry ::= SEQUENCE
  {    ffpCapRowStatus FspR7RowStatusCaps,
    ffpCapCreationMethod FfpTypeCaps,
    ffpCapSDswitching EnableStateCaps,
    ffpCapHoldOffTime ApsHoldoffTimeCaps,
    ffpCapProtectionMech ProtectionMechCaps,
    ffpCapWorkingAid SnmpAdminString,
    ffpCapProtectionAid SnmpAdminString,
    ffpCapSignalDegradeSwitching EnableStateCaps,
    ffpCapFarEndIp FspR7YesNo,
    ffpCapPeerAid SnmpAdminString,
    ffpCapApsType ApsTypeCaps,
    ffpCapRevertMode ApsRevertModeCaps,
    ffpCapWaitToRestore FspR7Unsigned32Caps,
    ffpCapDirection ApsDirectionCaps,
    ffpCapApsFarEndModule FspR7ApsFarEndModuleCaps }

ffpCapRowStatus OBJECT-TYPE
    SYNTAX        FspR7RowStatusCaps
    MAX-ACCESS    read-only
    STATUS        current
    DESCRIPTION   "RowStatus"
    ::= { ffpCapEntry 1 }

ffpCapCreationMethod OBJECT-TYPE
    SYNTAX        FfpTypeCaps
    MAX-ACCESS    read-only
    STATUS        current
    DESCRIPTION   "Type of protection (normal/forced)"
    ::= { ffpCapEntry 2 }

ffpCapSDswitching OBJECT-TYPE
    SYNTAX        EnableStateCaps
    MAX-ACCESS    read-only
    STATUS        current
    DESCRIPTION   "This state controls whether the switch criteria for the APS group will
        include the Signal Degrade alarm."
    ::= { ffpCapEntry 3 }

ffpCapHoldOffTime OBJECT-TYPE
    SYNTAX        ApsHoldoffTimeCaps
    MAX-ACCESS    read-only
    STATUS        current
    DESCRIPTION   "This value controls the switch delay (0 to 10 seconds in
        100ms steps) for the protection group. Changing the hold-off
        time when the timer is active will not affect the active
        timer. The change will take effect the next time the timer
        is active."
    ::= { ffpCapEntry 4 }

ffpCapProtectionMech OBJECT-TYPE
    SYNTAX        ProtectionMechCaps
    MAX-ACCESS    read-only
    STATUS        current
    DESCRIPTION   "The protection type of this protection group."
    ::= { ffpCapEntry 5 }

ffpCapWorkingAid OBJECT-TYPE
    SYNTAX        SnmpAdminString
    MAX-ACCESS    read-only
    STATUS        current
    DESCRIPTION   "AID of working port involved in the protection group."
    ::= { ffpCapEntry 6 }

ffpCapProtectionAid OBJECT-TYPE
    SYNTAX        SnmpAdminString
    MAX-ACCESS    read-only
    STATUS        current
    DESCRIPTION   "(Protection AID) AID of protection entity involved in the protection group."
    ::= { ffpCapEntry 7 }

ffpCapSignalDegradeSwitching OBJECT-TYPE
    SYNTAX        EnableStateCaps
    MAX-ACCESS    read-only
    STATUS        current
    DESCRIPTION   "Switch Trigger Additionally on Signal Degrade Link Detection"
    ::= { ffpCapEntry 8 }

ffpCapFarEndIp OBJECT-TYPE
    SYNTAX        FspR7YesNo
    MAX-ACCESS    read-only
    STATUS        current
    DESCRIPTION   "IP Address assigned to PPP Termination Point on Far-End NE. Default
        is set by NE System on LINK establishment if FENDIPACPT = Y"
    ::= { ffpCapEntry 9 }

ffpCapPeerAid OBJECT-TYPE
    SYNTAX        SnmpAdminString
    MAX-ACCESS    read-only
    STATUS        current
    DESCRIPTION   "AID of Protection Partner involved in the protection group."
    ::= { ffpCapEntry 10 }

ffpCapApsType OBJECT-TYPE
    SYNTAX        ApsTypeCaps
    MAX-ACCESS    read-only
    STATUS        current
    DESCRIPTION   "The type of APS implemented in this protection group."
    ::= { ffpCapEntry 11 }

ffpCapRevertMode OBJECT-TYPE
    SYNTAX        ApsRevertModeCaps
    MAX-ACCESS    read-only
    STATUS        current
    DESCRIPTION   "Revertive Protection Switching"
    ::= { ffpCapEntry 12 }

ffpCapWaitToRestore OBJECT-TYPE
    SYNTAX        FspR7Unsigned32Caps
    UNITS         "min"
    MAX-ACCESS    read-only
    STATUS        current
    DESCRIPTION   "Wait to Restore Timer value"
    ::= { ffpCapEntry 13 }

ffpCapDirection OBJECT-TYPE
    SYNTAX        ApsDirectionCaps
    MAX-ACCESS    read-only
    STATUS        current
    DESCRIPTION   "Indicates whether the APS function is 'unidirectional' (single-ended)
        or 'bidirectional' (dual-ended)."
    ::= { ffpCapEntry 14 }

ffpCapApsFarEndModule OBJECT-TYPE
    SYNTAX        FspR7ApsFarEndModuleCaps
    MAX-ACCESS    read-only
    STATUS        current
    DESCRIPTION   "This value is the far end module type(10tcc10g or other)."
    ::= { ffpCapEntry 15 }

endOfFfpCapTable OBJECT-TYPE
    SYNTAX        Integer32
    MAX-ACCESS    read-only
    STATUS        current
    DESCRIPTION   ""
    ::= { protectionCap 3 }

endOfProtectionCap OBJECT-TYPE
    SYNTAX        Integer32
    MAX-ACCESS    read-only
    STATUS        current
    DESCRIPTION   ""
    ::= { protectionCap 10000 }


END
