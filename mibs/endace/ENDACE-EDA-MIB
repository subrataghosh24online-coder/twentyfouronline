-- This MIB defines the traps that are generated by the Endace EDA event
-- protocol.
-- 
-- 
-- LEGAL NOTICE:
-- This source code:
-- 
-- a) is a proprietary trade secret of Endace Technology Limited or any of
-- its related or affiliated companies, a New Zealand company, and its
-- suppliers and licensors ('Endace'). You must keep it strictly
-- confidential, and you must not copy, modify, disclose or distribute any
-- part of it to anyone else, without the prior written
-- authorisation of Endace Limited;
-- 
-- b) may also be part of inventions that are protected by patents and
-- patent applications; and
-- 
-- c) is copyright (C) to Endace, 2012 to 2021. All rights reserved.
--

ENDACE-EDA-MIB DEFINITIONS ::= BEGIN

IMPORTS
    endace
        FROM ENDACE-MIB
    NOTIFICATION-GROUP, OBJECT-GROUP
        FROM SNMPv2-CONF
    Counter64, MODULE-IDENTITY, NOTIFICATION-TYPE, OBJECT-IDENTITY,
    OBJECT-TYPE, Unsigned32
        FROM SNMPv2-SMI
    ;

shogunEventMIB MODULE-IDENTITY
    LAST-UPDATED  "202107210349Z" -- July 21, 2021
    ORGANIZATION
        "Endace Technology"
    CONTACT-INFO
        "postal: Endace Technology
         6th floor
         KPMG Centre
         85 Alexandra Street
         Hamilton 3204
         New Zealand

         email:   support@endace.com"
    DESCRIPTION
        "MIB for event notification from integrated Endace's
         applications, formerly known as 'Shogun'."
    REVISION      "201205032150Z" -- May 03, 2012
    DESCRIPTION
        "New alarm descriptions."
    ::= { endace 9 }

shogunVariables OBJECT IDENTIFIER ::= { shogunEventMIB 1 }

-- VARIABLES

agentId OBJECT-TYPE
    SYNTAX        OCTET STRING (SIZE(0..255))
    MAX-ACCESS    read-only
    STATUS        current
    DESCRIPTION
        "Unique ID of the Agent that generated the event"
    ::= { shogunVariables 1 }

eventId OBJECT-TYPE
    SYNTAX        OCTET STRING (SIZE(0..255))
    MAX-ACCESS    read-only
    STATUS        current
    DESCRIPTION
        "Unique ID of the Event that the Agent generated."
    ::= { shogunVariables 2 }

eventDescr OBJECT-TYPE
    SYNTAX        OCTET STRING (SIZE(0..255))
    MAX-ACCESS    read-only
    STATUS        current
    DESCRIPTION
        "Textual description of the Event that the Agent generated."
    ::= { shogunVariables 3 }

alarmName OBJECT-TYPE
    SYNTAX        OCTET STRING (SIZE(0..255))
    MAX-ACCESS    read-only
    STATUS        current
    DESCRIPTION
        "Unique Name of the Rule that generated the alarm"
    ::= { shogunVariables 4 }

alarmDescr OBJECT-TYPE
    SYNTAX        OCTET STRING (SIZE(0..255))
    MAX-ACCESS    read-only
    STATUS        current
    DESCRIPTION
        "Description of the Rule that generated the alarm"
    ::= { shogunVariables 5 }

alarmTrigger OBJECT-TYPE
    SYNTAX        Counter64
    MAX-ACCESS    read-only
    STATUS        current
    DESCRIPTION
        "The trigger that generated the alarm"
    ::= { shogunVariables 6 }

alarmCriteria OBJECT-TYPE
    SYNTAX        Unsigned32
    MAX-ACCESS    read-only
    STATUS        current
    DESCRIPTION
        "The criteria that generated the alarm"
    ::= { shogunVariables 7 }

alarmType OBJECT-TYPE
    SYNTAX        Unsigned32
    MAX-ACCESS    read-write
    STATUS        current
    DESCRIPTION
        "The type of the alarm"
    ::= { shogunVariables 8 }

alarmSeverity OBJECT-TYPE
    SYNTAX        Unsigned32
    MAX-ACCESS    read-only
    STATUS        current
    DESCRIPTION
        "The severity of the alarm"
    ::= { shogunVariables 9 }

shogunEventTraps OBJECT IDENTIFIER ::= { shogunEventMIB 3 }

-- NOTIFICATIONS

shogunNotificationPrefix OBJECT IDENTIFIER ::= { shogunEventTraps 0 }

eventNotification NOTIFICATION-TYPE
    OBJECTS
        { agentId, eventId, eventDescr }
    STATUS        current
    DESCRIPTION
        "An eventNotification trap indicates that an application
         integrated with Shogun has generated an Event that requires the
         attention of the system administrator."
    ::= { shogunNotificationPrefix 1 }

alarmRaisedNotification NOTIFICATION-TYPE
    OBJECTS
        { alarmCriteria, alarmDescr, alarmName, alarmSeverity,
        alarmTrigger, alarmType }
    STATUS        current
    DESCRIPTION
        "An alarmRaisedNotification trap indicates that an alarm that
         requires the attention of the system administrator was
         raised."
    ::= { shogunNotificationPrefix 2 }

alarmClearedNotification NOTIFICATION-TYPE
    OBJECTS
        { alarmCriteria, alarmDescr, alarmName, alarmSeverity,
        alarmTrigger, alarmType }
    STATUS        current
    DESCRIPTION
        "An alarmClearedNotification trap indicates that an alarm that
         was raised previously was cleared."
    ::= { shogunNotificationPrefix 3 }

shogunConf OBJECT-IDENTITY
    STATUS        current
    DESCRIPTION
        "Container for Endace appliances MIB conformance groups."
    ::= { shogunEventMIB 4 }

shogunNotifyGroup NOTIFICATION-GROUP
    NOTIFICATIONS
        { alarmClearedNotification, alarmRaisedNotification,
        eventNotification }
    STATUS        current
    DESCRIPTION
        "General alarm-specific notifications shared among Endace
         applications."
    ::= { shogunConf 1 }

shogunObjectGroup OBJECT-GROUP
    OBJECTS
        { agentId, alarmCriteria, alarmDescr, alarmName, alarmSeverity,
        alarmTrigger, alarmType, eventDescr, eventId }
    STATUS        current
    DESCRIPTION
        "General alarm-specific managed objects  shared among Endace
         applications."
    ::= { shogunConf 2 }

END
