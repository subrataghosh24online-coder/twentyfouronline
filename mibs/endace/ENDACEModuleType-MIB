ENDACEModuleType-MIB DEFINITIONS ::= BEGIN

IMPORTS
    endace
        FROM ENDACE-MIB
    MODULE-IDENTITY
        FROM SNMPv2-SMI
    TEXTUAL-CONVENTION
        FROM SNMPv2-TC
    ;

endaceModuleType MODULE-IDENTITY
    LAST-UPDATED  "202202090434Z" -- February 09, 2022
    ORGANIZATION
        "Endace Technology"
    CONTACT-INFO
        "postal: Endace Technology
         6th floor
         KPMG Centre
         85 Alexandra Street
         Hamilton 3204
         New Zealand

         email:   support@endace.com"
    DESCRIPTION
        "The MIB module defines the endaceModuleType Textual
         Convention. Each enumeration corresponds to a particular DAG
         module type."
    REVISION      "202202090434Z" -- February 09, 2022
    DESCRIPTION
        "New card Nyx3 added."
    REVISION      "200705230000Z" -- May 23, 2007
    DESCRIPTION
        "Corrected incorrect enumeration value for DAG card."
    REVISION      "200701270000Z" -- January 27, 2007
    DESCRIPTION
        "Initial version provides support for managing Endace
         appliances equipped with standard Endace DAG modules."
    ::= { endace 3 }

EndaceModuleType ::= TEXTUAL-CONVENTION
    STATUS        current
    DESCRIPTION
        "This data type is used as the syntax of the moduleType object
         in the moduleTable.

         The definition of this textual convention with the addition of
         newly assigned values is published periodically by Endace.

         The relationship between the assignment of values and of  OIDs
         to particular module-specific MIBs is solely the  purview of
         IANA and is subject to change without notice."
    SYNTAX        INTEGER {
        -- none of the following
        unknown(0),
        dag35e(1),
        dag35(2),
        dag36d(3),
        dag36e(4),
        dag36ge(5),
        dag37d(6),
        dag37ge(7),
        dag37t(8),
        dag38s(9),
        dag42ge(10),
        dag423ge(11),
        dag42(12),
        dag423(13),
        dag43ge(14),
        dag43s(15),
        dag452e(16),
        dag452gf(17),
        dag452cf(18),
        dag454e(19),
        dag452z(20),
        dag50s(21),
        dag52x(22),
        dag52sxa(23),
        dag60(24),
        dag61(25),
        dag62(26),
        dag70s(27),
        dag70ge(28),
        dag71s(29),
        dag82x(30),
        dag82x2(31),
        dag82z(32),
        dag800(33),
        dag810(34),
        dag50z(35),
        dag50dup(36),
        dag50sg2a(37),
        dag50sg2adup(38),
        dag452z8(39),
        dag840(40),
        dag54s12(41),
        dag54sg48(42),
        dag50sg3a(43),
        dag54ga(44),
        dag54sa12(45),
        dag54sga48(46),
        dag75g2(47),
        dag75g4(48),
        dag75be(49),
        dag75ce(50),
        dag74s(51),
        dag74s48(52),
        dag37t4(53),
        dag91x2Rx(54),
        dag91x2Tx(55),
        dag850(56),
        dag92x(57),
        dag10x4p(58),
        nyx3(59)
    }

END
