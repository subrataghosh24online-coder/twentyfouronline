TIMETRA-LDP-MIB DEFINITIONS ::= BEGIN

IMPORTS
    InterfaceIndexOrZero
                                                         FROM IF-MIB
    InetAddress, InetAddressPrefixLength,
    InetAddressType
                                                         FROM INET-ADDRESS-MIB
    MplsLdpIdentifier, MplsLsrIdentifier
                                                         FROM MPLS-LDP-MIB
    MODULE-COMPLIANCE, NOTIFICATION-GROUP,
    OBJECT-GROUP
                                                         FROM SNMPv2-CONF
    Counter32, Counter64, Gauge32,
    IpAddress, MODULE-IDENTITY,
    NOTIFICATION-TYPE, OBJECT-TYPE,
    Unsigned32
                                                         FROM SNMPv2-SMI
    DisplayString, RowStatus,
    TEXTUAL-CONVENTION, TestAndIncr,
    TimeInterval, TimeStamp, TruthValue
                                                         FROM SNMPv2-TC
    TFilterID, TFilterLogId
                                                         FROM TIMETRA-FILTER-MIB
    timetraSRMIBModules, tmnxSRConfs,
    tmnxSRNotifyPrefix, tmnxSRObjs
                                                         FROM TIMETRA-GLOBAL-MIB
    SdpId, ServType,
    TdmOptionsCasTrunkFraming,
    TdmOptionsSigPkts
                                                         FROM TIMETRA-SERV-MIB
    TNamedItem, TNamedItemOrEmpty,
    TPolicyStatementNameOrEmpty,
    TmnxAddressAndPrefixAddress,
    TmnxAddressAndPrefixPrefix,
    TmnxAddressAndPrefixType,
    TmnxAdminState, TmnxEnabledDisabled,
    TmnxLdpFECType, TmnxOperState,
    TmnxServId, TmnxVRtrMplsLspID, TmnxVcId,
    TmnxVcType
                                                         FROM TIMETRA-TC-MIB
    vRtrID, vRtrLdpStatus
                                                         FROM TIMETRA-VRTR-MIB
    ;

timetraLdpMIBModule              MODULE-IDENTITY
    LAST-UPDATED "201701010000Z"
    ORGANIZATION "Nokia"
    CONTACT-INFO
        "Nokia SROS Support
         Web: http://www.nokia.com"
    DESCRIPTION
        "The MIB module to manage and provision the Nokia SROS LDP protocol
         features.

         Copyright 2003-2018 Nokia. All rights reserved. Reproduction of this
         document is authorized on the condition that the foregoing copyright
         notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201701010000Z"
    DESCRIPTION
        "Rev 15.0               1 Jan 2017 00:00
         15.0 release of the TIMETRA-LDP-MIB."

    REVISION    "201601010000Z"
    DESCRIPTION
        "Rev 14.0               1 Jan 2016 00:00
         14.0 release of the TIMETRA-LDP-MIB."

    REVISION    "201501010000Z"
    DESCRIPTION
        "Rev 13.0               1 Jan 2015 00:00
         13.0 release of the TIMETRA-LDP-MIB."

    REVISION    "201401010000Z"
    DESCRIPTION
        "Rev 12.0               1 Jan 2014 00:00
         12.0 release of the TIMETRA-LDP-MIB."

    REVISION    "201102010000Z"
    DESCRIPTION
        "Rev 9.0                1 Feb 2011 00:00
         9.0 release of the TIMETRA-LDP-MIB."

    REVISION    "200902280000Z"
    DESCRIPTION
        "Rev 7.0                28 Feb 2009 00:00
         7.0 release of the TIMETRA-LDP-MIB."

    REVISION    "200801010000Z"
    DESCRIPTION
        "Rev 6.0                01 Jan 2008 00:00
         6.0 release of the TIMETRA-LDP-MIB."

    REVISION    "200701010000Z"
    DESCRIPTION
        "Rev 5.0                01 Jan 2007 00:00
         5.0 release of the TIMETRA-LDP-MIB."

    REVISION    "200603160000Z"
    DESCRIPTION
        "Rev 4.0                16 Mar 2006 00:00
         4.0 release of the TIMETRA-LDP-MIB."

    REVISION    "200508310000Z"
    DESCRIPTION
        "Rev 3.0                31 Aug 2005 00:00
         3.0 release of the TIMETRA-LDP-MIB."

    REVISION    "200501240000Z"
    DESCRIPTION
        "Rev 2.1                24 Jan 2005 00:00
         2.1 release of the TIMETRA-LDP-MIB."

    REVISION    "200401150000Z"
    DESCRIPTION
        "Rev 2.0                15 Jan 2004 00:00
         2.0 release of the TIMETRA-LDP-MIB."

    REVISION    "200308150000Z"
    DESCRIPTION
        "Rev 1.2                15 Aug 2003 00:00
         1.2 release of the TIMETRA-LDP-MIB."

    REVISION    "200301200000Z"
    DESCRIPTION
        "Rev 1.0                20 Jan 2003 00:00
         1.0 Release of the TIMETRA-LDP-MIB."

    REVISION    "200108010000Z"
    DESCRIPTION
        "Rev 0.1                01 Aug 2001 00:00
         Initial version of the TIMETRA-LDP-MIB."

    ::= { timetraSRMIBModules 8 }

TmnxLdpKeepAliveFactor           ::= TEXTUAL-CONVENTION
    STATUS      current
    DESCRIPTION
        "TmnxLdpKeepAliveFactor specifies the value by which the keepalive
         timeout should be divided to give the keepalive time i.e. the time
         interval, in seconds, between LDP Keepalive messages. LDP Keepalive
         messages are sent to keep the LDP session from timing out when no
         other LDP traffic is being sent between the neighbors."
    SYNTAX      Unsigned32 (1..255)

TmnxLdpKeepAliveTimeout          ::= TEXTUAL-CONVENTION
    STATUS      current
    DESCRIPTION
        "TmnxLdpKeepAliveTimeout specifies the the time interval, in seconds,
         that LDP waits before tearing down a session. If no LDP messages are
         exchanged during this time interval, the LDP session is torn down.
         Generally the keepalive timeout interval should be configured to be 3
         times the keepalive time (the time interval between successive LDP
         Keepalive messages)."
    SYNTAX      Unsigned32 (1..65535)

TmnxLdpHelloFactor               ::= TEXTUAL-CONVENTION
    STATUS      current
    DESCRIPTION
        "TmnxLdpHelloFactor specifies the value by which the hello timeout
         should be divided to give the hello time i.e. the time interval, in
         seconds, between LDP Hello messages. LDP uses Hello messages to
         discover neighbors and to detect loss of connectivity with its
         neighbors."
    SYNTAX      Unsigned32 (1..255)

TmnxLdpHelloTimeout              ::= TEXTUAL-CONVENTION
    STATUS      current
    DESCRIPTION
        "TmnxLdpHelloTimeout specifies the the time interval, in seconds, that
         LDP waits before declaring a neighbor to be down. Hello timeout is
         local to the system and is sent in the Hello messages to a neighbor.
         Hello timeout cannot be set to a value that is less than 3 times the
         hello time."
    SYNTAX      Unsigned32 (1..65535)

TmnxLdpBackoffTime               ::= TEXTUAL-CONVENTION
    STATUS      current
    DESCRIPTION
        "TmnxLdpBackoffTime specifies the backoff interval (initial and
         maximum). The backoff interval is the time, in seconds, that LDP waits
         after an LDP session setup has failed before it attempts to setup the
         session again. After the LDP session startup fails the first time, the
         backoff interval is set to an initial value. Thereafter, if session
         startup fails again the backoff interval increases exponentially until
         it reaches a maximum value specified by the maximum backoff interval.
         If the maximum backoff interval is set to zero (0), then the backoff
         interval does not increase exponentially after the first session
         startup attempt fails. Instead it remains constant and LDP will keep
         retrying to establish a session until it succeeds."
    SYNTAX      Unsigned32 (0..2592000)

TmnxLdpFECPolicy                 ::= TEXTUAL-CONVENTION
    STATUS      current
    DESCRIPTION
        "TmnxLdpFECPolicy determines whether the LSR should generate FECs and
         which FECs it should generate.

         system(1) - LDP will distribute label bindings only for the router's
         system IP address

         interface(2) - LDP will distribute label bindings for all LDP
         interfaces

         all(3) - LDP will distribute label bindings for all prefixes in the
         routing table

         none(4) - LDP will not distribute any label bindings."
    SYNTAX      INTEGER {
        system    (1),
        interface (2),
        all       (3),
        none      (4)
    }

TmnxLdpLabelDistMethod           ::= TEXTUAL-CONVENTION
    STATUS      current
    DESCRIPTION
        "TmnxLdpLabelDistMethod describes the label distribution method used.

         When the value is 'downstreamOnDemand', label bindings are distributed
         to the upstream LSR only when a label request message is received.

         When the value is 'downstreamUnsolicited', label bindings are
         distributed to the upstream LSR, for each FEC, without requiring a
         request message for the FEC from the upstream LSR."
    SYNTAX      INTEGER {
        downstreamOnDemand    (1),
        downstreamUnsolicited (2)
    }

TmnxLdpAdjacencyType             ::= TEXTUAL-CONVENTION
    STATUS      current
    DESCRIPTION
        "TmnxLdpAdjacencyType describes the type of adjacency, either targeted
         or link, for a row in the vRtrLdpHelloAdjTable. It also describes the
         type of adjacencies in an LDP Session row in the vRtrLdpSessionTable."
    SYNTAX      INTEGER {
        link     (1),
        targeted (2),
        both     (3)
    }

TmnxVpnId                        ::= TEXTUAL-CONVENTION
    STATUS      current
    DESCRIPTION
        "TmnxVpnId specifies the value of a VPN (Virtual Private Network)
         identifier. This is a 10 byte value - the VPN 'type' is stored in the
         first two bytes the TmnxVpnId. The next four bytes store an 'AS
         (Autonomous System) number'. A 'local identifier' for the VPN is
         stored as the last four bytes."
    SYNTAX      OCTET STRING (SIZE (10))

TmnxLabelStatus                  ::= TEXTUAL-CONVENTION
    STATUS      current
    DESCRIPTION
        "TmnxLabelStatus bit flags specifies the status of an ingress or egress
         label.

         Flags marked dummy* are not used and MUST be 0.

         'statusSignalingSupported' - indicates whether status signaling is
                       enabled or not.
         'inUsePush' - indicates that the label contains valid information
                       that is currently being used as a 'push' label.
         'inUseSwap' - indicates that the label contains valid information
                       that is currently being used as a 'swap' label.
         'inUsePop'  - indicates that the label contains valid information
                       that is currently being used as a 'pop' label.
         'released'  - indicates that the label is in the process of being
                       freed. With this flag set, no other flags will be set.
         'notInUse'  - indicates that the label contains valid information
                       but is currently not being used possibly because the
                       service is temporarily down.
         'withdrawn' - indicates that the label has not been sent (possibly
                       due to a mismatch in control word or status signaling)
         'controlWord' - indicates that the control word will be signaled
         'withdrawPending' - indicates that the label withdrawal is pending
         'alternateNextHop' - indicates that the label is programmed as
                              alternate next-hop for fast reroute
         'alternatePHop' - indicates that the label is programmed as alternate
                           upstream for fast reroute.
         'unnumIf'   - indicates that the label is programmed using unnumbered
                       interface.
         'srIsisNextHop' - LDP binding is resolved to ISIS segment routing
                           next-hop.
         'srOspfNextHop' - LDP binding is resolved to OSPF segment routing
                           next-hop.
         'entLblCap' - entropy label capabilities.
         }"
    SYNTAX      BITS {
        dummyB0                  (0),
        dummyB1                  (1),
        statusSignalingSupported (2),
        inUsePush                (3),
        inUseSwap                (4),
        inUsePop                 (5),
        released                 (6),
        notInUse                 (7),
        withdrawn                (8),
        controlWord              (9),
        withdrawPending          (10),
        alternateNextHop         (11),
        alternatePHop            (12),
        unnumIf                  (13),
        srIsisNextHop            (14),
        srOspfNextHop            (15),
        entLblCap                (16)
    }

TmnxLabelSigStatus               ::= TEXTUAL-CONVENTION
    STATUS      current
    DESCRIPTION
        "TmnxLabelSigStatus specifies the status of the pseudowire and attached
         circuit.  The values are defined in
         draft-ietf-pwe3-iana-allocation-07.txt."
    REFERENCE
        "IETF draft-ietf-pwe3-iana-allocation-07.txt, sections 2,3 and 4"
    SYNTAX      Unsigned32

TmnxLdpFECTunnelType             ::= TEXTUAL-CONVENTION
    STATUS      current
    DESCRIPTION
        "TmnxLdpFECTunnelType determines the type of tunnel that the label
         mapping messages are referring to."
    SYNTAX      INTEGER {
        static (1)
    }

TmnxLdpFECFlags                  ::= TEXTUAL-CONVENTION
    STATUS      current
    DESCRIPTION
        "TmnxLdpFECFlags bit flags define the characteristics of FEC. Flags
         marked dummy* are not used and MUST be 0.

         Flag 'egress':  this node is an egress for this FEC.
         Flag 'ingress': this node is a potential ingress for this FEC.
         Flag 'installedSwap': the label for this FEC has been programmed
                               as a 'swap' label.
         Flag 'installedPush': the label for this FEC has been programmed
                               as a 'push' label.
         Flag 'installedPop':  the label for this FEC has been programmed
                               as a 'pop' label.
         Flag 'local':   this FEC is local to this node.
         Flag 'nextHop': the nextHop for this FEC is known.
         Flag 'importPolicyRejected': global LDP import policy has rejected
                                      this FEC.
         Flag 'exportPolicyAccepted': global LDP export policy has accepted
                                      this FEC.
         Flag 'installedStaticFec': this FEC is created by static FEC
                                    configuration on this node.
         Flag 'vcSwitching': vcSwitching is enabled for the FEC.
         Flag 'importTargPolicyRejected': targeted LDP import policy has
                                          rejected this FEC.
         Flag 'exportTargPolicyRejected': targeted LDP export policy has
                                          rejected this FEC.
         Flag 'importPeerPolicyRejected': peer LDP import policy has
                                          rejected this FEC.
         Flag 'localMultihomedSecondary': this FEC is local to this node
                                          and is a multi-homed secondary
                                          ip address.
         Flag 'bgpNextHop' : LDP binding is resolved to BGP next-hop.
         Flag 'labelReqSent' : Label request to peer has been sent.
         Flag 'classBasedForwarding' : Label binding is using
                                       class-based-forwarding.
         Flag 'srIsisNextHop' : LDP binding is resolved to ISIS segment routing
                                next-hop.
         Flag 'srOspfNextHop' : LDP binding is resolved to OSPF segment routing
                                next-hop.
         Flag 'upperFec' : this upper FEC is stitched to lower FEC
         Flag 'lowerFec' : this lower FEC is stitched to upper FEC
         Flag 'communityMismatch' : targeted LDP community mismatch
         Flag 'bkpUpperFec' : backup upper FEC"
    SYNTAX      BITS {
        dummyB0                  (0),
        egress                   (1),
        ingress                  (2),
        installedSwap            (3),
        installedPush            (4),
        installedPop             (5),
        local                    (6),
        nextHop                  (7),
        importPolicyRejected     (8),
        exportPolicyAccepted     (9),
        installedStaticFec       (10),
        vcSwitching              (11),
        importTargPolicyRejected (12),
        exportTargPolicyRejected (13),
        importPeerPolicyRejected (14),
        localMultihomedSecondary (15),
        bgpNextHop               (16),
        labelReqSent             (17),
        classBasedForwarding     (18),
        srIsisNextHop            (19),
        srOspfNextHop            (20),
        upperFec                 (21),
        lowerFec                 (22),
        communityMismatch        (23),
        bkpUpperFec              (24)
    }

TmnxLdpGenOperDownReasonCode     ::= TEXTUAL-CONVENTION
    STATUS      current
    DESCRIPTION
        "TmnxLdpGenOperDownReasonCode is an enumerated integer that specifies
         the reason that the LDP instance is operationally down."
    SYNTAX      INTEGER {
        operUp            (0),
        adminDown         (1),
        noListenSocket    (2),
        noDiscoverySocket (3),
        noRtm             (4),
        noTtm             (5),
        iomFailure        (6),
        recvFailure       (7),
        clearDown         (8),
        noResources       (9),
        systemIpDown      (10),
        helloFailure      (11),
        ipv6NotSupported  (12),
        noBgp             (13)
    }

TmnxLdpIntTargOperDownReasonCode ::= TEXTUAL-CONVENTION
    STATUS      current
    DESCRIPTION
        "TmnxLdpIntTargOperDownReasonCode is an enumerated integer that
         specifies the reason that the LDP interface and targeted peer is
         operationally down."
    SYNTAX      INTEGER {
        operUp                (0),
        adminDown             (1),
        noListenSocket        (2),
        noDiscoverySocket     (3),
        noResources           (4),
        addrFecDeprogram      (5),
        svcFecDeprogram       (6),
        clearDown             (7),
        instanceDown          (8),
        interfaceDown         (9),
        targetIpInvalid       (10),
        interfaceInvalid      (11),
        lsrInterfaceDown      (12),
        lsrInterfaceInvalid   (13),
        helloFailure          (14),
        parentIfDown          (15),
        interfaceNoValidIp    (16),
        lsrInterfaceNoValidIp (17)
    }

TmnxLdpFec129Tlv                 ::= TEXTUAL-CONVENTION
    STATUS      current
    DESCRIPTION
        "TmnxLdpFec129Tlv is a Type-Length-Value (Tlv) that specifies the value
         encoded as one byte Type followed by one byte Length followed by the
         'Length' size Value used for FEC-129 attribute."
    SYNTAX      OCTET STRING (SIZE (2..32))

TmnxLdpNewKeepAliveTimeout       ::= TEXTUAL-CONVENTION
    STATUS      current
    DESCRIPTION
        "TmnxLdpNewKeepAliveTimeout specifies the the time interval, in
         seconds, that LDP waits before tearing down a session. If no LDP
         messages are exchanged during this time interval, the LDP session is
         torn down. Generally the keepalive timeout interval should be
         configured to be 3 times the keepalive time (the time interval between
         successive LDP Keepalive messages).

         The minimum value TmnxLdpKeepAliveTimeout can have is 1 whereas the
         minimum value TmnxLdpNewKeepAliveTimeout can have is 3. This new
         textual convention prevents setting value for timeouts to be less than
         3 seconds."
    SYNTAX      Unsigned32 (3..65535)

TmnxLdpNewHelloTimeout           ::= TEXTUAL-CONVENTION
    STATUS      current
    DESCRIPTION
        "TmnxLdpNewHelloTimeout specifies the the time interval, in seconds,
         that LDP waits before declaring a neighbor to be down. Hello timeout
         is local to the system and is sent in the Hello messages to a
         neighbor. Hello timeout cannot be set to a value that is less than 3
         times the hello time.

         The minimum value TmnxLdpHelloTimeout can have is 1 whereas the
         minimum value TmnxLdpNewHelloTimeout can have is 3. This new textual
         convention prevents setting value for timeouts to be less than 3
         seconds."
    SYNTAX      Unsigned32 (3..65535)

TmnxLdpInLblWdrawalReasonCode    ::= TEXTUAL-CONVENTION
    STATUS      current
    DESCRIPTION
        "TmnxLdpInLblWdrawalReasonCode is an enumerated integer that specifies
         the reason that the LDP ingress label is withdrawn.

         The value of 'none(0)' means no reason specified for the withdrawal of
         the ingress label.

         The value of 'noSwLabel(1)' means the ingress label is withdrawn
         because there is no vc switching label from upstream.

         The value of 'localFault(2)' means the ingress label is withdrawn
         because there is a local fault.

         The value of 'stackMismatch(3)' means the ingress label is withdrawn
         due to stack capability mismatch."
    SYNTAX      INTEGER {
        none          (0),
        noSwLabel     (1),
        localFault    (2),
        stackMismatch (3)
    }

tmnxLdpObjs                      OBJECT IDENTIFIER ::= { tmnxSRObjs 8 }

vRtrLdpGeneralTable              OBJECT-TYPE
    SYNTAX      SEQUENCE OF VRtrLdpGeneralEntry
    MAX-ACCESS  not-accessible
    STATUS      obsolete
    DESCRIPTION
        "vRtrLdpGeneralTable has an entry for each virtual router in the system
         capable of supporting an instance of the Label Distribution Protocol
         (LDP).

         In 13.0 this table has been replaced by
         TIMETRA-LDP-NG-MIB::vRtrLdpNgGeneralTable,
         TIMETRA-LDP-NG-MIB::vRtrLdpNgCapabilityTable,
         TIMETRA-LDP-NG-MIB::vRtrLdpNgPolicyTable."
    ::= { tmnxLdpObjs 1 }

vRtrLdpGeneralEntry              OBJECT-TYPE
    SYNTAX      VRtrLdpGeneralEntry
    MAX-ACCESS  not-accessible
    STATUS      obsolete
    DESCRIPTION
        "Each row entry represents an instance of the Label Distribution
         Protocol (LDP) for a virtual router in the system.

         An entry in this table is created by the agent when vRtrLdpStatus in
         the vRtrConfTable is set to 'create'. The entry is destroyed when
         vRtrLdpStatus is set to 'delete' but only if vRtrLdpGenAdminState has
         a value of 'outOfService'."
    INDEX       { vRtrID }
    ::= { vRtrLdpGeneralTable 1 }

VRtrLdpGeneralEntry              ::= SEQUENCE
{
    vRtrLdpGenLastChange             TimeStamp,
    vRtrLdpGenAdminState             TmnxAdminState,
    vRtrLdpGenOperState              TmnxOperState,
    vRtrLdpGenLdpLsrId               MplsLsrIdentifier,
    vRtrLdpGenProtocolVersion        Unsigned32,
    vRtrLdpGenDeaggregateFec         TruthValue,
    vRtrLdpGenKeepAliveFactor        TmnxLdpKeepAliveFactor,
    vRtrLdpGenKeepAliveTimeout       TmnxLdpNewKeepAliveTimeout,
    vRtrLdpGenHelloFactor            TmnxLdpHelloFactor,
    vRtrLdpGenHelloTimeout           TmnxLdpNewHelloTimeout,
    vRtrLdpGenRoutePreference        Unsigned32,
    vRtrLdpGenControlMode            INTEGER,
    vRtrLdpGenDistMethod             TmnxLdpLabelDistMethod,
    vRtrLdpGenRetentionMode          INTEGER,
    vRtrLdpGenTransportAddrType      INTEGER,
    vRtrLdpGenPropagatePolicy        TmnxLdpFECPolicy,
    vRtrLdpGenLoopDetectCapable      INTEGER,
    vRtrLdpGenHopLimit               Unsigned32,
    vRtrLdpGenPathVectorLimit        Unsigned32,
    vRtrLdpGenBackoffTime            TmnxLdpBackoffTime,
    vRtrLdpGenMaxBackoffTime         TmnxLdpBackoffTime,
    vRtrLdpGenTargKeepAliveFactor    TmnxLdpKeepAliveFactor,
    vRtrLdpGenTargKeepAliveTimeout   TmnxLdpNewKeepAliveTimeout,
    vRtrLdpGenTargHelloFactor        TmnxLdpHelloFactor,
    vRtrLdpGenTargHelloTimeout       TmnxLdpNewHelloTimeout,
    vRtrLdpGenTargPassiveMode        TruthValue,
    vRtrLdpGenTargetedSessions       TruthValue,
    vRtrLdpGenCreateTime             TimeStamp,
    vRtrLdpGenUpTime                 TimeInterval,
    vRtrLdpGenImportPolicy1          TPolicyStatementNameOrEmpty,
    vRtrLdpGenImportPolicy2          TPolicyStatementNameOrEmpty,
    vRtrLdpGenImportPolicy3          TPolicyStatementNameOrEmpty,
    vRtrLdpGenImportPolicy4          TPolicyStatementNameOrEmpty,
    vRtrLdpGenImportPolicy5          TPolicyStatementNameOrEmpty,
    vRtrLdpGenExportPolicy1          TPolicyStatementNameOrEmpty,
    vRtrLdpGenExportPolicy2          TPolicyStatementNameOrEmpty,
    vRtrLdpGenExportPolicy3          TPolicyStatementNameOrEmpty,
    vRtrLdpGenExportPolicy4          TPolicyStatementNameOrEmpty,
    vRtrLdpGenExportPolicy5          TPolicyStatementNameOrEmpty,
    vRtrLdpGenTunnelDownDampTime     Unsigned32,
    vRtrLdpGenOperDownReason         TmnxLdpGenOperDownReasonCode,
    vRtrLdpGenTrustList              TFilterID,
    vRtrLdpGenGracefulRestart        TruthValue,
    vRtrLdpGenGRNbrLiveTime          Unsigned32,
    vRtrLdpGenGRMaxRecoveryTime      Unsigned32,
    vRtrLdpGenLabelWithdrawalDelay   Unsigned32,
    vRtrLdpGenImplicitNull           TruthValue,
    vRtrLdpGenShortTTLPropLocal      TruthValue,
    vRtrLdpGenShortTTLPropTransit    TruthValue,
    vRtrLdpGenMPMBBTime              Unsigned32,
    vRtrLdpGenTunlTblExportPolicy1   TPolicyStatementNameOrEmpty,
    vRtrLdpGenTunlTblExportPolicy2   TPolicyStatementNameOrEmpty,
    vRtrLdpGenTunlTblExportPolicy3   TPolicyStatementNameOrEmpty,
    vRtrLdpGenTunlTblExportPolicy4   TPolicyStatementNameOrEmpty,
    vRtrLdpGenTunlTblExportPolicy5   TPolicyStatementNameOrEmpty,
    vRtrLdpGenP2MPCapability         TruthValue,
    vRtrLdpGenMPMBBCapability        TruthValue,
    vRtrLdpGenDynamicCapability      TruthValue,
    vRtrLdpGenLdpFrr                 TruthValue,
    vRtrLdpGenTargHelloReduction     TruthValue,
    vRtrLdpGenTargHelloReductionFctr Unsigned32,
    vRtrLdpGenMcastUpstreamFrr       TruthValue,
    vRtrLdpGenOverloadCapability     TruthValue
}

vRtrLdpGenLastChange             OBJECT-TYPE
    SYNTAX      TimeStamp
    MAX-ACCESS  read-only
    STATUS      obsolete
    DESCRIPTION
        "The value of vRtrLdpGenLastChange specifies the sysUpTime when this
         row was last modified.

         This object was obsoleted in release 13.0."
    ::= { vRtrLdpGeneralEntry 1 }

vRtrLdpGenAdminState             OBJECT-TYPE
    SYNTAX      TmnxAdminState
    MAX-ACCESS  read-create
    STATUS      obsolete
    DESCRIPTION
        "The value of vRtrLdpGenAdminState specifies the desired administrative
         state for this LDP instance.

         This object was obsoleted in release 13.0."
    DEFVAL      { inService }
    ::= { vRtrLdpGeneralEntry 2 }

vRtrLdpGenOperState              OBJECT-TYPE
    SYNTAX      TmnxOperState
    MAX-ACCESS  read-only
    STATUS      obsolete
    DESCRIPTION
        "The value of vRtrLdpGenOperState specifies the current operational
         state of this LDP instance.

         This object was obsoleted in release 13.0."
    ::= { vRtrLdpGeneralEntry 3 }

vRtrLdpGenLdpLsrId               OBJECT-TYPE
    SYNTAX      MplsLsrIdentifier
    MAX-ACCESS  read-only
    STATUS      obsolete
    DESCRIPTION
        "The value of vRtrLdpGenLdpLsrId is the Label Switch Router (LSR)
         identifier which is used as the first 4 bytes or the Router Id
         component of the Label Distribution Protocol (LDP) identifier.

         This object was obsoleted in release 13.0."
    ::= { vRtrLdpGeneralEntry 4 }

vRtrLdpGenProtocolVersion        OBJECT-TYPE
    SYNTAX      Unsigned32
    MAX-ACCESS  read-only
    STATUS      obsolete
    DESCRIPTION
        "The value of  vRtrLdpGenProtocolVersion specifies the
         version of the LDP protocol instance. A value of zero (0)
         indicates that the version of the protocol is unknown.

         This object was obsoleted in release 13.0."
    ::= { vRtrLdpGeneralEntry 5 }

vRtrLdpGenDeaggregateFec         OBJECT-TYPE
    SYNTAX      TruthValue
    MAX-ACCESS  read-create
    STATUS      obsolete
    DESCRIPTION
        "When vRtrLdpGenDeaggregateFec has a value of 'false', LDP aggregates
         multiple prefixes into a single Forwarding Equivalence Class (FEC) and
         advertises a single label for the FEC. When the value is 'true', LDP
         deaggregates prefixes into multiple FECs.

         This value is only applicable to LDP interfaces and not for targeted
         sessions.

         This object was obsoleted in release 13.0."
    DEFVAL      { false }
    ::= { vRtrLdpGeneralEntry 6 }

vRtrLdpGenKeepAliveFactor        OBJECT-TYPE
    SYNTAX      TmnxLdpKeepAliveFactor
    MAX-ACCESS  read-create
    STATUS      obsolete
    DESCRIPTION
        "The value of vRtrLdpGenKeepAliveFactor specifies the value by which
         the keepalive timeout (vRtrLdpGenKeepAliveTimeout) should be divided
         to give the keepalive time i.e. the time interval, in seconds, between
         LDP keepalive messages. LDP keepalive messages are sent to keep the
         LDP session from timing out when no other LDP traffic is being sent
         between the neighbors.

         This value is only applicable to LDP interfaces and not for targeted
         sessions.

         This object was obsoleted in release 13.0."
    DEFVAL      { 3 }
    ::= { vRtrLdpGeneralEntry 7 }

vRtrLdpGenKeepAliveTimeout       OBJECT-TYPE
    SYNTAX      TmnxLdpNewKeepAliveTimeout
    UNITS       "seconds"
    MAX-ACCESS  read-create
    STATUS      obsolete
    DESCRIPTION
        "The value of vRtrLdpGenKeepAliveTimeout specifies the time interval,
         in seconds, that LDP waits before tearing down a session. If no LDP
         messages are exchanged during this time interval, the LDP session is
         torn down. Generally the value of vRtrLdpGenKeepAliveTimeout is
         configured to be 3 times the keepalive time (the time interval between
         successive LDP keepalive messages).

         This value is only applicable to LDP interfaces and not for targeted
         sessions.

         This object was obsoleted in release 13.0."
    DEFVAL      { 30 }
    ::= { vRtrLdpGeneralEntry 8 }

vRtrLdpGenHelloFactor            OBJECT-TYPE
    SYNTAX      TmnxLdpHelloFactor
    MAX-ACCESS  read-create
    STATUS      obsolete
    DESCRIPTION
        "The value of vRtrLdpGenHelloFactor specifies the value by which the
         hello timeout (vRtrLdpGenHelloTimeout) should be divided to give the
         hello time i.e. the time interval, in seconds, between LDP Hello
         messages. LDP uses hello messages to discover neighbors and to detect
         loss of connectivity with its neighbors.

         This value is only applicable to LDP interfaces and not for targeted
         sessions.

         This object was obsoleted in release 13.0."
    DEFVAL      { 3 }
    ::= { vRtrLdpGeneralEntry 9 }

vRtrLdpGenHelloTimeout           OBJECT-TYPE
    SYNTAX      TmnxLdpNewHelloTimeout
    UNITS       "seconds"
    MAX-ACCESS  read-create
    STATUS      obsolete
    DESCRIPTION
        "The value of vRtrLdpGenHelloTimeout specifies the hello time also
         known as hold time. It is the time interval, in seconds, that LDP
         waits before declaring a neighbor to be down. Hello timeout is local
         to the system and is sent in the hello messages to a neighbor. Hello
         timeout cannot be set to a value that is less than 3 times the hello
         time.

         This value is only applicable to LDP interfaces and not for targeted
         sessions.

         This object was obsoleted in release 13.0."
    DEFVAL      { 15 }
    ::= { vRtrLdpGeneralEntry 10 }

vRtrLdpGenRoutePreference        OBJECT-TYPE
    SYNTAX      Unsigned32 (1..255)
    MAX-ACCESS  read-create
    STATUS      obsolete
    DESCRIPTION
        "The value of vRtrLdpGenRoutePreference specifies the route preference
         assigned to LDP routes. When multiple routes are available to a
         destination, the route with the lowest preference will be used.

         This value is only applicable to LDP interfaces and not for targeted
         sessions.

         This object was obsoleted in release 13.0."
    DEFVAL      { 9 }
    ::= { vRtrLdpGeneralEntry 11 }

vRtrLdpGenControlMode            OBJECT-TYPE
    SYNTAX      INTEGER {
        ordered     (1),
        independent (2)
    }
    MAX-ACCESS  read-only
    STATUS      obsolete
    DESCRIPTION
        "The value of vRtrLdpGenControlMode specifies the mode used for
         distributing labels in response to label binding requests.

         When vRtrLdpGenControlMode has a value of 'ordered', label bindings
         are not distributed in response to a label request until a label
         binding has been received from the next hop for the destination.

         When vRtrLdpGenControlMode has a value of 'independent', label
         bindings are distributed immediately in response to a label request
         even if a label binding has not yet been received from the next hop
         for the destination.

         This object was obsoleted in release 13.0."
    ::= { vRtrLdpGeneralEntry 12 }

vRtrLdpGenDistMethod             OBJECT-TYPE
    SYNTAX      TmnxLdpLabelDistMethod
    MAX-ACCESS  read-only
    STATUS      obsolete
    DESCRIPTION
        "The value of vRtrLdpGenDistMethod specifies the label distribution
         method used.

         When vRtrLdpGenDistMethod has a value of 'downstreamOnDemand', label
         bindings are distributed to the upstream LSR, for each FEC, without
         requiring a request message for the FEC from the upstream LSR.

         When vRtrLdpGenDistMethod has a value of 'downstreamUnsolicited',
         label bindings are distributed to the upstream LSR only when a label
         request message is received.

         This object was obsoleted in release 13.0."
    ::= { vRtrLdpGeneralEntry 13 }

vRtrLdpGenRetentionMode          OBJECT-TYPE
    SYNTAX      INTEGER {
        conservative (1),
        liberal      (2)
    }
    MAX-ACCESS  read-only
    STATUS      obsolete
    DESCRIPTION
        "The value of vRtrLdpGenRetentionMode specifies the label retention
         mode used.

         If the value of this object is 'conservative', then advertised
         label mappings are retained only if they will be used to forward
         packets, i.e. if the label came from a valid next hop.  Label
         bindings received from non-nexthops for each FEC are discarded.

         If the value of this object is 'liberal', then all advertised
         label mappings are retained whether they are from a valid next
         hop or not.  When vRtrLdpGenDistMethod has a value of
         'downstreamUnsolicited', a LSR may receive label bindings for
         the same destination for all its neighbors.  Labels for the
         non-nexthops for the FECs are retained in the software but not
         used.  When a network topology change occurs where a non-nexthop
         becomes a true next hop, the label received earlier is then used.

         This object was obsoleted in release 13.0."
    ::= { vRtrLdpGeneralEntry 14 }

vRtrLdpGenTransportAddrType      OBJECT-TYPE
    SYNTAX      INTEGER {
        interface (1),
        system    (2)
    }
    MAX-ACCESS  read-create
    STATUS      obsolete
    DESCRIPTION
        "The value of vRtrLdpGenTransportAddrType specifies the source
         of the transport address to be used when setting up the LDP TCP
         sessions.  The transport address can be configured globally
         (applied to all interfaces) or per interface.

         When the value of this object is 'interface', the interface's IP
         address is used to setup the LDP session between neighbors. If
         multiple interfaces exist between two neighbors, the 'interface' mode
         cannot be used since only one LDP session is actually set up between
         the two neighbors.

         When the value of this object is 'system', the system's IP address is
         used to set up the LDP session between neighbors.

         This value is only applicable to LDP interfaces and not for targeted
         sessions.

         This object was obsoleted in release 13.0."
    DEFVAL      { system }
    ::= { vRtrLdpGeneralEntry 15 }

vRtrLdpGenPropagatePolicy        OBJECT-TYPE
    SYNTAX      TmnxLdpFECPolicy
    MAX-ACCESS  read-create
    STATUS      obsolete
    DESCRIPTION
        "The value of vRtrLdpGenPropagatePolicy determines whether the LSR
         should generate FECs and which FECs it should generate.

         When the value of this object is 'system', LDP will distribute label
         bindings only for the router's system IP address

         When the value of this object is 'interface', LDP will distribute
         label bindings for all LDP interfaces

         When the value of this object is 'all', LDP will distribute label
         bindings for all prefixes in the routing table

         When the value of this object is 'none', LDP will not distribute any
         label bindings.

         This value is only applicable to LDP interfaces and not for targeted
         sessions.

         This object was obsoleted in release 13.0."
    DEFVAL      { system }
    ::= { vRtrLdpGeneralEntry 16 }

vRtrLdpGenLoopDetectCapable      OBJECT-TYPE
    SYNTAX      INTEGER {
        none                  (1),
        other                 (2),
        hopCount              (3),
        pathVector            (4),
        hopCountAndPathVector (5)
    }
    MAX-ACCESS  read-create
    STATUS      obsolete
    DESCRIPTION
        "The value of vRtrLdpGenLoopDetectCapable indicate whether this LSR
         supports loop detection and if so, what type of loop detection is
         supported.

         When the value is 'none' loop detection is not supported on this LSR.

         When the value is 'other' Loop Detection is supported but by a method
         other than those listed below.

         When the value is 'hopCount' Loop Detection is supported by Hop Count
         only.

         When the value is 'pathVector' Loop Detection is supported by Path
         Vector only.

         When the value is 'hopCountAndPathVector' Loop Detection is supported
         by both Hop Count and Path Vector.

         Since Loop Detection is determined during Session Initialization, an
         individual session may not be running with loop detection. This object
         simply gives an indication of whether or not the LSR has the ability
         to support Loop Detection and which types.

         This object was obsoleted in release 13.0."
    DEFVAL      { none }
    ::= { vRtrLdpGeneralEntry 17 }

vRtrLdpGenHopLimit               OBJECT-TYPE
    SYNTAX      Unsigned32 (0..255)
    MAX-ACCESS  read-create
    STATUS      obsolete
    DESCRIPTION
        "The value of vRtrLdpGenHopLimit specifies the maximum
         allowable value for the hop count.  The value of this object
         is valid and used only if vRtrLdpGenLoopDetectCapable has
         a value of either 'hopCount' or 'hopCountAndPathVector'.

         This object was obsoleted in release 13.0."
    DEFVAL      { 255 }
    ::= { vRtrLdpGeneralEntry 18 }

vRtrLdpGenPathVectorLimit        OBJECT-TYPE
    SYNTAX      Unsigned32 (0..255)
    MAX-ACCESS  read-create
    STATUS      obsolete
    DESCRIPTION
        "The value of vRtrLdpGenPathVectorLimit specifies the maximum
         allowable value for the path vector count.  The value of this
         object is valid and used only if vRtrLdpGenLoopDetectCapable
         has a value of either 'pathVector' or 'hopCountAndPathVector'.

         This object was obsoleted in release 13.0."
    DEFVAL      { 255 }
    ::= { vRtrLdpGeneralEntry 19 }

vRtrLdpGenBackoffTime            OBJECT-TYPE
    SYNTAX      TmnxLdpBackoffTime (1..2592000)
    UNITS       "seconds"
    MAX-ACCESS  read-create
    STATUS      obsolete
    DESCRIPTION
        "The value of vRtrLdpGenBackoffTime specifies the initial value for the
         backoff interval.

         The backoff interval is the time, in seconds, that LDP waits after an
         LDP session setup has failed before it attempts to setup the session
         again. After the LDP session startup fails the first time, the backoff
         interval is set to the value of vRtrLdpGenBackoffTime. Thereafter, if
         session startup fails again the backoff interval increases
         exponentially.

         This object was obsoleted in release 13.0."
    DEFVAL      { 15 }
    ::= { vRtrLdpGeneralEntry 20 }

vRtrLdpGenMaxBackoffTime         OBJECT-TYPE
    SYNTAX      TmnxLdpBackoffTime
    UNITS       "seconds"
    MAX-ACCESS  read-create
    STATUS      obsolete
    DESCRIPTION
        "The value of vRtrLdpGenMaxBackoffTime specifies the maximum value for
         the backoff interval.

         For each successive failure of the LDP session startup, the backoff
         interval (the time for which the router waits before retrying)
         increases exponentially. If the backoff interval exceeds
         vRtrLdpGenMaxBackoffTime, the router will give up trying to establish
         the LDP session.

         If vRtrLdpGenMaxBackoffTime is set to zero (0), then the backoff
         interval does not increase exponentially after the first session
         startup attempt fails. Instead it remains constant and LDP will keep
         retrying to establish a session until it succeeds.

         This object was obsoleted in release 13.0."
    DEFVAL      { 120 }
    ::= { vRtrLdpGeneralEntry 21 }

vRtrLdpGenTargKeepAliveFactor    OBJECT-TYPE
    SYNTAX      TmnxLdpKeepAliveFactor
    MAX-ACCESS  read-create
    STATUS      obsolete
    DESCRIPTION
        "The value of vRtrLdpGenTargKeepAliveFactor specifies the value by
         which the keepalive timeout (vRtrLdpGenTargKeepAliveTimeout) should be
         divided to give the keepalive time i.e. the time interval, in seconds,
         between LDP keepalive messages. LDP keepalive messages are sent to
         keep the LDP session from timing out when no other LDP traffic is
         being sent between the neighbors.

         This value is only applicable to targeted sessions and not to LDP
         interfaces.

         This object was obsoleted in release 13.0."
    DEFVAL      { 4 }
    ::= { vRtrLdpGeneralEntry 22 }

vRtrLdpGenTargKeepAliveTimeout   OBJECT-TYPE
    SYNTAX      TmnxLdpNewKeepAliveTimeout
    UNITS       "seconds"
    MAX-ACCESS  read-create
    STATUS      obsolete
    DESCRIPTION
        "The value of vRtrLdpGenTargKeepAliveTimeout specifies the time
         interval, in seconds, that LDP waits before tearing down a session. If
         no LDP messages are exchanged during this time interval, the LDP
         session is torn down. Generally the value of
         vRtrLdpGenTargKeepAliveTimeout is configured to be 3 times the
         keepalive time (the time interval between successive LDP keepalive
         messages).

         This value is only applicable to targeted sessions and not to LDP
         interfaces.

         This object was obsoleted in release 13.0."
    DEFVAL      { 40 }
    ::= { vRtrLdpGeneralEntry 23 }

vRtrLdpGenTargHelloFactor        OBJECT-TYPE
    SYNTAX      TmnxLdpHelloFactor
    MAX-ACCESS  read-create
    STATUS      obsolete
    DESCRIPTION
        "The value of vRtrLdpGenTargHelloFactor specifies the value by which
         the hello timeout (vRtrLdpGenTargHelloTimeout) should be divided to
         give the hello time i.e. the time interval, in seconds, between LDP
         Hello messages. LDP uses hello messages to discover neighbors and to
         detect loss of connectivity with its neighbors.

         This value is only applicable to targeted sessions and not to LDP
         interfaces.

         This object was obsoleted in release 13.0."
    DEFVAL      { 3 }
    ::= { vRtrLdpGeneralEntry 24 }

vRtrLdpGenTargHelloTimeout       OBJECT-TYPE
    SYNTAX      TmnxLdpNewHelloTimeout
    UNITS       "seconds"
    MAX-ACCESS  read-create
    STATUS      obsolete
    DESCRIPTION
        "The value of vRtrLdpGenTargHelloTimeout specifies the hello time also
         known as hold time. It is the time interval, in seconds, that LDP
         waits before declaring a neighbor to be down. Hello timeout is local
         to the system and is sent in the hello messages to a neighbor. Hello
         timeout cannot be set to a value that is less than 3 times the hello
         time.

         This value is only applicable to targeted sessions and not to LDP
         interfaces.

         This object was obsoleted in release 13.0."
    DEFVAL      { 45 }
    ::= { vRtrLdpGeneralEntry 25 }

vRtrLdpGenTargPassiveMode        OBJECT-TYPE
    SYNTAX      TruthValue
    MAX-ACCESS  read-create
    STATUS      obsolete
    DESCRIPTION
        "The value of vRtrLdpGenTargPassiveMode specifies the mode used for
         setting up LDP sessions. When it has a value of 'true', LDP responds
         only when it gets a connect request from a peer and will not attempt
         to actively connect to its neighbors. When it has a value of 'false',
         LDP actively tries to connect to its peers.

         This value is only applicable to targeted sessions and not to LDP
         interfaces.

         This object was obsoleted in release 13.0."
    DEFVAL      { false }
    ::= { vRtrLdpGeneralEntry 26 }

vRtrLdpGenTargetedSessions       OBJECT-TYPE
    SYNTAX      TruthValue
    MAX-ACCESS  read-create
    STATUS      obsolete
    DESCRIPTION
        "The value of vRtrLdpGenTargetedSessions specifies whether or
         not targeted sessions are allowed.  Targeted sessions are LDP
         sessions between indirectly connected peers.  The discovery
         messages for an indirect LDP session are addressed to the
         specified peer instead of to the multicast address.  When this
         object has a value of 'true', targeted sessions are enabled.
         When its value is 'false', targeted sessions are disabled.

         This object was obsoleted in release 13.0."
    DEFVAL      { true }
    ::= { vRtrLdpGeneralEntry 27 }

vRtrLdpGenCreateTime             OBJECT-TYPE
    SYNTAX      TimeStamp
    MAX-ACCESS  read-only
    STATUS      obsolete
    DESCRIPTION
        "The value of vRtrLdpGenCreateTime specifies the sysUpTime when this
         LDP instance was created.

         This object was obsoleted in release 13.0."
    ::= { vRtrLdpGeneralEntry 28 }

vRtrLdpGenUpTime                 OBJECT-TYPE
    SYNTAX      TimeInterval
    MAX-ACCESS  read-only
    STATUS      obsolete
    DESCRIPTION
        "The value of vRtrLdpGenUpTime specifies the time, in hundreds of
         seconds, that the LDP instance has been in current operational state
         (vRtrLdpGenOperState).

         If the value of vRtrLdpGenOperState is 'inService (2)', then
         vRtrLdpGenUpTime specifies the time that the LDP instance has been
         operationally up.

         If the value of vRtrLdpGenOperState is 'outOfService (3)', then
         vRtrLdpGenUpTime specifies the time that the LDP instance has been
         operationally down.

         If the value of vRtrLdpGenOperState is 'transition (4)', then
         vRtrLdpGenUpTime specifies the time that the LDP instance has been
         operationally in transition.

         This object was obsoleted in release 13.0."
    ::= { vRtrLdpGeneralEntry 29 }

vRtrLdpGenImportPolicy1          OBJECT-TYPE
    SYNTAX      TPolicyStatementNameOrEmpty
    MAX-ACCESS  read-create
    STATUS      obsolete
    DESCRIPTION
        "The value of vRtrLdpGenImportPolicy1 specifies the first import policy
         used to filter LDP label bindings received from LDP peers.

         This object was obsoleted in release 13.0."
    DEFVAL      { ''H }
    ::= { vRtrLdpGeneralEntry 30 }

vRtrLdpGenImportPolicy2          OBJECT-TYPE
    SYNTAX      TPolicyStatementNameOrEmpty
    MAX-ACCESS  read-create
    STATUS      obsolete
    DESCRIPTION
        "The value of vRtrLdpGenImportPolicy2 specifies the second import
         policy used to filter LDP label bindings received from LDP peers.

         This object was obsoleted in release 13.0."
    DEFVAL      { ''H }
    ::= { vRtrLdpGeneralEntry 31 }

vRtrLdpGenImportPolicy3          OBJECT-TYPE
    SYNTAX      TPolicyStatementNameOrEmpty
    MAX-ACCESS  read-create
    STATUS      obsolete
    DESCRIPTION
        "The value of vRtrLdpGenImportPolicy3 specifies the third import policy
         used to filter LDP label bindings received from LDP peers.

         This object was obsoleted in release 13.0."
    DEFVAL      { ''H }
    ::= { vRtrLdpGeneralEntry 32 }

vRtrLdpGenImportPolicy4          OBJECT-TYPE
    SYNTAX      TPolicyStatementNameOrEmpty
    MAX-ACCESS  read-create
    STATUS      obsolete
    DESCRIPTION
        "The value of vRtrLdpGenImportPolicy4 specifies the fourth import
         policy used to filter LDP label bindings received from LDP peers.

         This object was obsoleted in release 13.0."
    DEFVAL      { ''H }
    ::= { vRtrLdpGeneralEntry 33 }

vRtrLdpGenImportPolicy5          OBJECT-TYPE
    SYNTAX      TPolicyStatementNameOrEmpty
    MAX-ACCESS  read-create
    STATUS      obsolete
    DESCRIPTION
        "The value of vRtrLdpGenImportPolicy5 specifies the fifth import policy
         used to filter LDP label bindings received from LDP peers.

         This object was obsoleted in release 13.0."
    DEFVAL      { ''H }
    ::= { vRtrLdpGeneralEntry 34 }

vRtrLdpGenExportPolicy1          OBJECT-TYPE
    SYNTAX      TPolicyStatementNameOrEmpty
    MAX-ACCESS  read-create
    STATUS      obsolete
    DESCRIPTION
        "The value of vRtrLdpGenExportPolicy1 specifies the first export policy
         used to filter LDP label bindings advertised to LDP peers.

         This object was obsoleted in release 13.0."
    DEFVAL      { ''H }
    ::= { vRtrLdpGeneralEntry 35 }

vRtrLdpGenExportPolicy2          OBJECT-TYPE
    SYNTAX      TPolicyStatementNameOrEmpty
    MAX-ACCESS  read-create
    STATUS      obsolete
    DESCRIPTION
        "The value of vRtrLdpGenExportPolicy2 specifies the second export
         policy used to filter LDP label bindings advertised to LDP peers.

         This object was obsoleted in release 13.0."
    DEFVAL      { ''H }
    ::= { vRtrLdpGeneralEntry 36 }

vRtrLdpGenExportPolicy3          OBJECT-TYPE
    SYNTAX      TPolicyStatementNameOrEmpty
    MAX-ACCESS  read-create
    STATUS      obsolete
    DESCRIPTION
        "The value of vRtrLdpGenExportPolicy3 specifies the third export policy
         used to filter LDP label bindings advertised to LDP peers.

         This object was obsoleted in release 13.0."
    DEFVAL      { ''H }
    ::= { vRtrLdpGeneralEntry 37 }

vRtrLdpGenExportPolicy4          OBJECT-TYPE
    SYNTAX      TPolicyStatementNameOrEmpty
    MAX-ACCESS  read-create
    STATUS      obsolete
    DESCRIPTION
        "The value of vRtrLdpGenExportPolicy4 specifies the fourth export
         policy used to filter LDP label bindings advertised to LDP peers.

         This object was obsoleted in release 13.0."
    DEFVAL      { ''H }
    ::= { vRtrLdpGeneralEntry 38 }

vRtrLdpGenExportPolicy5          OBJECT-TYPE
    SYNTAX      TPolicyStatementNameOrEmpty
    MAX-ACCESS  read-create
    STATUS      obsolete
    DESCRIPTION
        "The value of vRtrLdpGenExportPolicy5 specifies the fifth export policy
         used to filter LDP label bindings advertised to LDP peers.

         This object was obsoleted in release 13.0."
    DEFVAL      { ''H }
    ::= { vRtrLdpGeneralEntry 39 }

vRtrLdpGenTunnelDownDampTime     OBJECT-TYPE
    SYNTAX      Unsigned32 (0..20)
    UNITS       "seconds"
    MAX-ACCESS  read-create
    STATUS      obsolete
    DESCRIPTION
        "The value of vRtrLdpGenTunnelDownDampTime specifies the time interval,
         in seconds, that LDP waits before posting a tunnel down event to the
         Route Table Manager. If a tunnel up event is generated before the
         damping interval has elapsed, a tunnel modify event will be posted to
         the Route Table Manager (RTM). If this value is set to 0, then tunnel
         down events are not damped.

         This object was obsoleted in release 13.0."
    DEFVAL      { 3 }
    ::= { vRtrLdpGeneralEntry 40 }

vRtrLdpGenOperDownReason         OBJECT-TYPE
    SYNTAX      TmnxLdpGenOperDownReasonCode
    MAX-ACCESS  read-only
    STATUS      obsolete
    DESCRIPTION
        "The value of vRtrLdpGenOperDownReason specifies the reason that the
         LDP instance is operationally down.

         This object was obsoleted in release 13.0."
    ::= { vRtrLdpGeneralEntry 41 }

vRtrLdpGenTrustList              OBJECT-TYPE
    SYNTAX      TFilterID
    MAX-ACCESS  read-create
    STATUS      obsolete
    DESCRIPTION
        "The value of vRtrLdpGenTrustList specifies the IP filter ID used to
         verify trusted T-LDP peers. The IP filter specified by this object
         should contain a list of src-ip matches. The value '0' is not a valid
         IP filter ID, but it is used to indicate that there is no trust list.

         This object was obsoleted in release 5.0."
    DEFVAL      { 0 }
    ::= { vRtrLdpGeneralEntry 42 }

vRtrLdpGenGracefulRestart        OBJECT-TYPE
    SYNTAX      TruthValue
    MAX-ACCESS  read-create
    STATUS      obsolete
    DESCRIPTION
        "The value of vRtrLdpGenGracefulRestart specifies whether graceful
         restart helper is allowed.  When this object has a value of 'true',
         graceful restart helper is enabled.  When its value is 'false',
         graceful restart helper is disabled.

         This object was obsoleted in release 13.0."
    DEFVAL      { false }
    ::= { vRtrLdpGeneralEntry 43 }

vRtrLdpGenGRNbrLiveTime          OBJECT-TYPE
    SYNTAX      Unsigned32 (5..300)
    UNITS       "seconds"
    MAX-ACCESS  read-create
    STATUS      obsolete
    DESCRIPTION
        "The value of vRtrLdpGenGRNbrLiveTime specifies the value for neighbor
         liveness timer.  The amount of time the Label Switching Router (LSR)
         keeps its stale label-FEC bindings is set to the lesser of the FT
         Reconnect Timeout, as was advertised by the  neighbor, and this local
         timer, called the Neighbor Liveness Timer.

         The LSR waits for the specified time till a LDP session re-establishes
         itself.  If within that time the LSR still does not establish an LDP
         session with the neighbor, all the stale bindings are deleted.  This
         object has meaning only when vRtrLdpGenGracefulRestart is 'true'.

         This object was obsoleted in release 13.0."
    DEFVAL      { 120 }
    ::= { vRtrLdpGeneralEntry 44 }

vRtrLdpGenGRMaxRecoveryTime      OBJECT-TYPE
    SYNTAX      Unsigned32 (15..1800)
    UNITS       "seconds"
    MAX-ACCESS  read-create
    STATUS      obsolete
    DESCRIPTION
        "The value of vRtrLdpGenGRMaxRecoveryTime specifies the local maximum
         recovery time.

         If the Label Switching Router (LSR)  determines that the neighbor was
         able to preserve its MPLS forwarding state (as was indicated by the
         non-zero Recovery Time advertised by the neighbor), the LSR should
         further keep the stale label-FEC  bindings, received from the
         neighbor, for as long as the lesser of the Recovery Time advertised
         by the neighbor, and a local configurable value, called Maximum
         Recovery Time, allows.  This object has meaning only when
         vRtrLdpGenGracefulRestart is 'true'.

         This object was obsoleted in release 13.0."
    DEFVAL      { 120 }
    ::= { vRtrLdpGeneralEntry 45 }

vRtrLdpGenLabelWithdrawalDelay   OBJECT-TYPE
    SYNTAX      Unsigned32 (0 | 3..120)
    UNITS       "seconds"
    MAX-ACCESS  read-create
    STATUS      obsolete
    DESCRIPTION
        "The value of vRtrLdpGenLabelWithdrawalDelay specifies the time
         interval, in seconds, LDP will delay for the withdrawal of FEC-label
         binding it distributed to its neighbours when FEC is deactivated. When
         the timer expires, LDP then sends a label withdrawal for the FEC to
         all its neighbours. This is applicable only to LDP transport tunnels
         (ipv4 prefix FECs) and is not applicable to Pseudowires (service
         FECs).

         A value of 0 indicates that vRtrLdpGenLabelWithdrawalDelay is
         disabled.

         This object was obsoleted in release 13.0."
    DEFVAL      { 0 }
    ::= { vRtrLdpGeneralEntry 46 }

vRtrLdpGenImplicitNull           OBJECT-TYPE
    SYNTAX      TruthValue
    MAX-ACCESS  read-create
    STATUS      obsolete
    DESCRIPTION
        "The value of vRtrLdpGenImplicitNull specifies whether or not to signal
         implicit null values for all LDP FECs for which this node is an egress
         Label Edge Router (LER). When the value is true implicit null values
         are signaled.

         This object was obsoleted in release 13.0."
    DEFVAL      { false }
    ::= { vRtrLdpGeneralEntry 47 }

vRtrLdpGenShortTTLPropLocal      OBJECT-TYPE
    SYNTAX      TruthValue
    MAX-ACCESS  read-create
    STATUS      obsolete
    DESCRIPTION
        "The value of vRtrLdpGenShortTTLPropLocal specifies whether or not
         to enable the propagation of time to live (TTL) from the header of
         IP packet into the header of resulting MPLS packet for all local
         packets forwarded over a LDP shortcut.  When the value is set to
         'true' TTL is propagated from the header of IP packet into the
         header of the resulting MPLS packet for all local packets.

         This object was obsoleted in release 13.0."
    DEFVAL      { true }
    ::= { vRtrLdpGeneralEntry 48 }

vRtrLdpGenShortTTLPropTransit    OBJECT-TYPE
    SYNTAX      TruthValue
    MAX-ACCESS  read-create
    STATUS      obsolete
    DESCRIPTION
        "The value of vRtrLdpGenShortTTLPropTransit specifies whether or not
         to enable the propagation of time to live (TTL) from the header of
         IP packet into the header of resulting MPLS packet for all transit
         packets forwarded over a LDP shortcut.  When the value is set to
         'true' TTL is propagated from the header of IP packet into the
         header of the resulting MPLS packet for all transit packets.

         This object was obsoleted in release 13.0."
    DEFVAL      { true }
    ::= { vRtrLdpGeneralEntry 49 }

vRtrLdpGenMPMBBTime              OBJECT-TYPE
    SYNTAX      Unsigned32 (0..10)
    UNITS       "seconds"
    MAX-ACCESS  read-create
    STATUS      obsolete
    DESCRIPTION
        "The value of vRtrLdpGenMPMBBTime specifies the maximum time a Multi
         Point (MP) transit node must wait before switching over to a new path
         if the new node does not send Make Before Break (MBB) Tag Length Value
         (TLV) to inform of the availability of the data plane.

         This object was obsoleted in release 13.0."
    DEFVAL      { 3 }
    ::= { vRtrLdpGeneralEntry 50 }

vRtrLdpGenTunlTblExportPolicy1   OBJECT-TYPE
    SYNTAX      TPolicyStatementNameOrEmpty
    MAX-ACCESS  read-create
    STATUS      obsolete
    DESCRIPTION
        "The value of vRtrLdpGenTunlTblExportPolicy1 specifies the first tunnel
         table export policy used for exporting tunneled routes from the CPM
         tunnel table as LDP FEC.

         This object was obsoleted in release 13.0."
    DEFVAL      { ''H }
    ::= { vRtrLdpGeneralEntry 51 }

vRtrLdpGenTunlTblExportPolicy2   OBJECT-TYPE
    SYNTAX      TPolicyStatementNameOrEmpty
    MAX-ACCESS  read-create
    STATUS      obsolete
    DESCRIPTION
        "The value of vRtrLdpGenTunlTblExportPolicy2 specifies the second
         tunnel table export policy used for exporting tunneled routes from the
         CPM tunnel table as LDP FEC.

         This object was obsoleted in release 13.0."
    DEFVAL      { ''H }
    ::= { vRtrLdpGeneralEntry 52 }

vRtrLdpGenTunlTblExportPolicy3   OBJECT-TYPE
    SYNTAX      TPolicyStatementNameOrEmpty
    MAX-ACCESS  read-create
    STATUS      obsolete
    DESCRIPTION
        "The value of vRtrLdpGenTunlTblExportPolicy3 specifies the third tunnel
         table export policy used for exporting tunneled routes from the CPM
         tunnel table as LDP FEC.

         This object was obsoleted in release 13.0."
    DEFVAL      { ''H }
    ::= { vRtrLdpGeneralEntry 53 }

vRtrLdpGenTunlTblExportPolicy4   OBJECT-TYPE
    SYNTAX      TPolicyStatementNameOrEmpty
    MAX-ACCESS  read-create
    STATUS      obsolete
    DESCRIPTION
        "The value of vRtrLdpGenTunlTblExportPolicy4 specifies the fourth
         tunnel table export policy used for exporting tunneled routes from the
         CPM tunnel table as LDP FEC.

         This object was obsoleted in release 13.0."
    DEFVAL      { ''H }
    ::= { vRtrLdpGeneralEntry 54 }

vRtrLdpGenTunlTblExportPolicy5   OBJECT-TYPE
    SYNTAX      TPolicyStatementNameOrEmpty
    MAX-ACCESS  read-create
    STATUS      obsolete
    DESCRIPTION
        "The value of vRtrLdpGenTunlTblExportPolicy5 specifies the fifth tunnel
         table export policy used for exporting tunneled routes from the CPM
         tunnel table as LDP FEC.

         This object was obsoleted in release 13.0."
    DEFVAL      { ''H }
    ::= { vRtrLdpGeneralEntry 55 }

vRtrLdpGenP2MPCapability         OBJECT-TYPE
    SYNTAX      TruthValue
    MAX-ACCESS  read-only
    STATUS      obsolete
    DESCRIPTION
        "The value of vRtrLdpGenP2MPCapability specifies whether
         Point-to-Multipoint (P2MP) FEC capability is supported in the LDP
         instance or not. When the value is 'true', the LDP instance is P2MP
         capable.

         This object was obsoleted in release 13.0."
    DEFVAL      { false }
    ::= { vRtrLdpGeneralEntry 56 }

vRtrLdpGenMPMBBCapability        OBJECT-TYPE
    SYNTAX      TruthValue
    MAX-ACCESS  read-only
    STATUS      obsolete
    DESCRIPTION
        "The value of vRtrLdpGenMPMBBCapability specifies whether
         Multipoint(MP) Make-Before-Break (MBB) capability is supported
         in the LDP instance or not.  When the value is 'true', the LDP
         instance is MP MBB capable.

         This object was obsoleted in release 13.0."
    DEFVAL      { false }
    ::= { vRtrLdpGeneralEntry 57 }

vRtrLdpGenDynamicCapability      OBJECT-TYPE
    SYNTAX      TruthValue
    MAX-ACCESS  read-only
    STATUS      obsolete
    DESCRIPTION
        "The value of vRtrLdpGenDynamicCapability specifies whether dynamic
         capability negotiation is supported or not in LDP sessions associated
         with the LDP instance.  When 'true', the LDP instance supports dynamic
         capability negotiation.

         This object was obsoleted in release 13.0."
    DEFVAL      { false }
    ::= { vRtrLdpGeneralEntry 58 }

vRtrLdpGenLdpFrr                 OBJECT-TYPE
    SYNTAX      TruthValue
    MAX-ACCESS  read-create
    STATUS      obsolete
    DESCRIPTION
        "The value of vRtrLdpGenLdpFrr specifies whether fast reroute of LDP
         tunnel is enabled or disabled.

         When the value of vRtrLdpGenLdpFrr is set to 'true' fast reroute of
         LDP tunnel is enabled and when vRtrLdpGenLdpFrr is set to 'false' fast
         reroute of LDP tunnel is disabled.

         This object was obsoleted in release 13.0."
    DEFVAL      { false }
    ::= { vRtrLdpGeneralEntry 59 }

vRtrLdpGenTargHelloReduction     OBJECT-TYPE
    SYNTAX      TruthValue
    MAX-ACCESS  read-create
    STATUS      obsolete
    DESCRIPTION
        "The value of vRtrLdpGenTargHelloReduction specifies whether hello
         reduction to this targeted peer is enabled or not. If enabled, the
         sender advertises further dampened vRtrLdpGenTargHelloTimeout, to the
         targeted peer after LDP session is established.

         The value of 'true' means targeted hello reduction is enabled.

         This object was obsoleted in release 13.0."
    DEFVAL      { false }
    ::= { vRtrLdpGeneralEntry 60 }

vRtrLdpGenTargHelloReductionFctr OBJECT-TYPE
    SYNTAX      Unsigned32 (3..20)
    MAX-ACCESS  read-create
    STATUS      obsolete
    DESCRIPTION
        "The value of vRtrLdpGenTargHelloReductionFctr specifies the number of
         hello messages that are sent at consistent vRtrLdpGenTargHelloTimeout,
         before advertising further dampened vRtrLdpGenTargHelloTimeout.

         An 'inconsistentValue' error is returned if this object is set when
         vRtrLdpGenTargHelloReduction is disabled.

         This object was obsoleted in release 13.0."
    DEFVAL      { 3 }
    ::= { vRtrLdpGeneralEntry 61 }

vRtrLdpGenMcastUpstreamFrr       OBJECT-TYPE
    SYNTAX      TruthValue
    MAX-ACCESS  read-create
    STATUS      obsolete
    DESCRIPTION
        "The value of vRtrLdpGenMcastUpstreamFrr specifies whether mLDP fast
         upstream switchover feature is enabled or not for the LDP instance.
         When 'true', the LDP instance supports mLDP fast upstream switchover.

         This object was obsoleted in release 13.0."
    DEFVAL      { false }
    ::= { vRtrLdpGeneralEntry 62 }

vRtrLdpGenOverloadCapability     OBJECT-TYPE
    SYNTAX      TruthValue
    MAX-ACCESS  read-only
    STATUS      obsolete
    DESCRIPTION
        "The value of vRtrLdpGenOverloadCapability indicates whether LSR
         Overload is supported or not in LDP sessions associated with the LDP
         instance. When 'true', the LDP instance is LSR overload capable.

         This object was obsoleted in release 13.0."
    ::= { vRtrLdpGeneralEntry 63 }

vRtrLdpStatsTable                OBJECT-TYPE
    SYNTAX      SEQUENCE OF VRtrLdpStatsEntry
    MAX-ACCESS  not-accessible
    STATUS      obsolete
    DESCRIPTION
        "vRtrLdpStatsTable is a read-only table. The purpose of this table is
         to keep statistical information about an LDP Instance.

         Use of AUGMENTS clause implies a one-to-one dependent
         relationship between the base table, vRtrLdpGeneralTable,
         and the augmenting table, vRtrLdpStatsTable. This in
         effect extends the vRtrLdpGeneralTable with additional
         columns.  Creation or deletion of a row in the
         vRtrLdpGeneralTable results in the same fate for the row
         in the vRtrLdpStatsTable.

         In 13.0 this table has been replaced by
         TIMETRA-LDP-NG-MIB::vLdpNgStatsTable."
    ::= { tmnxLdpObjs 2 }

vRtrLdpStatsEntry                OBJECT-TYPE
    SYNTAX      VRtrLdpStatsEntry
    MAX-ACCESS  not-accessible
    STATUS      obsolete
    DESCRIPTION
        "A row in this table represents statistical information about an LDP
         instance."
    AUGMENTS    { vRtrLdpGeneralEntry }
    ::= { vRtrLdpStatsTable 1 }

VRtrLdpStatsEntry                ::= SEQUENCE
{
    vRtrLdpStatsOperDownEvents       Counter32,
    vRtrLdpStatsActiveSessions       Gauge32,
    vRtrLdpStatsActiveAdjacencies    Gauge32,
    vRtrLdpStatsActiveInterfaces     Gauge32,
    vRtrLdpStatsInactiveInterfaces   Gauge32,
    vRtrLdpStatsActiveTargSessions   Gauge32,
    vRtrLdpStatsInactiveTargSessions Gauge32,
    vRtrLdpStatsAddrFECRecv          Gauge32,
    vRtrLdpStatsAddrFECSent          Gauge32,
    vRtrLdpStatsSvcFECRecv           Gauge32,
    vRtrLdpStatsSvcFECSent           Gauge32,
    vRtrLdpStatsAttemptedSessions    Counter32,
    vRtrLdpStatsSessRejNoHelloErrors Counter32,
    vRtrLdpStatsSessRejAdvErrors     Counter32,
    vRtrLdpStatsSessRejMaxPduErrors  Counter32,
    vRtrLdpStatsSessRejLabelRangeErrors Counter32,
    vRtrLdpStatsBadLdpIdentifierErrors Counter32,
    vRtrLdpStatsBadPduLengthErrors   Counter32,
    vRtrLdpStatsBadMessageLengthErrors Counter32,
    vRtrLdpStatsBadTlvLengthErrors   Counter32,
    vRtrLdpStatsMalformedTlvValueErrors Counter32,
    vRtrLdpStatsKeepAliveExpiredErrors Counter32,
    vRtrLdpStatsShutdownNotifRecv    Counter32,
    vRtrLdpStatsShutdownNotifSent    Counter32,
    vRtrLdpStatsEgrFecPfxCount       Counter32,
    vRtrLdpStatsUnknownTlvErrors     Counter32,
    vRtrLdpStatsP2MPFECSent          Gauge32,
    vRtrLdpStatsP2MPFECRecv          Gauge32
}

vRtrLdpStatsOperDownEvents       OBJECT-TYPE
    SYNTAX      Counter32
    MAX-ACCESS  read-only
    STATUS      obsolete
    DESCRIPTION
        "The value of vRtrLdpStatsOperDownEvents specifies the number of times
         the LDP instance has gone operationally down since the instance was
         created.

         This object was obsoleted in release 13.0."
    ::= { vRtrLdpStatsEntry 1 }

vRtrLdpStatsActiveSessions       OBJECT-TYPE
    SYNTAX      Gauge32
    MAX-ACCESS  read-only
    STATUS      obsolete
    DESCRIPTION
        "The value of vRtrLdpStatsActiveSessions specifies the number of active
         sessions (i.e. session in some form of creation) associated with the
         LDP instance.

         This object was obsoleted in release 13.0."
    ::= { vRtrLdpStatsEntry 2 }

vRtrLdpStatsActiveAdjacencies    OBJECT-TYPE
    SYNTAX      Gauge32
    MAX-ACCESS  read-only
    STATUS      obsolete
    DESCRIPTION
        "The value of vRtrLdpStatsActiveAdjacencies specifies the number of
         active adjacencies (i.e. established sessions) associated with the LDP
         instance.

         This object was obsoleted in release 13.0."
    ::= { vRtrLdpStatsEntry 3 }

vRtrLdpStatsActiveInterfaces     OBJECT-TYPE
    SYNTAX      Gauge32
    MAX-ACCESS  read-only
    STATUS      obsolete
    DESCRIPTION
        "The value of vRtrLdpStatsActiveInterfaces specifies the number of
         active (i.e. operationally up) interfaces associated with the LDP
         instance.

         This object was obsoleted in release 13.0."
    ::= { vRtrLdpStatsEntry 4 }

vRtrLdpStatsInactiveInterfaces   OBJECT-TYPE
    SYNTAX      Gauge32
    MAX-ACCESS  read-only
    STATUS      obsolete
    DESCRIPTION
        "The value of vRtrLdpStatsInactiveInterfaces specifies the number of
         inactive (i.e. operationally down) interfaces associated with the LDP
         instance.

         This object was obsoleted in release 13.0."
    ::= { vRtrLdpStatsEntry 5 }

vRtrLdpStatsActiveTargSessions   OBJECT-TYPE
    SYNTAX      Gauge32
    MAX-ACCESS  read-only
    STATUS      obsolete
    DESCRIPTION
        "The value of vRtrLdpStatsActiveTargSessions specifies the number of
         configured targeted peers that are administratively up in an LDP
         instance.

         This object was obsoleted in release 13.0."
    ::= { vRtrLdpStatsEntry 6 }

vRtrLdpStatsInactiveTargSessions OBJECT-TYPE
    SYNTAX      Gauge32
    MAX-ACCESS  read-only
    STATUS      obsolete
    DESCRIPTION
        "The value of vRtrLdpStatsInactiveTargSessions specifies the number of
         inactive (i.e. operationally down) targeted sessions associated with
         the LDP instance.

         This object was obsoleted in release 13.0."
    ::= { vRtrLdpStatsEntry 7 }

vRtrLdpStatsAddrFECRecv          OBJECT-TYPE
    SYNTAX      Gauge32
    MAX-ACCESS  read-only
    STATUS      obsolete
    DESCRIPTION
        "The value of vRtrLdpStatsAddrFECRecv specifies the number of Address
         FECs received by the LDP instance from its neighbors.

         This object was obsoleted in release 13.0."
    ::= { vRtrLdpStatsEntry 8 }

vRtrLdpStatsAddrFECSent          OBJECT-TYPE
    SYNTAX      Gauge32
    MAX-ACCESS  read-only
    STATUS      obsolete
    DESCRIPTION
        "The value of vRtrLdpStatsAddrFECSent specifies the number of Address
         FECs sent by the LDP instance to its neighbors.

         This object was obsoleted in release 13.0."
    ::= { vRtrLdpStatsEntry 9 }

vRtrLdpStatsSvcFECRecv           OBJECT-TYPE
    SYNTAX      Gauge32
    MAX-ACCESS  read-only
    STATUS      obsolete
    DESCRIPTION
        "The value of vRtrLdpStatsSvcFECRecv specifies the number of Service
         FECs received by the LDP instance from its neighbors.

         This object was obsoleted in release 13.0."
    ::= { vRtrLdpStatsEntry 10 }

vRtrLdpStatsSvcFECSent           OBJECT-TYPE
    SYNTAX      Gauge32
    MAX-ACCESS  read-only
    STATUS      obsolete
    DESCRIPTION
        "The value of vRtrLdpStatsSvcFECSent specifies the number of Service
         FECs sent by the LDP instance to its neighbors.

         This object was obsoleted in release 13.0."
    ::= { vRtrLdpStatsEntry 11 }

vRtrLdpStatsAttemptedSessions    OBJECT-TYPE
    SYNTAX      Counter32
    MAX-ACCESS  read-only
    STATUS      obsolete
    DESCRIPTION
        "The value of vRtrLdpStatsAttemptedSessions specifies the total number
         of attempted sessions for this LDP instance.

         This object was obsoleted in release 13.0."
    ::= { vRtrLdpStatsEntry 12 }

vRtrLdpStatsSessRejNoHelloErrors OBJECT-TYPE
    SYNTAX      Counter32
    MAX-ACCESS  read-only
    STATUS      obsolete
    DESCRIPTION
        "The value of vRtrLdpStatsSessRejNoHelloErrors gives the total number
         of Session Rejected/No Hello Error Notification Messages sent or
         received by this LDP instance.

         This object was obsoleted in release 13.0."
    ::= { vRtrLdpStatsEntry 13 }

vRtrLdpStatsSessRejAdvErrors     OBJECT-TYPE
    SYNTAX      Counter32
    MAX-ACCESS  read-only
    STATUS      obsolete
    DESCRIPTION
        "The value of vRtrLdpStatsSessRejAdvErrors gives the total number of
         Session Rejected/Parameters Advertisement Mode Error Notification
         Messages sent or received by this LDP instance.

         This object was obsoleted in release 13.0."
    ::= { vRtrLdpStatsEntry 14 }

vRtrLdpStatsSessRejMaxPduErrors  OBJECT-TYPE
    SYNTAX      Counter32
    MAX-ACCESS  read-only
    STATUS      obsolete
    DESCRIPTION
        "The value of vRtrLdpStatsSessRejMaxPduErrors gives the total number of
         Session Rejected/Parameters Max Pdu Length Error Notification Messages
         sent or received by this LDP instance.

         This object was obsoleted in release 13.0."
    ::= { vRtrLdpStatsEntry 15 }

vRtrLdpStatsSessRejLabelRangeErrors OBJECT-TYPE
    SYNTAX      Counter32
    MAX-ACCESS  read-only
    STATUS      obsolete
    DESCRIPTION
        "The value of vRtrLdpStatsSessRejLabelRangeErrors gives the total
         number of Session Rejected/Parameters Label Range Error Notification
         Messages sent or received by this LDP instance.

         This object was obsoleted in release 13.0."
    ::= { vRtrLdpStatsEntry 16 }

vRtrLdpStatsBadLdpIdentifierErrors OBJECT-TYPE
    SYNTAX      Counter32
    MAX-ACCESS  read-only
    STATUS      obsolete
    DESCRIPTION
        "The value of vRtrLdpStatsBadLdpIdentifierErrors gives the number of
         Bad LDP Identifier Fatal Errors detected for sessions associated with
         this LDP instance.

         This object was obsoleted in release 13.0."
    REFERENCE
        "LDP Specification, Section 3.5.1.2."
    ::= { vRtrLdpStatsEntry 17 }

vRtrLdpStatsBadPduLengthErrors   OBJECT-TYPE
    SYNTAX      Counter32
    MAX-ACCESS  read-only
    STATUS      obsolete
    DESCRIPTION
        "The value of vRtrLdpStatsBadPduLengthErrors gives the number of Bad
         Pdu Length Fatal Errors detected for sessions associated with this LDP
         instance.

         This object was obsoleted in release 13.0."
    REFERENCE
        "LDP Specification, Section 3.5.1.2."
    ::= { vRtrLdpStatsEntry 18 }

vRtrLdpStatsBadMessageLengthErrors OBJECT-TYPE
    SYNTAX      Counter32
    MAX-ACCESS  read-only
    STATUS      obsolete
    DESCRIPTION
        "The value of vRtrLdpStatsBadMessageLengthErrors gives the number of
         Bad Message Length Fatal Errors detected for sessions associated with
         this LDP instance.

         This object was obsoleted in release 13.0."
    REFERENCE
        "LDP Specification, Section 3.5.1.2."
    ::= { vRtrLdpStatsEntry 19 }

vRtrLdpStatsBadTlvLengthErrors   OBJECT-TYPE
    SYNTAX      Counter32
    MAX-ACCESS  read-only
    STATUS      obsolete
    DESCRIPTION
        "The value of vRtrLdpStatsBadTlvLengthErrors gives the number of Bad
         TLV Length Fatal Errors detected for sessions associated with this LDP
         instance.

         This object was obsoleted in release 13.0."
    REFERENCE
        "LDP Specification, Section 3.5.1.2."
    ::= { vRtrLdpStatsEntry 20 }

vRtrLdpStatsMalformedTlvValueErrors OBJECT-TYPE
    SYNTAX      Counter32
    MAX-ACCESS  read-only
    STATUS      obsolete
    DESCRIPTION
        "The value of vRtrLdpStatsMalformedTlvValueErrors gives the number of
         Malformed TLV Value Fatal Errors detected for sessions associated with
         this LDP instance.

         This object was obsoleted in release 13.0."
    REFERENCE
        "LDP Specification, Section 3.5.1.2."
    ::= { vRtrLdpStatsEntry 21 }

vRtrLdpStatsKeepAliveExpiredErrors OBJECT-TYPE
    SYNTAX      Counter32
    MAX-ACCESS  read-only
    STATUS      obsolete
    DESCRIPTION
        "The value of vRtrLdpStatsKeepAliveExpiredErrors gives the number of
         Session Keep Alive Timer Expired Errors detected for sessions
         associated with this LDP instance.

         This object was obsoleted in release 13.0."
    REFERENCE
        "LDP Specification, Section 3.5.1.2."
    ::= { vRtrLdpStatsEntry 22 }

vRtrLdpStatsShutdownNotifRecv    OBJECT-TYPE
    SYNTAX      Counter32
    MAX-ACCESS  read-only
    STATUS      obsolete
    DESCRIPTION
        "The value of vRtrLdpStatsShutdownNotifRecv gives the number of
         Shutdown Notifications received related to sessions associated with
         this LDP instance.

         This object was obsoleted in release 13.0."
    ::= { vRtrLdpStatsEntry 23 }

vRtrLdpStatsShutdownNotifSent    OBJECT-TYPE
    SYNTAX      Counter32
    MAX-ACCESS  read-only
    STATUS      obsolete
    DESCRIPTION
        "The value of vRtrLdpStatsShutdownNotifSent gives the number of
         Shutdown Notifications sent related to sessions associated with this
         LDP instance.

         This object was obsoleted in release 13.0."
    ::= { vRtrLdpStatsEntry 24 }

vRtrLdpStatsEgrFecPfxCount       OBJECT-TYPE
    SYNTAX      Counter32
    MAX-ACCESS  read-only
    STATUS      obsolete
    DESCRIPTION
        "The value of vRtrLdpStatsEgrFecPfxCount indicates the number of egress
         FEC prefix statistics configured for this LDP instance.

         This object was obsoleted in release 13.0."
    ::= { vRtrLdpStatsEntry 25 }

vRtrLdpStatsUnknownTlvErrors     OBJECT-TYPE
    SYNTAX      Counter32
    MAX-ACCESS  read-only
    STATUS      obsolete
    DESCRIPTION
        "The value of vRtrLdpStatsUnknownTlvErrors indicates the number of
         Unknown TLV Fatal Errors detected for sessions associated with this
         LDP instance.

         This object was obsoleted in release 13.0."
    REFERENCE
        "LDP Specification, Section 3.5.1.2."
    ::= { vRtrLdpStatsEntry 26 }

vRtrLdpStatsP2MPFECSent          OBJECT-TYPE
    SYNTAX      Gauge32
    MAX-ACCESS  read-only
    STATUS      obsolete
    DESCRIPTION
        "The value of vRtrLdpStatsP2MPFECSent specifies the number of P2MP FECs
         sent by the LDP instance to its neighbors.

         This object was obsoleted in release 13.0."
    ::= { vRtrLdpStatsEntry 27 }

vRtrLdpStatsP2MPFECRecv          OBJECT-TYPE
    SYNTAX      Gauge32
    MAX-ACCESS  read-only
    STATUS      obsolete
    DESCRIPTION
        "The value of vRtrLdpStatsP2MPFECRecv specifies the number of P2MP FECs
         received by the LDP instance from its neighbors.

         This object was obsoleted in release 13.0."
    ::= { vRtrLdpStatsEntry 28 }

vRtrLdpPolicyTable               OBJECT-TYPE
    SYNTAX      SEQUENCE OF VRtrLdpPolicyEntry
    MAX-ACCESS  not-accessible
    STATUS      obsolete
    DESCRIPTION
        "vRtrLdpPolicyTable has an entry for each policy used by the LDP
         protocol instance running on the virtual router.

         This table is obsoleted in release 2.1."
    ::= { tmnxLdpObjs 3 }

vRtrLdpPolicyEntry               OBJECT-TYPE
    SYNTAX      VRtrLdpPolicyEntry
    MAX-ACCESS  not-accessible
    STATUS      obsolete
    DESCRIPTION
        "Each row entry represents a policy used by the LDP protocol instance.

         Entries can be created and deleted via SNMP SET operations to
         vRtrLdpPolicyRowStatus.

         This entry is obsoleted in release 2.1."
    INDEX       {
        vRtrID,
        vRtrLdpPolicyType,
        vRtrLdpPolicyIndex
    }
    ::= { vRtrLdpPolicyTable 1 }

VRtrLdpPolicyEntry               ::= SEQUENCE
{
    vRtrLdpPolicyType                INTEGER,
    vRtrLdpPolicyIndex               Unsigned32,
    vRtrLdpPolicyRowStatus           RowStatus,
    vRtrLdpPolicyName                TPolicyStatementNameOrEmpty
}

vRtrLdpPolicyType                OBJECT-TYPE
    SYNTAX      INTEGER {
        import  (1),
        export  (2),
        ingress (3),
        egress  (4)
    }
    MAX-ACCESS  not-accessible
    STATUS      obsolete
    DESCRIPTION
        "The value of vRtrLdpPolicyType indicates the type of policy specified
         in this row entry.

         When vRtrLdpPolicyType has a value of 'import' this row entry
         represents the policy filter to be applied to the label binding
         received from a neighbor.

         When the value is 'export', this row entry represents the policy
         filter to determine the labels to be advertised to the neighbors.

         When the value is 'ingress', this row entry represents the
         policy filter to control the route prefixes that are advertised
         by LDP to the route table.  LDP will advertise label bindings
         of prefixes that are advertised into it.

         When the value is 'egress', this row entry represents the
         policy filter to control the route prefixes that are advertised
         into LDP from the route table.  LDP will advertise label bindings
         of prefixes that are advertised into it.

         This object is obsoleted in release 2.1."
    ::= { vRtrLdpPolicyEntry 1 }

vRtrLdpPolicyIndex               OBJECT-TYPE
    SYNTAX      Unsigned32 (1..5)
    MAX-ACCESS  not-accessible
    STATUS      obsolete
    DESCRIPTION
        "vRtrLdpPolicyIndex is used to control the order that the LDP policies
         are applied. If multiple entries exist in this table with the same
         vRtrID and vRtrLdpPolicyType indexes, they are evaluated in ascending
         numeric order of vRtrLdpPolicyIndex (gaps are allowed). The first
         policy that matches is applied.

         This object is obsoleted in release 2.1."
    ::= { vRtrLdpPolicyEntry 2 }

vRtrLdpPolicyRowStatus           OBJECT-TYPE
    SYNTAX      RowStatus
    MAX-ACCESS  read-create
    STATUS      obsolete
    DESCRIPTION
        "vRtrLdpPolicyRowStatus controls the creation and deletion of rows in
         the vRtrLdpPolicyTable.

         This object is obsoleted in release 2.1."
    ::= { vRtrLdpPolicyEntry 3 }

vRtrLdpPolicyName                OBJECT-TYPE
    SYNTAX      TPolicyStatementNameOrEmpty
    MAX-ACCESS  read-create
    STATUS      obsolete
    DESCRIPTION
        "The value of vRtrLdpPolicyName is the name of the policy filter
         to be used.  If this object has the value of the empty string,
         ''H, there is no policy specified at this level.

         This object is obsoleted in release 2.1."
    DEFVAL      { ''H }
    ::= { vRtrLdpPolicyEntry 4 }

vRtrLdpIfTableSpinlock           OBJECT-TYPE
    SYNTAX      TestAndIncr
    MAX-ACCESS  read-write
    STATUS      obsolete
    DESCRIPTION
        "Voluntary serialization control for vRtrLdpIfTable. Primarily used by
         SNMP manager to coordinate changes to vRtrLdpIfInheritance."
    DEFVAL      { 0 }
    ::= { tmnxLdpObjs 4 }

vRtrLdpIfTable                   OBJECT-TYPE
    SYNTAX      SEQUENCE OF VRtrLdpIfEntry
    MAX-ACCESS  not-accessible
    STATUS      obsolete
    DESCRIPTION
        "vRtrLdpIfTable provides an entry for each virtual router interface or
         targeted peer configured to be used with the Label Distribution
         Protocol (LDP).

         In 13.0 this table has been replaced by
         TIMETRA-LDP-NG-MIB::vRtrLdpNgIfTable,
         TIMETRA-LDP-NG-MIB::vRtrLdpNgInetIfTable."
    ::= { tmnxLdpObjs 5 }

vRtrLdpIfEntry                   OBJECT-TYPE
    SYNTAX      VRtrLdpIfEntry
    MAX-ACCESS  not-accessible
    STATUS      obsolete
    DESCRIPTION
        "Each row entry represents an interface on this virtual router that
         participates in the LDP protocol.

         Row entries can be created or deleted via SNMP SET requests. A row
         with default attribute values is created by setting vRtrLdpIfRowStatus
         to 'createAndGo'. A row entry can be destroyed by setting
         vRtrLdpIfRowStatus to 'destroy'."
    INDEX       {
        vRtrID,
        vRtrLdpIfIndex,
        vRtrLdpPeerAddress
    }
    ::= { vRtrLdpIfTable 1 }

VRtrLdpIfEntry                   ::= SEQUENCE
{
    vRtrLdpIfIndex                   InterfaceIndexOrZero,
    vRtrLdpPeerAddress               IpAddress,
    vRtrLdpIfRowStatus               RowStatus,
    vRtrLdpIfLastChange              TimeStamp,
    vRtrLdpIfAdminState              TmnxAdminState,
    vRtrLdpIfOperState               TmnxOperState,
    vRtrLdpIfInheritance             Unsigned32,
    vRtrLdpIfKeepAliveFactor         TmnxLdpKeepAliveFactor,
    vRtrLdpIfKeepAliveTimeout        TmnxLdpNewKeepAliveTimeout,
    vRtrLdpIfHelloFactor             TmnxLdpHelloFactor,
    vRtrLdpIfHelloTimeout            TmnxLdpNewHelloTimeout,
    vRtrLdpIfBackoffTime             TmnxLdpBackoffTime,
    vRtrLdpIfMaxBackoffTime          TmnxLdpBackoffTime,
    vRtrLdpIfTransportAddrType       INTEGER,
    vRtrLdpIfPassiveMode             TruthValue,
    vRtrLdpIfAutoCreate              TruthValue,
    vRtrLdpIfOperDownReason          TmnxLdpIntTargOperDownReasonCode,
    vRtrLdpIfTunneling               TruthValue,
    vRtrLdpIfBfdEnabled              TruthValue,
    vRtrLdpIfLinkLsrIfType           INTEGER,
    vRtrLdpIfTargLsrIfIndex          InterfaceIndexOrZero,
    vRtrLdpIfMulticast               TmnxEnabledDisabled,
    vRtrLdpIfHelloReduction          TruthValue,
    vRtrLdpIfHelloReductionFactor    Unsigned32,
    vRtrLdpIfOperHelloTimeout        TmnxLdpNewHelloTimeout,
    vRtrLdpIfLinkLsrIfIndex          InterfaceIndexOrZero,
    vRtrLdpIfCreator                 INTEGER,
    vRtrLdpIfTemplName               TNamedItemOrEmpty,
    vRtrLdpIfUpTime                  TimeInterval
}

vRtrLdpIfIndex                   OBJECT-TYPE
    SYNTAX      InterfaceIndexOrZero
    MAX-ACCESS  not-accessible
    STATUS      obsolete
    DESCRIPTION
        "vRtrLdpIfIndex is an index for the row entry and is used mutually
         exclusively with the vRtrLdpPeerAddress field. If the
         vRtrLdpPeerAddress field is 0.0.0.0, then vRtrLdpIfIndex is the index
         for the interface on the virtual router and must be non-zero.
         Otherwise, vRtrLdpPeerAddress refers to a targeted peer and its
         vRtrLdpIfIndex is 0.

         This object was obsoleted in release 13.0."
    ::= { vRtrLdpIfEntry 1 }

vRtrLdpPeerAddress               OBJECT-TYPE
    SYNTAX      IpAddress
    MAX-ACCESS  not-accessible
    STATUS      obsolete
    DESCRIPTION
        "vRtrLdpPeerAddress is an index for the row entry and is used mutually
         exclusively with the vRtrLdpIfIndex field. If the vRtrLdpIfIndex field
         is 0, then the vRtrLdpPeerAddress is the IP address of the targeted
         peer and must be non-zero. Otherwise, vRtrLdpIfIndex refers to the LDP
         interface index and its vRtrLdpPeerAddress is 0.0.0.0

         This object was obsoleted in release 13.0."
    ::= { vRtrLdpIfEntry 2 }

vRtrLdpIfRowStatus               OBJECT-TYPE
    SYNTAX      RowStatus
    MAX-ACCESS  read-create
    STATUS      obsolete
    DESCRIPTION
        "vRtrLdpIfRowStatus is used to control the creation and deletion of
         rows in the vRtrLdpIfTable.

         A row can be created by setting vRtrLdpIfRowStatus to 'createAndGo'.
         The agent should assign the default attribute values and change the
         row status to 'active'.

         A row entry can be destroyed by setting vRtrLdpIfRowStatus to
         'destroy'.

         This object was obsoleted in release 13.0."
    ::= { vRtrLdpIfEntry 3 }

vRtrLdpIfLastChange              OBJECT-TYPE
    SYNTAX      TimeStamp
    MAX-ACCESS  read-only
    STATUS      obsolete
    DESCRIPTION
        "The value of vRtrLdpIfLastChange specifies the sysUpTime when this row
         was last modified.

         This object was obsoleted in release 13.0."
    ::= { vRtrLdpIfEntry 4 }

vRtrLdpIfAdminState              OBJECT-TYPE
    SYNTAX      TmnxAdminState
    MAX-ACCESS  read-create
    STATUS      obsolete
    DESCRIPTION
        "The value of vRtrLdpIfAdminState indicates the desired administrative
         state for LDP on this interface or targeted peer.

         This object was obsoleted in release 13.0."
    DEFVAL      { inService }
    ::= { vRtrLdpIfEntry 5 }

vRtrLdpIfOperState               OBJECT-TYPE
    SYNTAX      TmnxOperState
    MAX-ACCESS  read-only
    STATUS      obsolete
    DESCRIPTION
        "The value of vRtrLdpIfOperState specifies the current operational
         state of LDP on this interface or targeted peer.

         This object was obsoleted in release 13.0."
    ::= { vRtrLdpIfEntry 6 }

vRtrLdpIfInheritance             OBJECT-TYPE
    SYNTAX      Unsigned32
    MAX-ACCESS  read-create
    STATUS      obsolete
    DESCRIPTION
        "Some writable object in this row that can be configured to inherit its
         value from its corresponding object in the vRtrLdpGeneralTable for LDP
         interfaces or from the corresponding object in the vRtrLdpIfTable for
         targeted peers. vRtrLdpIfInheritance controls whether to inherit the
         operational value of that object, or use the administratively set
         value.

         Non mask bits will always have value of zero, and any attempt to
         change the value will be silently discarded.

         This object is a bit-mask, with the following positions:
         vRtrLdpIfKeepAliveFactor       0x1
         vRtrLdpIfKeepAliveTimeout      0x2
         vRtrLdpIfHelloFactor           0x4
         vRtrLdpIfHelloTimeout          0x8
         vRtrLdpIfBackoffTime           0x10
         vRtrLdpIfMaxBackoffTime        0x20
         vRtrLdpIfTransportAddrType     0x40
         vRtrLdpIfPassiveMode           0x80
         vRtrLdpIfHelloReduction        0x100
         vRtrLdpIfHelloReductionFactor    0x200

         When the bit for an object has value of one, then the object's
         administrative and operational value are whatever the DEFVAL or most
         recently SET value. The mask bit(s) will be set to one when set is
         performed on the inherited object(s). Any attempt to set the mask bit
         to one will be silently discarded.

         When the bit for an object is set to zero, then the object's
         administrative and operational value are inherited from the
         corresponding object in vRtrLdpGeneralTable for LDP interfaces or the
         vRtrLdpIfTable for targeted peers.

         This object was obsoleted in release 13.0."
    DEFVAL      { 0 }
    ::= { vRtrLdpIfEntry 7 }

vRtrLdpIfKeepAliveFactor         OBJECT-TYPE
    SYNTAX      TmnxLdpKeepAliveFactor
    MAX-ACCESS  read-create
    STATUS      obsolete
    DESCRIPTION
        "The value of vRtrLdpIfKeepAliveFactor specifies the value by which the
         keepalive timeout (vRtrLdpIfKeepAliveTimeout) should be divided to
         give the keepalive time i.e. the time interval, in seconds, between
         LDP keepalive messages. LDP keepalive messages are sent to keep the
         LDP session from timing out when no other LDP traffic is being sent
         between the neighbors.

         This object was obsoleted in release 13.0."
    DEFVAL      { 3 }
    ::= { vRtrLdpIfEntry 8 }

vRtrLdpIfKeepAliveTimeout        OBJECT-TYPE
    SYNTAX      TmnxLdpNewKeepAliveTimeout
    UNITS       "seconds"
    MAX-ACCESS  read-create
    STATUS      obsolete
    DESCRIPTION
        "The value of vRtrLdpIfKeepAliveTimeout specifies the time interval, in
         seconds, that LDP waits before tearing down a session. If no LDP
         messages are exchanged during this time interval, the LDP session is
         torn down. Generally the value of vRtrLdpIfKeepAliveTimeout is
         configured to be 3 times the keepalive time (the time interval between
         successive LDP keepalive messages).

         This object was obsoleted in release 13.0."
    DEFVAL      { 30 }
    ::= { vRtrLdpIfEntry 9 }

vRtrLdpIfHelloFactor             OBJECT-TYPE
    SYNTAX      TmnxLdpHelloFactor
    UNITS       "seconds"
    MAX-ACCESS  read-create
    STATUS      obsolete
    DESCRIPTION
        "The value of vRtrLdpIfHelloFactor specifies the value by which the
         hello timeout (vRtrLdpIfHelloTimeout) should be divided to give the
         hello time i.e. the time interval, in seconds, between LDP Hello
         messages. LDP uses hello messages to discover neighbors and to detect
         loss of connectivity with its neighbors.

         This object was obsoleted in release 13.0."
    DEFVAL      { 3 }
    ::= { vRtrLdpIfEntry 10 }

vRtrLdpIfHelloTimeout            OBJECT-TYPE
    SYNTAX      TmnxLdpNewHelloTimeout
    UNITS       "seconds"
    MAX-ACCESS  read-create
    STATUS      obsolete
    DESCRIPTION
        "The value of vRtrLdpIfHelloTimeout specifies the hello time also known
         as hold time. It is the time interval, in seconds, that LDP waits
         before declaring a neighbor to be down. Hello timeout is local to the
         system and is sent in the hello messages to a neighbor. Hello timeout
         cannot be set to a value that is less than 3 times the hello time.

         This object was obsoleted in release 13.0."
    DEFVAL      { 15 }
    ::= { vRtrLdpIfEntry 11 }

vRtrLdpIfBackoffTime             OBJECT-TYPE
    SYNTAX      TmnxLdpBackoffTime (1..2592000)
    UNITS       "seconds"
    MAX-ACCESS  read-create
    STATUS      obsolete
    DESCRIPTION
        "The value of vRtrLdpIfBackoffTime specifies the initial value for the
         backoff interval.

         The backoff interval is the time, in seconds, that LDP waits after an
         LDP session setup has failed before it attempts to setup the session
         again. After the LDP session startup fails the first time, the backoff
         interval is set to the value of vRtrLdpIfBackoffTime. Thereafter, if
         session startup fails again the backoff interval increases
         exponentially.

         This object was obsoleted in release 13.0."
    DEFVAL      { 15 }
    ::= { vRtrLdpIfEntry 12 }

vRtrLdpIfMaxBackoffTime          OBJECT-TYPE
    SYNTAX      TmnxLdpBackoffTime
    UNITS       "seconds"
    MAX-ACCESS  read-create
    STATUS      obsolete
    DESCRIPTION
        "The value of vRtrLdpIfMaxBackoffTime specifies the maximum value for
         the backoff interval.

         For each successive failure of the LDP session startup, the backoff
         interval (the time for which the router waits before retrying)
         increases exponentially. If the backoff interval exceeds
         vRtrLdpIfMaxBackoffTime, the router will give up trying to establish
         the LDP session.

         If vRtrLdpIfMaxBackoffTime is set to zero (0), then the backoff
         interval does not increase exponentially after the first session
         startup attempt fails. Instead it remains constant and LDP will keep
         retrying to establish a session until it succeeds.

         This object was obsoleted in release 13.0."
    DEFVAL      { 120 }
    ::= { vRtrLdpIfEntry 13 }

vRtrLdpIfTransportAddrType       OBJECT-TYPE
    SYNTAX      INTEGER {
        interface (1),
        system    (2)
    }
    MAX-ACCESS  read-create
    STATUS      obsolete
    DESCRIPTION
        "The value of vRtrLdpIfTransportAddrType specifies the source of the
         transport address to be used when setting up the LDP TCP sessions.
         This value is meaningful only in case of LDP interfaces and not for
         targeted peers.

         When the value of this object is 'interface', the interface's IP
         address is used to setup the LDP session between neighbors. If
         multiple interfaces exist between two neighbors, the 'interface' mode
         cannot be used since only one LDP session is actually set up between
         the two neighbors.

         When the value of this object is 'system', the system's IP address is
         used to set up the LDP session between neighbors.

         This object was obsoleted in release 13.0."
    DEFVAL      { system }
    ::= { vRtrLdpIfEntry 14 }

vRtrLdpIfPassiveMode             OBJECT-TYPE
    SYNTAX      TruthValue
    MAX-ACCESS  read-create
    STATUS      obsolete
    DESCRIPTION
        "The value of vRtrLdpIfPassiveMode specifies the mode used for setting
         up LDP sessions. This object is meaningful only in case of LDP
         targeted peers and not for interfaces. When it has a value of 'true',
         LDP responds only when it gets a connect request from a peer and will
         not attempt to actively connect to its neighbors. When it has a value
         of 'false', LDP actively tries to connect to its peers.

         This object was obsoleted in release 13.0."
    DEFVAL      { false }
    ::= { vRtrLdpIfEntry 15 }

vRtrLdpIfAutoCreate              OBJECT-TYPE
    SYNTAX      TruthValue
    MAX-ACCESS  read-only
    STATUS      obsolete
    DESCRIPTION
        "The value of vRtrLdpIfAutoCreate specifies whether or not the row
         entry was automatically created.

         This object was obsoleted in release 13.0."
    ::= { vRtrLdpIfEntry 16 }

vRtrLdpIfOperDownReason          OBJECT-TYPE
    SYNTAX      TmnxLdpIntTargOperDownReasonCode
    MAX-ACCESS  read-only
    STATUS      obsolete
    DESCRIPTION
        "The value of vRtrLdpIfOperDownReason specifies the reason that the LDP
         interface or targeted peer is operationally down.

         This object was obsoleted in release 13.0."
    ::= { vRtrLdpIfEntry 17 }

vRtrLdpIfTunneling               OBJECT-TYPE
    SYNTAX      TruthValue
    MAX-ACCESS  read-create
    STATUS      obsolete
    DESCRIPTION
        "The value of vRtrLdpIfTunneling specifies whether tunneling
         of LDP over tunnels is enabled.  When this object has a value of
         'true', tunneling is enabled.  When its value is 'false',
          tunneling is disabled.

          This object was obsoleted in release 13.0."
    DEFVAL      { false }
    ::= { vRtrLdpIfEntry 18 }

vRtrLdpIfBfdEnabled              OBJECT-TYPE
    SYNTAX      TruthValue
    MAX-ACCESS  read-create
    STATUS      obsolete
    DESCRIPTION
        "The value of vRtrLdpIfBfdEnabled specifies whether BFD tracking of a
         LDP Session on this interface is enabled. When this object has a value
         of 'true', BFD tracking is enabled. When its value is 'false', BFD
         tracking is disabled.

         This object was obsoleted in release 13.0."
    DEFVAL      { false }
    ::= { vRtrLdpIfEntry 19 }

vRtrLdpIfLinkLsrIfType           OBJECT-TYPE
    SYNTAX      INTEGER {
        system    (1),
        interface (2)
    }
    MAX-ACCESS  read-create
    STATUS      obsolete
    DESCRIPTION
        "The value of vRtrLdpIfLinkLsrIfType specifies whether the local
         interface address or the system interface address should be used as
         source Label Switch Router identifier (LSR-ID) to establish a link LDP
         adjacency with a LDP peer.

         This object was obsoleted in release 13.0."
    DEFVAL      { system }
    ::= { vRtrLdpIfEntry 20 }

vRtrLdpIfTargLsrIfIndex          OBJECT-TYPE
    SYNTAX      InterfaceIndexOrZero
    MAX-ACCESS  read-create
    STATUS      obsolete
    DESCRIPTION
        "The value of vRtrLdpIfTargLsrIfIndex specifies the local interface
         index that is to be used as source LSR-ID to establish targeted hello
         adjacency with a LDP peer.

         This object was obsoleted in release 13.0."
    DEFVAL      { 0 }
    ::= { vRtrLdpIfEntry 21 }

vRtrLdpIfMulticast               OBJECT-TYPE
    SYNTAX      TmnxEnabledDisabled
    MAX-ACCESS  read-create
    STATUS      obsolete
    DESCRIPTION
        "The value of vRtrLdpIfMulticast specifies whether multicast traffic
         forwarding is enabled or disabled on the interface.

         This object was obsoleted in release 13.0."
    DEFVAL      { enabled }
    ::= { vRtrLdpIfEntry 22 }

vRtrLdpIfHelloReduction          OBJECT-TYPE
    SYNTAX      TruthValue
    MAX-ACCESS  read-create
    STATUS      obsolete
    DESCRIPTION
        "The value of vRtrLdpIfHelloReduction specifies whether hello reduction
         to this targeted peer is enabled or not. If enabled, the sender
         advertises the dampened vRtrLdpIfHelloTimeout, to the targeted peer
         after LDP session is established.

         The value of this object is valid only for LDP targeted peers and not
         for interfaces.

         This object was obsoleted in release 13.0."
    DEFVAL      { false }
    ::= { vRtrLdpIfEntry 23 }

vRtrLdpIfHelloReductionFactor    OBJECT-TYPE
    SYNTAX      Unsigned32 (0 | 3..20)
    MAX-ACCESS  read-create
    STATUS      obsolete
    DESCRIPTION
        "The value of vRtrLdpIfHelloReductionFactor specifies the number of
         hello messages that are sent at consistent vRtrLdpIfHelloTimeout,
         before advertising further dampened vRtrLdpIfHelloTimeout.

         An 'inconsistentValue' error is returned if this object is set when
         vRtrLdpIfHelloReduction is disabled.

         The object is set to '0' for LDP interfaces to indicate that the hello
         reduction feature is not applicable.

         This object was obsoleted in release 13.0."
    DEFVAL      { 3 }
    ::= { vRtrLdpIfEntry 24 }

vRtrLdpIfOperHelloTimeout        OBJECT-TYPE
    SYNTAX      TmnxLdpNewHelloTimeout (3..65535)
    UNITS       "seconds"
    MAX-ACCESS  read-only
    STATUS      obsolete
    DESCRIPTION
        "The value of vRtrLdpIfOperHelloTimeout indicates the operational hello
         time also known as hold time used by the operational targeted peer or
         LDP interface. It is the time interval that LDP waits before declaring
         a neighbor to be down.

         This object was obsoleted in release 13.0."
    ::= { vRtrLdpIfEntry 25 }

vRtrLdpIfLinkLsrIfIndex          OBJECT-TYPE
    SYNTAX      InterfaceIndexOrZero
    MAX-ACCESS  read-create
    STATUS      obsolete
    DESCRIPTION
        "The value of vRtrLdpIfLinkLsrIfIndex specifies the local interface
         index that is to be used as source LSR-ID to establish link hello
         adjacency with a LDP peer.

         This object was obsoleted in release 13.0."
    DEFVAL      { 0 }
    ::= { vRtrLdpIfEntry 26 }

vRtrLdpIfCreator                 OBJECT-TYPE
    SYNTAX      INTEGER {
        manual   (1),
        template (2),
        sdp      (3)
    }
    MAX-ACCESS  read-only
    STATUS      obsolete
    DESCRIPTION
        "The value of vRtrLdpIfCreator indicates the creator of this row. A
         value of 'manual(1)' indicates the entry is created manually by the
         user. A value of 'template(2)' indicates the entry is auto created by
         template configuration. A value of 'sdp(3)' indicates the entry is
         auto created by service manager.

         This object was obsoleted in release 13.0."
    ::= { vRtrLdpIfEntry 27 }

vRtrLdpIfTemplName               OBJECT-TYPE
    SYNTAX      TNamedItemOrEmpty
    MAX-ACCESS  read-only
    STATUS      obsolete
    DESCRIPTION
        "The value of vRtrLdpIfTemplName specifies the template name that
         created this row. This object has valid value when vRtrLdpIfCreator
         has value of template.

         This object was obsoleted in release 13.0."
    ::= { vRtrLdpIfEntry 28 }

vRtrLdpIfUpTime                  OBJECT-TYPE
    SYNTAX      TimeInterval
    MAX-ACCESS  read-only
    STATUS      obsolete
    DESCRIPTION
        "The value of vRtrLdpIfUpTime indicates the time, in hundreds of
         seconds, that the LDP interface or targeted peer has been in current
         operational state vRtrLdpIfOperState.

         If the value of vRtrLdpIfOperState is 'inService (2)', then
         vRtrLdpIfUpTime specifies the time that the LDP interface or targeted
         peer has been operationally up.

         If the value of vRtrLdpIfOperState is 'outOfService (3)', then
         vRtrLdpIfUpTime specifies the time that the LDP interface or targeted
         peer has been operationally down.

         If the value of vRtrLdpIfOperState is 'transition (4)', then
         vRtrLdpIfUpTime specifies the time that the LDP instance has been
         operationally in transition.

         This object was obsoleted in release 13.0."
    ::= { vRtrLdpIfEntry 29 }

vRtrLdpIfStatsTable              OBJECT-TYPE
    SYNTAX      SEQUENCE OF VRtrLdpIfStatsEntry
    MAX-ACCESS  not-accessible
    STATUS      obsolete
    DESCRIPTION
        "vRtrLdpIfStatsTable is a read-only table. The purpose of this table is
         to keep statistical information about the LDP Interfaces and Targeted
         peers on the LSR.

         Use of AUGMENTS clause implies a one-to-one dependent relationship
         between the base table, vRtrLdpIfTable, and the augmenting table,
         vRtrLdpIfStatsTable. This in effect extends the vRtrLdpIfTable with
         additional columns. Creation or deletion of a row in the
         vRtrLdpIfTable results in the same fate for the row in the
         vRtrLdpIfStatsTable.

         In 13.0 this table has been replaced by
         TIMETRA-LDP-NG-MIB::vRtrLdpNgInetIfStatsTable."
    ::= { tmnxLdpObjs 6 }

vRtrLdpIfStatsEntry              OBJECT-TYPE
    SYNTAX      VRtrLdpIfStatsEntry
    MAX-ACCESS  not-accessible
    STATUS      obsolete
    DESCRIPTION
        "A row in this table contains statistical information about an LDP
         Interface or Targeted peer.

         Some counters contained in a row are for fatal errors received
         during a former LDP Session associated with this entry. For example,
         an LDP Pdu received on a TCP connection during an LDP Session
         contains a fatal error.  That error is counted here, because the
         session is terminated.

         If the error is NOT fatal (i.e. and the Session remains), then the
         error is counted in the vRtrLdpSessionStatsEntry."
    AUGMENTS    { vRtrLdpIfEntry }
    ::= { vRtrLdpIfStatsTable 1 }

VRtrLdpIfStatsEntry              ::= SEQUENCE
{ vRtrLdpIfExistingAdjacencies     Gauge32 }

vRtrLdpIfExistingAdjacencies     OBJECT-TYPE
    SYNTAX      Gauge32
    MAX-ACCESS  read-only
    STATUS      obsolete
    DESCRIPTION
        "The value of vRtrLdpIfExistingAdjacencies gives a count of the total
         active adjacencies on this LDP interface or with this targeted peer.

         This object was obsoleted in release 13.0."
    ::= { vRtrLdpIfStatsEntry 1 }

vRtrLdpHelloAdjTable             OBJECT-TYPE
    SYNTAX      SEQUENCE OF VRtrLdpHelloAdjEntry
    MAX-ACCESS  not-accessible
    STATUS      obsolete
    DESCRIPTION
        "vRtrLdpHelloAdjTable is a read-only table. The purpose of this table
         is to keep information about Hello Adjacencies for Sessions. A hello
         adjacency can be associated with an LDP interface or with a targeted
         peer. The index includes both the interface index and the peer IP
         address thus referring to the LDP interface or targeted peer.

         In 13.0 this table has been replaced by
         TIMETRA-LDP-NG-MIB::vRtrLdpNgHelloAdjTable."
    ::= { tmnxLdpObjs 7 }

vRtrLdpHelloAdjEntry             OBJECT-TYPE
    SYNTAX      VRtrLdpHelloAdjEntry
    MAX-ACCESS  not-accessible
    STATUS      obsolete
    DESCRIPTION
        "Each row represents a single LDP Hello Adjacency. An LDP Session can
         have one or more Hello adjacencies."
    INDEX       {
        vRtrID,
        vRtrLdpPeerLdpId,
        vRtrLdpIfIndex,
        vRtrLdpPeerAddress
    }
    ::= { vRtrLdpHelloAdjTable 1 }

VRtrLdpHelloAdjEntry             ::= SEQUENCE
{
    vRtrLdpPeerLdpId                 MplsLdpIdentifier,
    vRtrLdpHelloAdjLocalLdpId        MplsLdpIdentifier,
    vRtrLdpHelloAdjEntityIndex       Unsigned32,
    vRtrLdpHelloAdjIndex             Unsigned32,
    vRtrLdpHelloAdjHoldTimeRemaining Unsigned32,
    vRtrLdpHelloAdjType              TmnxLdpAdjacencyType,
    vRtrLdpHelloAdjRemoteConfSeqNum  Unsigned32,
    vRtrLdpHelloAdjRemoteIpAddress   IpAddress,
    vRtrLdpHelloAdjUpTime            TimeInterval,
    vRtrLdpHelloAdjLocalConfSeqNum   Unsigned32,
    vRtrLdpHelloAdjLocalIpAddress    IpAddress,
    vRtrLdpHelloAdjInHelloMsgCount   Counter32,
    vRtrLdpHelloAdjOutHelloMsgCount  Counter32,
    vRtrLdpHelloAdjLocalHelloTimeout TmnxLdpHelloTimeout,
    vRtrLdpHelloAdjRemoteHelloTimeout TmnxLdpHelloTimeout,
    vRtrLdpHelloAdjBfdStatus         INTEGER
}

vRtrLdpPeerLdpId                 OBJECT-TYPE
    SYNTAX      MplsLdpIdentifier
    MAX-ACCESS  not-accessible
    STATUS      obsolete
    DESCRIPTION
        "vRtrLdpPeerLdpId is an index for the row entry. It indicates the LDP
         identifier of the peer.

         This object was obsoleted in release 13.0."
    ::= { vRtrLdpHelloAdjEntry 1 }

vRtrLdpHelloAdjLocalLdpId        OBJECT-TYPE
    SYNTAX      MplsLdpIdentifier
    MAX-ACCESS  read-only
    STATUS      obsolete
    DESCRIPTION
        "The value of vRtrLdpHelloAdjLocalLdpId indicates the local LDP
         identifier for this specific adjacency.

         This object was obsoleted in release 13.0."
    ::= { vRtrLdpHelloAdjEntry 2 }

vRtrLdpHelloAdjEntityIndex       OBJECT-TYPE
    SYNTAX      Unsigned32 (1..4294967295)
    MAX-ACCESS  read-only
    STATUS      obsolete
    DESCRIPTION
        "The value of vRtrLdpHelloAdjEntityIndex indicates the Entity index
         which is an index for the mplsLdpHelloAdjacencyEntry defined in
         MPLS-LDP-MIB.

         This object was obsoleted in release 13.0."
    ::= { vRtrLdpHelloAdjEntry 3 }

vRtrLdpHelloAdjIndex             OBJECT-TYPE
    SYNTAX      Unsigned32 (1..4294967295)
    MAX-ACCESS  read-only
    STATUS      obsolete
    DESCRIPTION
        "The value of vRtrLdpHelloAdjIndex indicates the Hello adjacency index
         which is an index for the mplsLdpHelloAdjacencyEntry defined in
         MPLS-LDP-MIB.

         This object was obsoleted in release 13.0."
    ::= { vRtrLdpHelloAdjEntry 4 }

vRtrLdpHelloAdjHoldTimeRemaining OBJECT-TYPE
    SYNTAX      Unsigned32
    UNITS       "seconds"
    MAX-ACCESS  read-only
    STATUS      obsolete
    DESCRIPTION
        "The value of vRtrLdpHelloAdjHoldTimeRemaining indicates the hold time
         remaining for this Hello Adjacency. This interval will change when the
         next Hello message which corresponds to this Hello Adjacency is
         received.

         This object was obsoleted in release 13.0."
    ::= { vRtrLdpHelloAdjEntry 5 }

vRtrLdpHelloAdjType              OBJECT-TYPE
    SYNTAX      TmnxLdpAdjacencyType
    MAX-ACCESS  read-only
    STATUS      obsolete
    DESCRIPTION
        "The value of vRtrLdpHelloAdjType indicates the type of this Hello
         Adjacency. If this value is 'link' then this adjacency is a result of
         a Link Hello. If this value is 'hello', then the adjacency is a result
         of a Targeted Hello.

         This object was obsoleted in release 13.0."
    ::= { vRtrLdpHelloAdjEntry 6 }

vRtrLdpHelloAdjRemoteConfSeqNum  OBJECT-TYPE
    SYNTAX      Unsigned32
    MAX-ACCESS  read-only
    STATUS      obsolete
    DESCRIPTION
        "The value of vRtrLdpHelloAdjRemoteConfSeqNum indicates the
         Configuration sequence number that was in the Hello received when this
         adjacency started up. This configuration sequence number changes when
         there is a change of configuration.

         This object was obsoleted in release 13.0."
    ::= { vRtrLdpHelloAdjEntry 7 }

vRtrLdpHelloAdjRemoteIpAddress   OBJECT-TYPE
    SYNTAX      IpAddress
    MAX-ACCESS  read-only
    STATUS      obsolete
    DESCRIPTION
        "The value of vRtrLdpHelloAdjRemoteIpAddress indicates the peer IP
         address of the interface/targeted session that sent hellos for this
         specific adjacency.

         This object was obsoleted in release 13.0."
    ::= { vRtrLdpHelloAdjEntry 8 }

vRtrLdpHelloAdjUpTime            OBJECT-TYPE
    SYNTAX      TimeInterval
    MAX-ACCESS  read-only
    STATUS      obsolete
    DESCRIPTION
        "The value of vRtrLdpHelloAdjUpTime indicates the time, in hundreds of
         seconds, that this adjacency has been up.

         This object was obsoleted in release 13.0."
    ::= { vRtrLdpHelloAdjEntry 9 }

vRtrLdpHelloAdjLocalConfSeqNum   OBJECT-TYPE
    SYNTAX      Unsigned32
    MAX-ACCESS  read-only
    STATUS      obsolete
    DESCRIPTION
        "The value of vRtrLdpHelloAdjLocalConfSeqNum indicates the
         Configuration sequence number that was used in the Hello sent when
         this adjacency started up. This configuration sequence number changes
         when there is a change of configuration.

         This object was obsoleted in release 13.0."
    ::= { vRtrLdpHelloAdjEntry 10 }

vRtrLdpHelloAdjLocalIpAddress    OBJECT-TYPE
    SYNTAX      IpAddress
    MAX-ACCESS  read-only
    STATUS      obsolete
    DESCRIPTION
        "The value of vRtrLdpHelloAdjLocalIpAddress indicates the local IP
         address of the interface/targeted session used in Hellos sent for this
         specific adjacency.

         This object was obsoleted in release 13.0."
    ::= { vRtrLdpHelloAdjEntry 11 }

vRtrLdpHelloAdjInHelloMsgCount   OBJECT-TYPE
    SYNTAX      Counter32
    MAX-ACCESS  read-only
    STATUS      obsolete
    DESCRIPTION
        "The value of vRtrLdpHelloAdjInHelloMsgCount indicates the number of
         Hello messages that have been received for this adjacency.

         This object was obsoleted in release 13.0."
    ::= { vRtrLdpHelloAdjEntry 12 }

vRtrLdpHelloAdjOutHelloMsgCount  OBJECT-TYPE
    SYNTAX      Counter32
    MAX-ACCESS  read-only
    STATUS      obsolete
    DESCRIPTION
        "The value of vRtrLdpHelloAdjOutHelloMsgCount indicates the number of
         Hello messages that have been sent for this adjacency.

         This object was obsoleted in release 13.0."
    ::= { vRtrLdpHelloAdjEntry 13 }

vRtrLdpHelloAdjLocalHelloTimeout OBJECT-TYPE
    SYNTAX      TmnxLdpHelloTimeout
    MAX-ACCESS  read-only
    STATUS      obsolete
    DESCRIPTION
        "The value of vRtrLdpHelloAdjLocalHelloTimeout indicates the hello
         timeout used in the Hellos sent for this specific adjacency.

         This object was obsoleted in release 13.0."
    ::= { vRtrLdpHelloAdjEntry 14 }

vRtrLdpHelloAdjRemoteHelloTimeout OBJECT-TYPE
    SYNTAX      TmnxLdpHelloTimeout
    MAX-ACCESS  read-only
    STATUS      obsolete
    DESCRIPTION
        "The value of vRtrLdpHelloAdjRemoteHelloTimeout indicates the hello
         timeout used by the remote end that sent Hellos for this specific
         adjacency.

         This object was obsoleted in release 13.0."
    ::= { vRtrLdpHelloAdjEntry 15 }

vRtrLdpHelloAdjBfdStatus         OBJECT-TYPE
    SYNTAX      INTEGER {
        noService    (1),
        inService    (2),
        outOfService (3)
    }
    MAX-ACCESS  read-only
    STATUS      obsolete
    DESCRIPTION
        "The value of vRtrLdpHelloAdjBfdStatus indicates the BFD operational
         status for LDP hello adjacency.

         If the value of vRtrLdpHelloAdjBfdStatus is 'noService', BFD is not
         enabled for LDP hello adjacency. If the value of the object is
         'outOfService', BFD is enabled but it is down and not running. If the
         value of object is 'inService', BFD is enabled and it is running.

         This object was obsoleted in release 13.0."
    ::= { vRtrLdpHelloAdjEntry 16 }

vRtrLdpHelloAdjMapTable          OBJECT-TYPE
    SYNTAX      SEQUENCE OF VRtrLdpHelloAdjMapEntry
    MAX-ACCESS  not-accessible
    STATUS      obsolete
    DESCRIPTION
        "vRtrLdpHelloAdjMapTable is a read-only table which maps to the
         vRtrLdpHelloAdjTable. This table has the same indexes as the
         vRtrLdpHelloAdjTable but the order in which these indexes are
         specified is different for the two tables.

         In 13.0 this table has been replaced by
         TIMETRA-LDP-NG-MIB::vRtrLdpNgHelloAdjMapTable."
    ::= { tmnxLdpObjs 8 }

vRtrLdpHelloAdjMapEntry          OBJECT-TYPE
    SYNTAX      VRtrLdpHelloAdjMapEntry
    MAX-ACCESS  not-accessible
    STATUS      obsolete
    DESCRIPTION
        "Each row represents a single LDP Hello Adjacency. An LDP Session can
         have one or more Hello adjacencies."
    INDEX       {
        vRtrID,
        vRtrLdpIfIndex,
        vRtrLdpPeerAddress,
        vRtrLdpHelloAdjMapLdpId
    }
    ::= { vRtrLdpHelloAdjMapTable 1 }

VRtrLdpHelloAdjMapEntry          ::= SEQUENCE
{ vRtrLdpHelloAdjMapLdpId          MplsLdpIdentifier }

vRtrLdpHelloAdjMapLdpId          OBJECT-TYPE
    SYNTAX      MplsLdpIdentifier
    MAX-ACCESS  read-only
    STATUS      obsolete
    DESCRIPTION
        "vRtrLdpHelloAdjMapLdpId is an index for the row entry. It specifies
         the LDP identifier of the peer.

         This object was obsoleted in release 13.0."
    ::= { vRtrLdpHelloAdjMapEntry 1 }

vRtrLdpSessionTable              OBJECT-TYPE
    SYNTAX      SEQUENCE OF VRtrLdpSessionEntry
    MAX-ACCESS  not-accessible
    STATUS      obsolete
    DESCRIPTION
        "vRtrLdpSessionTable is a read-only table which parallels the
         mplsLdpSessionTable in the MPLS-LDP-MIB. The purpose of this table is
         to keep information about a single session between an LDP entity and
         an LDP Peer.

         In 13.0 this table has been replaced by
         TIMETRA-LDP-NG-MIB::vRtrLdpNgSessionTable."
    ::= { tmnxLdpObjs 9 }

vRtrLdpSessionEntry              OBJECT-TYPE
    SYNTAX      VRtrLdpSessionEntry
    MAX-ACCESS  not-accessible
    STATUS      obsolete
    DESCRIPTION
        "A row in this table represents information about a  single
         session between an LDP entity and an LDP Peer."
    INDEX       {
        vRtrID,
        vRtrLdpPeerLdpId
    }
    ::= { vRtrLdpSessionTable 1 }

VRtrLdpSessionEntry              ::= SEQUENCE
{
    vRtrLdpSessLocalLdpId            MplsLdpIdentifier,
    vRtrLdpSessEntityIndex           Unsigned32,
    vRtrLdpSessLabelDistMethod       TmnxLdpLabelDistMethod,
    vRtrLdpSessLoopDetectForPV       INTEGER,
    vRtrLdpSessPathVectorLimit       Unsigned32,
    vRtrLdpSessState                 INTEGER,
    vRtrLdpSessAdjacencyType         TmnxLdpAdjacencyType,
    vRtrLdpSessProtocolVersion       Unsigned32,
    vRtrLdpSessLocalUdpPort          Unsigned32,
    vRtrLdpSessPeerUdpPort           Unsigned32,
    vRtrLdpSessLocalTcpPort          Unsigned32,
    vRtrLdpSessPeerTcpPort           Unsigned32,
    vRtrLdpSessLocalAddress          IpAddress,
    vRtrLdpSessPeerAddress           IpAddress,
    vRtrLdpSessKAHoldTimeRemaining   TimeInterval,
    vRtrLdpSessMaxPduLength          Unsigned32,
    vRtrLdpSessUpTime                TimeInterval,
    vRtrLdpSessLocalKATimeout        TmnxLdpKeepAliveTimeout,
    vRtrLdpSessPeerKATimeout         TmnxLdpKeepAliveTimeout,
    vRtrLdpSessAdvertise             INTEGER,
    vRtrLdpSessRestartHelperState    TruthValue,
    vRtrLdpSessPeerNumRestart        Counter32,
    vRtrLdpSessLastRestartTime       TimeStamp,
    vRtrLdpSessFtReconnectTimeNego   Unsigned32,
    vRtrLdpSessFtRecoveryTimeNego    Unsigned32,
    vRtrLdpSessFtReconTimeRemaining  Unsigned32,
    vRtrLdpSessFtRecovTimeRemaining  Unsigned32,
    vRtrLdpSessBfdStatus             INTEGER,
    vRtrLdpSessP2MPCapabilityNego    TruthValue,
    vRtrLdpSessMPMBBCapabilityNego   TruthValue,
    vRtrLdpSessDynamicCapabilityNego TruthValue,
    vRtrLdpSessOvrloadCapabltyNego   TruthValue,
    vRtrLdpSessAddrFecOverloadSent   TruthValue,
    vRtrLdpSessAddrFecOverloadRecv   TruthValue,
    vRtrLdpSessMcastFecOverloadSent  TruthValue,
    vRtrLdpSessMcastFecOverloadRecv  TruthValue,
    vRtrLdpSessServFecOverloadSent   TruthValue,
    vRtrLdpSessServFecOverloadRecv   TruthValue,
    vRtrLdpSessOperMaxFecThreshold   Unsigned32
}

vRtrLdpSessLocalLdpId            OBJECT-TYPE
    SYNTAX      MplsLdpIdentifier
    MAX-ACCESS  read-only
    STATUS      obsolete
    DESCRIPTION
        "The value of vRtrLdpSessLocalLdpId specifies the local LDP identifier
         for this LDP session.

         This object was obsoleted in release 13.0."
    ::= { vRtrLdpSessionEntry 1 }

vRtrLdpSessEntityIndex           OBJECT-TYPE
    SYNTAX      Unsigned32 (1..4294967295)
    MAX-ACCESS  read-only
    STATUS      obsolete
    DESCRIPTION
        "The value of vRtrLdpSessEntityIndex specifies the Entity index for the
         LDP entity represented in this session.

         This object was obsoleted in release 13.0."
    ::= { vRtrLdpSessionEntry 2 }

vRtrLdpSessLabelDistMethod       OBJECT-TYPE
    SYNTAX      TmnxLdpLabelDistMethod
    MAX-ACCESS  read-only
    STATUS      obsolete
    DESCRIPTION
        "The value of vRtrLdpSessLabelDistMethod specifies the label
         distribution method used for this LDP session.

         This object was obsoleted in release 13.0."
    ::= { vRtrLdpSessionEntry 3 }

vRtrLdpSessLoopDetectForPV       OBJECT-TYPE
    SYNTAX      INTEGER {
        disabled (0),
        enabled  (1)
    }
    MAX-ACCESS  read-only
    STATUS      obsolete
    DESCRIPTION
        "The value of vRtrLdpSessLoopDetectForPV indicates whether loop
         detection based on path vectors is disabled or enabled for this LDP
         session.

         If this object has a value of disabled(0), then loop detection
         is disabled.  Otherwise, if this object has a value of enabled(1),
         then loop detection based on path vectors is enabled.

         This object was obsoleted in release 13.0."
    ::= { vRtrLdpSessionEntry 4 }

vRtrLdpSessPathVectorLimit       OBJECT-TYPE
    SYNTAX      Unsigned32 (0..255)
    MAX-ACCESS  read-only
    STATUS      obsolete
    DESCRIPTION
        "If the value of vRtrLdpSessLoopDetectForPV for this entry is
         'enabled', then the value of vRtrLdpSessPathVectorLimit represents the
         Path Vector Limit for this LDP Session.

         If the value of vRtrLdpSessLoopDetectForPV for this entry is
         'disabled', then the value of vRtrLdpSessPathVectorLimit be 0 (zero).

         This object was obsoleted in release 13.0."
    ::= { vRtrLdpSessionEntry 5 }

vRtrLdpSessState                 OBJECT-TYPE
    SYNTAX      INTEGER {
        nonexistent (1),
        initialized (2),
        openrec     (3),
        opensent    (4),
        operational (5)
    }
    MAX-ACCESS  read-only
    STATUS      obsolete
    DESCRIPTION
        "The value of vRtrLdpSessState specifies the current state of the LDP
         session. All of the states 1 - 5 are based on the state machine for
         session negotiation behavior.

         This object was obsoleted in release 13.0."
    ::= { vRtrLdpSessionEntry 6 }

vRtrLdpSessAdjacencyType         OBJECT-TYPE
    SYNTAX      TmnxLdpAdjacencyType
    MAX-ACCESS  read-only
    STATUS      obsolete
    DESCRIPTION
        "The value of vRtrLdpSessAdjacencyType specifies the adjacency type(s)
         supporting this LDP Session.

         This object was obsoleted in release 13.0."
    ::= { vRtrLdpSessionEntry 7 }

vRtrLdpSessProtocolVersion       OBJECT-TYPE
    SYNTAX      Unsigned32
    MAX-ACCESS  read-only
    STATUS      obsolete
    DESCRIPTION
        "The value of vRtrLdpSessProtocolVersion specifies the version of the
         LDP Protocol used by this session.

         This object was obsoleted in release 13.0."
    ::= { vRtrLdpSessionEntry 8 }

vRtrLdpSessLocalUdpPort          OBJECT-TYPE
    SYNTAX      Unsigned32 (0..65535)
    MAX-ACCESS  read-only
    STATUS      obsolete
    DESCRIPTION
        "The value of vRtrLdpSessLocalUdpPort specifies the UDP port used
         locally for LDP discovery.

         This object was obsoleted in release 13.0."
    ::= { vRtrLdpSessionEntry 9 }

vRtrLdpSessPeerUdpPort           OBJECT-TYPE
    SYNTAX      Unsigned32 (0..65535)
    MAX-ACCESS  read-only
    STATUS      obsolete
    DESCRIPTION
        "The value of vRtrLdpSessPeerUdpPort specifies the UDP port used on the
         remote end for LDP discovery.

         This object was obsoleted in release 13.0."
    ::= { vRtrLdpSessionEntry 10 }

vRtrLdpSessLocalTcpPort          OBJECT-TYPE
    SYNTAX      Unsigned32 (0..65535)
    MAX-ACCESS  read-only
    STATUS      obsolete
    DESCRIPTION
        "The value of vRtrLdpSessLocalTcpPort specifies the TCP port used
         locally for the LDP Session.

         This object was obsoleted in release 13.0."
    ::= { vRtrLdpSessionEntry 11 }

vRtrLdpSessPeerTcpPort           OBJECT-TYPE
    SYNTAX      Unsigned32 (0..65535)
    MAX-ACCESS  read-only
    STATUS      obsolete
    DESCRIPTION
        "The value of vRtrLdpSessPeerTcpPort specifies the TCP port used on the
         remote end for the LDP Session.

         This object was obsoleted in release 13.0."
    ::= { vRtrLdpSessionEntry 12 }

vRtrLdpSessLocalAddress          OBJECT-TYPE
    SYNTAX      IpAddress
    MAX-ACCESS  read-only
    STATUS      obsolete
    DESCRIPTION
        "The value of vRtrLdpSessLocalAddress specifies the IP address used
         locally for the LDP Session.

         This object was obsoleted in release 13.0."
    ::= { vRtrLdpSessionEntry 13 }

vRtrLdpSessPeerAddress           OBJECT-TYPE
    SYNTAX      IpAddress
    MAX-ACCESS  read-only
    STATUS      obsolete
    DESCRIPTION
        "The value of vRtrLdpSessPeerAddress specifies the IP address used on
         the remote end for the LDP Session.

         This object was obsoleted in release 13.0."
    ::= { vRtrLdpSessionEntry 14 }

vRtrLdpSessKAHoldTimeRemaining   OBJECT-TYPE
    SYNTAX      TimeInterval
    MAX-ACCESS  read-only
    STATUS      obsolete
    DESCRIPTION
        "The value of vRtrLdpSessKAHoldTimeRemaining specifies the keep alive
         hold time remaining, in hundredths of seconds, for this LDP session.

         This object was obsoleted in release 13.0."
    ::= { vRtrLdpSessionEntry 15 }

vRtrLdpSessMaxPduLength          OBJECT-TYPE
    SYNTAX      Unsigned32 (1..65535)
    MAX-ACCESS  read-only
    STATUS      obsolete
    DESCRIPTION
        "The value of vRtrLdpSessMaxPduLength specifies the maximum allowable
         length for LDP PDUs for this session. This value may have been
         negotiated during Session Initialization.

         This object was obsoleted in release 13.0."
    ::= { vRtrLdpSessionEntry 16 }

vRtrLdpSessUpTime                OBJECT-TYPE
    SYNTAX      TimeInterval
    MAX-ACCESS  read-only
    STATUS      obsolete
    DESCRIPTION
        "The value of vRtrLdpSessUpTime specifies the time, in hundreds of
         seconds, since the session was established.

         This object was obsoleted in release 13.0."
    ::= { vRtrLdpSessionEntry 17 }

vRtrLdpSessLocalKATimeout        OBJECT-TYPE
    SYNTAX      TmnxLdpKeepAliveTimeout
    MAX-ACCESS  read-only
    STATUS      obsolete
    DESCRIPTION
        "The value of vRtrLdpSessLocalKATimeout specifies the keepalive timeout
         used locally for the LDP Session.

         This object was obsoleted in release 13.0."
    ::= { vRtrLdpSessionEntry 18 }

vRtrLdpSessPeerKATimeout         OBJECT-TYPE
    SYNTAX      TmnxLdpKeepAliveTimeout
    MAX-ACCESS  read-only
    STATUS      obsolete
    DESCRIPTION
        "The value of vRtrLdpSessPeerKATimeout specifies the keepalive timeout
         used at the remote end of the LDP Session.

         This object was obsoleted in release 13.0."
    ::= { vRtrLdpSessionEntry 19 }

vRtrLdpSessAdvertise             OBJECT-TYPE
    SYNTAX      INTEGER {
        address           (1),
        service           (2),
        addressAndService (3)
    }
    MAX-ACCESS  read-only
    STATUS      obsolete
    DESCRIPTION
        "The value of vRtrLdpSessAdvertise indicates the type of FECs that will
         be transported by the session.

         This object was obsoleted in release 13.0."
    ::= { vRtrLdpSessionEntry 20 }

vRtrLdpSessRestartHelperState    OBJECT-TYPE
    SYNTAX      TruthValue
    MAX-ACCESS  read-only
    STATUS      obsolete
    DESCRIPTION
        "The value of vRtrLdpSessRestartHelperState indicates whether the
         entity session is capable of supporting graceful restart.  This is
         negotiated between peers during the session initialization setup.

         This object was obsoleted in release 13.0."
    ::= { vRtrLdpSessionEntry 21 }

vRtrLdpSessPeerNumRestart        OBJECT-TYPE
    SYNTAX      Counter32
    MAX-ACCESS  read-only
    STATUS      obsolete
    DESCRIPTION
        "The value of vRtrLdpSessPeerNumRestart indicates the number of times
         graceful restart helper was initiated for this session.

         This object was obsoleted in release 13.0."
    ::= { vRtrLdpSessionEntry 22 }

vRtrLdpSessLastRestartTime       OBJECT-TYPE
    SYNTAX      TimeStamp
    MAX-ACCESS  read-only
    STATUS      obsolete
    DESCRIPTION
        "The value of vRtrLdpSessLastRestartTime indicates the last time
         graceful restart helper was initiated.

         This object was obsoleted in release 13.0."
    ::= { vRtrLdpSessionEntry 23 }

vRtrLdpSessFtReconnectTimeNego   OBJECT-TYPE
    SYNTAX      Unsigned32
    UNITS       "seconds"
    MAX-ACCESS  read-only
    STATUS      obsolete
    DESCRIPTION
        "The value of vRtrLdpSessFtReconnectTimeNego indicates the session's
         Fault Tolerant(FT) Reconnect Timeout, it is set to  the lesser of
         the neighbor advertised FT Reconnect Timeout,
         vRtrLdpSessFtReconTimeRemaining and the local timer Neighbor Liveness
         Time, vRtrLdpGenGRNbrLiveTime.  It is within this period that the
         transport session is expected to re-establish, failure to do so
         will cause the teardown of the LDP session and deletion of stale
         bindings.

         This object was obsoleted in release 13.0."
    ::= { vRtrLdpSessionEntry 24 }

vRtrLdpSessFtRecoveryTimeNego    OBJECT-TYPE
    SYNTAX      Unsigned32
    UNITS       "seconds"
    MAX-ACCESS  read-only
    STATUS      obsolete
    DESCRIPTION
        "The value of vRtrLdpSessFtRecoveryTimeNego indicates the session's
         Fault Tolerant(FT) recovery timeout, it is set to the lesser of the
         neighbor advertised FT recovery timeout,
         vRtrLdpSessFtRecovTimeRemaining and the local timer
         maximum recovery time, vRtrLdpGenGRMaxRecoveryTime.  It is within
         this period that label-FEC binding message exchanges are expected
         to complete.  Any stale FEC entries left after this time will be
         deleted from the FEC table.

         This object was obsoleted in release 13.0."
    ::= { vRtrLdpSessionEntry 25 }

vRtrLdpSessFtReconTimeRemaining  OBJECT-TYPE
    SYNTAX      Unsigned32
    UNITS       "seconds"
    MAX-ACCESS  read-only
    STATUS      obsolete
    DESCRIPTION
        "The value of vRtrLdpSessFtReconTimeRemaining indicates the amount of
         time left before the session's Fault Tolerant(FT) reconnect
         timeout,vRtrLdpSessFtReconnectTimeNego expires.

         This object was obsoleted in release 13.0."
    ::= { vRtrLdpSessionEntry 26 }

vRtrLdpSessFtRecovTimeRemaining  OBJECT-TYPE
    SYNTAX      Unsigned32
    UNITS       "seconds"
    MAX-ACCESS  read-only
    STATUS      obsolete
    DESCRIPTION
        "This value indicates the amount of time left before session's Fault
         Tolerant(FT) recovery timeout, vRtrLdpSessFtRecoveryTimeNego expires.

         This object was obsoleted in release 13.0."
    ::= { vRtrLdpSessionEntry 27 }

vRtrLdpSessBfdStatus             OBJECT-TYPE
    SYNTAX      INTEGER {
        noService    (1),
        inService    (2),
        outOfService (3)
    }
    MAX-ACCESS  read-only
    STATUS      obsolete
    DESCRIPTION
        "The value of vRtrLdpSessBfdStatus indicates the BFD operational status
         for the LDP session.

         If the value of vRtrLdpSessBfdStatus is 'noService', BFD is not
         enabled for the LDP session. If the value of the object is
         'outOfService', BFD is enabled but it is down and not running. If the
         value of object is 'inService', BFD is enabled and it is running.

         This object was obsoleted in release 13.0."
    ::= { vRtrLdpSessionEntry 28 }

vRtrLdpSessP2MPCapabilityNego    OBJECT-TYPE
    SYNTAX      TruthValue
    MAX-ACCESS  read-only
    STATUS      obsolete
    DESCRIPTION
        "The value of vRtrLdpSessP2MPCapabilityNego indicates whether the
         entity session is capable of exchanging P2MP FECs. This is negotiated
         between peers during the session initialization setup.

         This object was obsoleted in release 13.0."
    ::= { vRtrLdpSessionEntry 29 }

vRtrLdpSessMPMBBCapabilityNego   OBJECT-TYPE
    SYNTAX      TruthValue
    MAX-ACCESS  read-only
    STATUS      obsolete
    DESCRIPTION
        "The value of vRtrLdpSessMPMBBCapabilityNego indicates whether the
         entity session is capable of Multipoint MBB. This is negotiated
         between peers during the session initialization setup.

         This object was obsoleted in release 13.0."
    ::= { vRtrLdpSessionEntry 30 }

vRtrLdpSessDynamicCapabilityNego OBJECT-TYPE
    SYNTAX      TruthValue
    MAX-ACCESS  read-only
    STATUS      obsolete
    DESCRIPTION
        "The value of vRtrLdpSessDynamicCapabilityNego indicates whether the
         entity session supports negotiation of LDP session capabilities
         dynamically. This is negotiated between peers during the session
         initialization setup.

         This object was obsoleted in release 13.0."
    ::= { vRtrLdpSessionEntry 31 }

vRtrLdpSessOvrloadCapabltyNego   OBJECT-TYPE
    SYNTAX      TruthValue
    MAX-ACCESS  read-only
    STATUS      obsolete
    DESCRIPTION
        "The value of vRtrLdpSessOvrloadCapabltyNego indicates whether the
         entity session is capable of signaling LSR Overload Notification.This
         is negotiated between peers during the session initialization setup.

         This object was obsoleted in release 13.0."
    ::= { vRtrLdpSessionEntry 32 }

vRtrLdpSessAddrFecOverloadSent   OBJECT-TYPE
    SYNTAX      TruthValue
    MAX-ACCESS  read-only
    STATUS      obsolete
    DESCRIPTION
        "The value of vRtrLdpSessAddrFecOverloadSent indicates whether LSR
         Overload Notification has been sent to the LDP peer for Address FEC
         Types.

         The value of 'true' indicates that Local LSR has set the LDP session
         as overloaded for Address FEC types and is not ready to receive new
         Label Mappings for Address FEC Types. In this state if a Label Mapping
         Message is received from peer for any Address FEC type then the Label
         is returned with a Label Release Message.

         This object was obsoleted in release 13.0."
    ::= { vRtrLdpSessionEntry 33 }

vRtrLdpSessAddrFecOverloadRecv   OBJECT-TYPE
    SYNTAX      TruthValue
    MAX-ACCESS  read-only
    STATUS      obsolete
    DESCRIPTION
        "The value of vRtrLdpSessAddrFecOverloadRecv indicates whether LSR
         Overload Notification has been received from the LDP peer for Address
         FEC Types.

         The value of 'true' indicates that Peer LSR has set the LDP session as
         overloaded for Address FEC types and is not ready to receive new Label
         Mappings for any Address FEC Type. In this state no new Label Mapping
         Message would be sent to peer for any Address FEC Type.

         This object was obsoleted in release 13.0."
    ::= { vRtrLdpSessionEntry 34 }

vRtrLdpSessMcastFecOverloadSent  OBJECT-TYPE
    SYNTAX      TruthValue
    MAX-ACCESS  read-only
    STATUS      obsolete
    DESCRIPTION
        "The value of vRtrLdpSessMcastFecOverloadSent indicates whether LSR
         Overload Notification has been sent to the LDP peer for Multicast FEC
         Types.

         The value of 'true' indicates that Local LSR has set the LDP session
         as overloaded for Multicast FEC types and is not ready to receive new
         Label Mappings for Multicast FEC Types. In this state if a Label
         Mapping Message is received from peer for Multicast FEC types then the
         Label is returned with a Label Release Message.

         This object was obsoleted in release 13.0."
    ::= { vRtrLdpSessionEntry 35 }

vRtrLdpSessMcastFecOverloadRecv  OBJECT-TYPE
    SYNTAX      TruthValue
    MAX-ACCESS  read-only
    STATUS      obsolete
    DESCRIPTION
        "The value of vRtrLdpSessMcastFecOverloadRecv indicates whether LSR
         Overload Notification has been received from the LDP peer for
         Multicast FEC Types.

         The value of 'true' indicates that Peer LSR has set the LDP session as
         overloaded for Multicast FEC types and is not ready to receive new
         Label Mappings for any Multicast FEC Type. In this state no new Label
         Mapping Message would be sent to peer for any Multicast FEC Type.

         This object was obsoleted in release 13.0."
    ::= { vRtrLdpSessionEntry 36 }

vRtrLdpSessServFecOverloadSent   OBJECT-TYPE
    SYNTAX      TruthValue
    MAX-ACCESS  read-only
    STATUS      obsolete
    DESCRIPTION
        "The value of vRtrLdpSessServFecOverloadSent indicates whether LSR
         Overload Notification has been sent to the LDP peer for Service FEC
         Types.

         The value of 'true' indicates that Local LSR has set the LDP session
         as overloaded for Service FEC types and is not ready to receive new
         Label Mappings for Service FEC Types. In this state if a Label Mapping
         Message is received from peer for Service FEC types then the Label is
         returned with a Label Release Message.

         This object was obsoleted in release 13.0."
    ::= { vRtrLdpSessionEntry 37 }

vRtrLdpSessServFecOverloadRecv   OBJECT-TYPE
    SYNTAX      TruthValue
    MAX-ACCESS  read-only
    STATUS      obsolete
    DESCRIPTION
        "The value of vRtrLdpSessServFecOverloadRecv indicates whether LSR
         Overload Notification has been received from the LDP peer for Service
         FEC Types.

         The value of 'true' indicates that Peer LSR has set the LDP session as
         overloaded for Service FEC types and is not ready to receive new Label
         Mappings for any Service FEC Type. In this state no new Label Mapping
         Message would be sent to peer for any Service FEC Type.

         This object was obsoleted in release 13.0."
    ::= { vRtrLdpSessionEntry 38 }

vRtrLdpSessOperMaxFecThreshold   OBJECT-TYPE
    SYNTAX      Unsigned32
    UNITS       "percent"
    MAX-ACCESS  read-only
    STATUS      obsolete
    DESCRIPTION
        "The value of vRtrLdpSessOperMaxFecThreshold indicates the operational
         percentage of vRtrLdpPeerMaxFec.

         This object was obsoleted in release 13.0."
    ::= { vRtrLdpSessionEntry 39 }

vRtrLdpSessionStatsTable         OBJECT-TYPE
    SYNTAX      SEQUENCE OF VRtrLdpSessionStatsEntry
    MAX-ACCESS  not-accessible
    STATUS      obsolete
    DESCRIPTION
        "vRtrLdpSessionStatsTable is a read-only table. The purpose of this
         table is to keep statistical information about a single session
         between an LDP entity and an LDP Peer.

         Use of AUGMENTS clause implies a one-to-one dependent relationship
         between the base table, vRtrLdpSessionTable, and the augmenting table,
         vRtrLdpSessionStatsTable. This in effect extends the
         vRtrLdpSessionTable with additional columns. Creation or deletion of a
         row in the vRtrLdpSessionTable results in the same fate for the row in
         the vRtrLdpSessionStatsTable.

         In 13.0 this table has been replaced by
         TIMETRA-LDP-NG-MIB::vRtrLdpNgSessionStatsTable."
    ::= { tmnxLdpObjs 10 }

vRtrLdpSessionStatsEntry         OBJECT-TYPE
    SYNTAX      VRtrLdpSessionStatsEntry
    MAX-ACCESS  not-accessible
    STATUS      obsolete
    DESCRIPTION
        "A row in this table represents statistical information about a single
         session between an LDP entity and an LDP Peer."
    AUGMENTS    { vRtrLdpSessionEntry }
    ::= { vRtrLdpSessionStatsTable 1 }

VRtrLdpSessionStatsEntry         ::= SEQUENCE
{
    vRtrLdpSessStatsTargAdj          Gauge32,
    vRtrLdpSessStatsLinkAdj          Gauge32,
    vRtrLdpSessStatsFECRecv          Counter32,
    vRtrLdpSessStatsFECSent          Counter32,
    vRtrLdpSessStatsHelloIn          Counter32,
    vRtrLdpSessStatsHelloOut         Counter32,
    vRtrLdpSessStatsKeepaliveIn      Counter32,
    vRtrLdpSessStatsKeepaliveOut     Counter32,
    vRtrLdpSessStatsInitIn           Counter32,
    vRtrLdpSessStatsInitOut          Counter32,
    vRtrLdpSessStatsLabelMappingIn   Counter32,
    vRtrLdpSessStatsLabelMappingOut  Counter32,
    vRtrLdpSessStatsLabelRequestIn   Counter32,
    vRtrLdpSessStatsLabelRequestOut  Counter32,
    vRtrLdpSessStatsLabelReleaseIn   Counter32,
    vRtrLdpSessStatsLabelReleaseOut  Counter32,
    vRtrLdpSessStatsLabelWithdrawIn  Counter32,
    vRtrLdpSessStatsLabelWithdrawOut Counter32,
    vRtrLdpSessStatsLabelAbortIn     Counter32,
    vRtrLdpSessStatsLabelAbortOut    Counter32,
    vRtrLdpSessStatsAddrIn           Counter32,
    vRtrLdpSessStatsAddrOut          Counter32,
    vRtrLdpSessStatsAddrWithdrawIn   Counter32,
    vRtrLdpSessStatsAddrWithdrawOut  Counter32,
    vRtrLdpSessStatsNotificationIn   Counter32,
    vRtrLdpSessStatsNotificationOut  Counter32,
    vRtrLdpSessStatsAddrRecv         Counter32,
    vRtrLdpSessStatsAddrSent         Counter32
}

vRtrLdpSessStatsTargAdj          OBJECT-TYPE
    SYNTAX      Gauge32
    MAX-ACCESS  read-only
    STATUS      obsolete
    DESCRIPTION
        "The value of vRtrLdpSessStatsTargAdj specifies the number of targeted
         adjacencies for this session.

         This object was obsoleted in release 13.0."
    ::= { vRtrLdpSessionStatsEntry 1 }

vRtrLdpSessStatsLinkAdj          OBJECT-TYPE
    SYNTAX      Gauge32
    MAX-ACCESS  read-only
    STATUS      obsolete
    DESCRIPTION
        "The value of vRtrLdpSessStatsLinkAdj specifies the number of link
         adjacencies for this session.

         This object was obsoleted in release 13.0."
    ::= { vRtrLdpSessionStatsEntry 2 }

vRtrLdpSessStatsFECRecv          OBJECT-TYPE
    SYNTAX      Counter32
    MAX-ACCESS  read-only
    STATUS      obsolete
    DESCRIPTION
        "The value of vRtrLdpSessStatsFECRecv counts the number of FECs
         received for this session.

         This object was obsoleted in release 13.0."
    ::= { vRtrLdpSessionStatsEntry 3 }

vRtrLdpSessStatsFECSent          OBJECT-TYPE
    SYNTAX      Counter32
    MAX-ACCESS  read-only
    STATUS      obsolete
    DESCRIPTION
        "The value of vRtrLdpSessStatsFECSent counts the number of FECs sent
         for this session.

         This object was obsoleted in release 13.0."
    ::= { vRtrLdpSessionStatsEntry 4 }

vRtrLdpSessStatsHelloIn          OBJECT-TYPE
    SYNTAX      Counter32
    MAX-ACCESS  read-only
    STATUS      obsolete
    DESCRIPTION
        "The value of vRtrLdpSessStatsHelloIn counts the number of Hello
         Messages that have been received during this session.

         This object was obsoleted in release 13.0."
    ::= { vRtrLdpSessionStatsEntry 5 }

vRtrLdpSessStatsHelloOut         OBJECT-TYPE
    SYNTAX      Counter32
    MAX-ACCESS  read-only
    STATUS      obsolete
    DESCRIPTION
        "The value of vRtrLdpSessStatsHelloOut counts the number of Hello
         Messages that have been sent during this session.

         This object was obsoleted in release 13.0."
    ::= { vRtrLdpSessionStatsEntry 6 }

vRtrLdpSessStatsKeepaliveIn      OBJECT-TYPE
    SYNTAX      Counter32
    MAX-ACCESS  read-only
    STATUS      obsolete
    DESCRIPTION
        "The value of vRtrLdpSessStatsKeepaliveIn counts the number of
         Keepalive Messages that have been received during this session.

         This object was obsoleted in release 13.0."
    ::= { vRtrLdpSessionStatsEntry 7 }

vRtrLdpSessStatsKeepaliveOut     OBJECT-TYPE
    SYNTAX      Counter32
    MAX-ACCESS  read-only
    STATUS      obsolete
    DESCRIPTION
        "The value of vRtrLdpSessStatsKeepaliveOut counts the number of
         Keepalive Messages that have been sent during this session.

         This object was obsoleted in release 13.0."
    ::= { vRtrLdpSessionStatsEntry 8 }

vRtrLdpSessStatsInitIn           OBJECT-TYPE
    SYNTAX      Counter32
    MAX-ACCESS  read-only
    STATUS      obsolete
    DESCRIPTION
        "The value of vRtrLdpSessStatsInitIn counts the number of Init Messages
         that have been received during this session.

         This object was obsoleted in release 13.0."
    ::= { vRtrLdpSessionStatsEntry 9 }

vRtrLdpSessStatsInitOut          OBJECT-TYPE
    SYNTAX      Counter32
    MAX-ACCESS  read-only
    STATUS      obsolete
    DESCRIPTION
        "The value of vRtrLdpSessStatsInitOut counts the number of Init
         Messages that have been sent during this session.

         This object was obsoleted in release 13.0."
    ::= { vRtrLdpSessionStatsEntry 10 }

vRtrLdpSessStatsLabelMappingIn   OBJECT-TYPE
    SYNTAX      Counter32
    MAX-ACCESS  read-only
    STATUS      obsolete
    DESCRIPTION
        "The value of vRtrLdpSessStatsLabelMappingIn counts the number of Label
         Mapping Messages that have been received during this session.

         This object was obsoleted in release 13.0."
    ::= { vRtrLdpSessionStatsEntry 11 }

vRtrLdpSessStatsLabelMappingOut  OBJECT-TYPE
    SYNTAX      Counter32
    MAX-ACCESS  read-only
    STATUS      obsolete
    DESCRIPTION
        "The value of vRtrLdpSessStatsLabelMappingOut counts the number of
         Label Mapping Messages that have been sent during this session.

         This object was obsoleted in release 13.0."
    ::= { vRtrLdpSessionStatsEntry 12 }

vRtrLdpSessStatsLabelRequestIn   OBJECT-TYPE
    SYNTAX      Counter32
    MAX-ACCESS  read-only
    STATUS      obsolete
    DESCRIPTION
        "The value of vRtrLdpSessStatsLabelRequestIn counts the number of Label
         Request Messages that have been received during this session.

         This object was obsoleted in release 13.0."
    ::= { vRtrLdpSessionStatsEntry 13 }

vRtrLdpSessStatsLabelRequestOut  OBJECT-TYPE
    SYNTAX      Counter32
    MAX-ACCESS  read-only
    STATUS      obsolete
    DESCRIPTION
        "The value of vRtrLdpSessStatsLabelRequestOut counts the number of
         Label Request Messages that have been sent during this session.

         This object was obsoleted in release 13.0."
    ::= { vRtrLdpSessionStatsEntry 14 }

vRtrLdpSessStatsLabelReleaseIn   OBJECT-TYPE
    SYNTAX      Counter32
    MAX-ACCESS  read-only
    STATUS      obsolete
    DESCRIPTION
        "The value of vRtrLdpSessStatsLabelReleaseIn counts the number of Label
         Release Messages that have been received during this session.

         This object was obsoleted in release 13.0."
    ::= { vRtrLdpSessionStatsEntry 15 }

vRtrLdpSessStatsLabelReleaseOut  OBJECT-TYPE
    SYNTAX      Counter32
    MAX-ACCESS  read-only
    STATUS      obsolete
    DESCRIPTION
        "The value of vRtrLdpSessStatsLabelReleaseOut counts the number of
         Label Release Messages that have been sent during this session.

         This object was obsoleted in release 13.0."
    ::= { vRtrLdpSessionStatsEntry 16 }

vRtrLdpSessStatsLabelWithdrawIn  OBJECT-TYPE
    SYNTAX      Counter32
    MAX-ACCESS  read-only
    STATUS      obsolete
    DESCRIPTION
        "The value of vRtrLdpSessStatsLabelWithdrawIn counts the number of
         Label Withdraw Messages that have been received during this session.

         This object was obsoleted in release 13.0."
    ::= { vRtrLdpSessionStatsEntry 17 }

vRtrLdpSessStatsLabelWithdrawOut OBJECT-TYPE
    SYNTAX      Counter32
    MAX-ACCESS  read-only
    STATUS      obsolete
    DESCRIPTION
        "The value of vRtrLdpSessStatsLabelWithdrawOut counts the number of
         Label Withdraw Messages that have been sent during this session.

         This object was obsoleted in release 13.0."
    ::= { vRtrLdpSessionStatsEntry 18 }

vRtrLdpSessStatsLabelAbortIn     OBJECT-TYPE
    SYNTAX      Counter32
    MAX-ACCESS  read-only
    STATUS      obsolete
    DESCRIPTION
        "The value of vRtrLdpSessStatsLabelAbortIn counts the number of Label
         Abort Messages that have been received during this session.

         This object was obsoleted in release 13.0."
    ::= { vRtrLdpSessionStatsEntry 19 }

vRtrLdpSessStatsLabelAbortOut    OBJECT-TYPE
    SYNTAX      Counter32
    MAX-ACCESS  read-only
    STATUS      obsolete
    DESCRIPTION
        "The value of vRtrLdpSessStatsLabelAbortOut counts the number of Label
         Abort Messages that have been sent during this session.

         This object was obsoleted in release 13.0."
    ::= { vRtrLdpSessionStatsEntry 20 }

vRtrLdpSessStatsAddrIn           OBJECT-TYPE
    SYNTAX      Counter32
    MAX-ACCESS  read-only
    STATUS      obsolete
    DESCRIPTION
        "The value of vRtrLdpSessStatsAddrIn counts the number of Address
         Messages that have been received during this session.

         This object was obsoleted in release 13.0."
    ::= { vRtrLdpSessionStatsEntry 21 }

vRtrLdpSessStatsAddrOut          OBJECT-TYPE
    SYNTAX      Counter32
    MAX-ACCESS  read-only
    STATUS      obsolete
    DESCRIPTION
        "The value of vRtrLdpSessStatsAddrOut counts the number of Address
         Messages that have been sent during this session.

         This object was obsoleted in release 13.0."
    ::= { vRtrLdpSessionStatsEntry 22 }

vRtrLdpSessStatsAddrWithdrawIn   OBJECT-TYPE
    SYNTAX      Counter32
    MAX-ACCESS  read-only
    STATUS      obsolete
    DESCRIPTION
        "The value of vRtrLdpSessStatsAddrWithdrawIn counts the number of
         Address Withdraw Messages that have been received during this session.

         This object was obsoleted in release 13.0."
    ::= { vRtrLdpSessionStatsEntry 23 }

vRtrLdpSessStatsAddrWithdrawOut  OBJECT-TYPE
    SYNTAX      Counter32
    MAX-ACCESS  read-only
    STATUS      obsolete
    DESCRIPTION
        "The value of vRtrLdpSessStatsAddrWithdrawOut counts the number of
         Address Withdraw Messages that have been sent during this session.

         This object was obsoleted in release 13.0."
    ::= { vRtrLdpSessionStatsEntry 24 }

vRtrLdpSessStatsNotificationIn   OBJECT-TYPE
    SYNTAX      Counter32
    MAX-ACCESS  read-only
    STATUS      obsolete
    DESCRIPTION
        "The value of vRtrLdpSessStatsNotificationIn counts the number of
         Notification Messages that have been received during this session.

         This object was obsoleted in release 13.0."
    ::= { vRtrLdpSessionStatsEntry 25 }

vRtrLdpSessStatsNotificationOut  OBJECT-TYPE
    SYNTAX      Counter32
    MAX-ACCESS  read-only
    STATUS      obsolete
    DESCRIPTION
        "The value of vRtrLdpSessStatsNotificationOut counts the number of
         Notification Messages that have been sent during this session.

         This object was obsoleted in release 13.0."
    ::= { vRtrLdpSessionStatsEntry 26 }

vRtrLdpSessStatsAddrRecv         OBJECT-TYPE
    SYNTAX      Counter32
    MAX-ACCESS  read-only
    STATUS      obsolete
    DESCRIPTION
        "The value of vRtrLdpSessStatsAddrRecv counts the number of local
         addresses received for this session.

         This object was obsoleted in release 13.0."
    ::= { vRtrLdpSessionStatsEntry 27 }

vRtrLdpSessStatsAddrSent         OBJECT-TYPE
    SYNTAX      Counter32
    MAX-ACCESS  read-only
    STATUS      obsolete
    DESCRIPTION
        "The value of vRtrLdpSessStatsAddrSent counts the number of local
         addresses sent for this session.

         This object was obsoleted in release 13.0."
    ::= { vRtrLdpSessionStatsEntry 28 }

vRtrLdpServFecTable              OBJECT-TYPE
    SYNTAX      SEQUENCE OF VRtrLdpServFecEntry
    MAX-ACCESS  not-accessible
    STATUS      obsolete
    DESCRIPTION
        "vRtrLdpServFecTable is a read-only table that represents all service
         FECs either sent to or received from an LDP peer known to the Virtual
         Router.

         In 13.0 this table has been replaced by
         TIMETRA-LDP-NG-MIB::vLdpNgSvcFec128Table,
         TIMETRA-LDP-NG-MIB::vLdpNgSvcFec128InLblTable,
         TIMETRA-LDP-NG-MIB::vLdpNgSvcFec128OutLblTable."
    ::= { tmnxLdpObjs 11 }

vRtrLdpServFecEntry              OBJECT-TYPE
    SYNTAX      VRtrLdpServFecEntry
    MAX-ACCESS  not-accessible
    STATUS      obsolete
    DESCRIPTION
        "Each row entry represents an instance of a service FEC sent to or
         received from an LDP peer."
    INDEX       {
        vRtrID,
        vRtrLdpServFecFecType,
        vRtrLdpServFecVcType,
        vRtrLdpServFecVcId,
        vRtrLdpPeerLdpId
    }
    ::= { vRtrLdpServFecTable 1 }

VRtrLdpServFecEntry              ::= SEQUENCE
{
    vRtrLdpServFecFecType            TmnxLdpFECType,
    vRtrLdpServFecVcType             TmnxVcType,
    vRtrLdpServFecVcId               TmnxVcId,
    vRtrLdpServFecServType           ServType,
    vRtrLdpServFecServId             TmnxServId,
    vRtrLdpServFecVpnId              TmnxVpnId,
    vRtrLdpServFecFlags              TmnxLdpFECFlags,
    vRtrLdpServFecNumInLabels        Unsigned32,
    vRtrLdpServFecNumOutLabels       Unsigned32,
    vRtrLdpServFecInLabel1           Unsigned32,
    vRtrLdpServFecInLabelStatus1     TmnxLabelStatus,
    vRtrLdpServFecInLabel2           Unsigned32,
    vRtrLdpServFecInLabelStatus2     TmnxLabelStatus,
    vRtrLdpServFecInLabel3           Unsigned32,
    vRtrLdpServFecInLabelStatus3     TmnxLabelStatus,
    vRtrLdpServFecInLabel4           Unsigned32,
    vRtrLdpServFecInLabelStatus4     TmnxLabelStatus,
    vRtrLdpServFecInLabel5           Unsigned32,
    vRtrLdpServFecInLabelStatus5     TmnxLabelStatus,
    vRtrLdpServFecOutLabel1          Unsigned32,
    vRtrLdpServFecOutLabelStatus1    TmnxLabelStatus,
    vRtrLdpServFecOutLabel2          Unsigned32,
    vRtrLdpServFecOutLabelStatus2    TmnxLabelStatus,
    vRtrLdpServFecOutLabel3          Unsigned32,
    vRtrLdpServFecOutLabelStatus3    TmnxLabelStatus,
    vRtrLdpServFecOutLabel4          Unsigned32,
    vRtrLdpServFecOutLabelStatus4    TmnxLabelStatus,
    vRtrLdpServFecOutLabel5          Unsigned32,
    vRtrLdpServFecOutLabelStatus5    TmnxLabelStatus,
    vRtrLdpServFecSdpId              SdpId,
    vRtrLdpServFecLocalMTU           Unsigned32,
    vRtrLdpServFecRemoteMTU          Unsigned32,
    vRtrLdpServFecLocalVlanTag       Unsigned32,
    vRtrLdpServFecRemoteVlanTag      Unsigned32,
    vRtrLdpServFecLocalMaxCellConcat Unsigned32,
    vRtrLdpServFecRemoteMaxCellConcat Unsigned32,
    vRtrLdpServFecInLabelSigStatus1  TmnxLabelSigStatus,
    vRtrLdpServFecInLabelSigStatus2  TmnxLabelSigStatus,
    vRtrLdpServFecInLabelSigStatus3  TmnxLabelSigStatus,
    vRtrLdpServFecInLabelSigStatus4  TmnxLabelSigStatus,
    vRtrLdpServFecInLabelSigStatus5  TmnxLabelSigStatus,
    vRtrLdpServFecOutLabelSigStatus1 TmnxLabelSigStatus,
    vRtrLdpServFecOutLabelSigStatus2 TmnxLabelSigStatus,
    vRtrLdpServFecOutLabelSigStatus3 TmnxLabelSigStatus,
    vRtrLdpServFecOutLabelSigStatus4 TmnxLabelSigStatus,
    vRtrLdpServFecOutLabelSigStatus5 TmnxLabelSigStatus,
    vRtrLdpServFecMateEndpointVcId   TmnxVcId,
    vRtrLdpServFecMateEndpointSdpId  SdpId,
    vRtrLdpServFecLocalIpv4Capblty   TruthValue,
    vRtrLdpServFecRemoteIpv4Capblty  TruthValue,
    vRtrLdpServFecLocalIpv6Capblty   TruthValue,
    vRtrLdpServFecRemoteIpv6Capblty  TruthValue,
    vRtrLdpServFecLocalIpv4CeIpAddr  IpAddress,
    vRtrLdpServFecRemoteIpv4CeIpAddr IpAddress,
    vRtrLdpServFecInLbl1WdwReason    TmnxLdpInLblWdrawalReasonCode,
    vRtrLdpServFecLocalFLTxCapblty   TruthValue,
    vRtrLdpServFecLocalFLRxCapblty   TruthValue,
    vRtrLdpServFecRemoteFLTxCapblty  TruthValue,
    vRtrLdpServFecRemoteFLRxCapblty  TruthValue
}

vRtrLdpServFecFecType            OBJECT-TYPE
    SYNTAX      TmnxLdpFECType
    MAX-ACCESS  not-accessible
    STATUS      obsolete
    DESCRIPTION
        "The value of vRtrLdpServFecFecType specifies the FEC type.

         This object was obsoleted in release 13.0."
    ::= { vRtrLdpServFecEntry 1 }

vRtrLdpServFecVcType             OBJECT-TYPE
    SYNTAX      TmnxVcType
    MAX-ACCESS  not-accessible
    STATUS      obsolete
    DESCRIPTION
        "The value of vRtrLdpServFecVcType specifies the VC type associated
         with this service FEC.

         This object was obsoleted in release 13.0."
    ::= { vRtrLdpServFecEntry 2 }

vRtrLdpServFecVcId               OBJECT-TYPE
    SYNTAX      TmnxVcId
    MAX-ACCESS  not-accessible
    STATUS      obsolete
    DESCRIPTION
        "The value of vRtrLdpServFecVcId specifies the VC identifier associated
         with this service FEC.

         This object was obsoleted in release 13.0."
    ::= { vRtrLdpServFecEntry 3 }

vRtrLdpServFecServType           OBJECT-TYPE
    SYNTAX      ServType
    MAX-ACCESS  read-only
    STATUS      obsolete
    DESCRIPTION
        "The value of vRtrLdpServFecServType specifies the Service type
         associated with this service FEC.

         This object was obsoleted in release 13.0."
    ::= { vRtrLdpServFecEntry 4 }

vRtrLdpServFecServId             OBJECT-TYPE
    SYNTAX      TmnxServId (1..2147483647)
    MAX-ACCESS  read-only
    STATUS      obsolete
    DESCRIPTION
        "The value of vRtrLdpServFecServId specifies the Service identifier
         associated with this service FEC.

         This object was obsoleted in release 13.0."
    ::= { vRtrLdpServFecEntry 5 }

vRtrLdpServFecVpnId              OBJECT-TYPE
    SYNTAX      TmnxVpnId
    MAX-ACCESS  read-only
    STATUS      obsolete
    DESCRIPTION
        "The value of vRtrLdpServFecVpnId identifies the VPN associated with
         the FEC.

         This object was obsoleted in release 13.0."
    ::= { vRtrLdpServFecEntry 6 }

vRtrLdpServFecFlags              OBJECT-TYPE
    SYNTAX      TmnxLdpFECFlags
    MAX-ACCESS  read-only
    STATUS      obsolete
    DESCRIPTION
        "The bit flags of vRtrLdpServFecFlags specify the characteristics of
         the FEC.

         This object was obsoleted in release 13.0."
    ::= { vRtrLdpServFecEntry 7 }

vRtrLdpServFecNumInLabels        OBJECT-TYPE
    SYNTAX      Unsigned32
    MAX-ACCESS  read-only
    STATUS      obsolete
    DESCRIPTION
        "The value of vRtrLdpServFecNumInLabels gives the number of labels that
         have been sent to the peer associated with this FEC. This value also
         indicates which of the following vRtrLdpServFecInLabel1 thru
         vRtrLdpServFecInLabel5 entries contain valid information i.e. if the
         value of vRtrLdpServFecNumInLabels is 3 then vRtrLdpServFecInLabel1,
         vRtrLdpServFecInLabel2 and vRtrLdpServFecInLabel3 will contain valid
         label information.

         This object was obsoleted in release 13.0."
    ::= { vRtrLdpServFecEntry 8 }

vRtrLdpServFecNumOutLabels       OBJECT-TYPE
    SYNTAX      Unsigned32
    MAX-ACCESS  read-only
    STATUS      obsolete
    DESCRIPTION
        "The value of vRtrLdpServFecNumOutLabels gives the number of labels
         that have been received from the peer associated with this FEC. This
         value also indicates which of the following vRtrLdpServFecOutLabel1
         thru vRtrLdpServFecOutLabel5 entries contain valid information i.e. if
         the value of vRtrLdpServFecNumOutLabels is 3, then
         vRtrLdpServFecOutLabel1, vRtrLdpServFecOutLabel2 and
         vRtrLdpServFecOutLabel3 will contain valid label information.

         This object was obsoleted in release 13.0."
    ::= { vRtrLdpServFecEntry 9 }

vRtrLdpServFecInLabel1           OBJECT-TYPE
    SYNTAX      Unsigned32
    MAX-ACCESS  read-only
    STATUS      obsolete
    DESCRIPTION
        "The value of vRtrLdpServFecInLabel1 specifies the first ingress label
         exchanged.

         This object was obsoleted in release 13.0."
    ::= { vRtrLdpServFecEntry 10 }

vRtrLdpServFecInLabelStatus1     OBJECT-TYPE
    SYNTAX      TmnxLabelStatus
    MAX-ACCESS  read-only
    STATUS      obsolete
    DESCRIPTION
        "The value of vRtrLdpServFecInLabelStatus1 specifies the status of the
         ingress label 1.

         This object was obsoleted in release 13.0."
    ::= { vRtrLdpServFecEntry 11 }

vRtrLdpServFecInLabel2           OBJECT-TYPE
    SYNTAX      Unsigned32
    MAX-ACCESS  read-only
    STATUS      obsolete
    DESCRIPTION
        "The value of vRtrLdpServFecInLabel2 specifies the second ingress label
         (if at all) exchanged.

         This object was obsoleted in release 13.0."
    ::= { vRtrLdpServFecEntry 12 }

vRtrLdpServFecInLabelStatus2     OBJECT-TYPE
    SYNTAX      TmnxLabelStatus
    MAX-ACCESS  read-only
    STATUS      obsolete
    DESCRIPTION
        "The value of vRtrLdpServFecInLabelStatus2 specifies the status of the
         ingress label 2.

         This object was obsoleted in release 13.0."
    ::= { vRtrLdpServFecEntry 13 }

vRtrLdpServFecInLabel3           OBJECT-TYPE
    SYNTAX      Unsigned32
    MAX-ACCESS  read-only
    STATUS      obsolete
    DESCRIPTION
        "The value of vRtrLdpServFecInLabel3 specifies the third ingress label
         (if at all) exchanged.

         This object was obsoleted in release 13.0."
    ::= { vRtrLdpServFecEntry 14 }

vRtrLdpServFecInLabelStatus3     OBJECT-TYPE
    SYNTAX      TmnxLabelStatus
    MAX-ACCESS  read-only
    STATUS      obsolete
    DESCRIPTION
        "The value of vRtrLdpServFecInLabelStatus3 specifies the status of the
         ingress label 3.

         This object was obsoleted in release 13.0."
    ::= { vRtrLdpServFecEntry 15 }

vRtrLdpServFecInLabel4           OBJECT-TYPE
    SYNTAX      Unsigned32
    MAX-ACCESS  read-only
    STATUS      obsolete
    DESCRIPTION
        "The value of vRtrLdpServFecInLabel4 specifies the fourth ingress label
         (if at all) exchanged.

         This object was obsoleted in release 13.0."
    ::= { vRtrLdpServFecEntry 16 }

vRtrLdpServFecInLabelStatus4     OBJECT-TYPE
    SYNTAX      TmnxLabelStatus
    MAX-ACCESS  read-only
    STATUS      obsolete
    DESCRIPTION
        "The value of vRtrLdpServFecInLabelStatus4 specifies the status of the
         ingress label 4.

         This object was obsoleted in release 13.0."
    ::= { vRtrLdpServFecEntry 17 }

vRtrLdpServFecInLabel5           OBJECT-TYPE
    SYNTAX      Unsigned32
    MAX-ACCESS  read-only
    STATUS      obsolete
    DESCRIPTION
        "The value of vRtrLdpServFecInLabel5 specifies the fifth ingress label
         (if at all) exchanged.

         This object was obsoleted in release 13.0."
    ::= { vRtrLdpServFecEntry 18 }

vRtrLdpServFecInLabelStatus5     OBJECT-TYPE
    SYNTAX      TmnxLabelStatus
    MAX-ACCESS  read-only
    STATUS      obsolete
    DESCRIPTION
        "The value of vRtrLdpServFecInLabelStatus5 specifies the status of the
         ingress label 5.

         This object was obsoleted in release 13.0."
    ::= { vRtrLdpServFecEntry 19 }

vRtrLdpServFecOutLabel1          OBJECT-TYPE
    SYNTAX      Unsigned32
    MAX-ACCESS  read-only
    STATUS      obsolete
    DESCRIPTION
        "The value of vRtrLdpServFecOutLabel1 specifies the first egress label
         exchanged.

         This object was obsoleted in release 13.0."
    ::= { vRtrLdpServFecEntry 20 }

vRtrLdpServFecOutLabelStatus1    OBJECT-TYPE
    SYNTAX      TmnxLabelStatus
    MAX-ACCESS  read-only
    STATUS      obsolete
    DESCRIPTION
        "The value of vRtrLdpServFecOutLabelStatus1 specifies the status of the
         egress label 1.

         This object was obsoleted in release 13.0."
    ::= { vRtrLdpServFecEntry 21 }

vRtrLdpServFecOutLabel2          OBJECT-TYPE
    SYNTAX      Unsigned32
    MAX-ACCESS  read-only
    STATUS      obsolete
    DESCRIPTION
        "The value of vRtrLdpServFecOutLabel2 specifies the second egress label
         (if at all) exchanged.

         This object was obsoleted in release 13.0."
    ::= { vRtrLdpServFecEntry 22 }

vRtrLdpServFecOutLabelStatus2    OBJECT-TYPE
    SYNTAX      TmnxLabelStatus
    MAX-ACCESS  read-only
    STATUS      obsolete
    DESCRIPTION
        "The value of vRtrLdpServFecOutLabelStatus2 specifies the status of the
         egress label 2.

         This object was obsoleted in release 13.0."
    ::= { vRtrLdpServFecEntry 23 }

vRtrLdpServFecOutLabel3          OBJECT-TYPE
    SYNTAX      Unsigned32
    MAX-ACCESS  read-only
    STATUS      obsolete
    DESCRIPTION
        "The value of vRtrLdpServFecOutLabel3 specifies the third egress label
         (if at all) exchanged.

         This object was obsoleted in release 13.0."
    ::= { vRtrLdpServFecEntry 24 }

vRtrLdpServFecOutLabelStatus3    OBJECT-TYPE
    SYNTAX      TmnxLabelStatus
    MAX-ACCESS  read-only
    STATUS      obsolete
    DESCRIPTION
        "The value of vRtrLdpServFecOutLabelStatus3 specifies the status of the
         egress label 3.

         This object was obsoleted in release 13.0."
    ::= { vRtrLdpServFecEntry 25 }

vRtrLdpServFecOutLabel4          OBJECT-TYPE
    SYNTAX      Unsigned32
    MAX-ACCESS  read-only
    STATUS      obsolete
    DESCRIPTION
        "The value of vRtrLdpServFecOutLabel4 specifies the fourth egress label
         (if at all) exchanged.

         This object was obsoleted in release 13.0."
    ::= { vRtrLdpServFecEntry 26 }

vRtrLdpServFecOutLabelStatus4    OBJECT-TYPE
    SYNTAX      TmnxLabelStatus
    MAX-ACCESS  read-only
    STATUS      obsolete
    DESCRIPTION
        "The value of vRtrLdpServFecOutLabelStatus4 specifies the status of the
         egress label 4.

         This object was obsoleted in release 13.0."
    ::= { vRtrLdpServFecEntry 27 }

vRtrLdpServFecOutLabel5          OBJECT-TYPE
    SYNTAX      Unsigned32
    MAX-ACCESS  read-only
    STATUS      obsolete
    DESCRIPTION
        "The value of vRtrLdpServFecOutLabel5 specifies the fifth egress label
         (if at all) exchanged.

         This object was obsoleted in release 13.0."
    ::= { vRtrLdpServFecEntry 28 }

vRtrLdpServFecOutLabelStatus5    OBJECT-TYPE
    SYNTAX      TmnxLabelStatus
    MAX-ACCESS  read-only
    STATUS      obsolete
    DESCRIPTION
        "The value of vRtrLdpServFecOutLabelStatus5 specifies the status of the
         egress label 5.

         This object was obsoleted in release 13.0."
    ::= { vRtrLdpServFecEntry 29 }

vRtrLdpServFecSdpId              OBJECT-TYPE
    SYNTAX      SdpId
    MAX-ACCESS  read-only
    STATUS      obsolete
    DESCRIPTION
        "The value of vRtrLdpServFecSdpId identifies the SDP associated with
         this peer.

         This object was obsoleted in release 13.0."
    ::= { vRtrLdpServFecEntry 30 }

vRtrLdpServFecLocalMTU           OBJECT-TYPE
    SYNTAX      Unsigned32
    MAX-ACCESS  read-only
    STATUS      obsolete
    DESCRIPTION
        "The value of vRtrLdpServFecLocalMTU specifies the largest service
         frame size (in octets) that can be handled by the local ESR.

         This object was obsoleted in release 13.0."
    ::= { vRtrLdpServFecEntry 31 }

vRtrLdpServFecRemoteMTU          OBJECT-TYPE
    SYNTAX      Unsigned32
    MAX-ACCESS  read-only
    STATUS      obsolete
    DESCRIPTION
        "The value of vRtrLdpServFecRemoteMTU specifies the largest service
         frame size (in octets) that can be handled by the remote ESR.

         This object was obsoleted in release 13.0."
    ::= { vRtrLdpServFecEntry 32 }

vRtrLdpServFecLocalVlanTag       OBJECT-TYPE
    SYNTAX      Unsigned32
    MAX-ACCESS  read-only
    STATUS      obsolete
    DESCRIPTION
        "The value of vRtrLdpServFecLocalVlanTag specifies the local tag on a
         VLAN VC type SDP binding.

         This object was obsoleted in release 13.0."
    ::= { vRtrLdpServFecEntry 33 }

vRtrLdpServFecRemoteVlanTag      OBJECT-TYPE
    SYNTAX      Unsigned32
    MAX-ACCESS  read-only
    STATUS      obsolete
    DESCRIPTION
        "The value of vRtrLdpServFecRemoteVlanTag specifies the remote tag on a
         VLAN VC type SDP binding.

         This object was obsoleted in release 13.0."
    ::= { vRtrLdpServFecEntry 34 }

vRtrLdpServFecLocalMaxCellConcat OBJECT-TYPE
    SYNTAX      Unsigned32
    MAX-ACCESS  read-only
    STATUS      obsolete
    DESCRIPTION
        "The value of vRtrLdpServFecLocalMaxCellConcat specifies the local
         maximum number of ATM cells to concatenate on a ATM cell-mode VC type
         SDP binding.

         This object was obsoleted in release 13.0."
    ::= { vRtrLdpServFecEntry 35 }

vRtrLdpServFecRemoteMaxCellConcat OBJECT-TYPE
    SYNTAX      Unsigned32
    MAX-ACCESS  read-only
    STATUS      obsolete
    DESCRIPTION
        "The value of vRtrLdpServFecRemoteMaxCellConcat specifies the remote
         maximum number of ATM cells to concatenate on a ATM cell-mode VC type
         SDP binding.

         This object was obsoleted in release 13.0."
    ::= { vRtrLdpServFecEntry 36 }

vRtrLdpServFecInLabelSigStatus1  OBJECT-TYPE
    SYNTAX      TmnxLabelSigStatus
    MAX-ACCESS  read-only
    STATUS      obsolete
    DESCRIPTION
        "The value of vRtrLdpServFecInLabelSigStatus1 indicates the signaling
         status for vRtrLdpServFecInLabel1.

         This object was obsoleted in release 13.0."
    ::= { vRtrLdpServFecEntry 37 }

vRtrLdpServFecInLabelSigStatus2  OBJECT-TYPE
    SYNTAX      TmnxLabelSigStatus
    MAX-ACCESS  read-only
    STATUS      obsolete
    DESCRIPTION
        "The value of vRtrLdpServFecInLabelSigStatus2 indicates the signaling
         status for vRtrLdpServFecInLabel2.

         This object was obsoleted in release 13.0."
    ::= { vRtrLdpServFecEntry 38 }

vRtrLdpServFecInLabelSigStatus3  OBJECT-TYPE
    SYNTAX      TmnxLabelSigStatus
    MAX-ACCESS  read-only
    STATUS      obsolete
    DESCRIPTION
        "The value of vRtrLdpServFecInLabelSigStatus3 indicates the signaling
         status for vRtrLdpServFecInLabel3.

         This object was obsoleted in release 13.0."
    ::= { vRtrLdpServFecEntry 39 }

vRtrLdpServFecInLabelSigStatus4  OBJECT-TYPE
    SYNTAX      TmnxLabelSigStatus
    MAX-ACCESS  read-only
    STATUS      obsolete
    DESCRIPTION
        "The value of vRtrLdpServFecInLabelSigStatus4 indicates the signaling
         status for vRtrLdpServFecInLabel4.

         This object was obsoleted in release 13.0."
    ::= { vRtrLdpServFecEntry 40 }

vRtrLdpServFecInLabelSigStatus5  OBJECT-TYPE
    SYNTAX      TmnxLabelSigStatus
    MAX-ACCESS  read-only
    STATUS      obsolete
    DESCRIPTION
        "The value of vRtrLdpServFecInLabelSigStatus5 indicates the signaling
         status for vRtrLdpServFecInLabel5.

         This object was obsoleted in release 13.0."
    ::= { vRtrLdpServFecEntry 41 }

vRtrLdpServFecOutLabelSigStatus1 OBJECT-TYPE
    SYNTAX      TmnxLabelSigStatus
    MAX-ACCESS  read-only
    STATUS      obsolete
    DESCRIPTION
        "The value of vRtrLdpServFecOutLabelSigStatus1 indicates the signaling
         status for vRtrLdpServFecOutLabel1.

         This object was obsoleted in release 13.0."
    ::= { vRtrLdpServFecEntry 42 }

vRtrLdpServFecOutLabelSigStatus2 OBJECT-TYPE
    SYNTAX      TmnxLabelSigStatus
    MAX-ACCESS  read-only
    STATUS      obsolete
    DESCRIPTION
        "The value of vRtrLdpServFecOutLabelSigStatus2 indicates the signaling
         status for vRtrLdpServFecOutLabel2.

         This object was obsoleted in release 13.0."
    ::= { vRtrLdpServFecEntry 43 }

vRtrLdpServFecOutLabelSigStatus3 OBJECT-TYPE
    SYNTAX      TmnxLabelSigStatus
    MAX-ACCESS  read-only
    STATUS      obsolete
    DESCRIPTION
        "The value of vRtrLdpServFecOutLabelSigStatus3 indicates the signaling
         status for vRtrLdpServFecOutLabel3.

         This object was obsoleted in release 13.0."
    ::= { vRtrLdpServFecEntry 44 }

vRtrLdpServFecOutLabelSigStatus4 OBJECT-TYPE
    SYNTAX      TmnxLabelSigStatus
    MAX-ACCESS  read-only
    STATUS      obsolete
    DESCRIPTION
        "The value of vRtrLdpServFecOutLabelSigStatus4 indicates the signaling
         status for vRtrLdpServFecOutLabel4.

         This object was obsoleted in release 13.0."
    ::= { vRtrLdpServFecEntry 45 }

vRtrLdpServFecOutLabelSigStatus5 OBJECT-TYPE
    SYNTAX      TmnxLabelSigStatus
    MAX-ACCESS  read-only
    STATUS      obsolete
    DESCRIPTION
        "The value of vRtrLdpServFecOutLabelSigStatus5 indicates the signaling
         status for vRtrLdpServFecOutLabel5.

         This object was obsoleted in release 13.0."
    ::= { vRtrLdpServFecEntry 46 }

vRtrLdpServFecMateEndpointVcId   OBJECT-TYPE
    SYNTAX      TmnxVcId
    MAX-ACCESS  read-only
    STATUS      obsolete
    DESCRIPTION
        "The value of vRtrLdpServFecMateEndpointVcId specifies the VC
         identifier associated with this service FEC mate endpoint for
         vc-switching.

         This object was obsoleted in release 13.0."
    ::= { vRtrLdpServFecEntry 47 }

vRtrLdpServFecMateEndpointSdpId  OBJECT-TYPE
    SYNTAX      SdpId
    MAX-ACCESS  read-only
    STATUS      obsolete
    DESCRIPTION
        "The value of vRtrLdpServFecMateEndpointSdpId identifies the SDP
         associated with this service FEC mate endpoint for vc-switching.

         This object was obsoleted in release 13.0."
    ::= { vRtrLdpServFecEntry 48 }

vRtrLdpServFecLocalIpv4Capblty   OBJECT-TYPE
    SYNTAX      TruthValue
    MAX-ACCESS  read-only
    STATUS      obsolete
    DESCRIPTION
        "The value of vRtrLdpServFecLocalIpv4Capblty indicates whether or not
         the local ipv4 stack capability is supported for this LDP peer.

         The value of vRtrLdpServFecLocalIpv4Capblty is 'true' when the local
         ipv4 stack capability is supported and the value is 'false' when the
         local ipv4 stack capability is not supported.

         This object was obsoleted in release 13.0."
    ::= { vRtrLdpServFecEntry 49 }

vRtrLdpServFecRemoteIpv4Capblty  OBJECT-TYPE
    SYNTAX      TruthValue
    MAX-ACCESS  read-only
    STATUS      obsolete
    DESCRIPTION
        "The value of vRtrLdpServFecRemoteIpv4Capblty indicates whether or not
         the remote ipv4 stack capability is supported for this LDP peer.

         The value of vRtrLdpServFecLocalIpv4Capblty is 'true' when the remote
         ipv4 stack capability is supported and the value is 'false' when the
         remote ipv4 stack capability is not supported.

         This object was obsoleted in release 13.0."
    ::= { vRtrLdpServFecEntry 50 }

vRtrLdpServFecLocalIpv6Capblty   OBJECT-TYPE
    SYNTAX      TruthValue
    MAX-ACCESS  read-only
    STATUS      obsolete
    DESCRIPTION
        "The value of vRtrLdpServFecLocalIpv6Capblty indicates whether or not
         the local ipv6 stack capability is supported for this LDP peer.

         The value of vRtrLdpServFecLocalIpv6Capblty is 'true' when the local
         ipv6 stack capability is supported and the value is 'false' when the
         local ipv6 stack capability is not supported.

         This object was obsoleted in release 13.0."
    ::= { vRtrLdpServFecEntry 51 }

vRtrLdpServFecRemoteIpv6Capblty  OBJECT-TYPE
    SYNTAX      TruthValue
    MAX-ACCESS  read-only
    STATUS      obsolete
    DESCRIPTION
        "The value of vRtrLdpServFecRemoteIpv6Capblty indicates whether or not
         the remote ipv6 stack capability is supported for this LDP peer.

         The value of vRtrLdpServFecRemoteIpv6Capblty is 'true' when the remote
         ipv6 stack capability is supported and the value is 'false' when the
         remote ipv6 stack capability is not supported.

         This object was obsoleted in release 13.0."
    ::= { vRtrLdpServFecEntry 52 }

vRtrLdpServFecLocalIpv4CeIpAddr  OBJECT-TYPE
    SYNTAX      IpAddress
    MAX-ACCESS  read-only
    STATUS      obsolete
    DESCRIPTION
        "The value of vRtrLdpServFecLocalIpv4CeIpAddr indicates the local ipv4
         CE Address.

         This object was obsoleted in release 13.0."
    ::= { vRtrLdpServFecEntry 53 }

vRtrLdpServFecRemoteIpv4CeIpAddr OBJECT-TYPE
    SYNTAX      IpAddress
    MAX-ACCESS  read-only
    STATUS      obsolete
    DESCRIPTION
        "The value of vRtrLdpServFecRemoteIpv4CeIpAddr indicates the remote
         ipv4 CE Address.

         This object was obsoleted in release 13.0."
    ::= { vRtrLdpServFecEntry 54 }

vRtrLdpServFecInLbl1WdwReason    OBJECT-TYPE
    SYNTAX      TmnxLdpInLblWdrawalReasonCode
    MAX-ACCESS  read-only
    STATUS      obsolete
    DESCRIPTION
        "The value of vRtrLdpServFecInLbl1WdwReason indicates the reason of
         withdrawal of ingress label value in vRtrLdpServFecInLabel1.

         This object was obsoleted in release 13.0."
    ::= { vRtrLdpServFecEntry 55 }

vRtrLdpServFecLocalFLTxCapblty   OBJECT-TYPE
    SYNTAX      TruthValue
    MAX-ACCESS  read-only
    STATUS      obsolete
    DESCRIPTION
        "The value of vRtrLdpServFecLocalFLTxCapblty indicates whether or not
         this LDP peer is capable of sending Flow Label in its pseudowire (PW)
         packet.

         The value of vRtrLdpServFecLocalFLTxCapblty is 'true' when this LDP
         peer is capable of sending Flow Label and the value is 'false' when
         the peer is not capable of sending Flow Label in pseudowire packet.

         This object was obsoleted in release 13.0."
    ::= { vRtrLdpServFecEntry 56 }

vRtrLdpServFecLocalFLRxCapblty   OBJECT-TYPE
    SYNTAX      TruthValue
    MAX-ACCESS  read-only
    STATUS      obsolete
    DESCRIPTION
        "The value of vRtrLdpServFecLocalFLRxCapblty indicates whether or not
         this LDP peer is capable of receiving Flow Label in its pseudowire
         packet.

         The value of vRtrLdpServFecLocalFLRxCapblty is 'true' when this LDP
         peer is capable of receiving Flow Label and the value is 'false' when
         the peer is not capable of receiving Flow Label in pseudowire packet.

         This object was obsoleted in release 13.0."
    ::= { vRtrLdpServFecEntry 57 }

vRtrLdpServFecRemoteFLTxCapblty  OBJECT-TYPE
    SYNTAX      TruthValue
    MAX-ACCESS  read-only
    STATUS      obsolete
    DESCRIPTION
        "The value of vRtrLdpServFecRemoteFLTxCapblty indicates whether or not
         the remote LDP peer is capable of sending Flow Label in its pseudowire
         packet.

         The value of vRtrLdpServFecRemoteFLTxCapblty is 'true' when the remote
         LDP peer is capable of sending Flow Label and the value is 'false'
         when the peer is not capable of sending Flow Label in pseudowire
         packet.

         This object was obsoleted in release 13.0."
    ::= { vRtrLdpServFecEntry 58 }

vRtrLdpServFecRemoteFLRxCapblty  OBJECT-TYPE
    SYNTAX      TruthValue
    MAX-ACCESS  read-only
    STATUS      obsolete
    DESCRIPTION
        "The value of vRtrLdpServFecRemoteFLRxCapblty indicates whether or not
         the remote LDP peer is capable of receiving Flow Label in its
         pseudowire packet.

         The value of vRtrLdpServFecRemoteFLRxCapblty is 'true' when the remote
         LDP peer is capable of receiving Flow Label and the value is 'false'
         when the peer is not capable of receiving Flow Label in pseudowire
         packet.

         This object was obsoleted in release 13.0."
    ::= { vRtrLdpServFecEntry 59 }

vRtrLdpServFecMapTable           OBJECT-TYPE
    SYNTAX      SEQUENCE OF VRtrLdpServFecMapEntry
    MAX-ACCESS  not-accessible
    STATUS      obsolete
    DESCRIPTION
        "vRtrLdpServFecMapTable is a read-only table which maps to the
         vRtrLdpServFecTable. This table has the same indexes as the
         vRtrLdpServFecTable but the order in which these indexes are specified
         is different for the two tables."
    ::= { tmnxLdpObjs 12 }

vRtrLdpServFecMapEntry           OBJECT-TYPE
    SYNTAX      VRtrLdpServFecMapEntry
    MAX-ACCESS  not-accessible
    STATUS      obsolete
    DESCRIPTION
        "Each row entry represents an instance of a service FEC sent to or
         received from an LDP peer."
    INDEX       {
        vRtrID,
        vRtrLdpPeerLdpId,
        vRtrLdpServFecMapFecType,
        vRtrLdpServFecMapVcType,
        vRtrLdpServFecMapVcId
    }
    ::= { vRtrLdpServFecMapTable 1 }

VRtrLdpServFecMapEntry           ::= SEQUENCE
{
    vRtrLdpServFecMapFecType         TmnxLdpFECType,
    vRtrLdpServFecMapVcType          TmnxVcType,
    vRtrLdpServFecMapVcId            TmnxVcId
}

vRtrLdpServFecMapFecType         OBJECT-TYPE
    SYNTAX      TmnxLdpFECType
    MAX-ACCESS  read-only
    STATUS      obsolete
    DESCRIPTION
        "The value of vRtrLdpServFecMapFecType specifies the FEC type."
    ::= { vRtrLdpServFecMapEntry 1 }

vRtrLdpServFecMapVcType          OBJECT-TYPE
    SYNTAX      TmnxVcType
    MAX-ACCESS  read-only
    STATUS      obsolete
    DESCRIPTION
        "The value of vRtrLdpServFecMapVcType specifies the VC type associated
         with this service FEC."
    ::= { vRtrLdpServFecMapEntry 2 }

vRtrLdpServFecMapVcId            OBJECT-TYPE
    SYNTAX      TmnxVcId
    MAX-ACCESS  read-only
    STATUS      obsolete
    DESCRIPTION
        "The value of vRtrLdpServFecMapVcId specifies the VC identifier
         associated with this service FEC."
    ::= { vRtrLdpServFecMapEntry 3 }

vRtrLdpAddrFecTable              OBJECT-TYPE
    SYNTAX      SEQUENCE OF VRtrLdpAddrFecEntry
    MAX-ACCESS  not-accessible
    STATUS      obsolete
    DESCRIPTION
        "vRtrLdpAddrFecTable is a read-only table that represents all address
         FECs either sent to or received from an LDP peer known to the Virtual
         Router."
    ::= { tmnxLdpObjs 13 }

vRtrLdpAddrFecEntry              OBJECT-TYPE
    SYNTAX      VRtrLdpAddrFecEntry
    MAX-ACCESS  not-accessible
    STATUS      obsolete
    DESCRIPTION
        "Each row entry represents an instance of an address FEC sent to or
         received from an LDP peer."
    INDEX       {
        vRtrID,
        vRtrLdpAddrFecFecType,
        vRtrLdpAddrFecIpPrefix,
        vRtrLdpAddrFecIpMask,
        vRtrLdpPeerLdpId
    }
    ::= { vRtrLdpAddrFecTable 1 }

VRtrLdpAddrFecEntry              ::= SEQUENCE
{
    vRtrLdpAddrFecFecType            TmnxLdpFECType,
    vRtrLdpAddrFecIpPrefix           IpAddress,
    vRtrLdpAddrFecIpMask             IpAddress,
    vRtrLdpAddrFecFlags              TmnxLdpFECFlags,
    vRtrLdpAddrFecNumInLabels        Unsigned32,
    vRtrLdpAddrFecNumOutLabels       Unsigned32,
    vRtrLdpAddrFecInLabel1           Unsigned32,
    vRtrLdpAddrFecInLabelStatus1     TmnxLabelStatus,
    vRtrLdpAddrFecInLabelIfIndex1    InterfaceIndexOrZero,
    vRtrLdpAddrFecInLabel2           Unsigned32,
    vRtrLdpAddrFecInLabelStatus2     TmnxLabelStatus,
    vRtrLdpAddrFecInLabelIfIndex2    InterfaceIndexOrZero,
    vRtrLdpAddrFecInLabel3           Unsigned32,
    vRtrLdpAddrFecInLabelStatus3     TmnxLabelStatus,
    vRtrLdpAddrFecInLabelIfIndex3    InterfaceIndexOrZero,
    vRtrLdpAddrFecInLabel4           Unsigned32,
    vRtrLdpAddrFecInLabelStatus4     TmnxLabelStatus,
    vRtrLdpAddrFecInLabelIfIndex4    InterfaceIndexOrZero,
    vRtrLdpAddrFecInLabel5           Unsigned32,
    vRtrLdpAddrFecInLabelStatus5     TmnxLabelStatus,
    vRtrLdpAddrFecInLabelIfIndex5    InterfaceIndexOrZero,
    vRtrLdpAddrFecOutLabel1          Unsigned32,
    vRtrLdpAddrFecOutLabelStatus1    TmnxLabelStatus,
    vRtrLdpAddrFecOutLabelIfIndex1   InterfaceIndexOrZero,
    vRtrLdpAddrFecOutLabelNextHop1   IpAddress,
    vRtrLdpAddrFecOutLabel2          Unsigned32,
    vRtrLdpAddrFecOutLabelStatus2    TmnxLabelStatus,
    vRtrLdpAddrFecOutLabelIfIndex2   InterfaceIndexOrZero,
    vRtrLdpAddrFecOutLabelNextHop2   IpAddress,
    vRtrLdpAddrFecOutLabel3          Unsigned32,
    vRtrLdpAddrFecOutLabelStatus3    TmnxLabelStatus,
    vRtrLdpAddrFecOutLabelIfIndex3   InterfaceIndexOrZero,
    vRtrLdpAddrFecOutLabelNextHop3   IpAddress,
    vRtrLdpAddrFecOutLabel4          Unsigned32,
    vRtrLdpAddrFecOutLabelStatus4    TmnxLabelStatus,
    vRtrLdpAddrFecOutLabelIfIndex4   InterfaceIndexOrZero,
    vRtrLdpAddrFecOutLabelNextHop4   IpAddress,
    vRtrLdpAddrFecOutLabel5          Unsigned32,
    vRtrLdpAddrFecOutLabelStatus5    TmnxLabelStatus,
    vRtrLdpAddrFecOutLabelIfIndex5   InterfaceIndexOrZero,
    vRtrLdpAddrFecOutLabelNextHop5   IpAddress,
    vRtrLdpAddrFecLspId              TmnxVRtrMplsLspID,
    vRtrLdpAddrFecLspId2             TmnxVRtrMplsLspID,
    vRtrLdpAddrFecLspId3             TmnxVRtrMplsLspID,
    vRtrLdpAddrFecLspId4             TmnxVRtrMplsLspID,
    vRtrLdpAddrFecLspId5             TmnxVRtrMplsLspID
}

vRtrLdpAddrFecFecType            OBJECT-TYPE
    SYNTAX      TmnxLdpFECType
    MAX-ACCESS  not-accessible
    STATUS      obsolete
    DESCRIPTION
        "The value of vRtrLdpAddrFecFecType specifies the FEC type.

         This object was obsoleted in release 10.0."
    ::= { vRtrLdpAddrFecEntry 1 }

vRtrLdpAddrFecIpPrefix           OBJECT-TYPE
    SYNTAX      IpAddress
    MAX-ACCESS  not-accessible
    STATUS      obsolete
    DESCRIPTION
        "The value of vRtrLdpAddrFecIpPrefix specifies the IP Address Prefix
         for this address FEC.

         This object was obsoleted in release 10.0."
    ::= { vRtrLdpAddrFecEntry 2 }

vRtrLdpAddrFecIpMask             OBJECT-TYPE
    SYNTAX      IpAddress
    MAX-ACCESS  not-accessible
    STATUS      obsolete
    DESCRIPTION
        "The value of vRtrLdpAddrFecIpMask specifies the IP Address Mask for
         this address FEC.

         This object was obsoleted in release 10.0."
    ::= { vRtrLdpAddrFecEntry 3 }

vRtrLdpAddrFecFlags              OBJECT-TYPE
    SYNTAX      TmnxLdpFECFlags
    MAX-ACCESS  read-only
    STATUS      obsolete
    DESCRIPTION
        "The bit flags of vRtrLdpAddrFecFlags specify the characteristics of
         the FEC.

         This object was obsoleted in release 10.0."
    ::= { vRtrLdpAddrFecEntry 4 }

vRtrLdpAddrFecNumInLabels        OBJECT-TYPE
    SYNTAX      Unsigned32
    MAX-ACCESS  read-only
    STATUS      obsolete
    DESCRIPTION
        "The value of vRtrLdpAddrFecNumInLabels gives the number of labels that
         have been sent to the peer associated with this FEC. This value also
         indicates which of the following vRtrLdpAddrFecInLabel1 thru
         vRtrLdpAddrFecInLabel5 entries contain valid information i.e. if the
         value of vRtrLdpAddrFecNumInLabels is 3 then vRtrLdpAddrFecInLabel1,
         vRtrLdpAddrFecInLabel2 and vRtrLdpAddrFecInLabel3 will contain valid
         label information.

         This object was obsoleted in release 10.0."
    ::= { vRtrLdpAddrFecEntry 5 }

vRtrLdpAddrFecNumOutLabels       OBJECT-TYPE
    SYNTAX      Unsigned32
    MAX-ACCESS  read-only
    STATUS      obsolete
    DESCRIPTION
        "The value of vRtrLdpAddrFecNumOutLabels gives the number of labels
         that have been received from the peer associated with this FEC. This
         value also indicates which of the following vRtrLdpAddrFecOutLabel1
         thru vRtrLdpAddrFecOutLabel5 entries contain valid information i.e. if
         the value of vRtrLdpAddrFecNumOutLabels is 3, then
         vRtrLdpAddrFecOutLabel1, vRtrLdpAddrFecOutLabel2 and
         vRtrLdpAddrFecOutLabel3 will contain valid label information.

         This object was obsoleted in release 10.0."
    ::= { vRtrLdpAddrFecEntry 6 }

vRtrLdpAddrFecInLabel1           OBJECT-TYPE
    SYNTAX      Unsigned32
    MAX-ACCESS  read-only
    STATUS      obsolete
    DESCRIPTION
        "The value of vRtrLdpAddrFecInLabel1 specifies the first ingress label
         exchanged

         This object was obsoleted in release 10.0."
    ::= { vRtrLdpAddrFecEntry 7 }

vRtrLdpAddrFecInLabelStatus1     OBJECT-TYPE
    SYNTAX      TmnxLabelStatus
    MAX-ACCESS  read-only
    STATUS      obsolete
    DESCRIPTION
        "The value of vRtrLdpAddrFecInLabelStatus1 specifies the status of the
         ingress label 1

         This object was obsoleted in release 10.0."
    ::= { vRtrLdpAddrFecEntry 8 }

vRtrLdpAddrFecInLabelIfIndex1    OBJECT-TYPE
    SYNTAX      InterfaceIndexOrZero
    MAX-ACCESS  read-only
    STATUS      obsolete
    DESCRIPTION
        "The value of vRtrLdpAddrFecInLabelIfIndex1 specifies the interface
         index for ingress label 1.

         This object was obsoleted in release 10.0."
    ::= { vRtrLdpAddrFecEntry 9 }

vRtrLdpAddrFecInLabel2           OBJECT-TYPE
    SYNTAX      Unsigned32
    MAX-ACCESS  read-only
    STATUS      obsolete
    DESCRIPTION
        "The value of vRtrLdpAddrFecInLabel2 specifies the second ingress label
         (if at all) exchanged.

         This object was obsoleted in release 10.0."
    ::= { vRtrLdpAddrFecEntry 10 }

vRtrLdpAddrFecInLabelStatus2     OBJECT-TYPE
    SYNTAX      TmnxLabelStatus
    MAX-ACCESS  read-only
    STATUS      obsolete
    DESCRIPTION
        "The value of vRtrLdpAddrFecInLabelStatus2 specifies the status of the
         ingress label.

         This object was obsoleted in release 10.0."
    ::= { vRtrLdpAddrFecEntry 11 }

vRtrLdpAddrFecInLabelIfIndex2    OBJECT-TYPE
    SYNTAX      InterfaceIndexOrZero
    MAX-ACCESS  read-only
    STATUS      obsolete
    DESCRIPTION
        "The value of vRtrLdpAddrFecInLabelIfIndex2 specifies the interface
         index for ingress label 2.

         This object was obsoleted in release 10.0."
    ::= { vRtrLdpAddrFecEntry 12 }

vRtrLdpAddrFecInLabel3           OBJECT-TYPE
    SYNTAX      Unsigned32
    MAX-ACCESS  read-only
    STATUS      obsolete
    DESCRIPTION
        "The value of vRtrLdpAddrFecInLabel3 specifies the third ingress label
         (if at all) exchanged.

         This object was obsoleted in release 10.0."
    ::= { vRtrLdpAddrFecEntry 13 }

vRtrLdpAddrFecInLabelStatus3     OBJECT-TYPE
    SYNTAX      TmnxLabelStatus
    MAX-ACCESS  read-only
    STATUS      obsolete
    DESCRIPTION
        "The value of vRtrLdpAddrFecInLabelStatus3 specifies the status of the
         ingress label 3.

         This object was obsoleted in release 10.0."
    ::= { vRtrLdpAddrFecEntry 14 }

vRtrLdpAddrFecInLabelIfIndex3    OBJECT-TYPE
    SYNTAX      InterfaceIndexOrZero
    MAX-ACCESS  read-only
    STATUS      obsolete
    DESCRIPTION
        "The value of vRtrLdpAddrFecInLabelIfIndex3 specifies the interface
         index for ingress label 3.

         This object was obsoleted in release 10.0."
    ::= { vRtrLdpAddrFecEntry 15 }

vRtrLdpAddrFecInLabel4           OBJECT-TYPE
    SYNTAX      Unsigned32
    MAX-ACCESS  read-only
    STATUS      obsolete
    DESCRIPTION
        "The value of vRtrLdpAddrFecInLabel4 specifies the fourth ingress label
         (if at all) exchanged.

         This object was obsoleted in release 10.0."
    ::= { vRtrLdpAddrFecEntry 16 }

vRtrLdpAddrFecInLabelStatus4     OBJECT-TYPE
    SYNTAX      TmnxLabelStatus
    MAX-ACCESS  read-only
    STATUS      obsolete
    DESCRIPTION
        "The value of vRtrLdpAddrFecInLabelStatus4 specifies the status of the
         ingress label 4.

         This object was obsoleted in release 10.0."
    ::= { vRtrLdpAddrFecEntry 17 }

vRtrLdpAddrFecInLabelIfIndex4    OBJECT-TYPE
    SYNTAX      InterfaceIndexOrZero
    MAX-ACCESS  read-only
    STATUS      obsolete
    DESCRIPTION
        "The value of vRtrLdpAddrFecInLabelIfIndex4 specifies the interface
         index for ingress label 4.

         This object was obsoleted in release 10.0."
    ::= { vRtrLdpAddrFecEntry 18 }

vRtrLdpAddrFecInLabel5           OBJECT-TYPE
    SYNTAX      Unsigned32
    MAX-ACCESS  read-only
    STATUS      obsolete
    DESCRIPTION
        "The value of vRtrLdpAddrFecInLabel5 specifies the fifth ingress label
         (if at all) exchanged.

         This object was obsoleted in release 10.0."
    ::= { vRtrLdpAddrFecEntry 19 }

vRtrLdpAddrFecInLabelStatus5     OBJECT-TYPE
    SYNTAX      TmnxLabelStatus
    MAX-ACCESS  read-only
    STATUS      obsolete
    DESCRIPTION
        "The value of vRtrLdpAddrFecInLabelStatus5 specifies the status of the
         ingress label 5.

         This object was obsoleted in release 10.0."
    ::= { vRtrLdpAddrFecEntry 20 }

vRtrLdpAddrFecInLabelIfIndex5    OBJECT-TYPE
    SYNTAX      InterfaceIndexOrZero
    MAX-ACCESS  read-only
    STATUS      obsolete
    DESCRIPTION
        "The value of vRtrLdpAddrFecInLabelIfIndex5 specifies the interface
         index for ingress label 5.

         This object was obsoleted in release 10.0."
    ::= { vRtrLdpAddrFecEntry 21 }

vRtrLdpAddrFecOutLabel1          OBJECT-TYPE
    SYNTAX      Unsigned32
    MAX-ACCESS  read-only
    STATUS      obsolete
    DESCRIPTION
        "The value of vRtrLdpAddrFecOutLabel1 specifies the first egress label
         exchanged.

         This object was obsoleted in release 10.0."
    ::= { vRtrLdpAddrFecEntry 22 }

vRtrLdpAddrFecOutLabelStatus1    OBJECT-TYPE
    SYNTAX      TmnxLabelStatus
    MAX-ACCESS  read-only
    STATUS      obsolete
    DESCRIPTION
        "The value of vRtrLdpAddrFecOutLabelStatus1 specifies the status of the
         egress label 1.

         This object was obsoleted in release 10.0."
    ::= { vRtrLdpAddrFecEntry 23 }

vRtrLdpAddrFecOutLabelIfIndex1   OBJECT-TYPE
    SYNTAX      InterfaceIndexOrZero
    MAX-ACCESS  read-only
    STATUS      obsolete
    DESCRIPTION
        "The value of vRtrLdpAddrFecOutLabelIfIndex1 specifies the interface
         index for egress label 1.

         This object was obsoleted in release 10.0."
    ::= { vRtrLdpAddrFecEntry 24 }

vRtrLdpAddrFecOutLabelNextHop1   OBJECT-TYPE
    SYNTAX      IpAddress
    MAX-ACCESS  read-only
    STATUS      obsolete
    DESCRIPTION
        "The value of vRtrLdpAddrFecOutLabelNextHop1 specifies the IP address
         of the next hop for egress label 1.

         This object was obsoleted in release 10.0."
    ::= { vRtrLdpAddrFecEntry 25 }

vRtrLdpAddrFecOutLabel2          OBJECT-TYPE
    SYNTAX      Unsigned32
    MAX-ACCESS  read-only
    STATUS      obsolete
    DESCRIPTION
        "The value of vRtrLdpAddrFecOutLabel2 specifies the second egress label
         (if at all) exchanged.

         This object was obsoleted in release 10.0."
    ::= { vRtrLdpAddrFecEntry 26 }

vRtrLdpAddrFecOutLabelStatus2    OBJECT-TYPE
    SYNTAX      TmnxLabelStatus
    MAX-ACCESS  read-only
    STATUS      obsolete
    DESCRIPTION
        "The value of vRtrLdpAddrFecOutLabelStatus2 specifies the status of the
         egress label 2.

         This object was obsoleted in release 10.0."
    ::= { vRtrLdpAddrFecEntry 27 }

vRtrLdpAddrFecOutLabelIfIndex2   OBJECT-TYPE
    SYNTAX      InterfaceIndexOrZero
    MAX-ACCESS  read-only
    STATUS      obsolete
    DESCRIPTION
        "The value of vRtrLdpAddrFecOutLabelIfIndex2 specifies the interface
         index for egress label 2.

         This object was obsoleted in release 10.0."
    ::= { vRtrLdpAddrFecEntry 28 }

vRtrLdpAddrFecOutLabelNextHop2   OBJECT-TYPE
    SYNTAX      IpAddress
    MAX-ACCESS  read-only
    STATUS      obsolete
    DESCRIPTION
        "The value of vRtrLdpAddrFecOutLabelNextHop2 specifies the IP address
         of the next hop for egress label 2.

         This object was obsoleted in release 10.0."
    ::= { vRtrLdpAddrFecEntry 29 }

vRtrLdpAddrFecOutLabel3          OBJECT-TYPE
    SYNTAX      Unsigned32
    MAX-ACCESS  read-only
    STATUS      obsolete
    DESCRIPTION
        "The value of vRtrLdpAddrFecOutLabel3 specifies the third egress label
         (if at all) exchanged.

         This object was obsoleted in release 10.0."
    ::= { vRtrLdpAddrFecEntry 30 }

vRtrLdpAddrFecOutLabelStatus3    OBJECT-TYPE
    SYNTAX      TmnxLabelStatus
    MAX-ACCESS  read-only
    STATUS      obsolete
    DESCRIPTION
        "The value of vRtrLdpAddrFecOutLabelStatus3 specifies the status of the
         egress label 3.

         This object was obsoleted in release 10.0."
    ::= { vRtrLdpAddrFecEntry 31 }

vRtrLdpAddrFecOutLabelIfIndex3   OBJECT-TYPE
    SYNTAX      InterfaceIndexOrZero
    MAX-ACCESS  read-only
    STATUS      obsolete
    DESCRIPTION
        "The value of vRtrLdpAddrFecOutLabelIfIndex3 specifies the interface
         index for egress label 3.

         This object was obsoleted in release 10.0."
    ::= { vRtrLdpAddrFecEntry 32 }

vRtrLdpAddrFecOutLabelNextHop3   OBJECT-TYPE
    SYNTAX      IpAddress
    MAX-ACCESS  read-only
    STATUS      obsolete
    DESCRIPTION
        "The value of vRtrLdpAddrFecOutLabelNextHop3 specifies the IP address
         of the next hop for egress label 3.

         This object was obsoleted in release 10.0."
    ::= { vRtrLdpAddrFecEntry 33 }

vRtrLdpAddrFecOutLabel4          OBJECT-TYPE
    SYNTAX      Unsigned32
    MAX-ACCESS  read-only
    STATUS      obsolete
    DESCRIPTION
        "The value of vRtrLdpAddrFecOutLabel4 specifies the fourth egress label
         (if at all) exchanged.

         This object was obsoleted in release 10.0."
    ::= { vRtrLdpAddrFecEntry 34 }

vRtrLdpAddrFecOutLabelStatus4    OBJECT-TYPE
    SYNTAX      TmnxLabelStatus
    MAX-ACCESS  read-only
    STATUS      obsolete
    DESCRIPTION
        "The value of vRtrLdpAddrFecOutLabelStatus4 specifies the status of the
         egress label 4.

         This object was obsoleted in release 10.0."
    ::= { vRtrLdpAddrFecEntry 35 }

vRtrLdpAddrFecOutLabelIfIndex4   OBJECT-TYPE
    SYNTAX      InterfaceIndexOrZero
    MAX-ACCESS  read-only
    STATUS      obsolete
    DESCRIPTION
        "The value of vRtrLdpAddrFecOutLabelIfIndex4 specifies the interface
         index for egress label 4.

         This object was obsoleted in release 10.0."
    ::= { vRtrLdpAddrFecEntry 36 }

vRtrLdpAddrFecOutLabelNextHop4   OBJECT-TYPE
    SYNTAX      IpAddress
    MAX-ACCESS  read-only
    STATUS      obsolete
    DESCRIPTION
        "The value of vRtrLdpAddrFecOutLabelNextHop4 specifies the IP address
         of the next hop for egress label 4.

         This object was obsoleted in release 10.0."
    ::= { vRtrLdpAddrFecEntry 37 }

vRtrLdpAddrFecOutLabel5          OBJECT-TYPE
    SYNTAX      Unsigned32
    MAX-ACCESS  read-only
    STATUS      obsolete
    DESCRIPTION
        "The value of vRtrLdpAddrFecOutLabel5 specifies the fifth egress label
         (if at all) exchanged.

         This object was obsoleted in release 10.0."
    ::= { vRtrLdpAddrFecEntry 38 }

vRtrLdpAddrFecOutLabelStatus5    OBJECT-TYPE
    SYNTAX      TmnxLabelStatus
    MAX-ACCESS  read-only
    STATUS      obsolete
    DESCRIPTION
        "The value of vRtrLdpAddrFecOutLabelStatus5 specifies the status of the
         egress label 5.

         This object was obsoleted in release 10.0."
    ::= { vRtrLdpAddrFecEntry 39 }

vRtrLdpAddrFecOutLabelIfIndex5   OBJECT-TYPE
    SYNTAX      InterfaceIndexOrZero
    MAX-ACCESS  read-only
    STATUS      obsolete
    DESCRIPTION
        "The value of vRtrLdpAddrFecOutLabelIfIndex5 specifies the interface
         index for egress label 5.

         This object was obsoleted in release 10.0."
    ::= { vRtrLdpAddrFecEntry 40 }

vRtrLdpAddrFecOutLabelNextHop5   OBJECT-TYPE
    SYNTAX      IpAddress
    MAX-ACCESS  read-only
    STATUS      obsolete
    DESCRIPTION
        "The value of vRtrLdpAddrFecOutLabelNextHop5 specifies the IP address
         of the next hop for egress label 5.

         This object was obsoleted in release 10.0."
    ::= { vRtrLdpAddrFecEntry 41 }

vRtrLdpAddrFecLspId              OBJECT-TYPE
    SYNTAX      TmnxVRtrMplsLspID
    MAX-ACCESS  read-only
    STATUS      obsolete
    DESCRIPTION
        "The value of vRtrLdpAddrFecLspId indicates the LSP id of the LSP for
         the RSVP tunnel used by LDP in LDP over RSVP associated with egress
         label 1.

         This object was obsoleted in release 10.0."
    ::= { vRtrLdpAddrFecEntry 42 }

vRtrLdpAddrFecLspId2             OBJECT-TYPE
    SYNTAX      TmnxVRtrMplsLspID
    MAX-ACCESS  read-only
    STATUS      obsolete
    DESCRIPTION
        "The value of vRtrLdpAddrFecLspId2 indicates the LSP id of the LSP for
         the RSVP tunnel used by LDP in LDP over RSVP associated with egress
         label 2.

         This object was obsoleted in release 10.0."
    ::= { vRtrLdpAddrFecEntry 43 }

vRtrLdpAddrFecLspId3             OBJECT-TYPE
    SYNTAX      TmnxVRtrMplsLspID
    MAX-ACCESS  read-only
    STATUS      obsolete
    DESCRIPTION
        "The value of vRtrLdpAddrFecLspId3 indicates the LSP id of the LSP for
         the RSVP tunnel used by LDP in LDP over RSVP associated with egress
         label 3.

         This object was obsoleted in release 10.0."
    ::= { vRtrLdpAddrFecEntry 44 }

vRtrLdpAddrFecLspId4             OBJECT-TYPE
    SYNTAX      TmnxVRtrMplsLspID
    MAX-ACCESS  read-only
    STATUS      obsolete
    DESCRIPTION
        "The value of vRtrLdpAddrFecLspId4 indicates the LSP id of the LSP for
         the RSVP tunnel used by LDP in LDP over RSVP associated with egress
         label 4.

         This object was obsoleted in release 10.0."
    ::= { vRtrLdpAddrFecEntry 45 }

vRtrLdpAddrFecLspId5             OBJECT-TYPE
    SYNTAX      TmnxVRtrMplsLspID
    MAX-ACCESS  read-only
    STATUS      obsolete
    DESCRIPTION
        "The value of vRtrLdpAddrFecLspId5 indicates the LSP id of the LSP for
         the RSVP tunnel used by LDP in LDP over RSVP associated with egress
         label 5.

         This object was obsoleted in release 10.0."
    ::= { vRtrLdpAddrFecEntry 46 }

vRtrLdpAddrFecMapTable           OBJECT-TYPE
    SYNTAX      SEQUENCE OF VRtrLdpAddrFecMapEntry
    MAX-ACCESS  not-accessible
    STATUS      obsolete
    DESCRIPTION
        "vRtrLdpAddrFecMapTable is a read-only table which maps to the
         vRtrLdpAddrFecTable. This table has the same indexes as the
         vRtrLdpAddrFecTable but the order in which these indexes are specified
         is different for the two tables."
    ::= { tmnxLdpObjs 14 }

vRtrLdpAddrFecMapEntry           OBJECT-TYPE
    SYNTAX      VRtrLdpAddrFecMapEntry
    MAX-ACCESS  not-accessible
    STATUS      obsolete
    DESCRIPTION
        "Each row entry represents an instance of an address FEC sent to or
         received from an LDP peer."
    INDEX       {
        vRtrID,
        vRtrLdpPeerLdpId,
        vRtrLdpAddrFecMapFecType,
        vRtrLdpAddrFecMapIpPrefix,
        vRtrLdpAddrFecMapIpMask
    }
    ::= { vRtrLdpAddrFecMapTable 1 }

VRtrLdpAddrFecMapEntry           ::= SEQUENCE
{
    vRtrLdpAddrFecMapFecType         TmnxLdpFECType,
    vRtrLdpAddrFecMapIpPrefix        IpAddress,
    vRtrLdpAddrFecMapIpMask          IpAddress
}

vRtrLdpAddrFecMapFecType         OBJECT-TYPE
    SYNTAX      TmnxLdpFECType
    MAX-ACCESS  read-only
    STATUS      obsolete
    DESCRIPTION
        "The value of vRtrLdpAddrFecMapFecType specifies the FEC type.

         This object was obsoleted in release 10.0."
    ::= { vRtrLdpAddrFecMapEntry 1 }

vRtrLdpAddrFecMapIpPrefix        OBJECT-TYPE
    SYNTAX      IpAddress
    MAX-ACCESS  read-only
    STATUS      obsolete
    DESCRIPTION
        "The value of vRtrLdpAddrFecMapIpPrefix specifies the IP Address Prefix
         for this address FEC.

         This object was obsoleted in release 10.0."
    ::= { vRtrLdpAddrFecMapEntry 2 }

vRtrLdpAddrFecMapIpMask          OBJECT-TYPE
    SYNTAX      IpAddress
    MAX-ACCESS  read-only
    STATUS      obsolete
    DESCRIPTION
        "The value of vRtrLdpAddrFecMapIpMask specifies the IP Address Mask for
         this address FEC.

         This object was obsoleted in release 10.0."
    ::= { vRtrLdpAddrFecMapEntry 3 }

vRtrLdpAdjBackoffTable           OBJECT-TYPE
    SYNTAX      SEQUENCE OF VRtrLdpAdjBackoffEntry
    MAX-ACCESS  not-accessible
    STATUS      obsolete
    DESCRIPTION
        "vRtrLdpAdjBackoffTable is a read-only table which augments the
         vRtrLdpHelloAdjTable. The purpose of this table is to keep backoff
         information about the LDP Hello Adjacencies on the virtual router.

         Use of AUGMENTS clause implies a one-to-one dependent
         relationship between the base table, vRtrLdpHelloAdjTable,
         and the augmenting table vRtrLdpAdjBackoffTable. This in
         effect extends the vRtrLdpHelloAdjTable with additional
         columns.  Creation or deletion of a row in the
         vRtrLdpHelloAdjTable results in the same fate for the row
         in the vRtrLdpAdjBackoffTable."
    ::= { tmnxLdpObjs 15 }

vRtrLdpAdjBackoffEntry           OBJECT-TYPE
    SYNTAX      VRtrLdpAdjBackoffEntry
    MAX-ACCESS  not-accessible
    STATUS      obsolete
    DESCRIPTION
        "A row in this table contains backoff information about an LDP
         adjacency.

         When an LDP session startup fails for the first time, the LDP entity
         waits for a certain time interval before it tries to setup the session
         again. This interval is the backoff interval. The initial value for
         the backoff interval is set to the value of vRtrLdpAdjInitBackoff.
         After waiting for the backoff interval, LDP retries to setup the LDP
         session. If it fails again the backoff interval increases
         exponentially and this repeats for each successive LDP session startup
         failure. If the backoff interval exceeds vRtrLdpAdjMaxBackoff, LDP
         will not backoff anymore and will give up trying to establish the LDP
         session."
    AUGMENTS    { vRtrLdpHelloAdjEntry }
    ::= { vRtrLdpAdjBackoffTable 1 }

VRtrLdpAdjBackoffEntry           ::= SEQUENCE
{
    vRtrLdpAdjInitBackoff            Unsigned32,
    vRtrLdpAdjMaxBackoff             Unsigned32,
    vRtrLdpAdjCurrentBackoff         Unsigned32,
    vRtrLdpAdjWaitingTime            Unsigned32,
    vRtrLdpAdjBackoffStatus          TruthValue
}

vRtrLdpAdjInitBackoff            OBJECT-TYPE
    SYNTAX      Unsigned32 (1..2592000)
    UNITS       "seconds"
    MAX-ACCESS  read-only
    STATUS      obsolete
    DESCRIPTION
        "The value of vRtrLdpAdjInitBackoff specifies the initial backoff time.
         After a LDP session setup has failed, the value of
         vRtrLdpAdjInitBackoff is the time interval, in seconds, that the LDP
         entity waits before attempting to setup the session again. This
         interval is the backoff interval. This variable indicates the initial
         value for backoff interval when the LDP session startup first fails.
         Thereafter, if session startup fails again the backoff interval
         increases exponentially.

         This object was obsoleted in release 13.0."
    ::= { vRtrLdpAdjBackoffEntry 1 }

vRtrLdpAdjMaxBackoff             OBJECT-TYPE
    SYNTAX      Unsigned32 (0..2592000)
    UNITS       "seconds"
    MAX-ACCESS  read-only
    STATUS      obsolete
    DESCRIPTION
        "The value of vRtrLdpAdjMaxBackoff specifies the maximum backoff time.
         For each successive failure of the LDP session startup, the backoff
         interval (the time for which the router waits before retrying)
         increases exponentially. If the backoff interval exceeds
         vRtrLdpAdjMaxBackoff, the router will not backoff anymore and will
         give up trying to establish the LDP session. A value of 0 for
         vRtrLdpAdjMaxBackoff indicates that the backoff interval remains
         constant and will not increase exponentially. In effect the router
         will try to establish an LDP session till it succeeds.

         This object was obsoleted in release 13.0."
    ::= { vRtrLdpAdjBackoffEntry 2 }

vRtrLdpAdjCurrentBackoff         OBJECT-TYPE
    SYNTAX      Unsigned32
    UNITS       "seconds"
    MAX-ACCESS  read-only
    STATUS      obsolete
    DESCRIPTION
        "This value of vRtrLdpAdjCurrentBackoff specifies the current value of
         the backoff interval.

         This object was obsoleted in release 13.0."
    ::= { vRtrLdpAdjBackoffEntry 3 }

vRtrLdpAdjWaitingTime            OBJECT-TYPE
    SYNTAX      Unsigned32
    UNITS       "seconds"
    MAX-ACCESS  read-only
    STATUS      obsolete
    DESCRIPTION
        "The value of vRtrLdpAdjWaitingTime specifies the time for which the
         entity has been waiting in backoff state.

         This object was obsoleted in release 13.0."
    ::= { vRtrLdpAdjBackoffEntry 4 }

vRtrLdpAdjBackoffStatus          OBJECT-TYPE
    SYNTAX      TruthValue
    MAX-ACCESS  read-only
    STATUS      obsolete
    DESCRIPTION
        "The value of vRtrLdpAdjBackoffStatus indicates whether or not the
         entity is in backoff state. If this value is 'true', then the entity
         is in a backoff state and if the value is 'false' then the entity is
         not in a backoff state.

         This object was obsoleted in release 13.0."
    ::= { vRtrLdpAdjBackoffEntry 5 }

vRtrLdpPeerParamsTable           OBJECT-TYPE
    SYNTAX      SEQUENCE OF VRtrLdpPeerParamsEntry
    MAX-ACCESS  not-accessible
    STATUS      obsolete
    DESCRIPTION
        "vRtrLdpPeerParamsTable has an entry for an LDP peer. This table is
         used to configure parameters specific to the peer whether it is an
         interface or a targeted peer.

         In 13.0 this table has been replaced by
         TIMETRA-LDP-NG-MIB::vRtrLdpNgSessionParamsTable,
         TIMETRA-LDP-NG-MIB::vRtrLdpNgTcpSessParamsTable."
    ::= { tmnxLdpObjs 16 }

vRtrLdpPeerParamsEntry           OBJECT-TYPE
    SYNTAX      VRtrLdpPeerParamsEntry
    MAX-ACCESS  not-accessible
    STATUS      obsolete
    DESCRIPTION
        "Each row entry represents a peer that participates in the LDP protocol
         on this virtual router.

         Row entries can be created or deleted via SNMP SET requests. A row
         with default attribute values is created by setting
         vRtrLdpPeerRowStatus to 'createAndGo'. A row entry can be destroyed by
         setting vRtrLdpPeerRowStatus to 'destroy'.

         A row entry with vRtrLdpPeerAddress of 0.0.0.0 represents the default
         LDP parameters used for all peers that do not have a corresponding
         entry in this table."
    INDEX       {
        vRtrID,
        vRtrLdpPeerAddress
    }
    ::= { vRtrLdpPeerParamsTable 1 }

VRtrLdpPeerParamsEntry           ::= SEQUENCE
{
    vRtrLdpPeerRowStatus             RowStatus,
    vRtrLdpPeerAuth                  TruthValue,
    vRtrLdpPeerAuthKey               OCTET STRING,
    vRtrLdpPeerMinTTLValue           Unsigned32,
    vRtrLdpPeerTTLLogId              TFilterLogId,
    vRtrLdpPeerAuthKeyChain          TNamedItemOrEmpty,
    vRtrLdpPeerDODLabelDistribution  TruthValue,
    vRtrLdpPeerImportPolicy1         TPolicyStatementNameOrEmpty,
    vRtrLdpPeerImportPolicy2         TPolicyStatementNameOrEmpty,
    vRtrLdpPeerImportPolicy3         TPolicyStatementNameOrEmpty,
    vRtrLdpPeerImportPolicy4         TPolicyStatementNameOrEmpty,
    vRtrLdpPeerImportPolicy5         TPolicyStatementNameOrEmpty,
    vRtrLdpPeerExportPolicy1         TPolicyStatementNameOrEmpty,
    vRtrLdpPeerExportPolicy2         TPolicyStatementNameOrEmpty,
    vRtrLdpPeerExportPolicy3         TPolicyStatementNameOrEmpty,
    vRtrLdpPeerExportPolicy4         TPolicyStatementNameOrEmpty,
    vRtrLdpPeerExportPolicy5         TPolicyStatementNameOrEmpty,
    vRtrLdpPeerFec129CiscoInterop    TruthValue,
    vRtrLdpPeerPMTUDiscovery         TruthValue,
    vRtrLdpPeerAdvAdjAddrOnly        TruthValue,
    vRtrLdpPeerPeIDMacFlushInterop   TruthValue,
    vRtrLdpPeerMaxFec                Unsigned32,
    vRtrLdpPeerMaxFecLogOnly         TruthValue,
    vRtrLdpPeerMaxFecThreshold       Unsigned32
}

vRtrLdpPeerRowStatus             OBJECT-TYPE
    SYNTAX      RowStatus
    MAX-ACCESS  read-create
    STATUS      obsolete
    DESCRIPTION
        "vRtrLdpPeerRowStatus is used to control the creation and deletion of
         rows in the vRtrLdpPeerParamsTable.

         A row can be created by setting vRtrLdpPeerRowStatus to 'createAndGo'.
         The agent should assign the default attribute values and change the
         row status to 'active'.

         A row entry can be destroyed by setting vRtrLdpPeerRowStatus to
         'destroy'.

         This object was obsoleted in release 13.0."
    ::= { vRtrLdpPeerParamsEntry 1 }

vRtrLdpPeerAuth                  OBJECT-TYPE
    SYNTAX      TruthValue
    MAX-ACCESS  read-create
    STATUS      obsolete
    DESCRIPTION
        "When the value of vRtrLdpPeerAuth is 'true', authentication
         using MD5 message based digest protocol is enabled.  When 'false',
         no authentication is used.

         This object was obsoleted in release 13.0."
    DEFVAL      { false }
    ::= { vRtrLdpPeerParamsEntry 2 }

vRtrLdpPeerAuthKey               OBJECT-TYPE
    SYNTAX      OCTET STRING (SIZE (0..16))
    MAX-ACCESS  read-create
    STATUS      obsolete
    DESCRIPTION
        "The string specified in vRtrLdpPeerAuthKey is the authentication key
         to be used between LDP neighbors before establishing sessions.
         Authentication is done using the MD-5 message based digest protocol.
         The authentication key can be any combination of letters or numbers.
         Note that the string may contain embedded nulls.

         An SNMP Get request on this object should return an OCTET STRING of
         length 0.

         This object was obsoleted in release 13.0."
    DEFVAL      { ''H }
    ::= { vRtrLdpPeerParamsEntry 3 }

vRtrLdpPeerMinTTLValue           OBJECT-TYPE
    SYNTAX      Unsigned32 (0 | 1..255)
    MAX-ACCESS  read-create
    STATUS      obsolete
    DESCRIPTION
        "The value of vRtrLdpPeerMinTTLValue specifies the minimum TTL value
         for an incoming LDP packet.

         If vRtrLdpPeerMinTTLValue is set to zero (0), the TTL Security feature
         is disabled.

         This object was obsoleted in release 13.0."
    DEFVAL      { 0 }
    ::= { vRtrLdpPeerParamsEntry 4 }

vRtrLdpPeerTTLLogId              OBJECT-TYPE
    SYNTAX      TFilterLogId
    MAX-ACCESS  read-create
    STATUS      obsolete
    DESCRIPTION
        "The value of vRtrLdpPeerTTLLogId specifies the filter log to use for
         packets that fail TTL security check. The value zero indicates that
         logging is disabled.

         This object was obsoleted in release 13.0."
    DEFVAL      { 0 }
    ::= { vRtrLdpPeerParamsEntry 5 }

vRtrLdpPeerAuthKeyChain          OBJECT-TYPE
    SYNTAX      TNamedItemOrEmpty
    MAX-ACCESS  read-create
    STATUS      obsolete
    DESCRIPTION
        "The value of vRtrLdpPeerAuthKeyChain specifies the
         keychain which will be used to sign and/or authenticate  the LDP
         protocol stream.

         The keychain name is defined by tmnxKeyChainName and is the index for
         TIMETRA-SECURITY-MIB::tmnxKeyChainTable.

         This object was obsoleted in release 13.0."
    DEFVAL      { ''H }
    ::= { vRtrLdpPeerParamsEntry 6 }

vRtrLdpPeerDODLabelDistribution  OBJECT-TYPE
    SYNTAX      TruthValue
    MAX-ACCESS  read-create
    STATUS      obsolete
    DESCRIPTION
        "The value of vRtrLdpPeerDODLabelDistribution specifies whether or not
         Downstream-On-Demand (DOD) has been enabled for the LDP session. When
         the value is set to 'true' DOD is enabled for the LDP session.

         This object was obsoleted in release 13.0."
    DEFVAL      { false }
    ::= { vRtrLdpPeerParamsEntry 7 }

vRtrLdpPeerImportPolicy1         OBJECT-TYPE
    SYNTAX      TPolicyStatementNameOrEmpty
    MAX-ACCESS  read-create
    STATUS      obsolete
    DESCRIPTION
        "The value of vRtrLdpPeerImportPolicy1 specifies the first import
         policy used to determine which FEC prefixes received from other LDP
         and TLDP peers should be redistributed to this LDP peer.

         This object was obsoleted in release 13.0."
    DEFVAL      { ''H }
    ::= { vRtrLdpPeerParamsEntry 8 }

vRtrLdpPeerImportPolicy2         OBJECT-TYPE
    SYNTAX      TPolicyStatementNameOrEmpty
    MAX-ACCESS  read-create
    STATUS      obsolete
    DESCRIPTION
        "The value of vRtrLdpPeerImportPolicy2 specifies the second import
         policy used to determine which FEC prefixes received from other LDP
         and TLDP peers should be redistributed to this LDP peer.

         This object was obsoleted in release 13.0."
    DEFVAL      { ''H }
    ::= { vRtrLdpPeerParamsEntry 9 }

vRtrLdpPeerImportPolicy3         OBJECT-TYPE
    SYNTAX      TPolicyStatementNameOrEmpty
    MAX-ACCESS  read-create
    STATUS      obsolete
    DESCRIPTION
        "The value of vRtrLdpPeerImportPolicy3 specifies the third import
         policy used to determine which FEC prefixes received from other LDP
         and TLDP peers should be redistributed to this LDP peer.

         This object was obsoleted in release 13.0."
    DEFVAL      { ''H }
    ::= { vRtrLdpPeerParamsEntry 10 }

vRtrLdpPeerImportPolicy4         OBJECT-TYPE
    SYNTAX      TPolicyStatementNameOrEmpty
    MAX-ACCESS  read-create
    STATUS      obsolete
    DESCRIPTION
        "The value of vRtrLdpPeerImportPolicy4 specifies the fourth import
         policy used to determine which FEC prefixes received from other LDP
         and TLDP peers should be redistributed to this LDP peer.

         This object was obsoleted in release 13.0."
    DEFVAL      { ''H }
    ::= { vRtrLdpPeerParamsEntry 11 }

vRtrLdpPeerImportPolicy5         OBJECT-TYPE
    SYNTAX      TPolicyStatementNameOrEmpty
    MAX-ACCESS  read-create
    STATUS      obsolete
    DESCRIPTION
        "The value of vRtrLdpPeerImportPolicy5 specifies the fifth import
         policy used to determine which FEC prefixes received from other LDP
         and TLDP peers should be redistributed to this LDP peer.

         This object was obsoleted in release 13.0."
    DEFVAL      { ''H }
    ::= { vRtrLdpPeerParamsEntry 12 }

vRtrLdpPeerExportPolicy1         OBJECT-TYPE
    SYNTAX      TPolicyStatementNameOrEmpty
    MAX-ACCESS  read-create
    STATUS      obsolete
    DESCRIPTION
        "The value of vRtrLdpPeerExportPolicy1 specifies the first export
         policy used to determine which FEC prefixes received from this LDP
         peer should be redistributed to other LDP and TLDP peers.

         This object was obsoleted in release 13.0."
    DEFVAL      { ''H }
    ::= { vRtrLdpPeerParamsEntry 13 }

vRtrLdpPeerExportPolicy2         OBJECT-TYPE
    SYNTAX      TPolicyStatementNameOrEmpty
    MAX-ACCESS  read-create
    STATUS      obsolete
    DESCRIPTION
        "The value of vRtrLdpPeerExportPolicy2 specifies the second export
         policy used to determine which FEC prefixes received from this LDP
         peer should be redistributed to other LDP and TLDP peers.

         This object was obsoleted in release 13.0."
    DEFVAL      { ''H }
    ::= { vRtrLdpPeerParamsEntry 14 }

vRtrLdpPeerExportPolicy3         OBJECT-TYPE
    SYNTAX      TPolicyStatementNameOrEmpty
    MAX-ACCESS  read-create
    STATUS      obsolete
    DESCRIPTION
        "The value of vRtrLdpPeerExportPolicy3 specifies the third export
         policy used to determine which FEC prefixes received from this LDP
         peer should be redistributed to other LDP and TLDP peers.

         This object was obsoleted in release 13.0."
    DEFVAL      { ''H }
    ::= { vRtrLdpPeerParamsEntry 15 }

vRtrLdpPeerExportPolicy4         OBJECT-TYPE
    SYNTAX      TPolicyStatementNameOrEmpty
    MAX-ACCESS  read-create
    STATUS      obsolete
    DESCRIPTION
        "The value of vRtrLdpPeerExportPolicy4 specifies the fourth export
         policy used to determine which FEC prefixes received from this LDP
         peer should be redistributed to other LDP and TLDP peers.

         This object was obsoleted in release 13.0."
    DEFVAL      { ''H }
    ::= { vRtrLdpPeerParamsEntry 16 }

vRtrLdpPeerExportPolicy5         OBJECT-TYPE
    SYNTAX      TPolicyStatementNameOrEmpty
    MAX-ACCESS  read-create
    STATUS      obsolete
    DESCRIPTION
        "The value of vRtrLdpPeerExportPolicy5 specifies the fifth export
         policy used to determine which FEC prefixes received from this LDP
         peer should be redistributed to other LDP and TLDP peers.

         This object was obsoleted in release 13.0."
    DEFVAL      { ''H }
    ::= { vRtrLdpPeerParamsEntry 17 }

vRtrLdpPeerFec129CiscoInterop    OBJECT-TYPE
    SYNTAX      TruthValue
    MAX-ACCESS  read-create
    STATUS      obsolete
    DESCRIPTION
        "The value of vRtrLdpPeerFec129CiscoInterop specifies whether LDP will
         provide translation between non-compliant FEC 129 formats of Cisco.

         Peer LDP sessions must be manually configured towards the
         non-compliant Cisco PEs.

         When the value of vRtrLdpPeerFec129CiscoInterop is 'true', Cisco
         non-compliant format will be used to send and interpret received Label
         Release messages i.e. the FEC129 SAII and TAII fields will be
         reversed.

         When the value of vRtrLdpPeerFec129CiscoInterop is 'false', Cisco
         non-compliant format will not be used or supported.

         This object was obsoleted in release 13.0."
    DEFVAL      { false }
    ::= { vRtrLdpPeerParamsEntry 18 }

vRtrLdpPeerPMTUDiscovery         OBJECT-TYPE
    SYNTAX      TruthValue
    MAX-ACCESS  read-create
    STATUS      obsolete
    DESCRIPTION
        "The value of vRtrLdpPeerPMTUDiscovery specifies whether path MTU
         discovery is enabled for this LDP peer.

         When the value is set to 'true', path MTU discovery is enabled for
         this LDP peer. When the value is set to 'false', path MTU discovery is
         disabled.

         This object was obsoleted in release 13.0."
    DEFVAL      { false }
    ::= { vRtrLdpPeerParamsEntry 19 }

vRtrLdpPeerAdvAdjAddrOnly        OBJECT-TYPE
    SYNTAX      TruthValue
    MAX-ACCESS  read-create
    STATUS      obsolete
    DESCRIPTION
        "The value of vRtrLdpPeerAdvAdjAddrOnly specifies whether to only
         distribute the local addresses used by hello adjacencies with this LDP
         peer.

         When the value is SET to 'true', local addresses that are used by
         hello adjacencies with this LDP peer are only distributed to the peer
         session . When the value is SET to 'false', all known local addresses
         are distributed to the peer session.

         This object was obsoleted in release 13.0."
    DEFVAL      { false }
    ::= { vRtrLdpPeerParamsEntry 20 }

vRtrLdpPeerPeIDMacFlushInterop   OBJECT-TYPE
    SYNTAX      TruthValue
    MAX-ACCESS  read-create
    STATUS      obsolete
    DESCRIPTION
        "The value of vRtrLdpPeerPeIDMacFlushInterop specifies whether LDP will
         react to and send the non-standard  PE-ID TLV (type 0x405) in an
         address withdraw message to effect 'flush-all-from-me' behavior. It is
         used to provide interoperability with other vendors that use this TLV
         for the MAC flush mechanism. Only FEC type 128 is currently supported.

         Peer LDP sessions must be manually configured towards the PEs
         requiring support for this TLV.

         When the value of vRtrLdpPeerPeIDMacFlushInterop is set to 'true', the
         receipt of an address withdraw message with empty MAC list including
         the non-standard TLV will trigger 'flush-all-from-me' behavior instead
         of the normal 'flush-all-but-mine'. The TLV will be included in any
         forwarding towards like-configured peers.

         When the value of vRtrLdpPeerPeIDMacFlushInterop is set to 'false',
         the non-standard TLV will be ignored and will not be included in any
         address withdraw messages sent to the peer.

         This object was obsoleted in release 13.0."
    DEFVAL      { false }
    ::= { vRtrLdpPeerParamsEntry 21 }

vRtrLdpPeerMaxFec                OBJECT-TYPE
    SYNTAX      Unsigned32 (0 | 1..4294967295)
    MAX-ACCESS  read-create
    STATUS      obsolete
    DESCRIPTION
        " The value of vRtrLdpPeerMaxFec specifies the maximum number of FECs
         that will be accepted from this peer LSR.

         A value of zero specifies there is no limit to the number of FECs
         accepted from this peer LSR.

         The vRtrLdpSessMaxFecThresChanged notification is sent when the number
         of FECs receive from this peer LSR exceeds a percentage of this limit
         as specified by vRtrLdpPeerMaxFecThreshold.

         Furthermore, once the limit is exhausted, following actions are taken
         if vRtrLdpPeerMaxFecLogOnly has value of 'false'.

         (1) If LSR Overload capability is supported, this LSR will follow the
             LSR Overload procedure.

         (2) If LSR Overload capability is not supported, any further Label
             Mapping Message is returned with Label Release Message with LDP
             status code 'No_Label_Resources'.

         This object was obsoleted in release 13.0."
    DEFVAL      { 0 }
    ::= { vRtrLdpPeerParamsEntry 22 }

vRtrLdpPeerMaxFecLogOnly         OBJECT-TYPE
    SYNTAX      TruthValue
    MAX-ACCESS  read-create
    STATUS      obsolete
    DESCRIPTION
        " The value of vRtrLdpPeerMaxFecLogOnly specifies whether to only
         generate vRtrLdpSessMaxFecThresChanged notification or take further
         action when FECs received exceeds vRtrLdpPeerMaxFec limit.

         When this value is set to 'false', trap will be generated and one of
         the following action is taken:

         (1) If LSR Overload capability is supported, this LSR will follow the
             LSR Overload procedure.

         (2) If LSR Overload capability is not supported, any further Label
             Mapping Message is returned with Label Release Message with LDP
             status code 'No_Label_Resources'.

         When this value is set to 'true', trap will be generated only.

         This object was obsoleted in release 13.0."
    DEFVAL      { false }
    ::= { vRtrLdpPeerParamsEntry 23 }

vRtrLdpPeerMaxFecThreshold       OBJECT-TYPE
    SYNTAX      Unsigned32 (1..100)
    UNITS       "percent"
    MAX-ACCESS  read-create
    STATUS      obsolete
    DESCRIPTION
        " The value of vRtrLdpPeerMaxFecThreshold specifies a percentage of
         vRtrLdpPeerMaxFec.

         This object was obsoleted in release 13.0."
    DEFVAL      { 90 }
    ::= { vRtrLdpPeerParamsEntry 24 }

tmnxLdpNotificationObjects       OBJECT IDENTIFIER ::= { tmnxLdpObjs 17 }

vRtrLdpInstanceNotifyReasonCode  OBJECT-TYPE
    SYNTAX      INTEGER {
        adminUp   (1),
        adminDown (2),
        operUp    (3),
        operDown  (4)
    }
    MAX-ACCESS  accessible-for-notify
    STATUS      obsolete
    DESCRIPTION
        "Used by vRtrLdpInstanceStateChange, the value indicates the reason for
         the LDP instance state change."
    ::= { tmnxLdpNotificationObjects 1 }

vRtrLdpIfNotifyReasonCode        OBJECT-TYPE
    SYNTAX      INTEGER {
        adminUp   (1),
        adminDown (2),
        operUp    (3),
        operDown  (4),
        sysIpUp   (5),
        sysIpDown (6)
    }
    MAX-ACCESS  accessible-for-notify
    STATUS      obsolete
    DESCRIPTION
        "Used by vRtrLdpIfStateChange, the value indicates the reason for the
         LSP interface state change. This object was obsoleted in 7.0 as it is
         replaced by vRtrLdpIfOperDownReason in vRtrLdpIfStateChange."
    ::= { tmnxLdpNotificationObjects 2 }

vRtrLdpNotifyLocalServiceID      OBJECT-TYPE
    SYNTAX      TmnxServId (1..2147483647)
    MAX-ACCESS  accessible-for-notify
    STATUS      obsolete
    DESCRIPTION
        "Used by vRtrLdpSvcIdMismatch, the value indicates the local Service
         ID."
    ::= { tmnxLdpNotificationObjects 3 }

vRtrLdpNotifyRemoteServiceID     OBJECT-TYPE
    SYNTAX      TmnxServId (1..2147483647)
    MAX-ACCESS  accessible-for-notify
    STATUS      obsolete
    DESCRIPTION
        "Used by vRtrLdpSvcIdMismatch, the value indicates the remote Service
         ID."
    ::= { tmnxLdpNotificationObjects 4 }

vRtrLdpNotifyLocalGroupID        OBJECT-TYPE
    SYNTAX      TmnxVcId
    MAX-ACCESS  accessible-for-notify
    STATUS      current
    DESCRIPTION
        "Used by vRtrLdpGroupIdMismatch, the value indicates the local Group
         ID."
    ::= { tmnxLdpNotificationObjects 5 }

vRtrLdpNotifyRemoteGroupID       OBJECT-TYPE
    SYNTAX      TmnxVcId
    MAX-ACCESS  accessible-for-notify
    STATUS      current
    DESCRIPTION
        "Used by vRtrLdpGroupIdMismatch, the value indicates the remote Group
         ID."
    ::= { tmnxLdpNotificationObjects 6 }

vRtrLdpSessOverloadState         OBJECT-TYPE
    SYNTAX      TruthValue
    MAX-ACCESS  accessible-for-notify
    STATUS      obsolete
    DESCRIPTION
        "The value of vRtrLdpSessOverloadState indicates if session is overload
         or not.

         This object was obsoleted in release 13.0."
    ::= { tmnxLdpNotificationObjects 7 }

vRtrLdpSessOverloadDirection     OBJECT-TYPE
    SYNTAX      INTEGER {
        sent     (1),
        received (2)
    }
    MAX-ACCESS  accessible-for-notify
    STATUS      obsolete
    DESCRIPTION
        "The value of vRtrLdpSessOverloadDirection indicates if Overload
         Notification is sent to peer or received from peer.

         This object was obsoleted in release 13.0."
    ::= { tmnxLdpNotificationObjects 8 }

vRtrLdpSessOverloadFecType       OBJECT-TYPE
    SYNTAX      INTEGER {
        prefixes  (1),
        multicast (2),
        services  (3)
    }
    MAX-ACCESS  accessible-for-notify
    STATUS      obsolete
    DESCRIPTION
        "The value of vRtrLdpSessOverloadFecType indicates the overloaded FEC
         type."
    ::= { tmnxLdpNotificationObjects 9 }

vRtrLdpSessOperThresLevel        OBJECT-TYPE
    SYNTAX      INTEGER {
        up   (0),
        down (1)
    }
    MAX-ACCESS  accessible-for-notify
    STATUS      obsolete
    DESCRIPTION
        "The value of vRtrLdpSessOperThresLevel indicates whether the number of
         fec-bindings has exceeded or is below the configured fec threshold or
         has reached the configured fec limit."
    ::= { tmnxLdpNotificationObjects 10 }

vRtrLdpStaticFecTable            OBJECT-TYPE
    SYNTAX      SEQUENCE OF VRtrLdpStaticFecEntry
    MAX-ACCESS  not-accessible
    STATUS      obsolete
    DESCRIPTION
        "vRtrLdpStaticFecTable has an entry for each static prefix FEC
         configured on the virtual router.

         In 13.0 this table has been replaced by
         TIMETRA-LDP-NG-MIB::vRtrLdpNgStaticFecTable,
         TIMETRA-LDP-NG-MIB::vRtrLdpNgStaticFecInLabelTable."
    ::= { tmnxLdpObjs 18 }

vRtrLdpStaticFecEntry            OBJECT-TYPE
    SYNTAX      VRtrLdpStaticFecEntry
    MAX-ACCESS  not-accessible
    STATUS      obsolete
    DESCRIPTION
        "Each row entry represents a static prefix FEC configured on the
         virtual router.

         Entries can be created and deleted via SNMP SET operations to
         vRtrLdpStaticFecRowStatus.

         An entry is created by setting vRtrLdpStaticFecRowStatus to
         'createAndWait'. The row status can be set to 'active' only after a
         next-hop entry corresponding to this prefix has been created in the
         vRtrLdpStaticFecNHTable.

         An entry is deleted by setting vRtrLdpStaticFecRowStatus to 'destroy'.
         For deletion to succeed, there must be no next-hop entries
         corresponding to this prefix in the vRtrLdpStaticFecNHTable i.e.
         vRtrLdpStaticFecNumNH must have a value of 0."
    INDEX       {
        vRtrID,
        vRtrLdpStaticFecIpPrefix,
        vRtrLdpStaticFecIpMask
    }
    ::= { vRtrLdpStaticFecTable 1 }

VRtrLdpStaticFecEntry            ::= SEQUENCE
{
    vRtrLdpStaticFecIpPrefix         IpAddress,
    vRtrLdpStaticFecIpMask           IpAddress,
    vRtrLdpStaticFecRowStatus        RowStatus,
    vRtrLdpStaticFecNextNHIndex      Unsigned32,
    vRtrLdpStaticFecIngLabel         Unsigned32,
    vRtrLdpStaticFecNumNH            Gauge32,
    vRtrLdpStaticFecOperIngLabel     Unsigned32
}

vRtrLdpStaticFecIpPrefix         OBJECT-TYPE
    SYNTAX      IpAddress
    MAX-ACCESS  not-accessible
    STATUS      obsolete
    DESCRIPTION
        "The value of vRtrLdpStaticFecIpPrefix specifies the IP Address Prefix
         for this static FEC.

         This object was obsoleted in release 13.0."
    ::= { vRtrLdpStaticFecEntry 1 }

vRtrLdpStaticFecIpMask           OBJECT-TYPE
    SYNTAX      IpAddress
    MAX-ACCESS  not-accessible
    STATUS      obsolete
    DESCRIPTION
        "The value of vRtrLdpStaticFecIpMask specifies the IP Address Mask for
         this static FEC.

         This object was obsoleted in release 13.0."
    ::= { vRtrLdpStaticFecEntry 2 }

vRtrLdpStaticFecRowStatus        OBJECT-TYPE
    SYNTAX      RowStatus
    MAX-ACCESS  read-create
    STATUS      obsolete
    DESCRIPTION
        "vRtrLdpStaticFecRowStatus is used to create, delete or control entries
         in the vRtrLdpStaticFecTable.

         To create a row entry, set vRtrLdpStaticFecRowStatus to
         'createAndWait'. Before the row can be placed in the 'active' state, a
         next-hop entry corresponding to this prefix must exist in the
         vRtrLdpStaticFecNHTable.

         To delete a row entry, set vRtrLdpStaticFecRowStatus to 'destroy'. For
         deletion to succeed, no next-hop entry corresponding to this prefix
         must exist in the vRtrLdpStaticFecNHTable i.e. vRtrLdpStaticFecNumNH
         must have a value of 0.

         This object was obsoleted in release 13.0."
    ::= { vRtrLdpStaticFecEntry 3 }

vRtrLdpStaticFecNextNHIndex      OBJECT-TYPE
    SYNTAX      Unsigned32
    MAX-ACCESS  read-only
    STATUS      obsolete
    DESCRIPTION
        "The value of vRtrLdpStaticFecNextNHIndex is used to assign values to
         vRtrLdpStaticFecNHIndex when creating rows in the
         vRtrLdpStaticFecNHTable. The network manager reads this object and
         uses it in the SET request that creates a new row entry in the
         vRtrLdpStaticFecNHTable. If the SET fails with the code
         'inconsistentValue', the process must be repeated. If the SET
         succeeds, then this object will be incremented and the new instance is
         created according to the manager's directions.

         This object was obsoleted in release 13.0."
    ::= { vRtrLdpStaticFecEntry 4 }

vRtrLdpStaticFecIngLabel         OBJECT-TYPE
    SYNTAX      Unsigned32 (32..262112 | 4294967295)
    MAX-ACCESS  read-create
    STATUS      obsolete
    DESCRIPTION
        "The value of vRtrLdpStaticFecIngLabel specifies the label that is
         advertised to the upstream peer.

         The range of vRtrLdpStaticFecIngLabel is dynamic and depends on the
         value of vRtrMplsLabelStaticLabelRange.

         The normal range of vRtrLdpStaticFecIngLabel starts at 32 and ends at
         the value of vRtrMplsLabelStaticLabelRange + 32.

         If this variable is set to the default value of 4294967295, the
         ingress label will be dynamically assigned by the label manager.

         This object was obsoleted in release 13.0."
    DEFVAL      { 4294967295 }
    ::= { vRtrLdpStaticFecEntry 5 }

vRtrLdpStaticFecNumNH            OBJECT-TYPE
    SYNTAX      Gauge32
    MAX-ACCESS  read-only
    STATUS      obsolete
    DESCRIPTION
        "The value of vRtrLdpStaticFecNumNH specifies the number of next-hops
         that are associated with the static prefix FEC represented by this row
         entry. This is also the number of row entries configured in the
         vRtrLdpStaticFecNHTable for this static prefix FEC.

         If the static FEC has no next-hops associated with it, this value will
         be 0 and the row entry will be placed in the 'notReady' state.
         Deletion of the row entry will be allowed only if
         vRtrLdpStaticFecNumNH is 0.

         This object was obsoleted in release 13.0."
    ::= { vRtrLdpStaticFecEntry 6 }

vRtrLdpStaticFecOperIngLabel     OBJECT-TYPE
    SYNTAX      Unsigned32
    MAX-ACCESS  read-only
    STATUS      obsolete
    DESCRIPTION
        "The value of vRtrLdpStaticFecOperIngLabel specifies the actual or
         operational value of the label that was advertised to the upstream
         peer.

         This object was obsoleted in release 13.0."
    ::= { vRtrLdpStaticFecEntry 7 }

vRtrLdpStaticFecNHTable          OBJECT-TYPE
    SYNTAX      SEQUENCE OF VRtrLdpStaticFecNHEntry
    MAX-ACCESS  not-accessible
    STATUS      obsolete
    DESCRIPTION
        "vRtrLdpStaticFecNHTable has an entry for each next-hop configured for
         a static prefix FEC on the virtual router.

         In 13.0 this table has been replaced by
         TIMETRA-LDP-NG-MIB::vRtrLdpNgStaticFecOutLabelTable."
    ::= { tmnxLdpObjs 19 }

vRtrLdpStaticFecNHEntry          OBJECT-TYPE
    SYNTAX      VRtrLdpStaticFecNHEntry
    MAX-ACCESS  not-accessible
    STATUS      obsolete
    DESCRIPTION
        "Each row entry represents a next-hop configured for a static prefix
         FEC on the virtual router. The static prefix FEC corresponding to a
         next-hop entry must exist as a row entry in the vRtrLdpStaticFecTable.

         Entries can be created and deleted via SNMP SET operations to
         vRtrLdpStaticFecNHRowStatus.

         An entry is created by setting vRtrLdpStaticFecNHRowStatus to
         'createAndWait' or 'createAndGo'. Before the row can be placed in the
         'active' state, vRtrLdpStaticFecNHType must be set to a valid value.

         An entry is deleted by setting vRtrLdpStaticFecNHRowStatus to
         'destroy'."
    INDEX       {
        vRtrID,
        vRtrLdpStaticFecIpPrefix,
        vRtrLdpStaticFecIpMask,
        vRtrLdpStaticFecNHIndex
    }
    ::= { vRtrLdpStaticFecNHTable 1 }

VRtrLdpStaticFecNHEntry          ::= SEQUENCE
{
    vRtrLdpStaticFecNHIndex          Unsigned32,
    vRtrLdpStaticFecNHRowStatus      RowStatus,
    vRtrLdpStaticFecNHType           INTEGER,
    vRtrLdpStaticFecNHIpAddr         IpAddress,
    vRtrLdpStaticFecNHEgrLabel       Unsigned32,
    vRtrLdpStaticFecNHIfName         DisplayString
}

vRtrLdpStaticFecNHIndex          OBJECT-TYPE
    SYNTAX      Unsigned32
    MAX-ACCESS  not-accessible
    STATUS      obsolete
    DESCRIPTION
        "The value of vRtrLdpStaticFecNHIndex is used to identify the next-hop
         associated with a static prefix FEC. This value is unique amongst
         next-hop entries for the same static prefix FEC.

         This object was obsoleted in release 13.0."
    ::= { vRtrLdpStaticFecNHEntry 1 }

vRtrLdpStaticFecNHRowStatus      OBJECT-TYPE
    SYNTAX      RowStatus
    MAX-ACCESS  read-create
    STATUS      obsolete
    DESCRIPTION
        "vRtrLdpStaticFecNHRowStatus is used to create, delete or control
         entries in the vRtrLdpStaticFecNHTable.

         An entry is created by setting vRtrLdpStaticFecNHRowStatus to
         'createAndWait' or 'createAndGo'. Before the row can be placed in the
         'active' state, vRtrLdpStaticFecNHType must be set to a valid value.

         An entry is deleted by setting vRtrLdpStaticFecNHRowStatus to
         'destroy'.

         This object was obsoleted in release 13.0."
    ::= { vRtrLdpStaticFecNHEntry 2 }

vRtrLdpStaticFecNHType           OBJECT-TYPE
    SYNTAX      INTEGER {
        unknown            (0),
        ipAddress          (1),
        pop                (2),
        ifName             (3),
        ifNameAndIpAddress (4)
    }
    MAX-ACCESS  read-create
    STATUS      obsolete
    DESCRIPTION
        "The value of vRtrLdpStaticFecNHType specifies the type of next-hop
         represented by this row entry.

         unknown (0)    - the next-hop type has not been set.
         ipAddress (1)  - the next-hop is an IP address.
         pop (2)        - there is no next-hop i.e. pop the label and route
         ifName (3)     - the next-hop is of this ifName
         ifNameAndIpAddress (4) - the next-hop is an IP address of this
                                  ifName

         This object was obsoleted in release 13.0."
    DEFVAL      { unknown }
    ::= { vRtrLdpStaticFecNHEntry 3 }

vRtrLdpStaticFecNHIpAddr         OBJECT-TYPE
    SYNTAX      IpAddress
    MAX-ACCESS  read-create
    STATUS      obsolete
    DESCRIPTION
        "If vRtrLdpStaticFecNHType is set to 'ipAddress' or
         'ifNameAndIpAddress', the value of vRtrLdpStaticFecNHIpAddr specifies
         the IP address of the next-hop. In this case, this variable must be
         set to a valid value before the row be placed in an active state.

         If vRtrLdpStaticFecNHType is set to 'pop', this value of
         vRtrLdpStaticFecNHIpAddr will be 0.0.0.0

         This object was obsoleted in release 13.0."
    DEFVAL      { '00000000'H }
    ::= { vRtrLdpStaticFecNHEntry 4 }

vRtrLdpStaticFecNHEgrLabel       OBJECT-TYPE
    SYNTAX      Unsigned32 (16..1048575 | 4294967295)
    MAX-ACCESS  read-create
    STATUS      obsolete
    DESCRIPTION
        "The value of vRtrLdpStaticFecNHEgrLabel specifies the egress label
         associated with this next-hop entry. The LSR will swap the incoming
         label with the configured egress label. If this egress label has a
         value of 4294967295, the LSR will pop the incoming label.

         This object was obsoleted in release 13.0."
    DEFVAL      { 4294967295 }
    ::= { vRtrLdpStaticFecNHEntry 5 }

vRtrLdpStaticFecNHIfName         OBJECT-TYPE
    SYNTAX      DisplayString (SIZE (0..32))
    MAX-ACCESS  read-create
    STATUS      obsolete
    DESCRIPTION
        "If vRtrLdpStaticFecNHType is set to 'ifName' or 'ifNameAndIpAddress',
         the value of vRtrLdpStaticFecNHIfName specifies the interface name to
         use for this static fec prefix.

         If vRtrLdpStaticFecNHType is set to 'pop', this value of
         vRtrLdpStaticFecNHIfName will be a null string.

         This object was obsoleted in release 13.0."
    ::= { vRtrLdpStaticFecNHEntry 6 }

vRtrLdpTargTable                 OBJECT-TYPE
    SYNTAX      SEQUENCE OF VRtrLdpTargEntry
    MAX-ACCESS  not-accessible
    STATUS      obsolete
    DESCRIPTION
        "vRtrLdpTargTable keeps information about the export and import
         prefixes for a targeted LDP session.

         Use of AUGMENTS clause implies a one-to-one dependent
         relationship between the base table, vRtrLdpGeneralTable,
         and the augmenting table, vRtrLdpTargTable. This in
         effect extends the vRtrLdpGeneralTable with additional
         columns.  Creation or deletion of a row in the
         vRtrLdpGeneralTable results in the same fate for the row
         in the vRtrLdpTargTable.

         In 13.0 this table has been replaced by
         TIMETRA-LDP-NG-MIB::vRtrLdpNgTargTable."
    ::= { tmnxLdpObjs 20 }

vRtrLdpTargEntry                 OBJECT-TYPE
    SYNTAX      VRtrLdpTargEntry
    MAX-ACCESS  not-accessible
    STATUS      obsolete
    DESCRIPTION
        "A row in this table represents information about the targeted LDP
         session."
    AUGMENTS    { vRtrLdpGeneralEntry }
    ::= { vRtrLdpTargTable 1 }

VRtrLdpTargEntry                 ::= SEQUENCE
{
    vRtrLdpTargImportPolicy1         TPolicyStatementNameOrEmpty,
    vRtrLdpTargImportPolicy2         TPolicyStatementNameOrEmpty,
    vRtrLdpTargImportPolicy3         TPolicyStatementNameOrEmpty,
    vRtrLdpTargImportPolicy4         TPolicyStatementNameOrEmpty,
    vRtrLdpTargImportPolicy5         TPolicyStatementNameOrEmpty,
    vRtrLdpTargExportPolicy1         TPolicyStatementNameOrEmpty,
    vRtrLdpTargExportPolicy2         TPolicyStatementNameOrEmpty,
    vRtrLdpTargExportPolicy3         TPolicyStatementNameOrEmpty,
    vRtrLdpTargExportPolicy4         TPolicyStatementNameOrEmpty,
    vRtrLdpTargExportPolicy5         TPolicyStatementNameOrEmpty,
    vRtrLdpTargTunnelPreference      TruthValue
}

vRtrLdpTargImportPolicy1         OBJECT-TYPE
    SYNTAX      TPolicyStatementNameOrEmpty
    MAX-ACCESS  read-create
    STATUS      obsolete
    DESCRIPTION
        "The value of vRtrLdpTargImportPolicy1 specifies the import
         route policy to determine which routes are accepted from targeted
         LDP neighbors.  A maximum of 5 policies can be specified.
         vRtrLdpTargImportPolicy1 specifies the first policy.

         This object was obsoleted in release 13.0."
    DEFVAL      { ''H }
    ::= { vRtrLdpTargEntry 3 }

vRtrLdpTargImportPolicy2         OBJECT-TYPE
    SYNTAX      TPolicyStatementNameOrEmpty
    MAX-ACCESS  read-create
    STATUS      obsolete
    DESCRIPTION
        "The value of vRtrLdpTargImportPolicy2 specifies the second import
         policy used to determine which routes are accepted from targeted LDP
         neighbors.

         This object was obsoleted in release 13.0."
    DEFVAL      { ''H }
    ::= { vRtrLdpTargEntry 4 }

vRtrLdpTargImportPolicy3         OBJECT-TYPE
    SYNTAX      TPolicyStatementNameOrEmpty
    MAX-ACCESS  read-create
    STATUS      obsolete
    DESCRIPTION
        "The value of vRtrLdpTargImportPolicy3 specifies the third import
         policy used to determine which routes are accepted from targeted LDP
         neighbors.

         This object was obsoleted in release 13.0."
    DEFVAL      { ''H }
    ::= { vRtrLdpTargEntry 5 }

vRtrLdpTargImportPolicy4         OBJECT-TYPE
    SYNTAX      TPolicyStatementNameOrEmpty
    MAX-ACCESS  read-create
    STATUS      obsolete
    DESCRIPTION
        "The value of vRtrLdpTargImportPolicy4 specifies the fourth import
         policy to determine which routes are accepted from targeted LDP
         neighbors.

         This object was obsoleted in release 13.0."
    DEFVAL      { ''H }
    ::= { vRtrLdpTargEntry 6 }

vRtrLdpTargImportPolicy5         OBJECT-TYPE
    SYNTAX      TPolicyStatementNameOrEmpty
    MAX-ACCESS  read-create
    STATUS      obsolete
    DESCRIPTION
        "The value of vRtrLdpTargImportPolicy5 specifies the fifth import
         policy used to determine which routes are accepted from targeted LDP
         neighbors.

         This object was obsoleted in release 13.0."
    DEFVAL      { ''H }
    ::= { vRtrLdpTargEntry 7 }

vRtrLdpTargExportPolicy1         OBJECT-TYPE
    SYNTAX      TPolicyStatementNameOrEmpty
    MAX-ACCESS  read-create
    STATUS      obsolete
    DESCRIPTION
        "The value of vRtrLdpTargExportPolicy1 specifies the export
         route policy used to determine which routes are exported to this
         targeted LDP session.  A maximum of 5 policies can be specified.
         vRtrLdpTargExportPolicy1 specifies the first policy.

         This object was obsoleted in release 13.0."
    DEFVAL      { ''H }
    ::= { vRtrLdpTargEntry 8 }

vRtrLdpTargExportPolicy2         OBJECT-TYPE
    SYNTAX      TPolicyStatementNameOrEmpty
    MAX-ACCESS  read-create
    STATUS      obsolete
    DESCRIPTION
        "The value of vRtrLdpTargExportPolicy2 specifies the second export
         policy used to determine which routes are exported to this targeted
         LDP session.

         This object was obsoleted in release 13.0."
    DEFVAL      { ''H }
    ::= { vRtrLdpTargEntry 9 }

vRtrLdpTargExportPolicy3         OBJECT-TYPE
    SYNTAX      TPolicyStatementNameOrEmpty
    MAX-ACCESS  read-create
    STATUS      obsolete
    DESCRIPTION
        "The value of vRtrLdpTargExportPolicy3 specifies the third export
         policy used to determine which routes are exported to this targeted
         LDP session.

         This object was obsoleted in release 13.0."
    DEFVAL      { ''H }
    ::= { vRtrLdpTargEntry 10 }

vRtrLdpTargExportPolicy4         OBJECT-TYPE
    SYNTAX      TPolicyStatementNameOrEmpty
    MAX-ACCESS  read-create
    STATUS      obsolete
    DESCRIPTION
        "The value of vRtrLdpTargExportPolicy4 specifies the fourth export
         policy used to determine which routes are exported to this targeted
         LDP session.

         This object was obsoleted in release 13.0."
    DEFVAL      { ''H }
    ::= { vRtrLdpTargEntry 11 }

vRtrLdpTargExportPolicy5         OBJECT-TYPE
    SYNTAX      TPolicyStatementNameOrEmpty
    MAX-ACCESS  read-create
    STATUS      obsolete
    DESCRIPTION
        "The value of vRtrLdpTargExportPolicy5 specifies the fifth export
         policy used to determine which routes are exported to this targeted
         LDP session.

         This object was obsoleted in release 13.0."
    DEFVAL      { ''H }
    ::= { vRtrLdpTargEntry 12 }

vRtrLdpTargTunnelPreference      OBJECT-TYPE
    SYNTAX      TruthValue
    MAX-ACCESS  read-create
    STATUS      obsolete
    DESCRIPTION
        "The value of vRtrLdpTargTunnelPreference indicates whether LDP over
         tunnel is preferred when link-level LDP bindings are also available.
         If this value is 'true', then LDP tunnels are preferred and if the
         value is 'false' then LDP over tunnel is preferred.

         By default LDP tunnels are preferred.

         This object was obsoleted in release 13.0."
    DEFVAL      { true }
    ::= { vRtrLdpTargEntry 13 }

vRtrLdpIfTunnelingLspTable       OBJECT-TYPE
    SYNTAX      SEQUENCE OF VRtrLdpIfTunnelingLspEntry
    MAX-ACCESS  not-accessible
    STATUS      obsolete
    DESCRIPTION
        "vRtrLdpIfTunnelingLspTable keeps the list of LDP-over-RSVP LSP ids
         which are currently supported by the application.

         Each LSP ID in the list corresponds to the vRtrMplsLspIndex of the
         given MPLS LSP.

         In 13.0 this table has been replaced by
         TIMETRA-LDP-NG-MIB::vRtrLdpNgTargPeerTunnelLspTable."
    ::= { tmnxLdpObjs 21 }

vRtrLdpIfTunnelingLspEntry       OBJECT-TYPE
    SYNTAX      VRtrLdpIfTunnelingLspEntry
    MAX-ACCESS  not-accessible
    STATUS      obsolete
    DESCRIPTION
        "A row in this table contains the LSP id information about an LDP
         interface or targeted peer.

         Row entries can be created or deleted via SNMP SET requests. A row is
         created by setting vRtrLdpIfLspRowStatus to 'createAndGo' provided the
         corresponding LSP id exists as an MPLS lsp. A row entry can be
         destroyed by setting vRtrLdpIfLspRowStatus to 'destroy'."
    INDEX       {
        vRtrID,
        vRtrLdpIfIndex,
        vRtrLdpPeerAddress,
        vRtrLdpIfLspId
    }
    ::= { vRtrLdpIfTunnelingLspTable 1 }

VRtrLdpIfTunnelingLspEntry       ::= SEQUENCE
{
    vRtrLdpIfLspId                   TmnxVRtrMplsLspID,
    vRtrLdpIfLspRowStatus            RowStatus
}

vRtrLdpIfLspId                   OBJECT-TYPE
    SYNTAX      TmnxVRtrMplsLspID
    MAX-ACCESS  not-accessible
    STATUS      obsolete
    DESCRIPTION
        "The value of vRtrLdpIfLspId specifies the LSP id of the LSP associated
         with the specified interface or targeted peer.

         This object was obsoleted in release 13.0."
    ::= { vRtrLdpIfTunnelingLspEntry 1 }

vRtrLdpIfLspRowStatus            OBJECT-TYPE
    SYNTAX      RowStatus
    MAX-ACCESS  read-create
    STATUS      obsolete
    DESCRIPTION
        "vRtrLdpIfLspRowStatus is used to create, delete or control entries in
         the vRtrLdpIfTunnelingLspTable.

         An entry is created by setting vRtrLdpIfLspRowStatus to 'createAndGo'.

         An entry is deleted by setting vRtrLdpIfLspRowStatus to 'destroy'.

         This object was obsoleted in release 13.0."
    ::= { vRtrLdpIfTunnelingLspEntry 2 }

vRtrLdpCepTdmFecTable            OBJECT-TYPE
    SYNTAX      SEQUENCE OF VRtrLdpCepTdmFecEntry
    MAX-ACCESS  not-accessible
    STATUS      obsolete
    DESCRIPTION
        "vRtrLdpCepTdmFecTable is a read-only table that represents all CEP/TDM
         FECs either sent to or received from an LDP peer known to the Virtual
         Router. The CEP/TDM Sub-TLVs are defined in RFC 4446:

         Parameter Id    Description
         0x04            CEP/TDM Payload Bytes
         0x07            CEP/TDM bit-rate
         0x0B            TDM Options

         In 13.0 this table has been replaced by
         TIMETRA-LDP-NG-MIB::vLdpNgCepTdmFec128InLblTable,
         TIMETRA-LDP-NG-MIB::vLdpNgCepTdmFec129InLblTable."
    ::= { tmnxLdpObjs 22 }

vRtrLdpCepTdmFecEntry            OBJECT-TYPE
    SYNTAX      VRtrLdpCepTdmFecEntry
    MAX-ACCESS  not-accessible
    STATUS      obsolete
    DESCRIPTION
        "Each row entry represents an instance of a service FEC sent to or
         received from an LDP peer.

         Use of AUGMENTS clause implies a one-to-one dependent relationship
         between the base table, vRtrLdpServFecTable, and the augmenting
         table, vRtrLdpCepTdmFecTable.  This in effect extends the
         vRtrLdpServFecTable with additional columns.

          Creation or deletion of a row in the vRtrLdpServFecTable results
          in the same fate for the row in the VRtrLdpCepTdmFecEntry."
    AUGMENTS    { vRtrLdpServFecEntry }
    ::= { vRtrLdpCepTdmFecTable 1 }

VRtrLdpCepTdmFecEntry            ::= SEQUENCE
{
    vRtrLdpCepTdmLocalPayloadSize    Unsigned32,
    vRtrLdpCepTdmRemotePayloadSize   Unsigned32,
    vRtrLdpCepTdmLocalBitrate        Unsigned32,
    vRtrLdpCepTdmRemoteBitrate       Unsigned32,
    vRtrLdpCepTdmLocalRtpHeader      TruthValue,
    vRtrLdpCepTdmRemoteRtpHeader     TruthValue,
    vRtrLdpCepTdmLocalDiffTimestamp  TruthValue,
    vRtrLdpCepTdmRemoteDiffTimestamp TruthValue,
    vRtrLdpCepTdmLocalSigPkts        TdmOptionsSigPkts,
    vRtrLdpCepTdmRemoteSigPkts       TdmOptionsSigPkts,
    vRtrLdpCepTdmLocalCasTrunk       TdmOptionsCasTrunkFraming,
    vRtrLdpCepTdmRemoteCasTrunk      TdmOptionsCasTrunkFraming,
    vRtrLdpCepTdmLocalTimestampFreq  Unsigned32,
    vRtrLdpCepTdmRemoteTimestampFreq Unsigned32,
    vRtrLdpCepTdmLocalPayloadType    Unsigned32,
    vRtrLdpCepTdmRemotePayloadType   Unsigned32,
    vRtrLdpCepTdmLocalSsrcId         Unsigned32,
    vRtrLdpCepTdmRemoteSsrcId        Unsigned32
}

vRtrLdpCepTdmLocalPayloadSize    OBJECT-TYPE
    SYNTAX      Unsigned32
    UNITS       "bytes"
    MAX-ACCESS  read-only
    STATUS      obsolete
    DESCRIPTION
        "The value of vRtrLdpCepTdmLocalPayloadSize indicates the local payload
         size.

         This object was obsoleted in release 13.0."
    ::= { vRtrLdpCepTdmFecEntry 4 }

vRtrLdpCepTdmRemotePayloadSize   OBJECT-TYPE
    SYNTAX      Unsigned32
    UNITS       "bytes"
    MAX-ACCESS  read-only
    STATUS      obsolete
    DESCRIPTION
        "The value of vRtrLdpCepTdmRemotePayloadSize indicates the remote
         payload size.

         This object was obsoleted in release 13.0."
    ::= { vRtrLdpCepTdmFecEntry 5 }

vRtrLdpCepTdmLocalBitrate        OBJECT-TYPE
    SYNTAX      Unsigned32
    UNITS       "sixty-four kilobps"
    MAX-ACCESS  read-only
    STATUS      obsolete
    DESCRIPTION
        "The value of vRtrLdpCepTdmLocalBitrate indicates the local bitrate.

         This object was obsoleted in release 13.0."
    ::= { vRtrLdpCepTdmFecEntry 6 }

vRtrLdpCepTdmRemoteBitrate       OBJECT-TYPE
    SYNTAX      Unsigned32
    UNITS       "sixty-four kilobps"
    MAX-ACCESS  read-only
    STATUS      obsolete
    DESCRIPTION
        "The value of vRtrLdpCepTdmRemoteBitrate indicates the remote bitrate.

         This object was obsoleted in release 13.0."
    ::= { vRtrLdpCepTdmFecEntry 7 }

vRtrLdpCepTdmLocalRtpHeader      OBJECT-TYPE
    SYNTAX      TruthValue
    MAX-ACCESS  read-only
    STATUS      obsolete
    DESCRIPTION
        "The value of vRtrLdpCepTdmLocalRtpHeader indicates the local RTP
         header usage bit.

         This object was obsoleted in release 13.0."
    ::= { vRtrLdpCepTdmFecEntry 8 }

vRtrLdpCepTdmRemoteRtpHeader     OBJECT-TYPE
    SYNTAX      TruthValue
    MAX-ACCESS  read-only
    STATUS      obsolete
    DESCRIPTION
        "The value of vRtrLdpCepTdmRemoteRtpHeader indicates the remote RTP
         header usage bit.

         This object was obsoleted in release 13.0."
    ::= { vRtrLdpCepTdmFecEntry 9 }

vRtrLdpCepTdmLocalDiffTimestamp  OBJECT-TYPE
    SYNTAX      TruthValue
    MAX-ACCESS  read-only
    STATUS      obsolete
    DESCRIPTION
        "The value of vRtrLdpCepTdmLocalDiffTimestamp indicates the local
         differential (or dynamic) timestamping mode bit.

         This object was obsoleted in release 13.0."
    ::= { vRtrLdpCepTdmFecEntry 10 }

vRtrLdpCepTdmRemoteDiffTimestamp OBJECT-TYPE
    SYNTAX      TruthValue
    MAX-ACCESS  read-only
    STATUS      obsolete
    DESCRIPTION
        "The value of vRtrLdpCepTdmRemoteDiffTimestamp indicates the remote
         differential (or dynamic) timestamping mode bit.

         This object was obsoleted in release 13.0."
    ::= { vRtrLdpCepTdmFecEntry 11 }

vRtrLdpCepTdmLocalSigPkts        OBJECT-TYPE
    SYNTAX      TdmOptionsSigPkts
    MAX-ACCESS  read-only
    STATUS      obsolete
    DESCRIPTION
        "The value of vRtrLdpCepTdmLocalSigPkts indicates the local CE
         application signalling packets mode.

         This object was obsoleted in release 13.0."
    ::= { vRtrLdpCepTdmFecEntry 12 }

vRtrLdpCepTdmRemoteSigPkts       OBJECT-TYPE
    SYNTAX      TdmOptionsSigPkts
    MAX-ACCESS  read-only
    STATUS      obsolete
    DESCRIPTION
        "The value of vRtrLdpCepTdmRemoteSigPkts indicates the remote CE
         application signalling packets mode.

         This object was obsoleted in release 13.0."
    ::= { vRtrLdpCepTdmFecEntry 13 }

vRtrLdpCepTdmLocalCasTrunk       OBJECT-TYPE
    SYNTAX      TdmOptionsCasTrunkFraming
    MAX-ACCESS  read-only
    STATUS      obsolete
    DESCRIPTION
        "The value of vRtrLdpCepTdmLocalCasTrunk indicates the local CE
         application signalling packets mode.

         This object was obsoleted in release 13.0."
    ::= { vRtrLdpCepTdmFecEntry 14 }

vRtrLdpCepTdmRemoteCasTrunk      OBJECT-TYPE
    SYNTAX      TdmOptionsCasTrunkFraming
    MAX-ACCESS  read-only
    STATUS      obsolete
    DESCRIPTION
        "The value of vRtrLdpCepTdmRemoteCasTrunk indicates the remote CE
         application signalling packets mode.

         This object was obsoleted in release 13.0."
    ::= { vRtrLdpCepTdmFecEntry 15 }

vRtrLdpCepTdmLocalTimestampFreq  OBJECT-TYPE
    SYNTAX      Unsigned32
    UNITS       "8 KHz"
    MAX-ACCESS  read-only
    STATUS      obsolete
    DESCRIPTION
        "The value of vRtrLdpCepTdmLocalTimestampFreq indicates the local CE
         application signalling packets mode.

         This object was obsoleted in release 13.0."
    ::= { vRtrLdpCepTdmFecEntry 16 }

vRtrLdpCepTdmRemoteTimestampFreq OBJECT-TYPE
    SYNTAX      Unsigned32
    UNITS       "8 KHz"
    MAX-ACCESS  read-only
    STATUS      obsolete
    DESCRIPTION
        "The value of vRtrLdpCepTdmRemoteTimestampFreq indicates the remote CE
         application signalling packets mode.

         This object was obsoleted in release 13.0."
    ::= { vRtrLdpCepTdmFecEntry 17 }

vRtrLdpCepTdmLocalPayloadType    OBJECT-TYPE
    SYNTAX      Unsigned32
    MAX-ACCESS  read-only
    STATUS      obsolete
    DESCRIPTION
        "The value of vRtrLdpCepTdmLocalPayloadType indicates the local payload
         type.

         This object was obsoleted in release 13.0."
    ::= { vRtrLdpCepTdmFecEntry 18 }

vRtrLdpCepTdmRemotePayloadType   OBJECT-TYPE
    SYNTAX      Unsigned32
    MAX-ACCESS  read-only
    STATUS      obsolete
    DESCRIPTION
        "The value of vRtrLdpCepTdmRemotePayloadType indicates the remote
         payload type.

         This object was obsoleted in release 13.0."
    ::= { vRtrLdpCepTdmFecEntry 19 }

vRtrLdpCepTdmLocalSsrcId         OBJECT-TYPE
    SYNTAX      Unsigned32
    MAX-ACCESS  read-only
    STATUS      obsolete
    DESCRIPTION
        "The value of vRtrLdpCepTdmLocalSsrcId indicates the local value of
         SSRC ID.

         This object was obsoleted in release 13.0."
    ::= { vRtrLdpCepTdmFecEntry 20 }

vRtrLdpCepTdmRemoteSsrcId        OBJECT-TYPE
    SYNTAX      Unsigned32
    MAX-ACCESS  read-only
    STATUS      obsolete
    DESCRIPTION
        "The value of vRtrLdpCepTdmRemoteSsrcId indicates the remote value of
         SSRC ID.

         This object was obsoleted in release 13.0."
    ::= { vRtrLdpCepTdmFecEntry 21 }

vLdpServFec129Table              OBJECT-TYPE
    SYNTAX      SEQUENCE OF VLdpServFec129Entry
    MAX-ACCESS  not-accessible
    STATUS      obsolete
    DESCRIPTION
        "vLdpServFec129Table is a read-only table that represents all service
         FEC-129s either sent to or received from an LDP peer known to the
         Virtual Router.

         In 13.0 this table has been replaced by
         TIMETRA-LDP-NG-MIB::vLdpNgSvcFec129Table,
         TIMETRA-LDP-NG-MIB::vLdpNgSvcFec129InLblTable,
         TIMETRA-LDP-NG-MIB::vLdpNgSvcFec129OutLblTable."
    ::= { tmnxLdpObjs 23 }

vLdpServFec129Entry              OBJECT-TYPE
    SYNTAX      VLdpServFec129Entry
    MAX-ACCESS  not-accessible
    STATUS      obsolete
    DESCRIPTION
        "Each row entry represents an instance of a service FEC-129 sent to or
         received from an LDP peer."
    INDEX       {
        vRtrID,
        vRtrLdpServFecVcType,
        vLdpServFec129AgiTlv,
        vLdpServFec129SrcAiiTlv,
        vLdpServFec129TgtAiiTlv,
        vRtrLdpPeerLdpId
    }
    ::= { vLdpServFec129Table 1 }

VLdpServFec129Entry              ::= SEQUENCE
{
    vLdpServFec129AgiTlv             TmnxLdpFec129Tlv,
    vLdpServFec129SrcAiiTlv          TmnxLdpFec129Tlv,
    vLdpServFec129TgtAiiTlv          TmnxLdpFec129Tlv,
    vLdpServFec129ServType           ServType,
    vLdpServFec129ServId             TmnxServId,
    vLdpServFec129VpnId              TmnxVpnId,
    vLdpServFec129Flags              TmnxLdpFECFlags,
    vLdpServFec129NumInLabels        Unsigned32,
    vLdpServFec129NumOutLabels       Unsigned32,
    vLdpServFec129InLabel1           Unsigned32,
    vLdpServFec129InLabelStatus1     TmnxLabelStatus,
    vLdpServFec129OutLabel1          Unsigned32,
    vLdpServFec129OutLabelStatus1    TmnxLabelStatus,
    vLdpServFec129SdpId              SdpId,
    vLdpServFec129LocalMTU           Unsigned32,
    vLdpServFec129RemoteMTU          Unsigned32,
    vLdpServFec129LocalVlanTag       Unsigned32,
    vLdpServFec129RemoteVlanTag      Unsigned32,
    vLdpServFec129LocalMaxCellConcat Unsigned32,
    vLdpServFec129RemoteMaxCellConcat Unsigned32,
    vLdpServFec129InLabelSigStatus1  TmnxLabelSigStatus,
    vLdpServFec129OutLabelSigStatus1 TmnxLabelSigStatus,
    vLdpServFec129LocalIpv4Capblty   TruthValue,
    vLdpServFec129RemoteIpv4Capblty  TruthValue,
    vLdpServFec129LocalIpv6Capblty   TruthValue,
    vLdpServFec129RemoteIpv6Capblty  TruthValue,
    vLdpServFec129LocalIpv4CeIpAddr  IpAddress,
    vLdpServFec129RemoteIpv4CeIpAddr IpAddress,
    vLdpServFec129InLbl1WdwReason    TmnxLdpInLblWdrawalReasonCode,
    vLdpServFec129LocalFLTxCapblty   TruthValue,
    vLdpServFec129LocalFLRxCapblty   TruthValue,
    vLdpServFec129RemoteFLTxCapblty  TruthValue,
    vLdpServFec129RemoteFLRxCapblty  TruthValue,
    vLdpServFec129MateAgiTlv         TmnxLdpFec129Tlv,
    vLdpServFec129MateSrcAiiTlv      TmnxLdpFec129Tlv,
    vLdpServFec129MateTgtAiiTlv      TmnxLdpFec129Tlv,
    vLdpServFec129MateSdpId          SdpId
}

vLdpServFec129AgiTlv             OBJECT-TYPE
    SYNTAX      TmnxLdpFec129Tlv
    MAX-ACCESS  not-accessible
    STATUS      obsolete
    DESCRIPTION
        "The value of vLdpServFec129AgiTlv specifies the Attachment Group
         Identifier TLV associated with this service FEC.

         This object was obsoleted in release 13.0."
    ::= { vLdpServFec129Entry 1 }

vLdpServFec129SrcAiiTlv          OBJECT-TYPE
    SYNTAX      TmnxLdpFec129Tlv
    MAX-ACCESS  not-accessible
    STATUS      obsolete
    DESCRIPTION
        "The value of vLdpServFec129SrcAiiTlv specifies the Source Attachment
         Individual Identifier TLV associated with this service FEC.

         This object was obsoleted in release 13.0."
    ::= { vLdpServFec129Entry 2 }

vLdpServFec129TgtAiiTlv          OBJECT-TYPE
    SYNTAX      TmnxLdpFec129Tlv
    MAX-ACCESS  not-accessible
    STATUS      obsolete
    DESCRIPTION
        "The value of vLdpServFec129TgtAiiTlv specifies the Target Attachment
         Individual Identifier TLV associated with this service FEC.

         This object was obsoleted in release 13.0."
    ::= { vLdpServFec129Entry 3 }

vLdpServFec129ServType           OBJECT-TYPE
    SYNTAX      ServType
    MAX-ACCESS  read-only
    STATUS      obsolete
    DESCRIPTION
        "The value of vLdpServFec129ServType specifies the Service type
         associated with this service FEC.

         This object was obsoleted in release 13.0."
    ::= { vLdpServFec129Entry 4 }

vLdpServFec129ServId             OBJECT-TYPE
    SYNTAX      TmnxServId (1..2147483647)
    MAX-ACCESS  read-only
    STATUS      obsolete
    DESCRIPTION
        "The value of vLdpServFec129ServId specifies the Service identifier
         associated with this service FEC.

         This object was obsoleted in release 13.0."
    ::= { vLdpServFec129Entry 5 }

vLdpServFec129VpnId              OBJECT-TYPE
    SYNTAX      TmnxVpnId
    MAX-ACCESS  read-only
    STATUS      obsolete
    DESCRIPTION
        "The value of vLdpServFec129VpnId identifies the VPN associated with
         the FEC.

         This object was obsoleted in release 13.0."
    ::= { vLdpServFec129Entry 6 }

vLdpServFec129Flags              OBJECT-TYPE
    SYNTAX      TmnxLdpFECFlags
    MAX-ACCESS  read-only
    STATUS      obsolete
    DESCRIPTION
        "The bit flags of vLdpServFec129Flags specify the characteristics of
         the FEC.

         This object was obsoleted in release 13.0."
    ::= { vLdpServFec129Entry 7 }

vLdpServFec129NumInLabels        OBJECT-TYPE
    SYNTAX      Unsigned32
    MAX-ACCESS  read-only
    STATUS      obsolete
    DESCRIPTION
        "The value of vLdpServFec129NumInLabels gives the number of labels that
         have been sent to the peer associated with this FEC. This value also
         indicates whether vLdpServFec129InLabel1 entry contain valid
         information i.e. if the value of vLdpServFec129NumInLabels is 1 then
         vLdpServFec129InLabel1 will contain valid label information.

         This object was obsoleted in release 13.0."
    ::= { vLdpServFec129Entry 8 }

vLdpServFec129NumOutLabels       OBJECT-TYPE
    SYNTAX      Unsigned32
    MAX-ACCESS  read-only
    STATUS      obsolete
    DESCRIPTION
        "The value of vLdpServFec129NumOutLabels gives the number of labels
         that have been received from the peer associated with this FEC. This
         value also indicates whether vLdpServFec129OutLabel1 entry contain
         valid information i.e. if the value of vLdpServFec129NumOutLabels is
         1, then vLdpServFec129OutLabel1 will contain valid label information.

         This object was obsoleted in release 13.0."
    ::= { vLdpServFec129Entry 9 }

vLdpServFec129InLabel1           OBJECT-TYPE
    SYNTAX      Unsigned32
    MAX-ACCESS  read-only
    STATUS      obsolete
    DESCRIPTION
        "The value of vLdpServFec129InLabel1 specifies the first ingress label
         exchanged.

         This object was obsoleted in release 13.0."
    ::= { vLdpServFec129Entry 10 }

vLdpServFec129InLabelStatus1     OBJECT-TYPE
    SYNTAX      TmnxLabelStatus
    MAX-ACCESS  read-only
    STATUS      obsolete
    DESCRIPTION
        "The value of vLdpServFec129InLabelStatus1 specifies the status of the
         ingress label 1.

         This object was obsoleted in release 13.0."
    ::= { vLdpServFec129Entry 11 }

vLdpServFec129OutLabel1          OBJECT-TYPE
    SYNTAX      Unsigned32
    MAX-ACCESS  read-only
    STATUS      obsolete
    DESCRIPTION
        "The value of vLdpServFec129OutLabel1 specifies the first egress label
         exchanged.

         This object was obsoleted in release 13.0."
    ::= { vLdpServFec129Entry 20 }

vLdpServFec129OutLabelStatus1    OBJECT-TYPE
    SYNTAX      TmnxLabelStatus
    MAX-ACCESS  read-only
    STATUS      obsolete
    DESCRIPTION
        "The value of vLdpServFec129OutLabelStatus1 specifies the status of the
         egress label 1.

         This object was obsoleted in release 13.0."
    ::= { vLdpServFec129Entry 21 }

vLdpServFec129SdpId              OBJECT-TYPE
    SYNTAX      SdpId
    MAX-ACCESS  read-only
    STATUS      obsolete
    DESCRIPTION
        "The value of vLdpServFec129SdpId identifies the SDP associated with
         this peer.

         This object was obsoleted in release 13.0."
    ::= { vLdpServFec129Entry 22 }

vLdpServFec129LocalMTU           OBJECT-TYPE
    SYNTAX      Unsigned32
    MAX-ACCESS  read-only
    STATUS      obsolete
    DESCRIPTION
        "The value of vLdpServFec129LocalMTU specifies the largest service
         frame size (in octets) that can be handled by the local ESR.

         This object was obsoleted in release 13.0."
    ::= { vLdpServFec129Entry 23 }

vLdpServFec129RemoteMTU          OBJECT-TYPE
    SYNTAX      Unsigned32
    MAX-ACCESS  read-only
    STATUS      obsolete
    DESCRIPTION
        "The value of vLdpServFec129RemoteMTU specifies the largest service
         frame size (in octets) that can be handled by the remote ESR.

         This object was obsoleted in release 13.0."
    ::= { vLdpServFec129Entry 24 }

vLdpServFec129LocalVlanTag       OBJECT-TYPE
    SYNTAX      Unsigned32
    MAX-ACCESS  read-only
    STATUS      obsolete
    DESCRIPTION
        "The value of vLdpServFec129LocalVlanTag specifies the local tag on a
         VLAN VC type SDP binding.

         This object was obsoleted in release 13.0."
    ::= { vLdpServFec129Entry 25 }

vLdpServFec129RemoteVlanTag      OBJECT-TYPE
    SYNTAX      Unsigned32
    MAX-ACCESS  read-only
    STATUS      obsolete
    DESCRIPTION
        "The value of vLdpServFec129RemoteVlanTag specifies the remote tag on a
         VLAN VC type SDP binding.

         This object was obsoleted in release 13.0."
    ::= { vLdpServFec129Entry 26 }

vLdpServFec129LocalMaxCellConcat OBJECT-TYPE
    SYNTAX      Unsigned32
    MAX-ACCESS  read-only
    STATUS      obsolete
    DESCRIPTION
        "The value of vLdpServFec129LocalMaxCellConcat specifies the local
         maximum number of ATM cells to concatenate on a ATM cell-mode VC type
         SDP binding.

         This object was obsoleted in release 13.0."
    ::= { vLdpServFec129Entry 27 }

vLdpServFec129RemoteMaxCellConcat OBJECT-TYPE
    SYNTAX      Unsigned32
    MAX-ACCESS  read-only
    STATUS      obsolete
    DESCRIPTION
        "The value of vLdpServFec129RemoteMaxCellConcat specifies the remote
         maximum number of ATM cells to concatenate on a ATM cell-mode VC type
         SDP binding.

         This object was obsoleted in release 13.0."
    ::= { vLdpServFec129Entry 28 }

vLdpServFec129InLabelSigStatus1  OBJECT-TYPE
    SYNTAX      TmnxLabelSigStatus
    MAX-ACCESS  read-only
    STATUS      obsolete
    DESCRIPTION
        "The value of vLdpServFec129InLabelSigStatus1 indicates the signaling
         status for vLdpServFec129InLabel1.

         This object was obsoleted in release 13.0."
    ::= { vLdpServFec129Entry 29 }

vLdpServFec129OutLabelSigStatus1 OBJECT-TYPE
    SYNTAX      TmnxLabelSigStatus
    MAX-ACCESS  read-only
    STATUS      obsolete
    DESCRIPTION
        "The value of vLdpServFec129OutLabelSigStatus1 indicates the signaling
         status for vLdpServFec129OutLabel1.

         This object was obsoleted in release 13.0."
    ::= { vLdpServFec129Entry 30 }

vLdpServFec129LocalIpv4Capblty   OBJECT-TYPE
    SYNTAX      TruthValue
    MAX-ACCESS  read-only
    STATUS      obsolete
    DESCRIPTION
        "The value of vLdpServFec129LocalIpv4Capblty indicates whether or not
         the local ipv4 stack capability is supported for this LDP peer.

         The value of vLdpServFec129LocalIpv4Capblty is 'true' when the local
         ipv4 stack capability is supported and the value is 'false' when the
         local ipv4 stack capability is not supported.

         This object was obsoleted in release 13.0."
    ::= { vLdpServFec129Entry 31 }

vLdpServFec129RemoteIpv4Capblty  OBJECT-TYPE
    SYNTAX      TruthValue
    MAX-ACCESS  read-only
    STATUS      obsolete
    DESCRIPTION
        "The value of vLdpServFec129RemoteIpv4Capblty indicates whether or not
         the remote ipv4 stack capability is supported for this LDP peer.

         The value of vLdpServFec129RemoteIpv4Capblty is 'true' when the remote
         ipv4 stack capability is supported and the value is 'false' when the
         remote ipv4 stack capability is not supported.

         This object was obsoleted in release 13.0."
    ::= { vLdpServFec129Entry 32 }

vLdpServFec129LocalIpv6Capblty   OBJECT-TYPE
    SYNTAX      TruthValue
    MAX-ACCESS  read-only
    STATUS      obsolete
    DESCRIPTION
        "The value of vLdpServFec129LocalIpv6Capblty indicates whether or not
         the local ipv6 stack capability is supported for this LDP peer.

         The value of vLdpServFec129LocalIpv6Capblty is 'true' when the local
         ipv6 stack capability is supported and the value is 'false' when the
         local ipv6 stack capability is not supported.

         This object was obsoleted in release 13.0."
    ::= { vLdpServFec129Entry 33 }

vLdpServFec129RemoteIpv6Capblty  OBJECT-TYPE
    SYNTAX      TruthValue
    MAX-ACCESS  read-only
    STATUS      obsolete
    DESCRIPTION
        "The value of vLdpServFec129RemoteIpv6Capblty indicates whether or not
         the remote ipv6 stack capability is supported for this LDP peer.

         The value of vLdpServFec129RemoteIpv6Capblty is 'true' when the remote
         ipv6 stack capability is supported and the value is 'false' when the
         remote ipv6 stack capability is not supported.

         This object was obsoleted in release 13.0."
    ::= { vLdpServFec129Entry 34 }

vLdpServFec129LocalIpv4CeIpAddr  OBJECT-TYPE
    SYNTAX      IpAddress
    MAX-ACCESS  read-only
    STATUS      obsolete
    DESCRIPTION
        "The value of vLdpServFec129LocalIpv4CeIpAddr indicates the local ipv4
         CE Address.

         This object was obsoleted in release 13.0."
    ::= { vLdpServFec129Entry 35 }

vLdpServFec129RemoteIpv4CeIpAddr OBJECT-TYPE
    SYNTAX      IpAddress
    MAX-ACCESS  read-only
    STATUS      obsolete
    DESCRIPTION
        "The value of vLdpServFec129RemoteIpv4CeIpAddr indicates the remote
         ipv4 CE Address.

         This object was obsoleted in release 13.0."
    ::= { vLdpServFec129Entry 36 }

vLdpServFec129InLbl1WdwReason    OBJECT-TYPE
    SYNTAX      TmnxLdpInLblWdrawalReasonCode
    MAX-ACCESS  read-only
    STATUS      obsolete
    DESCRIPTION
        "The value of vLdpServFec129InLbl1WdwReason indicates the reason of
         withdrawal of ingress label value in vLdpServFec129InLabel1.

         This object was obsoleted in release 13.0."
    ::= { vLdpServFec129Entry 37 }

vLdpServFec129LocalFLTxCapblty   OBJECT-TYPE
    SYNTAX      TruthValue
    MAX-ACCESS  read-only
    STATUS      obsolete
    DESCRIPTION
        "The value of vLdpServFec129LocalFLTxCapblty indicates whether or not
         this LDP peer is capable of sending Flow Label in its pseudowire (PW)
         packet.

         The value of vLdpServFec129LocalFLTxCapblty is 'true' when this LDP
         peer is capable of sending Flow Label and the value is 'false' when
         the peer is not capable of sending Flow Label in pseudowire packet.

         This object was obsoleted in release 13.0."
    ::= { vLdpServFec129Entry 38 }

vLdpServFec129LocalFLRxCapblty   OBJECT-TYPE
    SYNTAX      TruthValue
    MAX-ACCESS  read-only
    STATUS      obsolete
    DESCRIPTION
        "The value of vLdpServFec129LocalFLRxCapblty indicates whether or not
         this LDP peer is capable of receiving Flow Label in its pseudowire
         packet.

         The value of vLdpServFec129LocalFLRxCapblty is 'true' when this LDP
         peer is capable of receiving Flow Label and the value is 'false' when
         the peer is not capable of receiving Flow Label in pseudowire packet.

         This object was obsoleted in release 13.0."
    ::= { vLdpServFec129Entry 39 }

vLdpServFec129RemoteFLTxCapblty  OBJECT-TYPE
    SYNTAX      TruthValue
    MAX-ACCESS  read-only
    STATUS      obsolete
    DESCRIPTION
        "The value of vLdpServFec129RemoteFLTxCapblty indicates whether or not
         the remote LDP peer is capable of sending Flow Label in its pseudowire
         packet.

         The value of vLdpServFec129RemoteFLTxCapblty is 'true' when the remote
         LDP peer is capable of sending Flow Label and the value is 'false'
         when the peer is not capable of sending Flow Label in pseudowire
         packet.

         This object was obsoleted in release 13.0."
    ::= { vLdpServFec129Entry 40 }

vLdpServFec129RemoteFLRxCapblty  OBJECT-TYPE
    SYNTAX      TruthValue
    MAX-ACCESS  read-only
    STATUS      obsolete
    DESCRIPTION
        "The value of vLdpServFec129RemoteFLRxCapblty indicates whether or not
         the remote LDP peer is capable of receiving Flow Label in its
         pseudowire packet.

         The value of vLdpServFec129RemoteFLRxCapblty is 'true' when the remote
         LDP peer is capable of receiving Flow Label and the value is 'false'
         when the peer is not capable of receiving Flow Label in pseudowire
         packet.

         This object was obsoleted in release 13.0."
    ::= { vLdpServFec129Entry 41 }

vLdpServFec129MateAgiTlv         OBJECT-TYPE
    SYNTAX      TmnxLdpFec129Tlv
    MAX-ACCESS  read-only
    STATUS      obsolete
    DESCRIPTION
        "The value of vLdpServFec129MateAgiTlv identifies the Attachment Group
         Identifier TLV switched with this service FEC.

         This object was obsoleted in release 13.0."
    ::= { vLdpServFec129Entry 42 }

vLdpServFec129MateSrcAiiTlv      OBJECT-TYPE
    SYNTAX      TmnxLdpFec129Tlv
    MAX-ACCESS  read-only
    STATUS      obsolete
    DESCRIPTION
        "The value of vLdpServFec129MateSrcAiiTlv identifies the Source
         Attachment Individual Identifier TLV switched with this service FEC.

         This object was obsoleted in release 13.0."
    ::= { vLdpServFec129Entry 43 }

vLdpServFec129MateTgtAiiTlv      OBJECT-TYPE
    SYNTAX      TmnxLdpFec129Tlv
    MAX-ACCESS  read-only
    STATUS      obsolete
    DESCRIPTION
        "The value of vLdpServFec129MateTgtAiiTlv identifies the Target
         Attachment Individual Identifier TLV switched with this service FEC.

         This object was obsoleted in release 13.0."
    ::= { vLdpServFec129Entry 44 }

vLdpServFec129MateSdpId          OBJECT-TYPE
    SYNTAX      SdpId
    MAX-ACCESS  read-only
    STATUS      obsolete
    DESCRIPTION
        "The value of vLdpServFec129MateSdpId identifies the SDP switched with
         this peer.

         This object was obsoleted in release 13.0."
    ::= { vLdpServFec129Entry 45 }

vLdpServFec129MapTable           OBJECT-TYPE
    SYNTAX      SEQUENCE OF VLdpServFec129MapEntry
    MAX-ACCESS  not-accessible
    STATUS      obsolete
    DESCRIPTION
        "vLdpServFec129MapTable is a read-only table which maps to the
         vLdpServFec129Table. This table has the same indexes as the
         vLdpServFec129Table but the order in which these indexes are specified
         is different for the two tables."
    ::= { tmnxLdpObjs 24 }

vLdpServFec129MapEntry           OBJECT-TYPE
    SYNTAX      VLdpServFec129MapEntry
    MAX-ACCESS  not-accessible
    STATUS      obsolete
    DESCRIPTION
        "Each row entry represents an instance of a service FEC sent to or
         received from an LDP peer."
    INDEX       {
        vRtrID,
        vRtrLdpPeerLdpId,
        vLdpServFec129MapVcType,
        vLdpServFec129MapAgiTlv,
        vLdpServFec129MapSrcAiiTlv,
        vLdpServFec129MapTgtAiiTlv
    }
    ::= { vLdpServFec129MapTable 1 }

VLdpServFec129MapEntry           ::= SEQUENCE
{
    vLdpServFec129MapVcType          TmnxVcType,
    vLdpServFec129MapAgiTlv          TmnxLdpFec129Tlv,
    vLdpServFec129MapSrcAiiTlv       TmnxLdpFec129Tlv,
    vLdpServFec129MapTgtAiiTlv       TmnxLdpFec129Tlv
}

vLdpServFec129MapVcType          OBJECT-TYPE
    SYNTAX      TmnxVcType
    MAX-ACCESS  read-only
    STATUS      obsolete
    DESCRIPTION
        "The value of vLdpServFec129MapVcType specifies the VC type associated
         with this service FEC."
    ::= { vLdpServFec129MapEntry 1 }

vLdpServFec129MapAgiTlv          OBJECT-TYPE
    SYNTAX      TmnxLdpFec129Tlv
    MAX-ACCESS  read-only
    STATUS      obsolete
    DESCRIPTION
        "The value of vLdpServFec129MapAgiTlv specifies the Attachment Group
         Identifier TLV associated with this service FEC."
    ::= { vLdpServFec129MapEntry 2 }

vLdpServFec129MapSrcAiiTlv       OBJECT-TYPE
    SYNTAX      TmnxLdpFec129Tlv
    MAX-ACCESS  read-only
    STATUS      obsolete
    DESCRIPTION
        "The value of vLdpServFec129MapSrcAiiTlv specifies the Source
         Attachment Individual Identifier TLV associated with this service FEC."
    ::= { vLdpServFec129MapEntry 3 }

vLdpServFec129MapTgtAiiTlv       OBJECT-TYPE
    SYNTAX      TmnxLdpFec129Tlv
    MAX-ACCESS  read-only
    STATUS      obsolete
    DESCRIPTION
        "The value of vLdpServFec129MapTgtAiiTlv specifies the Target
         Attachment Individual Identifier TLV associated with this service FEC."
    ::= { vLdpServFec129MapEntry 4 }

vLdpCepTdmFec129Table            OBJECT-TYPE
    SYNTAX      SEQUENCE OF VLdpCepTdmFec129Entry
    MAX-ACCESS  not-accessible
    STATUS      obsolete
    DESCRIPTION
        "vLdpCepTdmFec129Table is a read-only table that represents all CEP/TDM
         FECs either sent to or received from an LDP peer known to the Virtual
         Router. The CEP/TDM Sub-TLVs are defined in RFC 4446:

         Parameter Id    Description
         0x04            CEP/TDM Payload Bytes
         0x07            CEP/TDM bit-rate
         0x0B            TDM Options

         In 13.0 this table has been replaced by
         TIMETRA-LDP-NG-MIB::vLdpNgCepTdmFec129InLblTable,
         TIMETRA-LDP-NG-MIB::vLdpNgCepTdmFec129OutLblTable."
    ::= { tmnxLdpObjs 25 }

vLdpCepTdmFec129Entry            OBJECT-TYPE
    SYNTAX      VLdpCepTdmFec129Entry
    MAX-ACCESS  not-accessible
    STATUS      obsolete
    DESCRIPTION
        "Each row entry represents an instance of a service FEC sent to or
         received from an LDP peer.

         Use of AUGMENTS clause implies a one-to-one dependent relationship
         between the base table, vRtrLdpServFecTable, and the augmenting
         table, vLdpCepTdmFec129Table.  This in effect extends the
         vRtrLdpServFecTable with additional columns.

          Creation or deletion of a row in the vRtrLdpServFecTable results
          in the same fate for the row in the VLdpCepTdmFec129Entry."
    AUGMENTS    { vLdpServFec129Entry }
    ::= { vLdpCepTdmFec129Table 1 }

VLdpCepTdmFec129Entry            ::= SEQUENCE
{
    vLdpCepTdmFec129LocalPayloadSize Unsigned32,
    vLdpCepTdmFec129RemotePayloadSize Unsigned32,
    vLdpCepTdmFec129LocalBitrate     Unsigned32,
    vLdpCepTdmFec129RemoteBitrate    Unsigned32,
    vLdpCepTdmFec129LocalRtpHeader   TruthValue,
    vLdpCepTdmFec129RemoteRtpHeader  TruthValue,
    vLdpCepTdmFec129LocalDiffTimestamp TruthValue,
    vLdpCepTdmFec129RemoteDiffTimestamp TruthValue,
    vLdpCepTdmFec129LocalSigPkts     TdmOptionsSigPkts,
    vLdpCepTdmFec129RemoteSigPkts    TdmOptionsSigPkts,
    vLdpCepTdmFec129LocalCasTrunk    TdmOptionsCasTrunkFraming,
    vLdpCepTdmFec129RemoteCasTrunk   TdmOptionsCasTrunkFraming,
    vLdpCepTdmFec129LocalTimestampFreq Unsigned32,
    vLdpCepTdmFec129RemoteTimestampFreq Unsigned32,
    vLdpCepTdmFec129LocalPayloadType Unsigned32,
    vLdpCepTdmFec129RemotePayloadType Unsigned32,
    vLdpCepTdmFec129LocalSsrcId      Unsigned32,
    vLdpCepTdmFec129RemoteSsrcId     Unsigned32
}

vLdpCepTdmFec129LocalPayloadSize OBJECT-TYPE
    SYNTAX      Unsigned32
    UNITS       "bytes"
    MAX-ACCESS  read-only
    STATUS      obsolete
    DESCRIPTION
        "The value of vLdpCepTdmFec129LocalPayloadSize indicates the local
         payload size.

         This object was obsoleted in release 13.0."
    ::= { vLdpCepTdmFec129Entry 4 }

vLdpCepTdmFec129RemotePayloadSize OBJECT-TYPE
    SYNTAX      Unsigned32
    UNITS       "bytes"
    MAX-ACCESS  read-only
    STATUS      obsolete
    DESCRIPTION
        "The value of vLdpCepTdmFec129RemotePayloadSize indicates the remote
         payload size.

         This object was obsoleted in release 13.0."
    ::= { vLdpCepTdmFec129Entry 5 }

vLdpCepTdmFec129LocalBitrate     OBJECT-TYPE
    SYNTAX      Unsigned32
    UNITS       "sixty-four kilobps"
    MAX-ACCESS  read-only
    STATUS      obsolete
    DESCRIPTION
        "The value of vLdpCepTdmFec129LocalBitrate indicates the local bitrate.

         This object was obsoleted in release 13.0."
    ::= { vLdpCepTdmFec129Entry 6 }

vLdpCepTdmFec129RemoteBitrate    OBJECT-TYPE
    SYNTAX      Unsigned32
    UNITS       "sixty-four kilobps"
    MAX-ACCESS  read-only
    STATUS      obsolete
    DESCRIPTION
        "The value of vLdpCepTdmFec129RemoteBitrate indicates the remote
         bitrate.

         This object was obsoleted in release 13.0."
    ::= { vLdpCepTdmFec129Entry 7 }

vLdpCepTdmFec129LocalRtpHeader   OBJECT-TYPE
    SYNTAX      TruthValue
    MAX-ACCESS  read-only
    STATUS      obsolete
    DESCRIPTION
        "The value of vLdpCepTdmFec129LocalRtpHeader indicates the local RTP
         header usage bit.

         This object was obsoleted in release 13.0."
    ::= { vLdpCepTdmFec129Entry 8 }

vLdpCepTdmFec129RemoteRtpHeader  OBJECT-TYPE
    SYNTAX      TruthValue
    MAX-ACCESS  read-only
    STATUS      obsolete
    DESCRIPTION
        "The value of vLdpCepTdmFec129RemoteRtpHeader indicates the remote RTP
         header usage bit.

         This object was obsoleted in release 13.0."
    ::= { vLdpCepTdmFec129Entry 9 }

vLdpCepTdmFec129LocalDiffTimestamp OBJECT-TYPE
    SYNTAX      TruthValue
    MAX-ACCESS  read-only
    STATUS      obsolete
    DESCRIPTION
        "The value of vLdpCepTdmFec129LocalDiffTimestamp indicates the local
         differential (or dynamic) timestamping mode bit.

         This object was obsoleted in release 13.0."
    ::= { vLdpCepTdmFec129Entry 10 }

vLdpCepTdmFec129RemoteDiffTimestamp OBJECT-TYPE
    SYNTAX      TruthValue
    MAX-ACCESS  read-only
    STATUS      obsolete
    DESCRIPTION
        "The value of vLdpCepTdmFec129RemoteDiffTimestamp indicates the remote
         differential (or dynamic) timestamping mode bit.

         This object was obsoleted in release 13.0."
    ::= { vLdpCepTdmFec129Entry 11 }

vLdpCepTdmFec129LocalSigPkts     OBJECT-TYPE
    SYNTAX      TdmOptionsSigPkts
    MAX-ACCESS  read-only
    STATUS      obsolete
    DESCRIPTION
        "The value of vLdpCepTdmFec129LocalSigPkts indicates the local CE
         application signalling packets mode.

         This object was obsoleted in release 13.0."
    ::= { vLdpCepTdmFec129Entry 12 }

vLdpCepTdmFec129RemoteSigPkts    OBJECT-TYPE
    SYNTAX      TdmOptionsSigPkts
    MAX-ACCESS  read-only
    STATUS      obsolete
    DESCRIPTION
        "The value of vLdpCepTdmFec129RemoteSigPkts indicates the remote CE
         application signalling packets mode.

         This object was obsoleted in release 13.0."
    ::= { vLdpCepTdmFec129Entry 13 }

vLdpCepTdmFec129LocalCasTrunk    OBJECT-TYPE
    SYNTAX      TdmOptionsCasTrunkFraming
    MAX-ACCESS  read-only
    STATUS      obsolete
    DESCRIPTION
        "The value of vLdpCepTdmFec129LocalCasTrunk indicates the local CE
         application signalling packets mode.

         This object was obsoleted in release 13.0."
    ::= { vLdpCepTdmFec129Entry 14 }

vLdpCepTdmFec129RemoteCasTrunk   OBJECT-TYPE
    SYNTAX      TdmOptionsCasTrunkFraming
    MAX-ACCESS  read-only
    STATUS      obsolete
    DESCRIPTION
        "The value of vLdpCepTdmFec129RemoteCasTrunk indicates the remote CE
         application signalling packets mode.

         This object was obsoleted in release 13.0."
    ::= { vLdpCepTdmFec129Entry 15 }

vLdpCepTdmFec129LocalTimestampFreq OBJECT-TYPE
    SYNTAX      Unsigned32
    UNITS       "8 KHz"
    MAX-ACCESS  read-only
    STATUS      obsolete
    DESCRIPTION
        "The value of vLdpCepTdmFec129LocalTimestampFreq indicates the local CE
         application signalling packets mode.

         This object was obsoleted in release 13.0."
    ::= { vLdpCepTdmFec129Entry 16 }

vLdpCepTdmFec129RemoteTimestampFreq OBJECT-TYPE
    SYNTAX      Unsigned32
    UNITS       "8 KHz"
    MAX-ACCESS  read-only
    STATUS      obsolete
    DESCRIPTION
        "The value of vLdpCepTdmFec129RemoteTimestampFreq indicates the remote
         CE application signalling packets mode.

         This object was obsoleted in release 13.0."
    ::= { vLdpCepTdmFec129Entry 17 }

vLdpCepTdmFec129LocalPayloadType OBJECT-TYPE
    SYNTAX      Unsigned32
    MAX-ACCESS  read-only
    STATUS      obsolete
    DESCRIPTION
        "The value of vLdpCepTdmFec129LocalPayloadType indicates the local
         payload type.

         This object was obsoleted in release 13.0."
    ::= { vLdpCepTdmFec129Entry 18 }

vLdpCepTdmFec129RemotePayloadType OBJECT-TYPE
    SYNTAX      Unsigned32
    MAX-ACCESS  read-only
    STATUS      obsolete
    DESCRIPTION
        "The value of vLdpCepTdmFec129RemotePayloadType indicates the remote
         payload type.

         This object was obsoleted in release 13.0."
    ::= { vLdpCepTdmFec129Entry 19 }

vLdpCepTdmFec129LocalSsrcId      OBJECT-TYPE
    SYNTAX      Unsigned32
    MAX-ACCESS  read-only
    STATUS      obsolete
    DESCRIPTION
        "The value of vLdpCepTdmFec129LocalSsrcId indicates the local value of
         SSRC ID.

         This object was obsoleted in release 13.0."
    ::= { vLdpCepTdmFec129Entry 20 }

vLdpCepTdmFec129RemoteSsrcId     OBJECT-TYPE
    SYNTAX      Unsigned32
    MAX-ACCESS  read-only
    STATUS      obsolete
    DESCRIPTION
        "The value of vLdpCepTdmFec129RemoteSsrcId indicates the remote value
         of SSRC ID.

         This object was obsoleted in release 13.0."
    ::= { vLdpCepTdmFec129Entry 21 }

vRtrLdpAggrPreMatchTable         OBJECT-TYPE
    SYNTAX      SEQUENCE OF VRtrLdpAggrPreMatchEntry
    MAX-ACCESS  not-accessible
    STATUS      obsolete
    DESCRIPTION
        "vRtrLdpAggrPreMatchTable keeps information about aggregate prefix
         match procedures.

         Use of AUGMENTS clause implies a one-to-one dependent
         relationship between the base table, vRtrLdpGeneralTable,
         and the augmenting table, vRtrLdpAggrPreMatchTable. This in
         effect extends the vRtrLdpGeneralTable with additional
         columns.  Creation or deletion of a row in the
         vRtrLdpGeneralTable results in the same fate for the row
         in the vRtrLdpAggrPreMatchTable.

         In 13.0 this table has been replaced by
         TIMETRA-LDP-NG-MIB::vRtrLdpNgAggrPreMatchTable."
    REFERENCE
        "RFC5283 LDP Extension for Inter-Area Label Switched Paths (LSPs)"
    ::= { tmnxLdpObjs 26 }

vRtrLdpAggrPreMatchEntry         OBJECT-TYPE
    SYNTAX      VRtrLdpAggrPreMatchEntry
    MAX-ACCESS  not-accessible
    STATUS      obsolete
    DESCRIPTION
        "A row in this table represents information about the aggregate prefix
         match procedures."
    AUGMENTS    { vRtrLdpGeneralEntry }
    ::= { vRtrLdpAggrPreMatchTable 1 }

VRtrLdpAggrPreMatchEntry         ::= SEQUENCE
{
    vRtrLdpAggrPreMatchEnabled       TruthValue,
    vRtrLdpAggrPreMatchPreExcPolicy1 TPolicyStatementNameOrEmpty,
    vRtrLdpAggrPreMatchPreExcPolicy2 TPolicyStatementNameOrEmpty,
    vRtrLdpAggrPreMatchPreExcPolicy3 TPolicyStatementNameOrEmpty,
    vRtrLdpAggrPreMatchPreExcPolicy4 TPolicyStatementNameOrEmpty,
    vRtrLdpAggrPreMatchPreExcPolicy5 TPolicyStatementNameOrEmpty,
    vRtrLdpAggrPreMatchAdminState    TmnxAdminState
}

vRtrLdpAggrPreMatchEnabled       OBJECT-TYPE
    SYNTAX      TruthValue
    MAX-ACCESS  read-create
    STATUS      obsolete
    DESCRIPTION
        "The value of vRtrLdpAggrPreMatchEnabled specifies whether aggregate
         prefix match procedures are enabled.

         This object was obsoleted in release 13.0."
    DEFVAL      { false }
    ::= { vRtrLdpAggrPreMatchEntry 1 }

vRtrLdpAggrPreMatchPreExcPolicy1 OBJECT-TYPE
    SYNTAX      TPolicyStatementNameOrEmpty
    MAX-ACCESS  read-create
    STATUS      obsolete
    DESCRIPTION
        "The value of vRtrLdpAggrPreMatchPreExcPolicy1 specifies the policy
         name containing the prefixes to be excluded from the aggregate prefix match procedures.
         A maximum of 5 policies can be specified.  vRtrLdpAggrPreMatchPreExcPolicy1 specifies the
         first policy.

         This object was obsoleted in release 13.0."
    DEFVAL      { ''H }
    ::= { vRtrLdpAggrPreMatchEntry 2 }

vRtrLdpAggrPreMatchPreExcPolicy2 OBJECT-TYPE
    SYNTAX      TPolicyStatementNameOrEmpty
    MAX-ACCESS  read-create
    STATUS      obsolete
    DESCRIPTION
        "The value of vRtrLdpAggrPreMatchPreExcPolicy2 specifies the second
         policy name containing the prefixes to be excluded from the aggregate
         prefix match procedures.

         This object was obsoleted in release 13.0."
    DEFVAL      { ''H }
    ::= { vRtrLdpAggrPreMatchEntry 4 }

vRtrLdpAggrPreMatchPreExcPolicy3 OBJECT-TYPE
    SYNTAX      TPolicyStatementNameOrEmpty
    MAX-ACCESS  read-create
    STATUS      obsolete
    DESCRIPTION
        "The value of vRtrLdpAggrPreMatchPreExcPolicy3 specifies the third
         policy name containing the prefixes to be excluded from the aggregate
         prefix match procedures.

         This object was obsoleted in release 13.0."
    DEFVAL      { ''H }
    ::= { vRtrLdpAggrPreMatchEntry 5 }

vRtrLdpAggrPreMatchPreExcPolicy4 OBJECT-TYPE
    SYNTAX      TPolicyStatementNameOrEmpty
    MAX-ACCESS  read-create
    STATUS      obsolete
    DESCRIPTION
        "The value of vRtrLdpAggrPreMatchPreExcPolicy4 specifies the fourth
         policy name containing the prefixes to be excluded from the aggregate
         prefix match procedures.

         This object was obsoleted in release 13.0."
    DEFVAL      { ''H }
    ::= { vRtrLdpAggrPreMatchEntry 6 }

vRtrLdpAggrPreMatchPreExcPolicy5 OBJECT-TYPE
    SYNTAX      TPolicyStatementNameOrEmpty
    MAX-ACCESS  read-create
    STATUS      obsolete
    DESCRIPTION
        "The value of vRtrLdpAggrPreMatchPreExcPolicy5 specifies the fifth
         policy name containing the prefixes to be excluded from the aggregate
         prefix match procedures.

         This object was obsoleted in release 13.0."
    DEFVAL      { ''H }
    ::= { vRtrLdpAggrPreMatchEntry 7 }

vRtrLdpAggrPreMatchAdminState    OBJECT-TYPE
    SYNTAX      TmnxAdminState
    MAX-ACCESS  read-create
    STATUS      obsolete
    DESCRIPTION
        "The value of vRtrLdpAggrPreMatchAdminState specifies whether the
         aggregate prefix procedures will be used by LDP.

         This object was obsoleted in release 13.0."
    DEFVAL      { outOfService }
    ::= { vRtrLdpAggrPreMatchEntry 8 }

vRtrLdpEgrStatFecPfxTblLastChgd  OBJECT-TYPE
    SYNTAX      TimeStamp
    MAX-ACCESS  read-only
    STATUS      current
    DESCRIPTION
        "Timestamp of the last change to the vRtrLdpEgrStatFecPfxTable either
         from adding a row or removing a row."
    ::= { tmnxLdpObjs 27 }

vRtrLdpEgrStatFecPfxTable        OBJECT-TYPE
    SYNTAX      SEQUENCE OF VRtrLdpEgrStatFecPfxEntry
    MAX-ACCESS  not-accessible
    STATUS      current
    DESCRIPTION
        "vRtrLdpEgrStatFecPfxTable controls statistics in the egress data path
         at the ingress Label Switched Path (LSP) for an LDP FEC."
    ::= { tmnxLdpObjs 28 }

vRtrLdpEgrStatFecPfxEntry        OBJECT-TYPE
    SYNTAX      VRtrLdpEgrStatFecPfxEntry
    MAX-ACCESS  not-accessible
    STATUS      current
    DESCRIPTION
        "A row in this table represents information about the statistics
         collection per FEC prefix."
    INDEX       {
        vRtrID,
        vRtrLdpEgrStatFecPfxAddrType,
        vRtrLdpEgrStatFecPfxAddr,
        vRtrLdpEgrStatFecPfxMaskLen
    }
    ::= { vRtrLdpEgrStatFecPfxTable 1 }

VRtrLdpEgrStatFecPfxEntry        ::= SEQUENCE
{
    vRtrLdpEgrStatFecPfxAddrType     TmnxAddressAndPrefixType,
    vRtrLdpEgrStatFecPfxAddr         TmnxAddressAndPrefixAddress,
    vRtrLdpEgrStatFecPfxMaskLen      TmnxAddressAndPrefixPrefix,
    vRtrLdpEgrStatFecPfxRowStatus    RowStatus,
    vRtrLdpEgrStatFecPfxLastChgd     TimeStamp,
    vRtrLdpEgrStatFecPfxCollStats    TruthValue,
    vRtrLdpEgrStatFecPfxActgPol      Unsigned32,
    vRtrLdpEgrStatFecPfxAdminState   TmnxAdminState
}

vRtrLdpEgrStatFecPfxAddrType     OBJECT-TYPE
    SYNTAX      TmnxAddressAndPrefixType
    MAX-ACCESS  not-accessible
    STATUS      current
    DESCRIPTION
        "The IP address type of vRtrLdpEgrStatFecPfxAddr."
    ::= { vRtrLdpEgrStatFecPfxEntry 1 }

vRtrLdpEgrStatFecPfxAddr         OBJECT-TYPE
    SYNTAX      TmnxAddressAndPrefixAddress (SIZE (4|16))
    MAX-ACCESS  not-accessible
    STATUS      current
    DESCRIPTION
        "The index value vRtrLdpEgrStatFecPfxAddr identifies the IP prefix for
         the LDP FEC."
    ::= { vRtrLdpEgrStatFecPfxEntry 2 }

vRtrLdpEgrStatFecPfxMaskLen      OBJECT-TYPE
    SYNTAX      TmnxAddressAndPrefixPrefix
    MAX-ACCESS  not-accessible
    STATUS      current
    DESCRIPTION
        "The index value vRtrLdpEgrStatFecPfxMaskLen identifies the prefix mask
         length of vRtrLdpEgrStatFecPfxAddr."
    ::= { vRtrLdpEgrStatFecPfxEntry 3 }

vRtrLdpEgrStatFecPfxRowStatus    OBJECT-TYPE
    SYNTAX      RowStatus
    MAX-ACCESS  read-create
    STATUS      current
    DESCRIPTION
        "vRtrLdpEgrStatFecPfxRowStatus is used for the creation or deletion of
         entries in the vRtrLdpEgrStatFecPfxTable."
    ::= { vRtrLdpEgrStatFecPfxEntry 4 }

vRtrLdpEgrStatFecPfxLastChgd     OBJECT-TYPE
    SYNTAX      TimeStamp
    MAX-ACCESS  read-only
    STATUS      current
    DESCRIPTION
        "The value of vRtrLdpEgrStatFecPfxLastChgd indicates the time stamp of
         the last change to this row of this table."
    ::= { vRtrLdpEgrStatFecPfxEntry 5 }

vRtrLdpEgrStatFecPfxCollStats    OBJECT-TYPE
    SYNTAX      TruthValue
    MAX-ACCESS  read-create
    STATUS      current
    DESCRIPTION
        "The value of vRtrLdpEgrStatFecPfxCollStats specifies whether to
         collect statistics for this prefix."
    DEFVAL      { false }
    ::= { vRtrLdpEgrStatFecPfxEntry 6 }

vRtrLdpEgrStatFecPfxActgPol      OBJECT-TYPE
    SYNTAX      Unsigned32 (0 | 1..99)
    MAX-ACCESS  read-create
    STATUS      current
    DESCRIPTION
        "The value of vRtrLdpEgrStatFecPfxActgPol specifies the accounting
         policy to be used for this prefix.

         A value of zero indicates that the default accounting policy should be
         used."
    DEFVAL      { 0 }
    ::= { vRtrLdpEgrStatFecPfxEntry 7 }

vRtrLdpEgrStatFecPfxAdminState   OBJECT-TYPE
    SYNTAX      TmnxAdminState
    MAX-ACCESS  read-create
    STATUS      current
    DESCRIPTION
        "The value of vRtrLdpEgrStatFecPfxAdminState specifies whether egress
         statistics are enabled for this prefix."
    DEFVAL      { outOfService }
    ::= { vRtrLdpEgrStatFecPfxEntry 8 }

vRtrLdpEgrStatisticsTable        OBJECT-TYPE
    SYNTAX      SEQUENCE OF VRtrLdpEgrStatisticsEntry
    MAX-ACCESS  not-accessible
    STATUS      current
    DESCRIPTION
        "The vRtrLdpEgrStatisticsTable has an entry for each Labeled Switch
         Path (LSP) configured for a virtual router in the system."
    ::= { tmnxLdpObjs 29 }

vRtrLdpEgrStatisticsEntry        OBJECT-TYPE
    SYNTAX      VRtrLdpEgrStatisticsEntry
    MAX-ACCESS  not-accessible
    STATUS      current
    DESCRIPTION
        "Each row entry represents a collection of statistics for a Labeled
         Switch Path (LSP) configured for a virtual router in the system.

         Entries cannot be created and deleted via SNMP SET operations."
    AUGMENTS    { vRtrLdpEgrStatFecPfxEntry }
    ::= { vRtrLdpEgrStatisticsTable 1 }

VRtrLdpEgrStatisticsEntry        ::= SEQUENCE
{
    vRtrLdpInProfilePktsFc0          Counter64,
    vRtrLdpInProfilePktsFc0Low32     Counter32,
    vRtrLdpInProfilePktsFc0High32    Counter32,
    vRtrLdpInProfilePktsFc1          Counter64,
    vRtrLdpInProfilePktsFc1Low32     Counter32,
    vRtrLdpInProfilePktsFc1High32    Counter32,
    vRtrLdpInProfilePktsFc2          Counter64,
    vRtrLdpInProfilePktsFc2Low32     Counter32,
    vRtrLdpInProfilePktsFc2High32    Counter32,
    vRtrLdpInProfilePktsFc3          Counter64,
    vRtrLdpInProfilePktsFc3Low32     Counter32,
    vRtrLdpInProfilePktsFc3High32    Counter32,
    vRtrLdpInProfilePktsFc4          Counter64,
    vRtrLdpInProfilePktsFc4Low32     Counter32,
    vRtrLdpInProfilePktsFc4High32    Counter32,
    vRtrLdpInProfilePktsFc5          Counter64,
    vRtrLdpInProfilePktsFc5Low32     Counter32,
    vRtrLdpInProfilePktsFc5High32    Counter32,
    vRtrLdpInProfilePktsFc6          Counter64,
    vRtrLdpInProfilePktsFc6Low32     Counter32,
    vRtrLdpInProfilePktsFc6High32    Counter32,
    vRtrLdpInProfilePktsFc7          Counter64,
    vRtrLdpInProfilePktsFc7Low32     Counter32,
    vRtrLdpInProfilePktsFc7High32    Counter32,
    vRtrLdpInProfileOctetsFc0        Counter64,
    vRtrLdpInProfileOctetsFc0Low32   Counter32,
    vRtrLdpInProfileOctetsFc0High32  Counter32,
    vRtrLdpInProfileOctetsFc1        Counter64,
    vRtrLdpInProfileOctetsFc1Low32   Counter32,
    vRtrLdpInProfileOctetsFc1High32  Counter32,
    vRtrLdpInProfileOctetsFc2        Counter64,
    vRtrLdpInProfileOctetsFc2Low32   Counter32,
    vRtrLdpInProfileOctetsFc2High32  Counter32,
    vRtrLdpInProfileOctetsFc3        Counter64,
    vRtrLdpInProfileOctetsFc3Low32   Counter32,
    vRtrLdpInProfileOctetsFc3High32  Counter32,
    vRtrLdpInProfileOctetsFc4        Counter64,
    vRtrLdpInProfileOctetsFc4Low32   Counter32,
    vRtrLdpInProfileOctetsFc4High32  Counter32,
    vRtrLdpInProfileOctetsFc5        Counter64,
    vRtrLdpInProfileOctetsFc5Low32   Counter32,
    vRtrLdpInProfileOctetsFc5High32  Counter32,
    vRtrLdpInProfileOctetsFc6        Counter64,
    vRtrLdpInProfileOctetsFc6Low32   Counter32,
    vRtrLdpInProfileOctetsFc6High32  Counter32,
    vRtrLdpInProfileOctetsFc7        Counter64,
    vRtrLdpInProfileOctetsFc7Low32   Counter32,
    vRtrLdpInProfileOctetsFc7High32  Counter32,
    vRtrLdpOutOfProfPktsFc0          Counter64,
    vRtrLdpOutOfProfPktsFc0Low32     Counter32,
    vRtrLdpOutOfProfPktsFc0High32    Counter32,
    vRtrLdpOutOfProfPktsFc1          Counter64,
    vRtrLdpOutOfProfPktsFc1Low32     Counter32,
    vRtrLdpOutOfProfPktsFc1High32    Counter32,
    vRtrLdpOutOfProfPktsFc2          Counter64,
    vRtrLdpOutOfProfPktsFc2Low32     Counter32,
    vRtrLdpOutOfProfPktsFc2High32    Counter32,
    vRtrLdpOutOfProfPktsFc3          Counter64,
    vRtrLdpOutOfProfPktsFc3Low32     Counter32,
    vRtrLdpOutOfProfPktsFc3High32    Counter32,
    vRtrLdpOutOfProfPktsFc4          Counter64,
    vRtrLdpOutOfProfPktsFc4Low32     Counter32,
    vRtrLdpOutOfProfPktsFc4High32    Counter32,
    vRtrLdpOutOfProfPktsFc5          Counter64,
    vRtrLdpOutOfProfPktsFc5Low32     Counter32,
    vRtrLdpOutOfProfPktsFc5High32    Counter32,
    vRtrLdpOutOfProfPktsFc6          Counter64,
    vRtrLdpOutOfProfPktsFc6Low32     Counter32,
    vRtrLdpOutOfProfPktsFc6High32    Counter32,
    vRtrLdpOutOfProfPktsFc7          Counter64,
    vRtrLdpOutOfProfPktsFc7Low32     Counter32,
    vRtrLdpOutOfProfPktsFc7High32    Counter32,
    vRtrLdpOutOfProfOctetsFc0        Counter64,
    vRtrLdpOutOfProfOctetsFc0Low32   Counter32,
    vRtrLdpOutOfProfOctetsFc0High32  Counter32,
    vRtrLdpOutOfProfOctetsFc1        Counter64,
    vRtrLdpOutOfProfOctetsFc1Low32   Counter32,
    vRtrLdpOutOfProfOctetsFc1High32  Counter32,
    vRtrLdpOutOfProfOctetsFc2        Counter64,
    vRtrLdpOutOfProfOctetsFc2Low32   Counter32,
    vRtrLdpOutOfProfOctetsFc2High32  Counter32,
    vRtrLdpOutOfProfOctetsFc3        Counter64,
    vRtrLdpOutOfProfOctetsFc3Low32   Counter32,
    vRtrLdpOutOfProfOctetsFc3High32  Counter32,
    vRtrLdpOutOfProfOctetsFc4        Counter64,
    vRtrLdpOutOfProfOctetsFc4Low32   Counter32,
    vRtrLdpOutOfProfOctetsFc4High32  Counter32,
    vRtrLdpOutOfProfOctetsFc5        Counter64,
    vRtrLdpOutOfProfOctetsFc5Low32   Counter32,
    vRtrLdpOutOfProfOctetsFc5High32  Counter32,
    vRtrLdpOutOfProfOctetsFc6        Counter64,
    vRtrLdpOutOfProfOctetsFc6Low32   Counter32,
    vRtrLdpOutOfProfOctetsFc6High32  Counter32,
    vRtrLdpOutOfProfOctetsFc7        Counter64,
    vRtrLdpOutOfProfOctetsFc7Low32   Counter32,
    vRtrLdpOutOfProfOctetsFc7High32  Counter32,
    vRtrLdpAggregatePkts             Counter64,
    vRtrLdpAggregatePktsLow32        Counter32,
    vRtrLdpAggregatePktsHigh32       Counter32,
    vRtrLdpAggregateOctets           Counter64,
    vRtrLdpAggregateOctetsLow32      Counter32,
    vRtrLdpAggregateOctetsHigh32     Counter32
}

vRtrLdpInProfilePktsFc0          OBJECT-TYPE
    SYNTAX      Counter64
    MAX-ACCESS  read-only
    STATUS      current
    DESCRIPTION
        "The value of vRtrLdpInProfilePktsFc0 indicates the number of in
         profile packets received for Forwarding Class 0."
    ::= { vRtrLdpEgrStatisticsEntry 1 }

vRtrLdpInProfilePktsFc0Low32     OBJECT-TYPE
    SYNTAX      Counter32
    MAX-ACCESS  read-only
    STATUS      current
    DESCRIPTION
        "The value of vRtrLdpInProfilePktsFc0Low32 indicates the lower 32 bits
         of the value of vRtrLdpInProfilePktsFc0."
    ::= { vRtrLdpEgrStatisticsEntry 2 }

vRtrLdpInProfilePktsFc0High32    OBJECT-TYPE
    SYNTAX      Counter32
    MAX-ACCESS  read-only
    STATUS      current
    DESCRIPTION
        "The value of vRtrLdpInProfilePktsFc0High32 indicates the higher 32
         bits of the value of vRtrLdpInProfilePktsFc0."
    ::= { vRtrLdpEgrStatisticsEntry 3 }

vRtrLdpInProfilePktsFc1          OBJECT-TYPE
    SYNTAX      Counter64
    MAX-ACCESS  read-only
    STATUS      current
    DESCRIPTION
        "The value of vRtrLdpInProfilePktsFc1 indicates the number of in
         profile packets received for Forwarding Class 1."
    ::= { vRtrLdpEgrStatisticsEntry 4 }

vRtrLdpInProfilePktsFc1Low32     OBJECT-TYPE
    SYNTAX      Counter32
    MAX-ACCESS  read-only
    STATUS      current
    DESCRIPTION
        "The value of vRtrLdpInProfilePktsFc1Low32 indicates the lower 32 bits
         of the value of vRtrLdpInProfilePktsFc1."
    ::= { vRtrLdpEgrStatisticsEntry 5 }

vRtrLdpInProfilePktsFc1High32    OBJECT-TYPE
    SYNTAX      Counter32
    MAX-ACCESS  read-only
    STATUS      current
    DESCRIPTION
        "The value of vRtrLdpInProfilePktsFc1High32 indicates the higher 32
         bits of the value of vRtrLdpInProfilePktsFc1."
    ::= { vRtrLdpEgrStatisticsEntry 6 }

vRtrLdpInProfilePktsFc2          OBJECT-TYPE
    SYNTAX      Counter64
    MAX-ACCESS  read-only
    STATUS      current
    DESCRIPTION
        "The value of vRtrLdpInProfilePktsFc2 indicates the number of in
         profile packets received for Forwarding Class 2."
    ::= { vRtrLdpEgrStatisticsEntry 7 }

vRtrLdpInProfilePktsFc2Low32     OBJECT-TYPE
    SYNTAX      Counter32
    MAX-ACCESS  read-only
    STATUS      current
    DESCRIPTION
        "The value of vRtrLdpInProfilePktsFc2Low32 indicates the lower 32 bits
         of the value of vRtrLdpInProfilePktsFc2."
    ::= { vRtrLdpEgrStatisticsEntry 8 }

vRtrLdpInProfilePktsFc2High32    OBJECT-TYPE
    SYNTAX      Counter32
    MAX-ACCESS  read-only
    STATUS      current
    DESCRIPTION
        "The value of vRtrLdpInProfilePktsFc2High32 indicates the higher 32
         bits of the value of vRtrLdpInProfilePktsFc2."
    ::= { vRtrLdpEgrStatisticsEntry 9 }

vRtrLdpInProfilePktsFc3          OBJECT-TYPE
    SYNTAX      Counter64
    MAX-ACCESS  read-only
    STATUS      current
    DESCRIPTION
        "The value of vRtrLdpInProfilePktsFc3 indicates the number of in
         profile packets received for Forwarding Class 3."
    ::= { vRtrLdpEgrStatisticsEntry 10 }

vRtrLdpInProfilePktsFc3Low32     OBJECT-TYPE
    SYNTAX      Counter32
    MAX-ACCESS  read-only
    STATUS      current
    DESCRIPTION
        "The value of vRtrLdpInProfilePktsFc3Low32 indicates the lower 32 bits
         of the value of vRtrLdpInProfilePktsFc3."
    ::= { vRtrLdpEgrStatisticsEntry 11 }

vRtrLdpInProfilePktsFc3High32    OBJECT-TYPE
    SYNTAX      Counter32
    MAX-ACCESS  read-only
    STATUS      current
    DESCRIPTION
        "The value of vRtrLdpInProfilePktsFc3High32 indicates the higher 32
         bits of the value of vRtrLdpInProfilePktsFc3."
    ::= { vRtrLdpEgrStatisticsEntry 12 }

vRtrLdpInProfilePktsFc4          OBJECT-TYPE
    SYNTAX      Counter64
    MAX-ACCESS  read-only
    STATUS      current
    DESCRIPTION
        "The value of vRtrLdpInProfilePktsFc4 indicates the number of in
         profile packets received for Forwarding Class 4."
    ::= { vRtrLdpEgrStatisticsEntry 13 }

vRtrLdpInProfilePktsFc4Low32     OBJECT-TYPE
    SYNTAX      Counter32
    MAX-ACCESS  read-only
    STATUS      current
    DESCRIPTION
        "The value of vRtrLdpInProfilePktsFc4Low32 indicates the lower 32 bits
         of the value of vRtrLdpInProfilePktsFc4."
    ::= { vRtrLdpEgrStatisticsEntry 14 }

vRtrLdpInProfilePktsFc4High32    OBJECT-TYPE
    SYNTAX      Counter32
    MAX-ACCESS  read-only
    STATUS      current
    DESCRIPTION
        "The value of vRtrLdpInProfilePktsFc4High32 indicates the higher 32
         bits of the value of vRtrLdpInProfilePktsFc4."
    ::= { vRtrLdpEgrStatisticsEntry 15 }

vRtrLdpInProfilePktsFc5          OBJECT-TYPE
    SYNTAX      Counter64
    MAX-ACCESS  read-only
    STATUS      current
    DESCRIPTION
        "The value of vRtrLdpInProfilePktsFc5 indicates the number of in
         profile packets received for Forwarding Class 5."
    ::= { vRtrLdpEgrStatisticsEntry 16 }

vRtrLdpInProfilePktsFc5Low32     OBJECT-TYPE
    SYNTAX      Counter32
    MAX-ACCESS  read-only
    STATUS      current
    DESCRIPTION
        "The value of vRtrLdpInProfilePktsFc5Low32 indicates the lower 32 bits
         of the value of vRtrLdpInProfilePktsFc5."
    ::= { vRtrLdpEgrStatisticsEntry 17 }

vRtrLdpInProfilePktsFc5High32    OBJECT-TYPE
    SYNTAX      Counter32
    MAX-ACCESS  read-only
    STATUS      current
    DESCRIPTION
        "The value of vRtrLdpInProfilePktsFc5High32 indicates the higher 32
         bits of the value of vRtrLdpInProfilePktsFc5."
    ::= { vRtrLdpEgrStatisticsEntry 18 }

vRtrLdpInProfilePktsFc6          OBJECT-TYPE
    SYNTAX      Counter64
    MAX-ACCESS  read-only
    STATUS      current
    DESCRIPTION
        "The value of vRtrLdpInProfilePktsFc6 indicates the number of in
         profile packets received for Forwarding Class 6."
    ::= { vRtrLdpEgrStatisticsEntry 19 }

vRtrLdpInProfilePktsFc6Low32     OBJECT-TYPE
    SYNTAX      Counter32
    MAX-ACCESS  read-only
    STATUS      current
    DESCRIPTION
        "The value of vRtrLdpInProfilePktsFc6Low32 indicates the lower 32 bits
         of the value of vRtrLdpInProfilePktsFc6."
    ::= { vRtrLdpEgrStatisticsEntry 20 }

vRtrLdpInProfilePktsFc6High32    OBJECT-TYPE
    SYNTAX      Counter32
    MAX-ACCESS  read-only
    STATUS      current
    DESCRIPTION
        "The value of vRtrLdpInProfilePktsFc6High32 indicates the higher 32
         bits of the value of vRtrLdpInProfilePktsFc6."
    ::= { vRtrLdpEgrStatisticsEntry 21 }

vRtrLdpInProfilePktsFc7          OBJECT-TYPE
    SYNTAX      Counter64
    MAX-ACCESS  read-only
    STATUS      current
    DESCRIPTION
        "The value of vRtrLdpInProfilePktsFc7 indicates the number of in
         profile packets received for Forwarding Class 7."
    ::= { vRtrLdpEgrStatisticsEntry 22 }

vRtrLdpInProfilePktsFc7Low32     OBJECT-TYPE
    SYNTAX      Counter32
    MAX-ACCESS  read-only
    STATUS      current
    DESCRIPTION
        "The value of vRtrLdpInProfilePktsFc7Low32 indicates the lower 32 bits
         of the value of vRtrLdpInProfilePktsFc7."
    ::= { vRtrLdpEgrStatisticsEntry 23 }

vRtrLdpInProfilePktsFc7High32    OBJECT-TYPE
    SYNTAX      Counter32
    MAX-ACCESS  read-only
    STATUS      current
    DESCRIPTION
        "The value of vRtrLdpInProfilePktsFc7High32 indicates the higher 32
         bits of the value of vRtrLdpInProfilePktsFc7."
    ::= { vRtrLdpEgrStatisticsEntry 24 }

vRtrLdpInProfileOctetsFc0        OBJECT-TYPE
    SYNTAX      Counter64
    MAX-ACCESS  read-only
    STATUS      current
    DESCRIPTION
        "The value of vRtrLdpInProfileOctetsFc0 indicates the number of in
         profile octets received for Forwarding Class 0."
    ::= { vRtrLdpEgrStatisticsEntry 25 }

vRtrLdpInProfileOctetsFc0Low32   OBJECT-TYPE
    SYNTAX      Counter32
    MAX-ACCESS  read-only
    STATUS      current
    DESCRIPTION
        "The value of vRtrLdpInProfileOctetsFc0Low32 indicates the lower 32
         bits of the value of vRtrLdpInProfileOctetsFc0."
    ::= { vRtrLdpEgrStatisticsEntry 26 }

vRtrLdpInProfileOctetsFc0High32  OBJECT-TYPE
    SYNTAX      Counter32
    MAX-ACCESS  read-only
    STATUS      current
    DESCRIPTION
        "The value of vRtrLdpInProfileOctetsFc0High32 indicates the higher 32
         bits of the value of vRtrLdpInProfileOctetsFc0."
    ::= { vRtrLdpEgrStatisticsEntry 27 }

vRtrLdpInProfileOctetsFc1        OBJECT-TYPE
    SYNTAX      Counter64
    MAX-ACCESS  read-only
    STATUS      current
    DESCRIPTION
        "The value of vRtrLdpInProfileOctetsFc1 indicates the number of in
         profile octets received for Forwarding Class 1."
    ::= { vRtrLdpEgrStatisticsEntry 28 }

vRtrLdpInProfileOctetsFc1Low32   OBJECT-TYPE
    SYNTAX      Counter32
    MAX-ACCESS  read-only
    STATUS      current
    DESCRIPTION
        "The value of vRtrLdpInProfileOctetsFc1Low32 indicates the lower 32
         bits of the value of vRtrLdpInProfileOctetsFc1."
    ::= { vRtrLdpEgrStatisticsEntry 29 }

vRtrLdpInProfileOctetsFc1High32  OBJECT-TYPE
    SYNTAX      Counter32
    MAX-ACCESS  read-only
    STATUS      current
    DESCRIPTION
        "The value of vRtrLdpInProfileOctetsFc1High32 indicates the higher 32
         bits of the value of vRtrLdpInProfileOctetsFc1."
    ::= { vRtrLdpEgrStatisticsEntry 30 }

vRtrLdpInProfileOctetsFc2        OBJECT-TYPE
    SYNTAX      Counter64
    MAX-ACCESS  read-only
    STATUS      current
    DESCRIPTION
        "The value of vRtrLdpInProfileOctetsFc2 indicates the number of in
         profile octets received for Forwarding Class 2."
    ::= { vRtrLdpEgrStatisticsEntry 31 }

vRtrLdpInProfileOctetsFc2Low32   OBJECT-TYPE
    SYNTAX      Counter32
    MAX-ACCESS  read-only
    STATUS      current
    DESCRIPTION
        "The value of vRtrLdpInProfileOctetsFc2Low32 indicates the lower 32
         bits of the value of vRtrLdpInProfileOctetsFc2."
    ::= { vRtrLdpEgrStatisticsEntry 32 }

vRtrLdpInProfileOctetsFc2High32  OBJECT-TYPE
    SYNTAX      Counter32
    MAX-ACCESS  read-only
    STATUS      current
    DESCRIPTION
        "The value of vRtrLdpInProfileOctetsFc2High32 indicates the higher 32
         bits of the value of vRtrLdpInProfileOctetsFc2."
    ::= { vRtrLdpEgrStatisticsEntry 33 }

vRtrLdpInProfileOctetsFc3        OBJECT-TYPE
    SYNTAX      Counter64
    MAX-ACCESS  read-only
    STATUS      current
    DESCRIPTION
        "The value of vRtrLdpInProfileOctetsFc3 indicates the number of in
         profile octets received for Forwarding Class 3."
    ::= { vRtrLdpEgrStatisticsEntry 34 }

vRtrLdpInProfileOctetsFc3Low32   OBJECT-TYPE
    SYNTAX      Counter32
    MAX-ACCESS  read-only
    STATUS      current
    DESCRIPTION
        "The value of vRtrLdpInProfileOctetsFc3Low32 indicates the lower 32
         bits of the value of vRtrLdpInProfileOctetsFc3."
    ::= { vRtrLdpEgrStatisticsEntry 35 }

vRtrLdpInProfileOctetsFc3High32  OBJECT-TYPE
    SYNTAX      Counter32
    MAX-ACCESS  read-only
    STATUS      current
    DESCRIPTION
        "The value of vRtrLdpInProfileOctetsFc3High32 indicates the higher 32
         bits of the value of vRtrLdpInProfileOctetsFc3."
    ::= { vRtrLdpEgrStatisticsEntry 36 }

vRtrLdpInProfileOctetsFc4        OBJECT-TYPE
    SYNTAX      Counter64
    MAX-ACCESS  read-only
    STATUS      current
    DESCRIPTION
        "The value of vRtrLdpInProfileOctetsFc4 indicates the number of in
         profile octets received for Forwarding Class 4."
    ::= { vRtrLdpEgrStatisticsEntry 37 }

vRtrLdpInProfileOctetsFc4Low32   OBJECT-TYPE
    SYNTAX      Counter32
    MAX-ACCESS  read-only
    STATUS      current
    DESCRIPTION
        "The value of vRtrLdpInProfileOctetsFc4Low32 indicates the lower 32
         bits of the value of vRtrLdpInProfileOctetsFc4."
    ::= { vRtrLdpEgrStatisticsEntry 38 }

vRtrLdpInProfileOctetsFc4High32  OBJECT-TYPE
    SYNTAX      Counter32
    MAX-ACCESS  read-only
    STATUS      current
    DESCRIPTION
        "The value of vRtrLdpInProfileOctetsFc4High32 indicates the higher 32
         bits of the value of vRtrLdpInProfileOctetsFc4."
    ::= { vRtrLdpEgrStatisticsEntry 39 }

vRtrLdpInProfileOctetsFc5        OBJECT-TYPE
    SYNTAX      Counter64
    MAX-ACCESS  read-only
    STATUS      current
    DESCRIPTION
        "The value of vRtrLdpInProfileOctetsFc5 indicates the number of in
         profile octets received for Forwarding Class 5."
    ::= { vRtrLdpEgrStatisticsEntry 40 }

vRtrLdpInProfileOctetsFc5Low32   OBJECT-TYPE
    SYNTAX      Counter32
    MAX-ACCESS  read-only
    STATUS      current
    DESCRIPTION
        "The value of vRtrLdpInProfileOctetsFc5Low32 indicates the lower 32
         bits of the value of vRtrLdpInProfileOctetsFc5."
    ::= { vRtrLdpEgrStatisticsEntry 41 }

vRtrLdpInProfileOctetsFc5High32  OBJECT-TYPE
    SYNTAX      Counter32
    MAX-ACCESS  read-only
    STATUS      current
    DESCRIPTION
        "The value of vRtrLdpInProfileOctetsFc5High32 indicates the higher 32
         bits of the value of vRtrLdpInProfileOctetsFc5."
    ::= { vRtrLdpEgrStatisticsEntry 42 }

vRtrLdpInProfileOctetsFc6        OBJECT-TYPE
    SYNTAX      Counter64
    MAX-ACCESS  read-only
    STATUS      current
    DESCRIPTION
        "The value of vRtrLdpInProfileOctetsFc6 indicates the number of in
         profile octets received for Forwarding Class 6."
    ::= { vRtrLdpEgrStatisticsEntry 43 }

vRtrLdpInProfileOctetsFc6Low32   OBJECT-TYPE
    SYNTAX      Counter32
    MAX-ACCESS  read-only
    STATUS      current
    DESCRIPTION
        "The value of vRtrLdpInProfileOctetsFc6Low32 indicates the lower 32
         bits of the value of vRtrLdpInProfileOctetsFc6."
    ::= { vRtrLdpEgrStatisticsEntry 44 }

vRtrLdpInProfileOctetsFc6High32  OBJECT-TYPE
    SYNTAX      Counter32
    MAX-ACCESS  read-only
    STATUS      current
    DESCRIPTION
        "The value of vRtrLdpInProfileOctetsFc6High32 indicates the higher 32
         bits of the value of vRtrLdpInProfileOctetsFc6."
    ::= { vRtrLdpEgrStatisticsEntry 45 }

vRtrLdpInProfileOctetsFc7        OBJECT-TYPE
    SYNTAX      Counter64
    MAX-ACCESS  read-only
    STATUS      current
    DESCRIPTION
        "The value of vRtrLdpInProfileOctetsFc7 indicates the number of in
         profile octets received for Forwarding Class 7."
    ::= { vRtrLdpEgrStatisticsEntry 46 }

vRtrLdpInProfileOctetsFc7Low32   OBJECT-TYPE
    SYNTAX      Counter32
    MAX-ACCESS  read-only
    STATUS      current
    DESCRIPTION
        "The value of vRtrLdpInProfileOctetsFc7Low32 indicates the lower 32
         bits of the value of vRtrLdpInProfileOctetsFc7."
    ::= { vRtrLdpEgrStatisticsEntry 47 }

vRtrLdpInProfileOctetsFc7High32  OBJECT-TYPE
    SYNTAX      Counter32
    MAX-ACCESS  read-only
    STATUS      current
    DESCRIPTION
        "The value of vRtrLdpInProfileOctetsFc7High32 indicates the higher 32
         bits of the value of vRtrLdpInProfileOctetsFc7."
    ::= { vRtrLdpEgrStatisticsEntry 48 }

vRtrLdpOutOfProfPktsFc0          OBJECT-TYPE
    SYNTAX      Counter64
    MAX-ACCESS  read-only
    STATUS      current
    DESCRIPTION
        "The value of vRtrLdpOutOfProfPktsFc0 indicates the number of out of
         profile packets received for Forwarding Class 0."
    ::= { vRtrLdpEgrStatisticsEntry 49 }

vRtrLdpOutOfProfPktsFc0Low32     OBJECT-TYPE
    SYNTAX      Counter32
    MAX-ACCESS  read-only
    STATUS      current
    DESCRIPTION
        "The value of vRtrLdpOutOfProfPktsFc0Low32 indicates the lower 32 bits
         of the value of vRtrLdpOutOfProfPktsFc0."
    ::= { vRtrLdpEgrStatisticsEntry 50 }

vRtrLdpOutOfProfPktsFc0High32    OBJECT-TYPE
    SYNTAX      Counter32
    MAX-ACCESS  read-only
    STATUS      current
    DESCRIPTION
        "The value of vRtrLdpOutOfProfPktsFc0High32 indicates the higher 32
         bits of the value of vRtrLdpOutOfProfPktsFc0."
    ::= { vRtrLdpEgrStatisticsEntry 51 }

vRtrLdpOutOfProfPktsFc1          OBJECT-TYPE
    SYNTAX      Counter64
    MAX-ACCESS  read-only
    STATUS      current
    DESCRIPTION
        "The value of vRtrLdpOutOfProfPktsFc1 indicates the number of out of
         profile packets received for Forwarding Class 1."
    ::= { vRtrLdpEgrStatisticsEntry 52 }

vRtrLdpOutOfProfPktsFc1Low32     OBJECT-TYPE
    SYNTAX      Counter32
    MAX-ACCESS  read-only
    STATUS      current
    DESCRIPTION
        "The value of vRtrLdpOutOfProfPktsFc1Low32 indicates the lower 32 bits
         of the value of vRtrLdpOutOfProfPktsFc1."
    ::= { vRtrLdpEgrStatisticsEntry 53 }

vRtrLdpOutOfProfPktsFc1High32    OBJECT-TYPE
    SYNTAX      Counter32
    MAX-ACCESS  read-only
    STATUS      current
    DESCRIPTION
        "The value of vRtrLdpOutOfProfPktsFc1High32 indicates the higher 32
         bits of the value of vRtrLdpOutOfProfPktsFc1."
    ::= { vRtrLdpEgrStatisticsEntry 54 }

vRtrLdpOutOfProfPktsFc2          OBJECT-TYPE
    SYNTAX      Counter64
    MAX-ACCESS  read-only
    STATUS      current
    DESCRIPTION
        "The value of vRtrLdpOutOfProfPktsFc2 indicates the number of out of
         profile packets received for Forwarding Class 2."
    ::= { vRtrLdpEgrStatisticsEntry 55 }

vRtrLdpOutOfProfPktsFc2Low32     OBJECT-TYPE
    SYNTAX      Counter32
    MAX-ACCESS  read-only
    STATUS      current
    DESCRIPTION
        "The value of vRtrLdpOutOfProfPktsFc2Low32 indicates the lower 32 bits
         of the value of vRtrLdpOutOfProfPktsFc2."
    ::= { vRtrLdpEgrStatisticsEntry 56 }

vRtrLdpOutOfProfPktsFc2High32    OBJECT-TYPE
    SYNTAX      Counter32
    MAX-ACCESS  read-only
    STATUS      current
    DESCRIPTION
        "The value of vRtrLdpOutOfProfPktsFc2High32 indicates the higher 32
         bits of the value of vRtrLdpOutOfProfPktsFc2."
    ::= { vRtrLdpEgrStatisticsEntry 57 }

vRtrLdpOutOfProfPktsFc3          OBJECT-TYPE
    SYNTAX      Counter64
    MAX-ACCESS  read-only
    STATUS      current
    DESCRIPTION
        "The value of vRtrLdpOutOfProfPktsFc3 indicates the number of out of
         profile packets received for Forwarding Class 3."
    ::= { vRtrLdpEgrStatisticsEntry 58 }

vRtrLdpOutOfProfPktsFc3Low32     OBJECT-TYPE
    SYNTAX      Counter32
    MAX-ACCESS  read-only
    STATUS      current
    DESCRIPTION
        "The value of vRtrLdpOutOfProfPktsFc3Low32 indicates the lower 32 bits
         of the value of vRtrLdpOutOfProfPktsFc3."
    ::= { vRtrLdpEgrStatisticsEntry 59 }

vRtrLdpOutOfProfPktsFc3High32    OBJECT-TYPE
    SYNTAX      Counter32
    MAX-ACCESS  read-only
    STATUS      current
    DESCRIPTION
        "The value of vRtrLdpOutOfProfPktsFc3High32 indicates the higher 32
         bits of the value of vRtrLdpOutOfProfPktsFc3."
    ::= { vRtrLdpEgrStatisticsEntry 60 }

vRtrLdpOutOfProfPktsFc4          OBJECT-TYPE
    SYNTAX      Counter64
    MAX-ACCESS  read-only
    STATUS      current
    DESCRIPTION
        "The value of vRtrLdpOutOfProfPktsFc4 indicates the number of out of
         profile packets received for Forwarding Class 4."
    ::= { vRtrLdpEgrStatisticsEntry 61 }

vRtrLdpOutOfProfPktsFc4Low32     OBJECT-TYPE
    SYNTAX      Counter32
    MAX-ACCESS  read-only
    STATUS      current
    DESCRIPTION
        "The value of vRtrLdpOutOfProfPktsFc4Low32 indicates the lower 32 bits
         of the value of vRtrLdpOutOfProfPktsFc4."
    ::= { vRtrLdpEgrStatisticsEntry 62 }

vRtrLdpOutOfProfPktsFc4High32    OBJECT-TYPE
    SYNTAX      Counter32
    MAX-ACCESS  read-only
    STATUS      current
    DESCRIPTION
        "The value of vRtrLdpOutOfProfPktsFc4High32 indicates the higher 32
         bits of the value of vRtrLdpOutOfProfPktsFc4."
    ::= { vRtrLdpEgrStatisticsEntry 63 }

vRtrLdpOutOfProfPktsFc5          OBJECT-TYPE
    SYNTAX      Counter64
    MAX-ACCESS  read-only
    STATUS      current
    DESCRIPTION
        "The value of vRtrLdpOutOfProfPktsFc5 indicates the number of out of
         profile packets received for Forwarding Class 5."
    ::= { vRtrLdpEgrStatisticsEntry 64 }

vRtrLdpOutOfProfPktsFc5Low32     OBJECT-TYPE
    SYNTAX      Counter32
    MAX-ACCESS  read-only
    STATUS      current
    DESCRIPTION
        "The value of vRtrLdpOutOfProfPktsFc5Low32 indicates the lower 32 bits
         of the value of vRtrLdpOutOfProfPktsFc5."
    ::= { vRtrLdpEgrStatisticsEntry 65 }

vRtrLdpOutOfProfPktsFc5High32    OBJECT-TYPE
    SYNTAX      Counter32
    MAX-ACCESS  read-only
    STATUS      current
    DESCRIPTION
        "The value of vRtrLdpOutOfProfPktsFc5High32 indicates the higher 32
         bits of the value of vRtrLdpOutOfProfPktsFc5."
    ::= { vRtrLdpEgrStatisticsEntry 66 }

vRtrLdpOutOfProfPktsFc6          OBJECT-TYPE
    SYNTAX      Counter64
    MAX-ACCESS  read-only
    STATUS      current
    DESCRIPTION
        "The value of vRtrLdpOutOfProfPktsFc6 indicates the number of out of
         profile packets received for Forwarding Class 6."
    ::= { vRtrLdpEgrStatisticsEntry 67 }

vRtrLdpOutOfProfPktsFc6Low32     OBJECT-TYPE
    SYNTAX      Counter32
    MAX-ACCESS  read-only
    STATUS      current
    DESCRIPTION
        "The value of vRtrLdpOutOfProfPktsFc6Low32 indicates the lower 32 bits
         of the value of vRtrLdpOutOfProfPktsFc6."
    ::= { vRtrLdpEgrStatisticsEntry 68 }

vRtrLdpOutOfProfPktsFc6High32    OBJECT-TYPE
    SYNTAX      Counter32
    MAX-ACCESS  read-only
    STATUS      current
    DESCRIPTION
        "The value of vRtrLdpOutOfProfPktsFc6High32 indicates the higher 32
         bits of the value of vRtrLdpOutOfProfPktsFc6."
    ::= { vRtrLdpEgrStatisticsEntry 69 }

vRtrLdpOutOfProfPktsFc7          OBJECT-TYPE
    SYNTAX      Counter64
    MAX-ACCESS  read-only
    STATUS      current
    DESCRIPTION
        "The value of vRtrLdpOutOfProfPktsFc7 indicates the number of out of
         profile packets received for Forwarding Class 7."
    ::= { vRtrLdpEgrStatisticsEntry 70 }

vRtrLdpOutOfProfPktsFc7Low32     OBJECT-TYPE
    SYNTAX      Counter32
    MAX-ACCESS  read-only
    STATUS      current
    DESCRIPTION
        "The value of vRtrLdpOutOfProfPktsFc7Low32 indicates the lower 32 bits
         of the value of vRtrLdpOutOfProfPktsFc7."
    ::= { vRtrLdpEgrStatisticsEntry 71 }

vRtrLdpOutOfProfPktsFc7High32    OBJECT-TYPE
    SYNTAX      Counter32
    MAX-ACCESS  read-only
    STATUS      current
    DESCRIPTION
        "The value of vRtrLdpOutOfProfPktsFc7High32 indicates the higher 32
         bits of the value of vRtrLdpOutOfProfPktsFc7."
    ::= { vRtrLdpEgrStatisticsEntry 72 }

vRtrLdpOutOfProfOctetsFc0        OBJECT-TYPE
    SYNTAX      Counter64
    MAX-ACCESS  read-only
    STATUS      current
    DESCRIPTION
        "The value of vRtrLdpOutOfProfOctetsFc0 indicates the number of out of
         profile octets received for Forwarding Class 0."
    ::= { vRtrLdpEgrStatisticsEntry 73 }

vRtrLdpOutOfProfOctetsFc0Low32   OBJECT-TYPE
    SYNTAX      Counter32
    MAX-ACCESS  read-only
    STATUS      current
    DESCRIPTION
        "The value of vRtrLdpOutOfProfOctetsFc0Low32 indicates the lower 32
         bits of the value of vRtrLdpOutOfProfOctetsFc0."
    ::= { vRtrLdpEgrStatisticsEntry 74 }

vRtrLdpOutOfProfOctetsFc0High32  OBJECT-TYPE
    SYNTAX      Counter32
    MAX-ACCESS  read-only
    STATUS      current
    DESCRIPTION
        "The value of vRtrLdpOutOfProfOctetsFc0High32 indicates the higher 32
         bits of the value of vRtrLdpOutOfProfOctetsFc0."
    ::= { vRtrLdpEgrStatisticsEntry 75 }

vRtrLdpOutOfProfOctetsFc1        OBJECT-TYPE
    SYNTAX      Counter64
    MAX-ACCESS  read-only
    STATUS      current
    DESCRIPTION
        "The value of vRtrLdpOutOfProfOctetsFc1 indicates the number of out of
         profile octets received for Forwarding Class 1."
    ::= { vRtrLdpEgrStatisticsEntry 76 }

vRtrLdpOutOfProfOctetsFc1Low32   OBJECT-TYPE
    SYNTAX      Counter32
    MAX-ACCESS  read-only
    STATUS      current
    DESCRIPTION
        "The value of vRtrLdpOutOfProfOctetsFc1Low32 indicates the lower 32
         bits of the value of vRtrLdpOutOfProfOctetsFc1."
    ::= { vRtrLdpEgrStatisticsEntry 77 }

vRtrLdpOutOfProfOctetsFc1High32  OBJECT-TYPE
    SYNTAX      Counter32
    MAX-ACCESS  read-only
    STATUS      current
    DESCRIPTION
        "The value of vRtrLdpOutOfProfOctetsFc1High32 indicates the higher 32
         bits of the value of vRtrLdpOutOfProfOctetsFc1."
    ::= { vRtrLdpEgrStatisticsEntry 78 }

vRtrLdpOutOfProfOctetsFc2        OBJECT-TYPE
    SYNTAX      Counter64
    MAX-ACCESS  read-only
    STATUS      current
    DESCRIPTION
        "The value of vRtrLdpOutOfProfOctetsFc2 indicates the number of out of
         profile octets received for Forwarding Class 2."
    ::= { vRtrLdpEgrStatisticsEntry 79 }

vRtrLdpOutOfProfOctetsFc2Low32   OBJECT-TYPE
    SYNTAX      Counter32
    MAX-ACCESS  read-only
    STATUS      current
    DESCRIPTION
        "The value of vRtrLdpOutOfProfOctetsFc2Low32 indicates the lower 32
         bits of the value of vRtrLdpOutOfProfOctetsFc2."
    ::= { vRtrLdpEgrStatisticsEntry 80 }

vRtrLdpOutOfProfOctetsFc2High32  OBJECT-TYPE
    SYNTAX      Counter32
    MAX-ACCESS  read-only
    STATUS      current
    DESCRIPTION
        "The value of vRtrLdpOutOfProfOctetsFc2High32 indicates the higher 32
         bits of the value of vRtrLdpOutOfProfOctetsFc2."
    ::= { vRtrLdpEgrStatisticsEntry 81 }

vRtrLdpOutOfProfOctetsFc3        OBJECT-TYPE
    SYNTAX      Counter64
    MAX-ACCESS  read-only
    STATUS      current
    DESCRIPTION
        "The value of vRtrLdpOutOfProfOctetsFc3 indicates the number of out of
         profile octets received for Forwarding Class 3."
    ::= { vRtrLdpEgrStatisticsEntry 82 }

vRtrLdpOutOfProfOctetsFc3Low32   OBJECT-TYPE
    SYNTAX      Counter32
    MAX-ACCESS  read-only
    STATUS      current
    DESCRIPTION
        "The value of vRtrLdpOutOfProfOctetsFc3Low32 indicates the lower 32
         bits of the value of vRtrLdpOutOfProfOctetsFc3."
    ::= { vRtrLdpEgrStatisticsEntry 83 }

vRtrLdpOutOfProfOctetsFc3High32  OBJECT-TYPE
    SYNTAX      Counter32
    MAX-ACCESS  read-only
    STATUS      current
    DESCRIPTION
        "The value of vRtrLdpOutOfProfOctetsFc3High32 indicates the higher 32
         bits of the value of vRtrLdpOutOfProfOctetsFc3."
    ::= { vRtrLdpEgrStatisticsEntry 84 }

vRtrLdpOutOfProfOctetsFc4        OBJECT-TYPE
    SYNTAX      Counter64
    MAX-ACCESS  read-only
    STATUS      current
    DESCRIPTION
        "The value of vRtrLdpOutOfProfOctetsFc4 indicates the number of out of
         profile octets received for Forwarding Class 4."
    ::= { vRtrLdpEgrStatisticsEntry 85 }

vRtrLdpOutOfProfOctetsFc4Low32   OBJECT-TYPE
    SYNTAX      Counter32
    MAX-ACCESS  read-only
    STATUS      current
    DESCRIPTION
        "The value of vRtrLdpOutOfProfOctetsFc4Low32 indicates the lower 32
         bits of the value of vRtrLdpOutOfProfOctetsFc4."
    ::= { vRtrLdpEgrStatisticsEntry 86 }

vRtrLdpOutOfProfOctetsFc4High32  OBJECT-TYPE
    SYNTAX      Counter32
    MAX-ACCESS  read-only
    STATUS      current
    DESCRIPTION
        "The value of vRtrLdpOutOfProfOctetsFc4High32 indicates the higher 32
         bits of the value of vRtrLdpOutOfProfOctetsFc4."
    ::= { vRtrLdpEgrStatisticsEntry 87 }

vRtrLdpOutOfProfOctetsFc5        OBJECT-TYPE
    SYNTAX      Counter64
    MAX-ACCESS  read-only
    STATUS      current
    DESCRIPTION
        "The value of vRtrLdpOutOfProfOctetsFc5 indicates the number of out of
         profile octets received for Forwarding Class 5."
    ::= { vRtrLdpEgrStatisticsEntry 88 }

vRtrLdpOutOfProfOctetsFc5Low32   OBJECT-TYPE
    SYNTAX      Counter32
    MAX-ACCESS  read-only
    STATUS      current
    DESCRIPTION
        "The value of vRtrLdpOutOfProfOctetsFc5Low32 indicates the lower 32
         bits of the value of vRtrLdpOutOfProfOctetsFc5."
    ::= { vRtrLdpEgrStatisticsEntry 89 }

vRtrLdpOutOfProfOctetsFc5High32  OBJECT-TYPE
    SYNTAX      Counter32
    MAX-ACCESS  read-only
    STATUS      current
    DESCRIPTION
        "The value of vRtrLdpOutOfProfOctetsFc5High32 indicates the higher 32
         bits of the value of vRtrLdpOutOfProfOctetsFc5."
    ::= { vRtrLdpEgrStatisticsEntry 90 }

vRtrLdpOutOfProfOctetsFc6        OBJECT-TYPE
    SYNTAX      Counter64
    MAX-ACCESS  read-only
    STATUS      current
    DESCRIPTION
        "The value of vRtrLdpOutOfProfOctetsFc6 indicates the number of out of
         profile octets received for Forwarding Class 6."
    ::= { vRtrLdpEgrStatisticsEntry 91 }

vRtrLdpOutOfProfOctetsFc6Low32   OBJECT-TYPE
    SYNTAX      Counter32
    MAX-ACCESS  read-only
    STATUS      current
    DESCRIPTION
        "The value of vRtrLdpOutOfProfOctetsFc6Low32 indicates the lower 32
         bits of the value of vRtrLdpOutOfProfOctetsFc6."
    ::= { vRtrLdpEgrStatisticsEntry 92 }

vRtrLdpOutOfProfOctetsFc6High32  OBJECT-TYPE
    SYNTAX      Counter32
    MAX-ACCESS  read-only
    STATUS      current
    DESCRIPTION
        "The value of vRtrLdpOutOfProfOctetsFc6High32 indicates the higher 32
         bits of the value of vRtrLdpOutOfProfOctetsFc6."
    ::= { vRtrLdpEgrStatisticsEntry 93 }

vRtrLdpOutOfProfOctetsFc7        OBJECT-TYPE
    SYNTAX      Counter64
    MAX-ACCESS  read-only
    STATUS      current
    DESCRIPTION
        "The value of vRtrLdpOutOfProfOctetsFc7 indicates the number of out of
         profile octets received for Forwarding Class 7."
    ::= { vRtrLdpEgrStatisticsEntry 94 }

vRtrLdpOutOfProfOctetsFc7Low32   OBJECT-TYPE
    SYNTAX      Counter32
    MAX-ACCESS  read-only
    STATUS      current
    DESCRIPTION
        "The value of vRtrLdpOutOfProfOctetsFc7Low32 indicates the lower 32
         bits of the value of vRtrLdpOutOfProfOctetsFc7."
    ::= { vRtrLdpEgrStatisticsEntry 95 }

vRtrLdpOutOfProfOctetsFc7High32  OBJECT-TYPE
    SYNTAX      Counter32
    MAX-ACCESS  read-only
    STATUS      current
    DESCRIPTION
        "The value of vRtrLdpOutOfProfOctetsFc7High32 indicates the higher 32
         bits of the value of vRtrLdpOutOfProfOctetsFc7."
    ::= { vRtrLdpEgrStatisticsEntry 96 }

vRtrLdpAggregatePkts             OBJECT-TYPE
    SYNTAX      Counter64
    MAX-ACCESS  read-only
    STATUS      current
    DESCRIPTION
        "The value of vRtrLdpAggregatePkts indicates the number of packets sent
         for the FEC."
    ::= { vRtrLdpEgrStatisticsEntry 97 }

vRtrLdpAggregatePktsLow32        OBJECT-TYPE
    SYNTAX      Counter32
    MAX-ACCESS  read-only
    STATUS      current
    DESCRIPTION
        "The value of vRtrLdpAggregatePktsLow32 indicates the lower 32 bits of
         the value of vRtrLdpAggregatePkts."
    ::= { vRtrLdpEgrStatisticsEntry 98 }

vRtrLdpAggregatePktsHigh32       OBJECT-TYPE
    SYNTAX      Counter32
    MAX-ACCESS  read-only
    STATUS      current
    DESCRIPTION
        "The value of vRtrLdpAggregatePktsHigh32 indicates the higher 32 bits
         of the value of vRtrLdpAggregatePkts."
    ::= { vRtrLdpEgrStatisticsEntry 99 }

vRtrLdpAggregateOctets           OBJECT-TYPE
    SYNTAX      Counter64
    MAX-ACCESS  read-only
    STATUS      current
    DESCRIPTION
        "The value of vRtrLdpAggregateOctets indicates the number of octets
         sent for the FEC."
    ::= { vRtrLdpEgrStatisticsEntry 100 }

vRtrLdpAggregateOctetsLow32      OBJECT-TYPE
    SYNTAX      Counter32
    MAX-ACCESS  read-only
    STATUS      current
    DESCRIPTION
        "The value of vRtrLdpAggregateOctetsLow32 indicates the lower 32 bits
         of the value of vRtrLdpAggregateOctets."
    ::= { vRtrLdpEgrStatisticsEntry 101 }

vRtrLdpAggregateOctetsHigh32     OBJECT-TYPE
    SYNTAX      Counter32
    MAX-ACCESS  read-only
    STATUS      current
    DESCRIPTION
        "The value of vRtrLdpAggregateOctetsHigh32 indicates the higher 32 bits
         of the value of vRtrLdpAggregateOctets."
    ::= { vRtrLdpEgrStatisticsEntry 102 }

vRtrLdpAddrFecExtTable           OBJECT-TYPE
    SYNTAX      SEQUENCE OF VRtrLdpAddrFecExtEntry
    MAX-ACCESS  not-accessible
    STATUS      obsolete
    DESCRIPTION
        "The vRtrLdpAddrFecExtTable has an entry with few fields which are
         extensions for all address FECs either sent to or received from an LDP
         peer known to the Virtual Router."
    ::= { tmnxLdpObjs 30 }

vRtrLdpAddrFecExtEntry           OBJECT-TYPE
    SYNTAX      VRtrLdpAddrFecExtEntry
    MAX-ACCESS  not-accessible
    STATUS      obsolete
    DESCRIPTION
        "Each row entry represents an instance of an extension to address FEC
         sent to or received from an LDP peer.

         Entries cannot be created and deleted via SNMP SET operations."
    AUGMENTS    { vRtrLdpAddrFecEntry }
    ::= { vRtrLdpAddrFecExtTable 1 }

VRtrLdpAddrFecExtEntry           ::= SEQUENCE
{
    vRtrLdpAddrFecOutLbl6            Unsigned32,
    vRtrLdpAddrFecOutLblStatus6      TmnxLabelStatus,
    vRtrLdpAddrFecOutLblIfIndex6     InterfaceIndexOrZero,
    vRtrLdpAddrFecOutLblNxtHopType6  InetAddressType,
    vRtrLdpAddrFecOutLblNxtHopAddr6  InetAddress,
    vRtrLdpAddrFecLspId6             TmnxVRtrMplsLspID,
    vRtrLdpAddrFecOutLbl7            Unsigned32,
    vRtrLdpAddrFecOutLblStatus7      TmnxLabelStatus,
    vRtrLdpAddrFecOutLblIfIndex7     InterfaceIndexOrZero,
    vRtrLdpAddrFecOutLblNxtHopType7  InetAddressType,
    vRtrLdpAddrFecOutLblNxtHopAddr7  InetAddress,
    vRtrLdpAddrFecLspId7             TmnxVRtrMplsLspID,
    vRtrLdpAddrFecOutLbl8            Unsigned32,
    vRtrLdpAddrFecOutLblStatus8      TmnxLabelStatus,
    vRtrLdpAddrFecOutLblIfIndex8     InterfaceIndexOrZero,
    vRtrLdpAddrFecOutLblNxtHopType8  InetAddressType,
    vRtrLdpAddrFecOutLblNxtHopAddr8  InetAddress,
    vRtrLdpAddrFecLspId8             TmnxVRtrMplsLspID,
    vRtrLdpAddrFecOutLbl9            Unsigned32,
    vRtrLdpAddrFecOutLblStatus9      TmnxLabelStatus,
    vRtrLdpAddrFecOutLblIfIndex9     InterfaceIndexOrZero,
    vRtrLdpAddrFecOutLblNxtHopType9  InetAddressType,
    vRtrLdpAddrFecOutLblNxtHopAddr9  InetAddress,
    vRtrLdpAddrFecLspId9             TmnxVRtrMplsLspID,
    vRtrLdpAddrFecOutLbl10           Unsigned32,
    vRtrLdpAddrFecOutLblStatus10     TmnxLabelStatus,
    vRtrLdpAddrFecOutLblIfIndex10    InterfaceIndexOrZero,
    vRtrLdpAddrFecOutLblNxtHopType10 InetAddressType,
    vRtrLdpAddrFecOutLblNxtHopAddr10 InetAddress,
    vRtrLdpAddrFecLspId10            TmnxVRtrMplsLspID,
    vRtrLdpAddrFecOutLbl11           Unsigned32,
    vRtrLdpAddrFecOutLblStatus11     TmnxLabelStatus,
    vRtrLdpAddrFecOutLblIfIndex11    InterfaceIndexOrZero,
    vRtrLdpAddrFecOutLblNxtHopType11 InetAddressType,
    vRtrLdpAddrFecOutLblNxtHopAddr11 InetAddress,
    vRtrLdpAddrFecLspId11            TmnxVRtrMplsLspID,
    vRtrLdpAddrFecOutLbl12           Unsigned32,
    vRtrLdpAddrFecOutLblStatus12     TmnxLabelStatus,
    vRtrLdpAddrFecOutLblIfIndex12    InterfaceIndexOrZero,
    vRtrLdpAddrFecOutLblNxtHopType12 InetAddressType,
    vRtrLdpAddrFecOutLblNxtHopAddr12 InetAddress,
    vRtrLdpAddrFecLspId12            TmnxVRtrMplsLspID,
    vRtrLdpAddrFecOutLbl13           Unsigned32,
    vRtrLdpAddrFecOutLblStatus13     TmnxLabelStatus,
    vRtrLdpAddrFecOutLblIfIndex13    InterfaceIndexOrZero,
    vRtrLdpAddrFecOutLblNxtHopType13 InetAddressType,
    vRtrLdpAddrFecOutLblNxtHopAddr13 InetAddress,
    vRtrLdpAddrFecLspId13            TmnxVRtrMplsLspID,
    vRtrLdpAddrFecOutLbl14           Unsigned32,
    vRtrLdpAddrFecOutLblStatus14     TmnxLabelStatus,
    vRtrLdpAddrFecOutLblIfIndex14    InterfaceIndexOrZero,
    vRtrLdpAddrFecOutLblNxtHopType14 InetAddressType,
    vRtrLdpAddrFecOutLblNxtHopAddr14 InetAddress,
    vRtrLdpAddrFecLspId14            TmnxVRtrMplsLspID,
    vRtrLdpAddrFecOutLbl15           Unsigned32,
    vRtrLdpAddrFecOutLblStatus15     TmnxLabelStatus,
    vRtrLdpAddrFecOutLblIfIndex15    InterfaceIndexOrZero,
    vRtrLdpAddrFecOutLblNxtHopType15 InetAddressType,
    vRtrLdpAddrFecOutLblNxtHopAddr15 InetAddress,
    vRtrLdpAddrFecLspId15            TmnxVRtrMplsLspID,
    vRtrLdpAddrFecOutLbl16           Unsigned32,
    vRtrLdpAddrFecOutLblStatus16     TmnxLabelStatus,
    vRtrLdpAddrFecOutLblIfIndex16    InterfaceIndexOrZero,
    vRtrLdpAddrFecOutLblNxtHopType16 InetAddressType,
    vRtrLdpAddrFecOutLblNxtHopAddr16 InetAddress,
    vRtrLdpAddrFecLspId16            TmnxVRtrMplsLspID
}

vRtrLdpAddrFecOutLbl6            OBJECT-TYPE
    SYNTAX      Unsigned32
    MAX-ACCESS  read-only
    STATUS      obsolete
    DESCRIPTION
        "The value of vRtrLdpAddrFecOutLbl6 specifies the sixth egress label
         exchanged.

         This object was obsoleted in release 10.0."
    ::= { vRtrLdpAddrFecExtEntry 1 }

vRtrLdpAddrFecOutLblStatus6      OBJECT-TYPE
    SYNTAX      TmnxLabelStatus
    MAX-ACCESS  read-only
    STATUS      obsolete
    DESCRIPTION
        "The value of vRtrLdpAddrFecOutLblStatus6 specifies the status of the
         egress label 6.

         This object was obsoleted in release 10.0."
    ::= { vRtrLdpAddrFecExtEntry 2 }

vRtrLdpAddrFecOutLblIfIndex6     OBJECT-TYPE
    SYNTAX      InterfaceIndexOrZero
    MAX-ACCESS  read-only
    STATUS      obsolete
    DESCRIPTION
        "The value of vRtrLdpAddrFecOutLblIfIndex6 specifies the interface
         index for egress label 6.

         This object was obsoleted in release 10.0."
    ::= { vRtrLdpAddrFecExtEntry 3 }

vRtrLdpAddrFecOutLblNxtHopType6  OBJECT-TYPE
    SYNTAX      InetAddressType
    MAX-ACCESS  read-only
    STATUS      obsolete
    DESCRIPTION
        "The value of vRtrLdpAddrFecOutLblNxtHopType6 specifies the address
         type of vRtrLdpAddrFecOutLblNxtHopAddr6.

         This object was obsoleted in release 10.0."
    ::= { vRtrLdpAddrFecExtEntry 4 }

vRtrLdpAddrFecOutLblNxtHopAddr6  OBJECT-TYPE
    SYNTAX      InetAddress (SIZE (4|16))
    MAX-ACCESS  read-only
    STATUS      obsolete
    DESCRIPTION
        "The value of vRtrLdpAddrFecOutLblNxtHopAddr6 specifies the IP address
         of the next hop for egress label 6.

         This object was obsoleted in release 10.0."
    ::= { vRtrLdpAddrFecExtEntry 5 }

vRtrLdpAddrFecLspId6             OBJECT-TYPE
    SYNTAX      TmnxVRtrMplsLspID
    MAX-ACCESS  read-only
    STATUS      obsolete
    DESCRIPTION
        "The value of vRtrLdpAddrFecLspId6 indicates the LSP id of the LSP for
         the RSVP tunnel used by LDP in LDP over RSVP associated with egress
         label 6.

         This object was obsoleted in release 10.0."
    ::= { vRtrLdpAddrFecExtEntry 6 }

vRtrLdpAddrFecOutLbl7            OBJECT-TYPE
    SYNTAX      Unsigned32
    MAX-ACCESS  read-only
    STATUS      obsolete
    DESCRIPTION
        "The value of vRtrLdpAddrFecOutLbl7 specifies the seventh egress label
         exchanged.

         This object was obsoleted in release 10.0."
    ::= { vRtrLdpAddrFecExtEntry 7 }

vRtrLdpAddrFecOutLblStatus7      OBJECT-TYPE
    SYNTAX      TmnxLabelStatus
    MAX-ACCESS  read-only
    STATUS      obsolete
    DESCRIPTION
        "The value of vRtrLdpAddrFecOutLblStatus7 specifies the status of the
         egress label 7.

         This object was obsoleted in release 10.0."
    ::= { vRtrLdpAddrFecExtEntry 8 }

vRtrLdpAddrFecOutLblIfIndex7     OBJECT-TYPE
    SYNTAX      InterfaceIndexOrZero
    MAX-ACCESS  read-only
    STATUS      obsolete
    DESCRIPTION
        "The value of vRtrLdpAddrFecOutLblIfIndex7 specifies the interface
         index for egress label 7.

         This object was obsoleted in release 10.0."
    ::= { vRtrLdpAddrFecExtEntry 9 }

vRtrLdpAddrFecOutLblNxtHopType7  OBJECT-TYPE
    SYNTAX      InetAddressType
    MAX-ACCESS  read-only
    STATUS      obsolete
    DESCRIPTION
        "The value of vRtrLdpAddrFecOutLblNxtHopType7 specifies the address
         type of vRtrLdpAddrFecOutLblNxtHopAddr7.

         This object was obsoleted in release 10.0."
    ::= { vRtrLdpAddrFecExtEntry 10 }

vRtrLdpAddrFecOutLblNxtHopAddr7  OBJECT-TYPE
    SYNTAX      InetAddress (SIZE (4|16))
    MAX-ACCESS  read-only
    STATUS      obsolete
    DESCRIPTION
        "The value of vRtrLdpAddrFecOutLblNxtHopAddr7 specifies the IP address
         of the next hop for egress label 7.

         This object was obsoleted in release 10.0."
    ::= { vRtrLdpAddrFecExtEntry 11 }

vRtrLdpAddrFecLspId7             OBJECT-TYPE
    SYNTAX      TmnxVRtrMplsLspID
    MAX-ACCESS  read-only
    STATUS      obsolete
    DESCRIPTION
        "The value of vRtrLdpAddrFecLspId7 indicates the LSP id of the LSP for
         the RSVP tunnel used by LDP in LDP over RSVP associated with egress
         label 7.

         This object was obsoleted in release 10.0."
    ::= { vRtrLdpAddrFecExtEntry 12 }

vRtrLdpAddrFecOutLbl8            OBJECT-TYPE
    SYNTAX      Unsigned32
    MAX-ACCESS  read-only
    STATUS      obsolete
    DESCRIPTION
        "The value of vRtrLdpAddrFecOutLbl8 specifies the eighth egress label
         exchanged.

         This object was obsoleted in release 10.0."
    ::= { vRtrLdpAddrFecExtEntry 13 }

vRtrLdpAddrFecOutLblStatus8      OBJECT-TYPE
    SYNTAX      TmnxLabelStatus
    MAX-ACCESS  read-only
    STATUS      obsolete
    DESCRIPTION
        "The value of vRtrLdpAddrFecOutLblStatus8 specifies the status of the
         egress label 8.

         This object was obsoleted in release 10.0."
    ::= { vRtrLdpAddrFecExtEntry 14 }

vRtrLdpAddrFecOutLblIfIndex8     OBJECT-TYPE
    SYNTAX      InterfaceIndexOrZero
    MAX-ACCESS  read-only
    STATUS      obsolete
    DESCRIPTION
        "The value of vRtrLdpAddrFecOutLblIfIndex8 specifies the interface
         index for egress label 8.

         This object was obsoleted in release 10.0."
    ::= { vRtrLdpAddrFecExtEntry 15 }

vRtrLdpAddrFecOutLblNxtHopType8  OBJECT-TYPE
    SYNTAX      InetAddressType
    MAX-ACCESS  read-only
    STATUS      obsolete
    DESCRIPTION
        "The value of vRtrLdpAddrFecOutLblNxtHopType8 specifies the address
         type of vRtrLdpAddrFecOutLblNxtHopAddr8.

         This object was obsoleted in release 10.0."
    ::= { vRtrLdpAddrFecExtEntry 16 }

vRtrLdpAddrFecOutLblNxtHopAddr8  OBJECT-TYPE
    SYNTAX      InetAddress (SIZE (4|16))
    MAX-ACCESS  read-only
    STATUS      obsolete
    DESCRIPTION
        "The value of vRtrLdpAddrFecOutLblNxtHopAddr8 specifies the IP address
         of the next hop for egress label 8.

         This object was obsoleted in release 10.0."
    ::= { vRtrLdpAddrFecExtEntry 17 }

vRtrLdpAddrFecLspId8             OBJECT-TYPE
    SYNTAX      TmnxVRtrMplsLspID
    MAX-ACCESS  read-only
    STATUS      obsolete
    DESCRIPTION
        "The value of vRtrLdpAddrFecLspId8 indicates the LSP id of the LSP for
         the RSVP tunnel used by LDP in LDP over RSVP associated with egress
         label 8.

         This object was obsoleted in release 10.0."
    ::= { vRtrLdpAddrFecExtEntry 18 }

vRtrLdpAddrFecOutLbl9            OBJECT-TYPE
    SYNTAX      Unsigned32
    MAX-ACCESS  read-only
    STATUS      obsolete
    DESCRIPTION
        "The value of vRtrLdpAddrFecOutLbl9 specifies the ninth egress label
         exchanged.

         This object was obsoleted in release 10.0."
    ::= { vRtrLdpAddrFecExtEntry 19 }

vRtrLdpAddrFecOutLblStatus9      OBJECT-TYPE
    SYNTAX      TmnxLabelStatus
    MAX-ACCESS  read-only
    STATUS      obsolete
    DESCRIPTION
        "The value of vRtrLdpAddrFecOutLblStatus9 specifies the status of the
         egress label 9.

         This object was obsoleted in release 10.0."
    ::= { vRtrLdpAddrFecExtEntry 20 }

vRtrLdpAddrFecOutLblIfIndex9     OBJECT-TYPE
    SYNTAX      InterfaceIndexOrZero
    MAX-ACCESS  read-only
    STATUS      obsolete
    DESCRIPTION
        "The value of vRtrLdpAddrFecOutLblIfIndex9 specifies the interface
         index for egress label 9.

         This object was obsoleted in release 10.0."
    ::= { vRtrLdpAddrFecExtEntry 21 }

vRtrLdpAddrFecOutLblNxtHopType9  OBJECT-TYPE
    SYNTAX      InetAddressType
    MAX-ACCESS  read-only
    STATUS      obsolete
    DESCRIPTION
        "The value of vRtrLdpAddrFecOutLblNxtHopType9 specifies the address
         type of vRtrLdpAddrFecOutLblNxtHopAddr9.

         This object was obsoleted in release 10.0."
    ::= { vRtrLdpAddrFecExtEntry 22 }

vRtrLdpAddrFecOutLblNxtHopAddr9  OBJECT-TYPE
    SYNTAX      InetAddress (SIZE (4|16))
    MAX-ACCESS  read-only
    STATUS      obsolete
    DESCRIPTION
        "The value of vRtrLdpAddrFecOutLblNxtHopAddr9 specifies the IP address
         of the next hop for egress label 9.

         This object was obsoleted in release 10.0."
    ::= { vRtrLdpAddrFecExtEntry 23 }

vRtrLdpAddrFecLspId9             OBJECT-TYPE
    SYNTAX      TmnxVRtrMplsLspID
    MAX-ACCESS  read-only
    STATUS      obsolete
    DESCRIPTION
        "The value of vRtrLdpAddrFecLspId9 indicates the LSP id of the LSP for
         the RSVP tunnel used by LDP in LDP over RSVP associated with egress
         label 9.

         This object was obsoleted in release 10.0."
    ::= { vRtrLdpAddrFecExtEntry 24 }

vRtrLdpAddrFecOutLbl10           OBJECT-TYPE
    SYNTAX      Unsigned32
    MAX-ACCESS  read-only
    STATUS      obsolete
    DESCRIPTION
        "The value of vRtrLdpAddrFecOutLbl10 specifies the tenth egress label
         exchanged.

         This object was obsoleted in release 10.0."
    ::= { vRtrLdpAddrFecExtEntry 25 }

vRtrLdpAddrFecOutLblStatus10     OBJECT-TYPE
    SYNTAX      TmnxLabelStatus
    MAX-ACCESS  read-only
    STATUS      obsolete
    DESCRIPTION
        "The value of vRtrLdpAddrFecOutLblStatus10 specifies the status of the
         egress label 10.

         This object was obsoleted in release 10.0."
    ::= { vRtrLdpAddrFecExtEntry 26 }

vRtrLdpAddrFecOutLblIfIndex10    OBJECT-TYPE
    SYNTAX      InterfaceIndexOrZero
    MAX-ACCESS  read-only
    STATUS      obsolete
    DESCRIPTION
        "The value of vRtrLdpAddrFecOutLblIfIndex10 specifies the interface
         index for egress label 10.

         This object was obsoleted in release 10.0."
    ::= { vRtrLdpAddrFecExtEntry 27 }

vRtrLdpAddrFecOutLblNxtHopType10 OBJECT-TYPE
    SYNTAX      InetAddressType
    MAX-ACCESS  read-only
    STATUS      obsolete
    DESCRIPTION
        "The value of vRtrLdpAddrFecOutLblNxtHopType10 specifies the address
         type of vRtrLdpAddrFecOutLblNxtHopAddr10.

         This object was obsoleted in release 10.0."
    ::= { vRtrLdpAddrFecExtEntry 28 }

vRtrLdpAddrFecOutLblNxtHopAddr10 OBJECT-TYPE
    SYNTAX      InetAddress (SIZE (4|16))
    MAX-ACCESS  read-only
    STATUS      obsolete
    DESCRIPTION
        "The value of vRtrLdpAddrFecOutLblNxtHopAddr10 specifies the IP address
         of the next hop for egress label 10.

         This object was obsoleted in release 10.0."
    ::= { vRtrLdpAddrFecExtEntry 29 }

vRtrLdpAddrFecLspId10            OBJECT-TYPE
    SYNTAX      TmnxVRtrMplsLspID
    MAX-ACCESS  read-only
    STATUS      obsolete
    DESCRIPTION
        "The value of vRtrLdpAddrFecLspId10 indicates the LSP id of the LSP for
         the RSVP tunnel used by LDP in LDP over RSVP associated with egress
         label 10.

         This object was obsoleted in release 10.0."
    ::= { vRtrLdpAddrFecExtEntry 30 }

vRtrLdpAddrFecOutLbl11           OBJECT-TYPE
    SYNTAX      Unsigned32
    MAX-ACCESS  read-only
    STATUS      obsolete
    DESCRIPTION
        "The value of vRtrLdpAddrFecOutLbl11 specifies the eleventh egress
         label exchanged.

         This object was obsoleted in release 10.0."
    ::= { vRtrLdpAddrFecExtEntry 31 }

vRtrLdpAddrFecOutLblStatus11     OBJECT-TYPE
    SYNTAX      TmnxLabelStatus
    MAX-ACCESS  read-only
    STATUS      obsolete
    DESCRIPTION
        "The value of vRtrLdpAddrFecOutLblStatus11 specifies the status of the
         egress label 11.

         This object was obsoleted in release 10.0."
    ::= { vRtrLdpAddrFecExtEntry 32 }

vRtrLdpAddrFecOutLblIfIndex11    OBJECT-TYPE
    SYNTAX      InterfaceIndexOrZero
    MAX-ACCESS  read-only
    STATUS      obsolete
    DESCRIPTION
        "The value of vRtrLdpAddrFecOutLblIfIndex11 specifies the interface
         index for egress label 11.

         This object was obsoleted in release 10.0."
    ::= { vRtrLdpAddrFecExtEntry 33 }

vRtrLdpAddrFecOutLblNxtHopType11 OBJECT-TYPE
    SYNTAX      InetAddressType
    MAX-ACCESS  read-only
    STATUS      obsolete
    DESCRIPTION
        "The value of vRtrLdpAddrFecOutLblNxtHopType11 specifies the address
         type of vRtrLdpAddrFecOutLblNxtHopAddr11.

         This object was obsoleted in release 10.0."
    ::= { vRtrLdpAddrFecExtEntry 34 }

vRtrLdpAddrFecOutLblNxtHopAddr11 OBJECT-TYPE
    SYNTAX      InetAddress (SIZE (4|16))
    MAX-ACCESS  read-only
    STATUS      obsolete
    DESCRIPTION
        "The value of vRtrLdpAddrFecOutLblNxtHopAddr11 specifies the IP address
         of the next hop for egress label 11.

         This object was obsoleted in release 10.0."
    ::= { vRtrLdpAddrFecExtEntry 35 }

vRtrLdpAddrFecLspId11            OBJECT-TYPE
    SYNTAX      TmnxVRtrMplsLspID
    MAX-ACCESS  read-only
    STATUS      obsolete
    DESCRIPTION
        "The value of vRtrLdpAddrFecLspId11 indicates the LSP id of the LSP for
         the RSVP tunnel used by LDP in LDP over RSVP associated with egress
         label 11.

         This object was obsoleted in release 10.0."
    ::= { vRtrLdpAddrFecExtEntry 36 }

vRtrLdpAddrFecOutLbl12           OBJECT-TYPE
    SYNTAX      Unsigned32
    MAX-ACCESS  read-only
    STATUS      obsolete
    DESCRIPTION
        "The value of vRtrLdpAddrFecOutLbl12 specifies the twelfth egress label
         exchanged.

         This object was obsoleted in release 10.0."
    ::= { vRtrLdpAddrFecExtEntry 37 }

vRtrLdpAddrFecOutLblStatus12     OBJECT-TYPE
    SYNTAX      TmnxLabelStatus
    MAX-ACCESS  read-only
    STATUS      obsolete
    DESCRIPTION
        "The value of vRtrLdpAddrFecOutLblStatus12 specifies the status of the
         egress label 12.

         This object was obsoleted in release 10.0."
    ::= { vRtrLdpAddrFecExtEntry 38 }

vRtrLdpAddrFecOutLblIfIndex12    OBJECT-TYPE
    SYNTAX      InterfaceIndexOrZero
    MAX-ACCESS  read-only
    STATUS      obsolete
    DESCRIPTION
        "The value of vRtrLdpAddrFecOutLblIfIndex12 specifies the interface
         index for egress label 12.

         This object was obsoleted in release 10.0."
    ::= { vRtrLdpAddrFecExtEntry 39 }

vRtrLdpAddrFecOutLblNxtHopType12 OBJECT-TYPE
    SYNTAX      InetAddressType
    MAX-ACCESS  read-only
    STATUS      obsolete
    DESCRIPTION
        "The value of vRtrLdpAddrFecOutLblNxtHopType12 specifies the address
         type of vRtrLdpAddrFecOutLblNxtHopAddr12.

         This object was obsoleted in release 10.0."
    ::= { vRtrLdpAddrFecExtEntry 40 }

vRtrLdpAddrFecOutLblNxtHopAddr12 OBJECT-TYPE
    SYNTAX      InetAddress (SIZE (4|16))
    MAX-ACCESS  read-only
    STATUS      obsolete
    DESCRIPTION
        "The value of vRtrLdpAddrFecOutLblNxtHopAddr12 specifies the IP address
         of the next hop for egress label 12.

         This object was obsoleted in release 10.0."
    ::= { vRtrLdpAddrFecExtEntry 41 }

vRtrLdpAddrFecLspId12            OBJECT-TYPE
    SYNTAX      TmnxVRtrMplsLspID
    MAX-ACCESS  read-only
    STATUS      obsolete
    DESCRIPTION
        "The value of vRtrLdpAddrFecLspId12 indicates the LSP id of the LSP for
         the RSVP tunnel used by LDP in LDP over RSVP associated with egress
         label 12.

         This object was obsoleted in release 10.0."
    ::= { vRtrLdpAddrFecExtEntry 42 }

vRtrLdpAddrFecOutLbl13           OBJECT-TYPE
    SYNTAX      Unsigned32
    MAX-ACCESS  read-only
    STATUS      obsolete
    DESCRIPTION
        "The value of vRtrLdpAddrFecOutLbl13 specifies the thirteenth egress
         label exchanged.

         This object was obsoleted in release 10.0."
    ::= { vRtrLdpAddrFecExtEntry 43 }

vRtrLdpAddrFecOutLblStatus13     OBJECT-TYPE
    SYNTAX      TmnxLabelStatus
    MAX-ACCESS  read-only
    STATUS      obsolete
    DESCRIPTION
        "The value of vRtrLdpAddrFecOutLblStatus13 specifies the status of the
         egress label 13.

         This object was obsoleted in release 10.0."
    ::= { vRtrLdpAddrFecExtEntry 44 }

vRtrLdpAddrFecOutLblIfIndex13    OBJECT-TYPE
    SYNTAX      InterfaceIndexOrZero
    MAX-ACCESS  read-only
    STATUS      obsolete
    DESCRIPTION
        "The value of vRtrLdpAddrFecOutLblIfIndex13 specifies the interface
         index for egress label 13.

         This object was obsoleted in release 10.0."
    ::= { vRtrLdpAddrFecExtEntry 45 }

vRtrLdpAddrFecOutLblNxtHopType13 OBJECT-TYPE
    SYNTAX      InetAddressType
    MAX-ACCESS  read-only
    STATUS      obsolete
    DESCRIPTION
        "The value of vRtrLdpAddrFecOutLblNxtHopType13 specifies the address
         type of vRtrLdpAddrFecOutLblNxtHopAddr13.

         This object was obsoleted in release 10.0."
    ::= { vRtrLdpAddrFecExtEntry 46 }

vRtrLdpAddrFecOutLblNxtHopAddr13 OBJECT-TYPE
    SYNTAX      InetAddress (SIZE (4|16))
    MAX-ACCESS  read-only
    STATUS      obsolete
    DESCRIPTION
        "The value of vRtrLdpAddrFecOutLblNxtHopAddr13 specifies the IP address
         of the next hop for egress label 13.

         This object was obsoleted in release 10.0."
    ::= { vRtrLdpAddrFecExtEntry 47 }

vRtrLdpAddrFecLspId13            OBJECT-TYPE
    SYNTAX      TmnxVRtrMplsLspID
    MAX-ACCESS  read-only
    STATUS      obsolete
    DESCRIPTION
        "The value of vRtrLdpAddrFecLspId13 indicates the LSP id of the LSP for
         the RSVP tunnel used by LDP in LDP over RSVP associated with egress
         label 13.

         This object was obsoleted in release 10.0."
    ::= { vRtrLdpAddrFecExtEntry 48 }

vRtrLdpAddrFecOutLbl14           OBJECT-TYPE
    SYNTAX      Unsigned32
    MAX-ACCESS  read-only
    STATUS      obsolete
    DESCRIPTION
        "The value of vRtrLdpAddrFecOutLbl14 specifies the fourteenth egress
         label exchanged.

         This object was obsoleted in release 10.0."
    ::= { vRtrLdpAddrFecExtEntry 49 }

vRtrLdpAddrFecOutLblStatus14     OBJECT-TYPE
    SYNTAX      TmnxLabelStatus
    MAX-ACCESS  read-only
    STATUS      obsolete
    DESCRIPTION
        "The value of vRtrLdpAddrFecOutLblStatus14 specifies the status of the
         egress label 14.

         This object was obsoleted in release 10.0."
    ::= { vRtrLdpAddrFecExtEntry 50 }

vRtrLdpAddrFecOutLblIfIndex14    OBJECT-TYPE
    SYNTAX      InterfaceIndexOrZero
    MAX-ACCESS  read-only
    STATUS      obsolete
    DESCRIPTION
        "The value of vRtrLdpAddrFecOutLblIfIndex14 specifies the interface
         index for egress label 14.

         This object was obsoleted in release 10.0."
    ::= { vRtrLdpAddrFecExtEntry 51 }

vRtrLdpAddrFecOutLblNxtHopType14 OBJECT-TYPE
    SYNTAX      InetAddressType
    MAX-ACCESS  read-only
    STATUS      obsolete
    DESCRIPTION
        "The value of vRtrLdpAddrFecOutLblNxtHopType14 specifies the address
         type of vRtrLdpAddrFecOutLblNxtHopAddr14.

         This object was obsoleted in release 10.0."
    ::= { vRtrLdpAddrFecExtEntry 52 }

vRtrLdpAddrFecOutLblNxtHopAddr14 OBJECT-TYPE
    SYNTAX      InetAddress (SIZE (4|16))
    MAX-ACCESS  read-only
    STATUS      obsolete
    DESCRIPTION
        "The value of vRtrLdpAddrFecOutLblNxtHopAddr14 specifies the IP address
         of the next hop for egress label 14.

         This object was obsoleted in release 10.0."
    ::= { vRtrLdpAddrFecExtEntry 53 }

vRtrLdpAddrFecLspId14            OBJECT-TYPE
    SYNTAX      TmnxVRtrMplsLspID
    MAX-ACCESS  read-only
    STATUS      obsolete
    DESCRIPTION
        "The value of vRtrLdpAddrFecLspId14 indicates the LSP id of the LSP for
         the RSVP tunnel used by LDP in LDP over RSVP associated with egress
         label 14.

         This object was obsoleted in release 10.0."
    ::= { vRtrLdpAddrFecExtEntry 54 }

vRtrLdpAddrFecOutLbl15           OBJECT-TYPE
    SYNTAX      Unsigned32
    MAX-ACCESS  read-only
    STATUS      obsolete
    DESCRIPTION
        "The value of vRtrLdpAddrFecOutLbl15 specifies the fifteenth egress
         label exchanged.

         This object was obsoleted in release 10.0."
    ::= { vRtrLdpAddrFecExtEntry 55 }

vRtrLdpAddrFecOutLblStatus15     OBJECT-TYPE
    SYNTAX      TmnxLabelStatus
    MAX-ACCESS  read-only
    STATUS      obsolete
    DESCRIPTION
        "The value of vRtrLdpAddrFecOutLblStatus15 specifies the status of the
         egress label 15.

         This object was obsoleted in release 10.0."
    ::= { vRtrLdpAddrFecExtEntry 56 }

vRtrLdpAddrFecOutLblIfIndex15    OBJECT-TYPE
    SYNTAX      InterfaceIndexOrZero
    MAX-ACCESS  read-only
    STATUS      obsolete
    DESCRIPTION
        "The value of vRtrLdpAddrFecOutLblIfIndex15 specifies the interface
         index for egress label 15.

         This object was obsoleted in release 10.0."
    ::= { vRtrLdpAddrFecExtEntry 57 }

vRtrLdpAddrFecOutLblNxtHopType15 OBJECT-TYPE
    SYNTAX      InetAddressType
    MAX-ACCESS  read-only
    STATUS      obsolete
    DESCRIPTION
        "The value of vRtrLdpAddrFecOutLblNxtHopType15 specifies the address
         type of vRtrLdpAddrFecOutLblNxtHopAddr15.

         This object was obsoleted in release 10.0."
    ::= { vRtrLdpAddrFecExtEntry 58 }

vRtrLdpAddrFecOutLblNxtHopAddr15 OBJECT-TYPE
    SYNTAX      InetAddress (SIZE (4|16))
    MAX-ACCESS  read-only
    STATUS      obsolete
    DESCRIPTION
        "The value of vRtrLdpAddrFecOutLblNxtHopAddr15 specifies the IP address
         of the next hop for egress label 15.

         This object was obsoleted in release 10.0."
    ::= { vRtrLdpAddrFecExtEntry 59 }

vRtrLdpAddrFecLspId15            OBJECT-TYPE
    SYNTAX      TmnxVRtrMplsLspID
    MAX-ACCESS  read-only
    STATUS      obsolete
    DESCRIPTION
        "The value of vRtrLdpAddrFecLspId15 indicates the LSP id of the LSP for
         the RSVP tunnel used by LDP in LDP over RSVP associated with egress
         label 15.

         This object was obsoleted in release 10.0."
    ::= { vRtrLdpAddrFecExtEntry 60 }

vRtrLdpAddrFecOutLbl16           OBJECT-TYPE
    SYNTAX      Unsigned32
    MAX-ACCESS  read-only
    STATUS      obsolete
    DESCRIPTION
        "The value of vRtrLdpAddrFecOutLbl16 specifies the sixteenth egress
         label exchanged.

         This object was obsoleted in release 10.0."
    ::= { vRtrLdpAddrFecExtEntry 61 }

vRtrLdpAddrFecOutLblStatus16     OBJECT-TYPE
    SYNTAX      TmnxLabelStatus
    MAX-ACCESS  read-only
    STATUS      obsolete
    DESCRIPTION
        "The value of vRtrLdpAddrFecOutLblStatus16 specifies the status of the
         egress label 16.

         This object was obsoleted in release 10.0."
    ::= { vRtrLdpAddrFecExtEntry 62 }

vRtrLdpAddrFecOutLblIfIndex16    OBJECT-TYPE
    SYNTAX      InterfaceIndexOrZero
    MAX-ACCESS  read-only
    STATUS      obsolete
    DESCRIPTION
        "The value of vRtrLdpAddrFecOutLblIfIndex16 specifies the interface
         index for egress label 16.

         This object was obsoleted in release 10.0."
    ::= { vRtrLdpAddrFecExtEntry 63 }

vRtrLdpAddrFecOutLblNxtHopType16 OBJECT-TYPE
    SYNTAX      InetAddressType
    MAX-ACCESS  read-only
    STATUS      obsolete
    DESCRIPTION
        "The value of vRtrLdpAddrFecOutLblNxtHopType16 specifies the address
         type of vRtrLdpAddrFecOutLblNxtHopAddr16.

         This object was obsoleted in release 10.0."
    ::= { vRtrLdpAddrFecExtEntry 64 }

vRtrLdpAddrFecOutLblNxtHopAddr16 OBJECT-TYPE
    SYNTAX      InetAddress (SIZE (4|16))
    MAX-ACCESS  read-only
    STATUS      obsolete
    DESCRIPTION
        "The value of vRtrLdpAddrFecOutLblNxtHopAddr16 specifies the IP address
         of the next hop for egress label 16.

         This object was obsoleted in release 10.0."
    ::= { vRtrLdpAddrFecExtEntry 65 }

vRtrLdpAddrFecLspId16            OBJECT-TYPE
    SYNTAX      TmnxVRtrMplsLspID
    MAX-ACCESS  read-only
    STATUS      obsolete
    DESCRIPTION
        "The value of vRtrLdpAddrFecLspId16 indicates the LSP id of the LSP for
         the RSVP tunnel used by LDP in LDP over RSVP associated with egress
         label 16.

         This object was obsoleted in release 10.0."
    ::= { vRtrLdpAddrFecExtEntry 66 }

vRtrLdpP2MPFecTable              OBJECT-TYPE
    SYNTAX      SEQUENCE OF VRtrLdpP2MPFecEntry
    MAX-ACCESS  not-accessible
    STATUS      obsolete
    DESCRIPTION
        "vRtrLdpP2MPFecTable is a read-only table that represents operational
         information of P2MP FECs either sent to or received from an LDP peer
         known to the Virtual Router."
    ::= { tmnxLdpObjs 31 }

vRtrLdpP2MPFecEntry              OBJECT-TYPE
    SYNTAX      VRtrLdpP2MPFecEntry
    MAX-ACCESS  not-accessible
    STATUS      obsolete
    DESCRIPTION
        "Each row entry represents an instance of operational information of a
         P2MP FEC sent to or received from an LDP peer."
    INDEX       {
        vRtrID,
        vRtrLdpP2MPFecRootAddrType,
        vRtrLdpP2MPFecRootAddress,
        vRtrLdpP2MPFecTunnelType,
        vRtrLdpP2MPFecTunnelId,
        vRtrLdpPeerLdpId
    }
    ::= { vRtrLdpP2MPFecTable 1 }

VRtrLdpP2MPFecEntry              ::= SEQUENCE
{
    vRtrLdpP2MPFecTunnelType         TmnxLdpFECTunnelType,
    vRtrLdpP2MPFecTunnelId           Unsigned32,
    vRtrLdpP2MPFecRootAddrType       InetAddressType,
    vRtrLdpP2MPFecRootAddress        InetAddress,
    vRtrLdpP2MPFecFlags              TmnxLdpFECFlags,
    vRtrLdpP2MPFecNumInLabels        Gauge32,
    vRtrLdpP2MPFecNumOutLabels       Gauge32,
    vRtrLdpP2MPFecTunnelIfId         Unsigned32,
    vRtrLdpP2MPFecMetric             Unsigned32,
    vRtrLdpP2MPFecMTU                Unsigned32
}

vRtrLdpP2MPFecTunnelType         OBJECT-TYPE
    SYNTAX      TmnxLdpFECTunnelType
    MAX-ACCESS  not-accessible
    STATUS      obsolete
    DESCRIPTION
        "The value of vRtrLdpP2MPFecTunnelType indicates the tunnel type of
         P2MP FEC.

         This object was obsoleted in release 10.0."
    ::= { vRtrLdpP2MPFecEntry 1 }

vRtrLdpP2MPFecTunnelId           OBJECT-TYPE
    SYNTAX      Unsigned32
    MAX-ACCESS  not-accessible
    STATUS      obsolete
    DESCRIPTION
        "The value of vRtrLdpP2MPFecTunnelId indicates the tunnel identifier
         for this P2MP FEC.

         This object was obsoleted in release 10.0."
    ::= { vRtrLdpP2MPFecEntry 2 }

vRtrLdpP2MPFecRootAddrType       OBJECT-TYPE
    SYNTAX      InetAddressType
    MAX-ACCESS  not-accessible
    STATUS      obsolete
    DESCRIPTION
        "The value of vRtrLdpP2MPFecRootAddrType indicates the type of ip
         address of the root for this P2MP FEC.

         This object was obsoleted in release 10.0."
    ::= { vRtrLdpP2MPFecEntry 3 }

vRtrLdpP2MPFecRootAddress        OBJECT-TYPE
    SYNTAX      InetAddress (SIZE (0|4))
    MAX-ACCESS  not-accessible
    STATUS      obsolete
    DESCRIPTION
        "The value of vRtrLdpP2MPFecRootAddress indicates the ip address of the
         root for this P2MP FEC.

         This object was obsoleted in release 10.0."
    ::= { vRtrLdpP2MPFecEntry 4 }

vRtrLdpP2MPFecFlags              OBJECT-TYPE
    SYNTAX      TmnxLdpFECFlags
    MAX-ACCESS  read-only
    STATUS      obsolete
    DESCRIPTION
        "The bit flags of vRtrLdpP2MPFecFlags indicates the characteristics of
         the FEC.

         This object was obsoleted in release 10.0."
    ::= { vRtrLdpP2MPFecEntry 5 }

vRtrLdpP2MPFecNumInLabels        OBJECT-TYPE
    SYNTAX      Gauge32
    MAX-ACCESS  read-only
    STATUS      obsolete
    DESCRIPTION
        "The value of vRtrLdpP2MPFecNumInLabels indicates the number of labels
         that have been sent to the peer associated with this FEC.

         This object was obsoleted in release 10.0."
    ::= { vRtrLdpP2MPFecEntry 6 }

vRtrLdpP2MPFecNumOutLabels       OBJECT-TYPE
    SYNTAX      Gauge32
    MAX-ACCESS  read-only
    STATUS      obsolete
    DESCRIPTION
        "The value of vRtrLdpP2MPFecNumOutLabels indicates the number of labels
         that have been received from the peer associated with this FEC.

         This object was obsoleted in release 10.0."
    ::= { vRtrLdpP2MPFecEntry 7 }

vRtrLdpP2MPFecTunnelIfId         OBJECT-TYPE
    SYNTAX      Unsigned32
    MAX-ACCESS  read-only
    STATUS      obsolete
    DESCRIPTION
        "The value of vRtrLdpP2MPFecTunnelIfId indicates the tunnel interface
         identifier for this P2MP FEC.

         This object was obsoleted in release 10.0."
    ::= { vRtrLdpP2MPFecEntry 8 }

vRtrLdpP2MPFecMetric             OBJECT-TYPE
    SYNTAX      Unsigned32
    MAX-ACCESS  read-only
    STATUS      obsolete
    DESCRIPTION
        "The value of vRtrLdpP2MPFecMetric indicates the relative cost of the
         tunnel represented by this P2MP FEC.

         This object was obsoleted in release 10.0."
    ::= { vRtrLdpP2MPFecEntry 9 }

vRtrLdpP2MPFecMTU                OBJECT-TYPE
    SYNTAX      Unsigned32
    MAX-ACCESS  read-only
    STATUS      obsolete
    DESCRIPTION
        "The value of vRtrLdpP2MPFecMTU indicates the maximum transfer unit for
         payloads represented by this P2MP FEC.

         This object was obsoleted in release 10.0."
    ::= { vRtrLdpP2MPFecEntry 10 }

vRtrLdpP2MPFecInLabelTable       OBJECT-TYPE
    SYNTAX      SEQUENCE OF VRtrLdpP2MPFecInLabelEntry
    MAX-ACCESS  not-accessible
    STATUS      obsolete
    DESCRIPTION
        "vRtrLdpP2MPFecInLabelTable is a read-only table that represents all
         P2MP FECs received from an LDP peer known to the virtual router."
    ::= { tmnxLdpObjs 32 }

vRtrLdpP2MPFecInLabelEntry       OBJECT-TYPE
    SYNTAX      VRtrLdpP2MPFecInLabelEntry
    MAX-ACCESS  not-accessible
    STATUS      obsolete
    DESCRIPTION
        "Each row entry represents an instance of a P2MP FEC received from an
         LDP peer."
    INDEX       {
        vRtrID,
        vRtrLdpP2MPFecRootAddrType,
        vRtrLdpP2MPFecRootAddress,
        vRtrLdpP2MPFecTunnelType,
        vRtrLdpP2MPFecTunnelId,
        vRtrLdpPeerLdpId,
        vRtrLdpP2MPFecInLblId
    }
    ::= { vRtrLdpP2MPFecInLabelTable 1 }

VRtrLdpP2MPFecInLabelEntry       ::= SEQUENCE
{
    vRtrLdpP2MPFecInLblId            Unsigned32,
    vRtrLdpP2MPFecInLbl              Unsigned32,
    vRtrLdpP2MPFecInLblStatus        TmnxLabelStatus,
    vRtrLdpP2MPFecInLblIfIndex       InterfaceIndexOrZero
}

vRtrLdpP2MPFecInLblId            OBJECT-TYPE
    SYNTAX      Unsigned32
    MAX-ACCESS  not-accessible
    STATUS      obsolete
    DESCRIPTION
        "The value of vRtrLdpP2MPFecInLblId indicates the label number of the
         ingress label exchanged.

         This object was obsoleted in release 10.0."
    ::= { vRtrLdpP2MPFecInLabelEntry 1 }

vRtrLdpP2MPFecInLbl              OBJECT-TYPE
    SYNTAX      Unsigned32
    MAX-ACCESS  read-only
    STATUS      obsolete
    DESCRIPTION
        "The value of vRtrLdpP2MPFecInLbl indicates the ingress label
         exchanged.

         This object was obsoleted in release 10.0."
    ::= { vRtrLdpP2MPFecInLabelEntry 2 }

vRtrLdpP2MPFecInLblStatus        OBJECT-TYPE
    SYNTAX      TmnxLabelStatus
    MAX-ACCESS  read-only
    STATUS      obsolete
    DESCRIPTION
        "The value of vRtrLdpP2MPFecInLblStatus indicates the status of the
         ingress label.

         This object was obsoleted in release 10.0."
    ::= { vRtrLdpP2MPFecInLabelEntry 3 }

vRtrLdpP2MPFecInLblIfIndex       OBJECT-TYPE
    SYNTAX      InterfaceIndexOrZero
    MAX-ACCESS  read-only
    STATUS      obsolete
    DESCRIPTION
        "The value of vRtrLdpP2MPFecInLblIfIndex indicates the interface index
         for ingress label.

         This object was obsoleted in release 10.0."
    ::= { vRtrLdpP2MPFecInLabelEntry 4 }

vRtrLdpP2MPFecOutLabelTable      OBJECT-TYPE
    SYNTAX      SEQUENCE OF VRtrLdpP2MPFecOutLabelEntry
    MAX-ACCESS  not-accessible
    STATUS      obsolete
    DESCRIPTION
        "vRtrLdpP2MPFecTable is a read-only table that represents all P2MP FECs
         sent to an LDP peer known to the Virtual Router."
    ::= { tmnxLdpObjs 33 }

vRtrLdpP2MPFecOutLabelEntry      OBJECT-TYPE
    SYNTAX      VRtrLdpP2MPFecOutLabelEntry
    MAX-ACCESS  not-accessible
    STATUS      obsolete
    DESCRIPTION
        "Each row entry represents an instance of a P2MP FEC sent to a LDP
         peer."
    INDEX       {
        vRtrID,
        vRtrLdpP2MPFecRootAddrType,
        vRtrLdpP2MPFecRootAddress,
        vRtrLdpP2MPFecTunnelType,
        vRtrLdpP2MPFecTunnelId,
        vRtrLdpPeerLdpId,
        vRtrLdpP2MPFecOutLblId
    }
    ::= { vRtrLdpP2MPFecOutLabelTable 1 }

VRtrLdpP2MPFecOutLabelEntry      ::= SEQUENCE
{
    vRtrLdpP2MPFecOutLblId           Unsigned32,
    vRtrLdpP2MPFecOutLbl             Unsigned32,
    vRtrLdpP2MPFecOutLblStatus       TmnxLabelStatus,
    vRtrLdpP2MPFecOutLblNxtHopType   InetAddressType,
    vRtrLdpP2MPFecOutLblNxtHopAddr   InetAddress,
    vRtrLdpP2MPFecOutLblIfIndex      InterfaceIndexOrZero,
    vRtrLdpP2MPFecOutLblLspId        TmnxVRtrMplsLspID
}

vRtrLdpP2MPFecOutLblId           OBJECT-TYPE
    SYNTAX      Unsigned32
    MAX-ACCESS  not-accessible
    STATUS      obsolete
    DESCRIPTION
        "The value of vRtrLdpP2MPFecOutLblId indicates the label number of the
         egress label exchanged.

         This object was obsoleted in release 10.0."
    ::= { vRtrLdpP2MPFecOutLabelEntry 1 }

vRtrLdpP2MPFecOutLbl             OBJECT-TYPE
    SYNTAX      Unsigned32
    MAX-ACCESS  read-only
    STATUS      obsolete
    DESCRIPTION
        "The value of vRtrLdpP2MPFecOutLbl indicates the egress label
         exchanged.

         This object was obsoleted in release 10.0."
    ::= { vRtrLdpP2MPFecOutLabelEntry 2 }

vRtrLdpP2MPFecOutLblStatus       OBJECT-TYPE
    SYNTAX      TmnxLabelStatus
    MAX-ACCESS  read-only
    STATUS      obsolete
    DESCRIPTION
        "The value of vRtrLdpP2MPFecOutLblStatus indicates the status of the
         egress label.

         This object was obsoleted in release 10.0."
    ::= { vRtrLdpP2MPFecOutLabelEntry 3 }

vRtrLdpP2MPFecOutLblNxtHopType   OBJECT-TYPE
    SYNTAX      InetAddressType
    MAX-ACCESS  read-only
    STATUS      obsolete
    DESCRIPTION
        "The value of vRtrLdpP2MPFecOutLblNxtHopType indicates the address type
         of vRtrLdpP2MPFecOutLblNxtHopAddr.

         This object was obsoleted in release 10.0."
    ::= { vRtrLdpP2MPFecOutLabelEntry 4 }

vRtrLdpP2MPFecOutLblNxtHopAddr   OBJECT-TYPE
    SYNTAX      InetAddress (SIZE (4|16))
    MAX-ACCESS  read-only
    STATUS      obsolete
    DESCRIPTION
        "The value of vRtrLdpP2MPFecOutLblNxtHopAddr indicates the IP address
         of the next hop for egress label.

         This object was obsoleted in release 10.0."
    ::= { vRtrLdpP2MPFecOutLabelEntry 5 }

vRtrLdpP2MPFecOutLblIfIndex      OBJECT-TYPE
    SYNTAX      InterfaceIndexOrZero
    MAX-ACCESS  read-only
    STATUS      obsolete
    DESCRIPTION
        "The value of vRtrLdpP2MPFecOutLblIfIndex indicates the interface index
         for egress label.

         This object was obsoleted in release 10.0."
    ::= { vRtrLdpP2MPFecOutLabelEntry 6 }

vRtrLdpP2MPFecOutLblLspId        OBJECT-TYPE
    SYNTAX      TmnxVRtrMplsLspID
    MAX-ACCESS  read-only
    STATUS      obsolete
    DESCRIPTION
        "The value of vRtrLdpP2MPFecOutLblLspId indicates the LSP id of the LSP
         for the RSVP tunnel used by LDP in LDP over RSVP associated with
         egress label.

         This object was obsoleted in release 10.0."
    ::= { vRtrLdpP2MPFecOutLabelEntry 7 }

vRtrLdpP2MPFecMapTable           OBJECT-TYPE
    SYNTAX      SEQUENCE OF VRtrLdpP2MPFecMapEntry
    MAX-ACCESS  not-accessible
    STATUS      obsolete
    DESCRIPTION
        "vRtrLdpP2MPFecMapTable is a read-only table which maps to the
         vRtrLdpP2MPFecTable. This table has the same indexes as the
         vRtrLdpP2MPFecTable but the order in which these indexes are specified
         is different for the two tables."
    ::= { tmnxLdpObjs 34 }

vRtrLdpP2MPFecMapEntry           OBJECT-TYPE
    SYNTAX      VRtrLdpP2MPFecMapEntry
    MAX-ACCESS  not-accessible
    STATUS      obsolete
    DESCRIPTION
        "Each row entry represents an instance of a P2MP FEC sent to or
         received from an LDP peer."
    INDEX       {
        vRtrID,
        vRtrLdpP2MPFecRootAddrType,
        vRtrLdpP2MPFecRootAddress,
        vRtrLdpPeerLdpId,
        vRtrLdpP2MPFecMapFecType,
        vRtrLdpP2MPFecMapId
    }
    ::= { vRtrLdpP2MPFecMapTable 1 }

VRtrLdpP2MPFecMapEntry           ::= SEQUENCE
{
    vRtrLdpP2MPFecMapFecType         TmnxLdpFECTunnelType,
    vRtrLdpP2MPFecMapId              Unsigned32
}

vRtrLdpP2MPFecMapFecType         OBJECT-TYPE
    SYNTAX      TmnxLdpFECTunnelType
    MAX-ACCESS  read-only
    STATUS      obsolete
    DESCRIPTION
        "The value of vRtrLdpP2MPFecMapFecType indicates the tunnel type of
         P2MP FEC.

         This object was obsoleted in release 10.0."
    ::= { vRtrLdpP2MPFecMapEntry 1 }

vRtrLdpP2MPFecMapId              OBJECT-TYPE
    SYNTAX      Unsigned32
    MAX-ACCESS  read-only
    STATUS      obsolete
    DESCRIPTION
        "The value of vRtrLdpP2MPFecMapId indicates the tunnel identifier for
         this P2MP FEC.

         This object was obsoleted in release 10.0."
    ::= { vRtrLdpP2MPFecMapEntry 2 }

vRtrLdpAddrFecOutLblInfoTable    OBJECT-TYPE
    SYNTAX      SEQUENCE OF VRtrLdpAddrFecOutLblInfoEntry
    MAX-ACCESS  not-accessible
    STATUS      obsolete
    DESCRIPTION
        "vRtrLdpAddrFecOutLblInfoTable is a read-only table that contains the
         information related to an egress label of an address FEC sent to or
         received from an LDP peer."
    ::= { tmnxLdpObjs 35 }

vRtrLdpAddrFecOutLblInfoEntry    OBJECT-TYPE
    SYNTAX      VRtrLdpAddrFecOutLblInfoEntry
    MAX-ACCESS  not-accessible
    STATUS      obsolete
    DESCRIPTION
        "Each row entry represents an instance of an egress label of an address
         FEC sent to or received from an LDP peer."
    INDEX       {
        vRtrID,
        vRtrLdpAddrFecFecType,
        vRtrLdpAddrFecIpPrefix,
        vRtrLdpAddrFecIpMask,
        vRtrLdpPeerLdpId,
        vRtrLdpAddrFecOutLblId
    }
    ::= { vRtrLdpAddrFecOutLblInfoTable 1 }

VRtrLdpAddrFecOutLblInfoEntry    ::= SEQUENCE
{
    vRtrLdpAddrFecOutLblId           Unsigned32,
    vRtrLdpAddrFecOutLblMetric       Unsigned32,
    vRtrLdpAddrFecOutLblMtu          Unsigned32
}

vRtrLdpAddrFecOutLblId           OBJECT-TYPE
    SYNTAX      Unsigned32
    MAX-ACCESS  read-only
    STATUS      obsolete
    DESCRIPTION
        "The value of vRtrLdpAddrFecOutLblId indicates the egress label
         exchanged.

         This object was obsoleted in release 10.0."
    ::= { vRtrLdpAddrFecOutLblInfoEntry 1 }

vRtrLdpAddrFecOutLblMetric       OBJECT-TYPE
    SYNTAX      Unsigned32
    MAX-ACCESS  read-only
    STATUS      obsolete
    DESCRIPTION
        "The value of vRtrLdpAddrFecOutLblMetric indicates the relative cost of
         the tunnel represented by this address FEC egress label.

         This object was obsoleted in release 10.0."
    ::= { vRtrLdpAddrFecOutLblInfoEntry 2 }

vRtrLdpAddrFecOutLblMtu          OBJECT-TYPE
    SYNTAX      Unsigned32
    MAX-ACCESS  read-only
    STATUS      obsolete
    DESCRIPTION
        "The value of vRtrLdpAddrFecOutLblMtu indicates the maximum transfer
         unit for payloads represented by this address FEC egress label.

         This object was obsoleted in release 10.0."
    ::= { vRtrLdpAddrFecOutLblInfoEntry 3 }

vRtrLdpNgP2MPFecTable            OBJECT-TYPE
    SYNTAX      SEQUENCE OF VRtrLdpNgP2MPFecEntry
    MAX-ACCESS  not-accessible
    STATUS      obsolete
    DESCRIPTION
        "vRtrLdpNgP2MPFecTable is a read-only table that represents operational
         information of P2MP FECs either sent to or received from an LDP peer
         known to the Virtual Router.

         In 13.0 this table has been replaced by
         TIMETRA-LDP-NG-MIB::vRtrLdpNgExtP2MPFecTable."
    ::= { tmnxLdpObjs 36 }

vRtrLdpNgP2MPFecEntry            OBJECT-TYPE
    SYNTAX      VRtrLdpNgP2MPFecEntry
    MAX-ACCESS  not-accessible
    STATUS      obsolete
    DESCRIPTION
        "Each row entry represents an instance of operational information of a
         P2MP FEC sent to or received from an LDP peer."
    INDEX       {
        vRtrID,
        vRtrLdpNgP2MPFecRootAddrType,
        vRtrLdpNgP2MPFecRootAddress,
        vRtrLdpNgP2MPFecOpaqueType,
        vRtrLdpNgP2MPFecOpaqueLength,
        vRtrLdpNgP2MPFecOpaqueValue,
        vRtrLdpPeerLdpId
    }
    ::= { vRtrLdpNgP2MPFecTable 1 }

VRtrLdpNgP2MPFecEntry            ::= SEQUENCE
{
    vRtrLdpNgP2MPFecOpaqueType       Unsigned32,
    vRtrLdpNgP2MPFecOpaqueLength     Unsigned32,
    vRtrLdpNgP2MPFecOpaqueValue      OCTET STRING,
    vRtrLdpNgP2MPFecRootAddrType     InetAddressType,
    vRtrLdpNgP2MPFecRootAddress      InetAddress,
    vRtrLdpNgP2MPFecFlags            TmnxLdpFECFlags,
    vRtrLdpNgP2MPFecNumInLabels      Gauge32,
    vRtrLdpNgP2MPFecNumOutLabels     Gauge32,
    vRtrLdpNgP2MPFecTunnelIfId       Unsigned32,
    vRtrLdpNgP2MPFecMetric           Unsigned32,
    vRtrLdpNgP2MPFecMTU              Unsigned32
}

vRtrLdpNgP2MPFecOpaqueType       OBJECT-TYPE
    SYNTAX      Unsigned32 (0..255)
    MAX-ACCESS  not-accessible
    STATUS      obsolete
    DESCRIPTION
        "The value of vRtrLdpNgP2MPFecOpaqueType indicates the type of a
         Multi-Point Opaque Value Element.

         This object was obsoleted in release 13.0."
    ::= { vRtrLdpNgP2MPFecEntry 1 }

vRtrLdpNgP2MPFecOpaqueLength     OBJECT-TYPE
    SYNTAX      Unsigned32 (0..65535)
    MAX-ACCESS  not-accessible
    STATUS      obsolete
    DESCRIPTION
        "The value of vRtrLdpNgP2MPFecOpaqueLength indicates the length of a
         Multi-Point Opaque Value Element.

         This object was obsoleted in release 13.0."
    ::= { vRtrLdpNgP2MPFecEntry 2 }

vRtrLdpNgP2MPFecOpaqueValue      OBJECT-TYPE
    SYNTAX      OCTET STRING (SIZE (0..32))
    MAX-ACCESS  not-accessible
    STATUS      obsolete
    DESCRIPTION
        "The value of vRtrLdpNgP2MPFecOpaqueValue indicates the value of a
         Multi-Point Opaque Value Element.

         This object was obsoleted in release 13.0."
    ::= { vRtrLdpNgP2MPFecEntry 3 }

vRtrLdpNgP2MPFecRootAddrType     OBJECT-TYPE
    SYNTAX      InetAddressType
    MAX-ACCESS  not-accessible
    STATUS      obsolete
    DESCRIPTION
        "The value of vRtrLdpNgP2MPFecRootAddrType indicates the type of ip
         address of the root for this P2MP FEC.

         This object was obsoleted in release 13.0."
    ::= { vRtrLdpNgP2MPFecEntry 4 }

vRtrLdpNgP2MPFecRootAddress      OBJECT-TYPE
    SYNTAX      InetAddress (SIZE (4|16))
    MAX-ACCESS  not-accessible
    STATUS      obsolete
    DESCRIPTION
        "The value of vRtrLdpNgP2MPFecRootAddress indicates the ip address of
         the root for this P2MP FEC.

         This object was obsoleted in release 13.0."
    ::= { vRtrLdpNgP2MPFecEntry 5 }

vRtrLdpNgP2MPFecFlags            OBJECT-TYPE
    SYNTAX      TmnxLdpFECFlags
    MAX-ACCESS  read-only
    STATUS      obsolete
    DESCRIPTION
        "The bit flags of vRtrLdpNgP2MPFecFlags indicates the characteristics
         of the FEC.

         This object was obsoleted in release 13.0."
    ::= { vRtrLdpNgP2MPFecEntry 6 }

vRtrLdpNgP2MPFecNumInLabels      OBJECT-TYPE
    SYNTAX      Gauge32
    MAX-ACCESS  read-only
    STATUS      obsolete
    DESCRIPTION
        "The value of vRtrLdpNgP2MPFecNumInLabels indicates the number of
         labels that have been sent to the peer associated with this FEC.

         This object was obsoleted in release 13.0."
    ::= { vRtrLdpNgP2MPFecEntry 7 }

vRtrLdpNgP2MPFecNumOutLabels     OBJECT-TYPE
    SYNTAX      Gauge32
    MAX-ACCESS  read-only
    STATUS      obsolete
    DESCRIPTION
        "The value of vRtrLdpNgP2MPFecNumOutLabels indicates the number of
         labels that have been received from the peer associated with this FEC.

         This object was obsoleted in release 13.0."
    ::= { vRtrLdpNgP2MPFecEntry 8 }

vRtrLdpNgP2MPFecTunnelIfId       OBJECT-TYPE
    SYNTAX      Unsigned32
    MAX-ACCESS  read-only
    STATUS      obsolete
    DESCRIPTION
        "The value of vRtrLdpNgP2MPFecTunnelIfId indicates the tunnel interface
         identifier for this P2MP FEC.

         This object was obsoleted in release 13.0."
    ::= { vRtrLdpNgP2MPFecEntry 9 }

vRtrLdpNgP2MPFecMetric           OBJECT-TYPE
    SYNTAX      Unsigned32
    MAX-ACCESS  read-only
    STATUS      obsolete
    DESCRIPTION
        "The value of vRtrLdpNgP2MPFecMetric indicates the relative cost of the
         tunnel represented by this P2MP FEC.

         This object was obsoleted in release 13.0."
    ::= { vRtrLdpNgP2MPFecEntry 10 }

vRtrLdpNgP2MPFecMTU              OBJECT-TYPE
    SYNTAX      Unsigned32
    MAX-ACCESS  read-only
    STATUS      obsolete
    DESCRIPTION
        "The value of vRtrLdpNgP2MPFecMTU indicates the maximum transfer unit
         for payloads represented by this P2MP FEC.

         This object was obsoleted in release 13.0."
    ::= { vRtrLdpNgP2MPFecEntry 11 }

vRtrLdpNgP2MPFecInLabelTable     OBJECT-TYPE
    SYNTAX      SEQUENCE OF VRtrLdpNgP2MPFecInLabelEntry
    MAX-ACCESS  not-accessible
    STATUS      obsolete
    DESCRIPTION
        "vRtrLdpNgP2MPFecInLabelTable is a read-only table that represents all
         P2MP FECs received from an LDP peer known to the virtual router.

         In 13.0 this table has been replaced by
         TIMETRA-LDP-NG-MIB::vRtrLdpNgExtP2MPFecInLblTable."
    ::= { tmnxLdpObjs 37 }

vRtrLdpNgP2MPFecInLabelEntry     OBJECT-TYPE
    SYNTAX      VRtrLdpNgP2MPFecInLabelEntry
    MAX-ACCESS  not-accessible
    STATUS      obsolete
    DESCRIPTION
        "Each row entry represents an instance of a P2MP FEC received from an
         LDP peer."
    INDEX       {
        vRtrID,
        vRtrLdpNgP2MPFecRootAddrType,
        vRtrLdpNgP2MPFecRootAddress,
        vRtrLdpNgP2MPFecOpaqueType,
        vRtrLdpNgP2MPFecOpaqueLength,
        vRtrLdpNgP2MPFecOpaqueValue,
        vRtrLdpPeerLdpId,
        vRtrLdpNgP2MPFecInLblId
    }
    ::= { vRtrLdpNgP2MPFecInLabelTable 1 }

VRtrLdpNgP2MPFecInLabelEntry     ::= SEQUENCE
{
    vRtrLdpNgP2MPFecInLblId          Unsigned32,
    vRtrLdpNgP2MPFecInLbl            Unsigned32,
    vRtrLdpNgP2MPFecInLblStatus      TmnxLabelStatus,
    vRtrLdpNgP2MPFecInLblIfIndex     InterfaceIndexOrZero
}

vRtrLdpNgP2MPFecInLblId          OBJECT-TYPE
    SYNTAX      Unsigned32
    MAX-ACCESS  not-accessible
    STATUS      obsolete
    DESCRIPTION
        "The value of vRtrLdpNgP2MPFecInLblId indicates the label number of the
         ingress label exchanged.

         This object was obsoleted in release 13.0."
    ::= { vRtrLdpNgP2MPFecInLabelEntry 1 }

vRtrLdpNgP2MPFecInLbl            OBJECT-TYPE
    SYNTAX      Unsigned32
    MAX-ACCESS  read-only
    STATUS      obsolete
    DESCRIPTION
        "The value of vRtrLdpNgP2MPFecInLbl indicates the ingress label
         exchanged.

         This object was obsoleted in release 13.0."
    ::= { vRtrLdpNgP2MPFecInLabelEntry 2 }

vRtrLdpNgP2MPFecInLblStatus      OBJECT-TYPE
    SYNTAX      TmnxLabelStatus
    MAX-ACCESS  read-only
    STATUS      obsolete
    DESCRIPTION
        "The value of vRtrLdpNgP2MPFecInLblStatus indicates the status of the
         ingress label.

         This object was obsoleted in release 13.0."
    ::= { vRtrLdpNgP2MPFecInLabelEntry 3 }

vRtrLdpNgP2MPFecInLblIfIndex     OBJECT-TYPE
    SYNTAX      InterfaceIndexOrZero
    MAX-ACCESS  read-only
    STATUS      obsolete
    DESCRIPTION
        "The value of vRtrLdpNgP2MPFecInLblIfIndex indicates the interface
         index for ingress label.

         This object was obsoleted in release 13.0."
    ::= { vRtrLdpNgP2MPFecInLabelEntry 4 }

vRtrLdpNgP2MPFecOutLabelTable    OBJECT-TYPE
    SYNTAX      SEQUENCE OF VRtrLdpNgP2MPFecOutLabelEntry
    MAX-ACCESS  not-accessible
    STATUS      obsolete
    DESCRIPTION
        "vRtrLdpNgP2MPFecTable is a read-only table that represents all P2MP
         FECs sent to an LDP peer known to the Virtual Router.

         In 13.0 this table has been replaced by
         TIMETRA-LDP-NG-MIB::vRtrLdpNgExtP2MPFecOutLblTable."
    ::= { tmnxLdpObjs 38 }

vRtrLdpNgP2MPFecOutLabelEntry    OBJECT-TYPE
    SYNTAX      VRtrLdpNgP2MPFecOutLabelEntry
    MAX-ACCESS  not-accessible
    STATUS      obsolete
    DESCRIPTION
        "Each row entry represents an instance of a P2MP FEC sent to a LDP
         peer."
    INDEX       {
        vRtrID,
        vRtrLdpNgP2MPFecRootAddrType,
        vRtrLdpNgP2MPFecRootAddress,
        vRtrLdpNgP2MPFecOpaqueType,
        vRtrLdpNgP2MPFecOpaqueLength,
        vRtrLdpNgP2MPFecOpaqueValue,
        vRtrLdpPeerLdpId,
        vRtrLdpNgP2MPFecOutLblId
    }
    ::= { vRtrLdpNgP2MPFecOutLabelTable 1 }

VRtrLdpNgP2MPFecOutLabelEntry    ::= SEQUENCE
{
    vRtrLdpNgP2MPFecOutLblId         Unsigned32,
    vRtrLdpNgP2MPFecOutLbl           Unsigned32,
    vRtrLdpNgP2MPFecOutLblStatus     TmnxLabelStatus,
    vRtrLdpNgP2MPFecOutLblNxtHopType InetAddressType,
    vRtrLdpNgP2MPFecOutLblNxtHopAddr InetAddress,
    vRtrLdpNgP2MPFecOutLblIfIndex    InterfaceIndexOrZero,
    vRtrLdpNgP2MPFecOutLblLspId      TmnxVRtrMplsLspID
}

vRtrLdpNgP2MPFecOutLblId         OBJECT-TYPE
    SYNTAX      Unsigned32
    MAX-ACCESS  not-accessible
    STATUS      obsolete
    DESCRIPTION
        "The value of vRtrLdpNgP2MPFecOutLblId indicates the label number of
         the egress label exchanged.

         This object was obsoleted in release 13.0."
    ::= { vRtrLdpNgP2MPFecOutLabelEntry 1 }

vRtrLdpNgP2MPFecOutLbl           OBJECT-TYPE
    SYNTAX      Unsigned32
    MAX-ACCESS  read-only
    STATUS      obsolete
    DESCRIPTION
        "The value of vRtrLdpNgP2MPFecOutLbl indicates the egress label
         exchanged.

         This object was obsoleted in release 13.0."
    ::= { vRtrLdpNgP2MPFecOutLabelEntry 2 }

vRtrLdpNgP2MPFecOutLblStatus     OBJECT-TYPE
    SYNTAX      TmnxLabelStatus
    MAX-ACCESS  read-only
    STATUS      obsolete
    DESCRIPTION
        "The value of vRtrLdpNgP2MPFecOutLblStatus indicates the status of the
         egress label.

         This object was obsoleted in release 13.0."
    ::= { vRtrLdpNgP2MPFecOutLabelEntry 3 }

vRtrLdpNgP2MPFecOutLblNxtHopType OBJECT-TYPE
    SYNTAX      InetAddressType
    MAX-ACCESS  read-only
    STATUS      obsolete
    DESCRIPTION
        "The value of vRtrLdpNgP2MPFecOutLblNxtHopType indicates the address
         type of vRtrLdpNgP2MPFecOutLblNxtHopAddr.

         This object was obsoleted in release 13.0."
    ::= { vRtrLdpNgP2MPFecOutLabelEntry 4 }

vRtrLdpNgP2MPFecOutLblNxtHopAddr OBJECT-TYPE
    SYNTAX      InetAddress (SIZE (4|16))
    MAX-ACCESS  read-only
    STATUS      obsolete
    DESCRIPTION
        "The value of vRtrLdpNgP2MPFecOutLblNxtHopAddr indicates the IP address
         of the next hop for egress label.

         This object was obsoleted in release 13.0."
    ::= { vRtrLdpNgP2MPFecOutLabelEntry 5 }

vRtrLdpNgP2MPFecOutLblIfIndex    OBJECT-TYPE
    SYNTAX      InterfaceIndexOrZero
    MAX-ACCESS  read-only
    STATUS      obsolete
    DESCRIPTION
        "The value of vRtrLdpNgP2MPFecOutLblIfIndex indicates the interface
         index for egress label.

         This object was obsoleted in release 13.0."
    ::= { vRtrLdpNgP2MPFecOutLabelEntry 6 }

vRtrLdpNgP2MPFecOutLblLspId      OBJECT-TYPE
    SYNTAX      TmnxVRtrMplsLspID
    MAX-ACCESS  read-only
    STATUS      obsolete
    DESCRIPTION
        "The value of vRtrLdpNgP2MPFecOutLblLspId indicates the LSP id of the
         LSP for the RSVP tunnel used by LDP in LDP over RSVP associated with
         egress label.

         This object was obsoleted in release 13.0."
    ::= { vRtrLdpNgP2MPFecOutLabelEntry 7 }

vRtrLdpNgP2MPFecMapTable         OBJECT-TYPE
    SYNTAX      SEQUENCE OF VRtrLdpNgP2MPFecMapEntry
    MAX-ACCESS  not-accessible
    STATUS      obsolete
    DESCRIPTION
        "vRtrLdpNgP2MPFecMapTable is a read-only table which maps to the
         vRtrLdpNgP2MPFecTable. This table has the same indexes as the
         vRtrLdpNgP2MPFecTable but the order in which these indexes are
         specified is different for the two tables.

         In 13.0 this table has been replaced by
         TIMETRA-LDP-NG-MIB::vRtrLdpNgExtP2MPFecMapTable."
    ::= { tmnxLdpObjs 39 }

vRtrLdpNgP2MPFecMapEntry         OBJECT-TYPE
    SYNTAX      VRtrLdpNgP2MPFecMapEntry
    MAX-ACCESS  not-accessible
    STATUS      obsolete
    DESCRIPTION
        "Each row entry represents an instance of a P2MP FEC sent to or
         received from an LDP peer."
    INDEX       {
        vRtrID,
        vRtrLdpPeerLdpId,
        vRtrLdpNgP2MPFecRootAddrType,
        vRtrLdpNgP2MPFecRootAddress,
        vRtrLdpNgP2MPFecOpaqueType,
        vRtrLdpNgP2MPFecOpaqueLength,
        vRtrLdpNgP2MPFecOpaqueValue
    }
    ::= { vRtrLdpNgP2MPFecMapTable 1 }

VRtrLdpNgP2MPFecMapEntry         ::= SEQUENCE
{
    vRtrLdpNgP2MPFecMapFlags         TmnxLdpFECFlags,
    vRtrLdpNgP2MPFecMapNumInLabels   Gauge32,
    vRtrLdpNgP2MPFecMapNumOutLabels  Gauge32,
    vRtrLdpNgP2MPFecMapTunnelIfId    Unsigned32,
    vRtrLdpNgP2MPFecMapMetric        Unsigned32,
    vRtrLdpNgP2MPFecMapMTU           Unsigned32
}

vRtrLdpNgP2MPFecMapFlags         OBJECT-TYPE
    SYNTAX      TmnxLdpFECFlags
    MAX-ACCESS  read-only
    STATUS      obsolete
    DESCRIPTION
        "The bit flags of vRtrLdpNgP2MPFecMapFlags indicates the
         characteristics of the FEC.

         This object was obsoleted in release 13.0."
    ::= { vRtrLdpNgP2MPFecMapEntry 1 }

vRtrLdpNgP2MPFecMapNumInLabels   OBJECT-TYPE
    SYNTAX      Gauge32
    MAX-ACCESS  read-only
    STATUS      obsolete
    DESCRIPTION
        "The value of vRtrLdpNgP2MPFecMapNumInLabels indicates the number of
         labels that have been sent to the peer associated with this FEC.

         This object was obsoleted in release 13.0."
    ::= { vRtrLdpNgP2MPFecMapEntry 2 }

vRtrLdpNgP2MPFecMapNumOutLabels  OBJECT-TYPE
    SYNTAX      Gauge32
    MAX-ACCESS  read-only
    STATUS      obsolete
    DESCRIPTION
        "The value of vRtrLdpNgP2MPFecMapNumOutLabels indicates the number of
         labels that have been received from the peer associated with this FEC.

         This object was obsoleted in release 13.0."
    ::= { vRtrLdpNgP2MPFecMapEntry 3 }

vRtrLdpNgP2MPFecMapTunnelIfId    OBJECT-TYPE
    SYNTAX      Unsigned32
    MAX-ACCESS  read-only
    STATUS      obsolete
    DESCRIPTION
        "The value of vRtrLdpNgP2MPFecMapTunnelIfId indicates the tunnel
         interface identifier for this P2MP FEC.

         This object was obsoleted in release 13.0."
    ::= { vRtrLdpNgP2MPFecMapEntry 4 }

vRtrLdpNgP2MPFecMapMetric        OBJECT-TYPE
    SYNTAX      Unsigned32
    MAX-ACCESS  read-only
    STATUS      obsolete
    DESCRIPTION
        "The value of vRtrLdpNgP2MPFecMapMetric indicates the relative cost of
         the tunnel represented by this P2MP FEC.

         This object was obsoleted in release 13.0."
    ::= { vRtrLdpNgP2MPFecMapEntry 5 }

vRtrLdpNgP2MPFecMapMTU           OBJECT-TYPE
    SYNTAX      Unsigned32
    MAX-ACCESS  read-only
    STATUS      obsolete
    DESCRIPTION
        "The value of vRtrLdpNgP2MPFecMapMTU indicates the maximum transfer
         unit for payloads represented by this P2MP FEC.

         This object was obsoleted in release 13.0."
    ::= { vRtrLdpNgP2MPFecMapEntry 6 }

vRtrLdpAddressFecTable           OBJECT-TYPE
    SYNTAX      SEQUENCE OF VRtrLdpAddressFecEntry
    MAX-ACCESS  not-accessible
    STATUS      obsolete
    DESCRIPTION
        "vRtrLdpAddressFecTable is a read-only table that represents all
         address FECs either sent to or received from an LDP peer known to the
         Virtual Router.

         In 13.0 this table has been replaced by
         TIMETRA-LDP-NG-MIB::vRtrLdpNgAddrFecTable."
    ::= { tmnxLdpObjs 40 }

vRtrLdpAddressFecEntry           OBJECT-TYPE
    SYNTAX      VRtrLdpAddressFecEntry
    MAX-ACCESS  not-accessible
    STATUS      obsolete
    DESCRIPTION
        "Each row entry represents an instance of an address FEC sent to or
         received from an LDP peer."
    INDEX       {
        vRtrID,
        vRtrLdpAddressFecFecType,
        vRtrLdpAddressFecIpPrefixType,
        vRtrLdpAddressFecIpPrefix,
        vRtrLdpAddressFecIpPrefixLen,
        vRtrLdpPeerLdpId
    }
    ::= { vRtrLdpAddressFecTable 1 }

VRtrLdpAddressFecEntry           ::= SEQUENCE
{
    vRtrLdpAddressFecFecType         TmnxLdpFECType,
    vRtrLdpAddressFecIpPrefixType    InetAddressType,
    vRtrLdpAddressFecIpPrefix        InetAddress,
    vRtrLdpAddressFecIpPrefixLen     InetAddressPrefixLength,
    vRtrLdpAddressFecFlags           TmnxLdpFECFlags,
    vRtrLdpAddressFecNumInLabels     Unsigned32,
    vRtrLdpAddressFecNumOutLabels    Unsigned32
}

vRtrLdpAddressFecFecType         OBJECT-TYPE
    SYNTAX      TmnxLdpFECType
    MAX-ACCESS  not-accessible
    STATUS      obsolete
    DESCRIPTION
        "The value of vRtrLdpAddressFecFecType specifies the FEC type.

         This object was obsoleted in release 13.0."
    ::= { vRtrLdpAddressFecEntry 1 }

vRtrLdpAddressFecIpPrefixType    OBJECT-TYPE
    SYNTAX      InetAddressType
    MAX-ACCESS  not-accessible
    STATUS      obsolete
    DESCRIPTION
        "The value of vRtrLdpAddressFecIpPrefixType indicates the address type
         of vRtrLdpAddressFecIpPrefix.

         This object was obsoleted in release 13.0."
    ::= { vRtrLdpAddressFecEntry 2 }

vRtrLdpAddressFecIpPrefix        OBJECT-TYPE
    SYNTAX      InetAddress (SIZE (4|16))
    MAX-ACCESS  not-accessible
    STATUS      obsolete
    DESCRIPTION
        "The value of vRtrLdpAddressFecIpPrefix specifies the IP Address Prefix
         for this address FEC.

         This object was obsoleted in release 13.0."
    ::= { vRtrLdpAddressFecEntry 3 }

vRtrLdpAddressFecIpPrefixLen     OBJECT-TYPE
    SYNTAX      InetAddressPrefixLength (0..128)
    MAX-ACCESS  not-accessible
    STATUS      obsolete
    DESCRIPTION
        "The value of vRtrLdpAddressFecIpPrefixLen indicates the prefix length
         of the subnet associated with vRtrLdpAddressFecIpPrefix.

         This object was obsoleted in release 13.0."
    ::= { vRtrLdpAddressFecEntry 4 }

vRtrLdpAddressFecFlags           OBJECT-TYPE
    SYNTAX      TmnxLdpFECFlags
    MAX-ACCESS  read-only
    STATUS      obsolete
    DESCRIPTION
        "The bit flags of vRtrLdpAddressFecFlags specify the characteristics of
         the FEC.

         This object was obsoleted in release 13.0."
    ::= { vRtrLdpAddressFecEntry 5 }

vRtrLdpAddressFecNumInLabels     OBJECT-TYPE
    SYNTAX      Unsigned32
    MAX-ACCESS  read-only
    STATUS      obsolete
    DESCRIPTION
        "The value of vRtrLdpAddressFecNumInLabels gives the number of labels
         that have been sent to the peer associated with this FEC.

         This object was obsoleted in release 13.0."
    ::= { vRtrLdpAddressFecEntry 6 }

vRtrLdpAddressFecNumOutLabels    OBJECT-TYPE
    SYNTAX      Unsigned32
    MAX-ACCESS  read-only
    STATUS      obsolete
    DESCRIPTION
        "The value of vRtrLdpAddressFecNumOutLabels gives the number of labels
         that have been received from the peer associated with this FEC.

         This object was obsoleted in release 13.0."
    ::= { vRtrLdpAddressFecEntry 7 }

vRtrLdpAddressFecInLabelTable    OBJECT-TYPE
    SYNTAX      SEQUENCE OF VRtrLdpAddressFecInLabelEntry
    MAX-ACCESS  not-accessible
    STATUS      obsolete
    DESCRIPTION
        "vRtrLdpAddressFecInLabelTable is a read-only table that represents all
         address FECs received from an LDP peer known to the Virtual Router.

         In 13.0 this table has been replaced by
         TIMETRA-LDP-NG-MIB::vRtrLdpNgAddrFecInLblTable."
    ::= { tmnxLdpObjs 41 }

vRtrLdpAddressFecInLabelEntry    OBJECT-TYPE
    SYNTAX      VRtrLdpAddressFecInLabelEntry
    MAX-ACCESS  not-accessible
    STATUS      obsolete
    DESCRIPTION
        "Each row entry represents an instance of an address FEC received from
         an LDP peer."
    INDEX       {
        vRtrID,
        vRtrLdpAddressFecFecType,
        vRtrLdpAddressFecIpPrefixType,
        vRtrLdpAddressFecIpPrefix,
        vRtrLdpAddressFecIpPrefixLen,
        vRtrLdpPeerLdpId,
        vRtrLdpAddressFecInLblId
    }
    ::= { vRtrLdpAddressFecInLabelTable 1 }

VRtrLdpAddressFecInLabelEntry    ::= SEQUENCE
{
    vRtrLdpAddressFecInLblId         Unsigned32,
    vRtrLdpAddressFecInLbl           Unsigned32,
    vRtrLdpAddressFecInLblStatus     TmnxLabelStatus,
    vRtrLdpAddressFecInLblIfIndex    InterfaceIndexOrZero
}

vRtrLdpAddressFecInLblId         OBJECT-TYPE
    SYNTAX      Unsigned32
    MAX-ACCESS  not-accessible
    STATUS      obsolete
    DESCRIPTION
        "The value of vRtrLdpAddressFecInLblId indicates the label number of
         the ingress label exchanged.

         This object was obsoleted in release 13.0."
    ::= { vRtrLdpAddressFecInLabelEntry 1 }

vRtrLdpAddressFecInLbl           OBJECT-TYPE
    SYNTAX      Unsigned32
    MAX-ACCESS  read-only
    STATUS      obsolete
    DESCRIPTION
        "The value of vRtrLdpAddressFecInLbl specifies the ingress label
         exchanged.

         This object was obsoleted in release 13.0."
    ::= { vRtrLdpAddressFecInLabelEntry 2 }

vRtrLdpAddressFecInLblStatus     OBJECT-TYPE
    SYNTAX      TmnxLabelStatus
    MAX-ACCESS  read-only
    STATUS      obsolete
    DESCRIPTION
        "The value of vRtrLdpAddressFecInLblStatus specifies the status of the
         ingress label.

         This object was obsoleted in release 13.0."
    ::= { vRtrLdpAddressFecInLabelEntry 3 }

vRtrLdpAddressFecInLblIfIndex    OBJECT-TYPE
    SYNTAX      InterfaceIndexOrZero
    MAX-ACCESS  read-only
    STATUS      obsolete
    DESCRIPTION
        "The value of vRtrLdpAddressFecInLblIfIndex specifies the interface
         index for ingress label.

         This object was obsoleted in release 13.0."
    ::= { vRtrLdpAddressFecInLabelEntry 4 }

vRtrLdpAddressFecOutLabelTable   OBJECT-TYPE
    SYNTAX      SEQUENCE OF VRtrLdpAddressFecOutLabelEntry
    MAX-ACCESS  not-accessible
    STATUS      obsolete
    DESCRIPTION
        "vRtrLdpAddressFecOutLabelTable is a read-only table that represents
         all address FECs received from an LDP peer known to the Virtual
         Router.

         In 13.0 this table has been replaced by
         TIMETRA-LDP-NG-MIB::vRtrLdpNgAddrFecOutLblTable."
    ::= { tmnxLdpObjs 42 }

vRtrLdpAddressFecOutLabelEntry   OBJECT-TYPE
    SYNTAX      VRtrLdpAddressFecOutLabelEntry
    MAX-ACCESS  not-accessible
    STATUS      obsolete
    DESCRIPTION
        "Each row entry represents an instance of an address FEC received from
         an LDP peer."
    INDEX       {
        vRtrID,
        vRtrLdpAddressFecFecType,
        vRtrLdpAddressFecIpPrefixType,
        vRtrLdpAddressFecIpPrefix,
        vRtrLdpAddressFecIpPrefixLen,
        vRtrLdpPeerLdpId,
        vRtrLdpAddressFecOutLblId
    }
    ::= { vRtrLdpAddressFecOutLabelTable 1 }

VRtrLdpAddressFecOutLabelEntry   ::= SEQUENCE
{
    vRtrLdpAddressFecOutLblId        Unsigned32,
    vRtrLdpAddressFecOutLbl          Unsigned32,
    vRtrLdpAddressFecOutLblStatus    TmnxLabelStatus,
    vRtrLdpAddressFecOutLblIfIndex   InterfaceIndexOrZero,
    vRtrLdpAddressFecOutLblNHType    InetAddressType,
    vRtrLdpAddressFecOutLblNHAddr    InetAddress,
    vRtrLdpAddressFecOutLblMetric    Unsigned32,
    vRtrLdpAddressFecOutLblMtu       Unsigned32,
    vRtrLdpAddressFecOutLblLspId     TmnxVRtrMplsLspID
}

vRtrLdpAddressFecOutLblId        OBJECT-TYPE
    SYNTAX      Unsigned32
    MAX-ACCESS  not-accessible
    STATUS      obsolete
    DESCRIPTION
        "The value of vRtrLdpAddressFecOutLblId indicates the label number of
         the egress label exchanged.

         This object was obsoleted in release 13.0."
    ::= { vRtrLdpAddressFecOutLabelEntry 1 }

vRtrLdpAddressFecOutLbl          OBJECT-TYPE
    SYNTAX      Unsigned32
    MAX-ACCESS  read-only
    STATUS      obsolete
    DESCRIPTION
        "The value of vRtrLdpAddressFecOutLbl specifies the egress label
         exchanged.

         This object was obsoleted in release 13.0."
    ::= { vRtrLdpAddressFecOutLabelEntry 2 }

vRtrLdpAddressFecOutLblStatus    OBJECT-TYPE
    SYNTAX      TmnxLabelStatus
    MAX-ACCESS  read-only
    STATUS      obsolete
    DESCRIPTION
        "The value of vRtrLdpAddressFecOutLblStatus specifies the status of the
         egress label.

         This object was obsoleted in release 13.0."
    ::= { vRtrLdpAddressFecOutLabelEntry 3 }

vRtrLdpAddressFecOutLblIfIndex   OBJECT-TYPE
    SYNTAX      InterfaceIndexOrZero
    MAX-ACCESS  read-only
    STATUS      obsolete
    DESCRIPTION
        "The value of vRtrLdpAddressFecOutLblIfIndex specifies the interface
         index for egress label.

         This object was obsoleted in release 13.0."
    ::= { vRtrLdpAddressFecOutLabelEntry 4 }

vRtrLdpAddressFecOutLblNHType    OBJECT-TYPE
    SYNTAX      InetAddressType
    MAX-ACCESS  read-only
    STATUS      obsolete
    DESCRIPTION
        "The value of vRtrLdpAddressFecOutLblNHType specifies the address type
         of vRtrLdpAddressFecOutLblNHAddr.

         This object was obsoleted in release 13.0."
    ::= { vRtrLdpAddressFecOutLabelEntry 5 }

vRtrLdpAddressFecOutLblNHAddr    OBJECT-TYPE
    SYNTAX      InetAddress (SIZE (4|16))
    MAX-ACCESS  read-only
    STATUS      obsolete
    DESCRIPTION
        "The value of vRtrLdpAddressFecOutLblNHAddr specifies the IP address of
         the next hop for egress label.

         This object was obsoleted in release 13.0."
    ::= { vRtrLdpAddressFecOutLabelEntry 6 }

vRtrLdpAddressFecOutLblMetric    OBJECT-TYPE
    SYNTAX      Unsigned32
    MAX-ACCESS  read-only
    STATUS      obsolete
    DESCRIPTION
        "The value of vRtrLdpAddressFecOutLblMetric indicates the relative cost
         of the tunnel represented by this address FEC egress label.

         This object was obsoleted in release 13.0."
    ::= { vRtrLdpAddressFecOutLabelEntry 7 }

vRtrLdpAddressFecOutLblMtu       OBJECT-TYPE
    SYNTAX      Unsigned32
    MAX-ACCESS  read-only
    STATUS      obsolete
    DESCRIPTION
        "The value of vRtrLdpAddressFecOutLblMtu indicates the maximum transfer
         unit for payloads represented by this address FEC egress label.

         This object was obsoleted in release 13.0."
    ::= { vRtrLdpAddressFecOutLabelEntry 8 }

vRtrLdpAddressFecOutLblLspId     OBJECT-TYPE
    SYNTAX      TmnxVRtrMplsLspID
    MAX-ACCESS  read-only
    STATUS      obsolete
    DESCRIPTION
        "The value of vRtrLdpAddressFecOutLblLspId indicates the LSP id of the
         LSP for the RSVP tunnel used by LDP in LDP over RSVP associated with
         egress label.

         This object was obsoleted in release 13.0."
    ::= { vRtrLdpAddressFecOutLabelEntry 9 }

vRtrLdpAddressFecMapTable        OBJECT-TYPE
    SYNTAX      SEQUENCE OF VRtrLdpAddressFecMapEntry
    MAX-ACCESS  not-accessible
    STATUS      obsolete
    DESCRIPTION
        "vRtrLdpAddressFecMapTable is a read-only table which maps to the
         vRtrLdpAddressFecTable. This table has the same indexes as the
         vRtrLdpAddressFecTable but the order in which these indexes are
         specified is different for the two tables.

         In 13.0 this table has been replaced by
         TIMETRA-LDP-NG-MIB::vRtrLdpNgAddrFecMapTable."
    ::= { tmnxLdpObjs 43 }

vRtrLdpAddressFecMapEntry        OBJECT-TYPE
    SYNTAX      VRtrLdpAddressFecMapEntry
    MAX-ACCESS  not-accessible
    STATUS      obsolete
    DESCRIPTION
        "Each row entry represents an instance of an address FEC sent to or
         received from an LDP peer."
    INDEX       {
        vRtrID,
        vRtrLdpPeerLdpId,
        vRtrLdpAddressFecFecType,
        vRtrLdpAddressFecIpPrefixType,
        vRtrLdpAddressFecIpPrefix,
        vRtrLdpAddressFecIpPrefixLen
    }
    ::= { vRtrLdpAddressFecMapTable 1 }

VRtrLdpAddressFecMapEntry        ::= SEQUENCE
{
    vRtrLdpAddressFecMapFlags        TmnxLdpFECFlags,
    vRtrLdpAddressFecMapNumInLabels  Unsigned32,
    vRtrLdpAddressFecMapNumOutLabels Unsigned32
}

vRtrLdpAddressFecMapFlags        OBJECT-TYPE
    SYNTAX      TmnxLdpFECFlags
    MAX-ACCESS  read-only
    STATUS      obsolete
    DESCRIPTION
        "The bit flags of vRtrLdpAddressFecMapFlags specify the characteristics
         of the FEC.

         This object was obsoleted in release 13.0."
    ::= { vRtrLdpAddressFecMapEntry 1 }

vRtrLdpAddressFecMapNumInLabels  OBJECT-TYPE
    SYNTAX      Unsigned32
    MAX-ACCESS  read-only
    STATUS      obsolete
    DESCRIPTION
        "The value of vRtrLdpAddressFecMapNumInLabels gives the number of
         labels that have been sent to the peer associated with this FEC.

         This object was obsoleted in release 13.0."
    ::= { vRtrLdpAddressFecMapEntry 2 }

vRtrLdpAddressFecMapNumOutLabels OBJECT-TYPE
    SYNTAX      Unsigned32
    MAX-ACCESS  read-only
    STATUS      obsolete
    DESCRIPTION
        "The value of vRtrLdpAddressFecMapNumOutLabels gives the number of
         labels that have been received from the peer associated with this FEC.

         This object was obsoleted in release 13.0."
    ::= { vRtrLdpAddressFecMapEntry 3 }

vRtrLdpAddrActiveFecTable        OBJECT-TYPE
    SYNTAX      SEQUENCE OF VRtrLdpAddrActiveFecEntry
    MAX-ACCESS  not-accessible
    STATUS      obsolete
    DESCRIPTION
        "vRtrLdpAddrActiveFecTable is a read-only table that represents all
         active in data plane address FECs either sent to or received from an
         LDP peer known to the Virtual Router.

         In 13.0 this table has been replaced by
         TIMETRA-LDP-NG-MIB::vLdpNgAddrActiveFecTable."
    ::= { tmnxLdpObjs 44 }

vRtrLdpAddrActiveFecEntry        OBJECT-TYPE
    SYNTAX      VRtrLdpAddrActiveFecEntry
    MAX-ACCESS  not-accessible
    STATUS      obsolete
    DESCRIPTION
        "Each row entry represents an instance of an active in data plane
         address FEC sent to or received from an LDP peer."
    INDEX       {
        vRtrID,
        vRtrLdpAddressFecFecType,
        vRtrLdpAddressFecIpPrefixType,
        vRtrLdpAddressFecIpPrefix,
        vRtrLdpAddressFecIpPrefixLen,
        vRtrLdpAddrActiveFecOpType
    }
    ::= { vRtrLdpAddrActiveFecTable 1 }

VRtrLdpAddrActiveFecEntry        ::= SEQUENCE
{
    vRtrLdpAddrActiveFecOpType       INTEGER,
    vRtrLdpAddrActiveFecFecFlags     TmnxLdpFECFlags,
    vRtrLdpAddrActiveFecNumInLbls    Unsigned32,
    vRtrLdpAddrActiveFecNumOutLbls   Unsigned32
}

vRtrLdpAddrActiveFecOpType       OBJECT-TYPE
    SYNTAX      INTEGER {
        pop  (1),
        push (2),
        swap (3)
    }
    MAX-ACCESS  not-accessible
    STATUS      obsolete
    DESCRIPTION
        "The value of vRtrLdpAddrActiveFecOpType indicates operation type of
         this FEC.

         This object was obsoleted in release 13.0."
    ::= { vRtrLdpAddrActiveFecEntry 1 }

vRtrLdpAddrActiveFecFecFlags     OBJECT-TYPE
    SYNTAX      TmnxLdpFECFlags
    MAX-ACCESS  read-only
    STATUS      obsolete
    DESCRIPTION
        "The bit flags of vRtrLdpAddrActiveFecFecFlags indicates the
         characteristics of the FEC.

         This object was obsoleted in release 13.0."
    ::= { vRtrLdpAddrActiveFecEntry 2 }

vRtrLdpAddrActiveFecNumInLbls    OBJECT-TYPE
    SYNTAX      Unsigned32
    MAX-ACCESS  read-only
    STATUS      obsolete
    DESCRIPTION
        "The value of vRtrLdpAddrActiveFecNumInLbls indicates the number of
         labels that have been sent to the peer associated with this FEC.

         This object was obsoleted in release 13.0."
    ::= { vRtrLdpAddrActiveFecEntry 3 }

vRtrLdpAddrActiveFecNumOutLbls   OBJECT-TYPE
    SYNTAX      Unsigned32
    MAX-ACCESS  read-only
    STATUS      obsolete
    DESCRIPTION
        "The value of vRtrLdpAddrActiveFecNumOutLbls indicates the number of
         labels that have been received from the peer associated with this FEC.

         This object was obsoleted in release 13.0."
    ::= { vRtrLdpAddrActiveFecEntry 4 }

vRtrLdpAddrActiveFecInLblTable   OBJECT-TYPE
    SYNTAX      SEQUENCE OF VRtrLdpAddrActiveFecInLblEntry
    MAX-ACCESS  not-accessible
    STATUS      obsolete
    DESCRIPTION
        "vRtrLdpAddrActiveFecInLblTable is a read-only table that represents
         all active in data plane address FECs received from an LDP peer known
         to the Virtual Router.

         In 13.0 this table has been replaced by
         TIMETRA-LDP-NG-MIB::vLdpNgAddrActiveFecInLblTable."
    ::= { tmnxLdpObjs 45 }

vRtrLdpAddrActiveFecInLblEntry   OBJECT-TYPE
    SYNTAX      VRtrLdpAddrActiveFecInLblEntry
    MAX-ACCESS  not-accessible
    STATUS      obsolete
    DESCRIPTION
        "Each row entry represents an instance of an active in data plane
         address FEC received from an LDP peer."
    INDEX       {
        vRtrID,
        vRtrLdpAddressFecFecType,
        vRtrLdpAddressFecIpPrefixType,
        vRtrLdpAddressFecIpPrefix,
        vRtrLdpAddressFecIpPrefixLen,
        vRtrLdpAddrActiveFecOpType,
        vRtrLdpAddrActiveFecInLblId
    }
    ::= { vRtrLdpAddrActiveFecInLblTable 1 }

VRtrLdpAddrActiveFecInLblEntry   ::= SEQUENCE
{
    vRtrLdpAddrActiveFecInLblId      Unsigned32,
    vRtrLdpAddrActiveFecInLbl        Unsigned32,
    vRtrLdpAddrActiveFecInLblIfIndex InterfaceIndexOrZero
}

vRtrLdpAddrActiveFecInLblId      OBJECT-TYPE
    SYNTAX      Unsigned32
    MAX-ACCESS  not-accessible
    STATUS      obsolete
    DESCRIPTION
        "The value of vRtrLdpAddrActiveFecInLblId indicates the label number of
         the ingress label exchanged.

         This object was obsoleted in release 13.0."
    ::= { vRtrLdpAddrActiveFecInLblEntry 1 }

vRtrLdpAddrActiveFecInLbl        OBJECT-TYPE
    SYNTAX      Unsigned32
    MAX-ACCESS  read-only
    STATUS      obsolete
    DESCRIPTION
        "The value of vRtrLdpAddrActiveFecInLbl indicates the ingress label
         exchanged.

         This object was obsoleted in release 13.0."
    ::= { vRtrLdpAddrActiveFecInLblEntry 2 }

vRtrLdpAddrActiveFecInLblIfIndex OBJECT-TYPE
    SYNTAX      InterfaceIndexOrZero
    MAX-ACCESS  read-only
    STATUS      obsolete
    DESCRIPTION
        "The value of vRtrLdpAddrActiveFecInLblIfIndex indicates the interface
         index for ingress label.

         This object was obsoleted in release 13.0."
    ::= { vRtrLdpAddrActiveFecInLblEntry 3 }

vRtrLdpAddrActiveFecOutLblTable  OBJECT-TYPE
    SYNTAX      SEQUENCE OF VRtrLdpAddrActiveFecOutLblEntry
    MAX-ACCESS  not-accessible
    STATUS      obsolete
    DESCRIPTION
        "vRtrLdpAddrActiveFecOutLblTable is a read-only table that represents
         all active in data plane address FECs received from an LDP peer known
         to the Virtual Router.

         In 13.0 this table has been replaced by
         TIMETRA-LDP-NG-MIB::vLdpNgAddrActiveFecOutLblTable."
    ::= { tmnxLdpObjs 46 }

vRtrLdpAddrActiveFecOutLblEntry  OBJECT-TYPE
    SYNTAX      VRtrLdpAddrActiveFecOutLblEntry
    MAX-ACCESS  not-accessible
    STATUS      obsolete
    DESCRIPTION
        "Each row entry represents an instance of an active in data plane
         address FEC received from an LDP peer."
    INDEX       {
        vRtrID,
        vRtrLdpAddressFecFecType,
        vRtrLdpAddressFecIpPrefixType,
        vRtrLdpAddressFecIpPrefix,
        vRtrLdpAddressFecIpPrefixLen,
        vRtrLdpAddrActiveFecOpType,
        vRtrLdpAddrActiveFecOutLblId
    }
    ::= { vRtrLdpAddrActiveFecOutLblTable 1 }

VRtrLdpAddrActiveFecOutLblEntry  ::= SEQUENCE
{
    vRtrLdpAddrActiveFecOutLblId     Unsigned32,
    vRtrLdpAddrActiveFecOutLbl       Unsigned32,
    vRtrLdpAddrActiveFecOutLblStatus TmnxLabelStatus,
    vRtrLdpAddrActiveFecOutLblIfIdx  InterfaceIndexOrZero,
    vRtrLdpAddrActiveFecOutLblNHType InetAddressType,
    vRtrLdpAddrActiveFecOutLblNHAddr InetAddress,
    vRtrLdpAddrActiveFecOutLblMetric Unsigned32,
    vRtrLdpAddrActiveFecOutLblMtu    Unsigned32,
    vRtrLdpAddrActiveFecOutLblLspId  TmnxVRtrMplsLspID
}

vRtrLdpAddrActiveFecOutLblId     OBJECT-TYPE
    SYNTAX      Unsigned32
    MAX-ACCESS  not-accessible
    STATUS      obsolete
    DESCRIPTION
        "The value of vRtrLdpAddrActiveFecOutLblId indicates the label number
         of the egress label exchanged.

         This object was obsoleted in release 13.0."
    ::= { vRtrLdpAddrActiveFecOutLblEntry 1 }

vRtrLdpAddrActiveFecOutLbl       OBJECT-TYPE
    SYNTAX      Unsigned32
    MAX-ACCESS  read-only
    STATUS      obsolete
    DESCRIPTION
        "The value of vRtrLdpAddrActiveFecOutLbl indicates the egress label
         exchanged.

         This object was obsoleted in release 13.0."
    ::= { vRtrLdpAddrActiveFecOutLblEntry 2 }

vRtrLdpAddrActiveFecOutLblStatus OBJECT-TYPE
    SYNTAX      TmnxLabelStatus
    MAX-ACCESS  read-only
    STATUS      obsolete
    DESCRIPTION
        "The value of vRtrLdpAddrActiveFecOutLblStatus indicates the status of
         the egress label.

         This object was obsoleted in release 13.0."
    ::= { vRtrLdpAddrActiveFecOutLblEntry 3 }

vRtrLdpAddrActiveFecOutLblIfIdx  OBJECT-TYPE
    SYNTAX      InterfaceIndexOrZero
    MAX-ACCESS  read-only
    STATUS      obsolete
    DESCRIPTION
        "The value of vRtrLdpAddrActiveFecOutLblIfIdx indicates the interface
         index for egress label.

         This object was obsoleted in release 13.0."
    ::= { vRtrLdpAddrActiveFecOutLblEntry 4 }

vRtrLdpAddrActiveFecOutLblNHType OBJECT-TYPE
    SYNTAX      InetAddressType
    MAX-ACCESS  read-only
    STATUS      obsolete
    DESCRIPTION
        "The value of vRtrLdpAddrActiveFecOutLblNHType indicates the address
         type of vRtrLdpAddrActiveFecOutLblNHAddr.

         This object was obsoleted in release 13.0."
    ::= { vRtrLdpAddrActiveFecOutLblEntry 5 }

vRtrLdpAddrActiveFecOutLblNHAddr OBJECT-TYPE
    SYNTAX      InetAddress (SIZE (4|16))
    MAX-ACCESS  read-only
    STATUS      obsolete
    DESCRIPTION
        "The value of vRtrLdpAddrActiveFecOutLblNHAddr indicates the IP address
         of the next hop for egress label.

         This object was obsoleted in release 13.0."
    ::= { vRtrLdpAddrActiveFecOutLblEntry 6 }

vRtrLdpAddrActiveFecOutLblMetric OBJECT-TYPE
    SYNTAX      Unsigned32
    MAX-ACCESS  read-only
    STATUS      obsolete
    DESCRIPTION
        "The value of vRtrLdpAddrActiveFecOutLblMetric indicates the relative
         cost of the tunnel represented by this address FEC egress label.

         This object was obsoleted in release 13.0."
    ::= { vRtrLdpAddrActiveFecOutLblEntry 7 }

vRtrLdpAddrActiveFecOutLblMtu    OBJECT-TYPE
    SYNTAX      Unsigned32
    MAX-ACCESS  read-only
    STATUS      obsolete
    DESCRIPTION
        "The value of vRtrLdpAddrActiveFecOutLblMtu indicates the maximum
         transfer unit for payloads represented by this address FEC egress
         label.

         This object was obsoleted in release 13.0."
    ::= { vRtrLdpAddrActiveFecOutLblEntry 8 }

vRtrLdpAddrActiveFecOutLblLspId  OBJECT-TYPE
    SYNTAX      TmnxVRtrMplsLspID
    MAX-ACCESS  read-only
    STATUS      obsolete
    DESCRIPTION
        "The value of vRtrLdpAddrActiveFecOutLblLspId indicates the LSP id of
         the LSP for the RSVP tunnel used by LDP in LDP over RSVP associated
         with egress label.

         This object was obsoleted in release 13.0."
    ::= { vRtrLdpAddrActiveFecOutLblEntry 9 }

vRtrLdpSessionAddrTable          OBJECT-TYPE
    SYNTAX      SEQUENCE OF VRtrLdpSessionAddrEntry
    MAX-ACCESS  not-accessible
    STATUS      obsolete
    DESCRIPTION
        "vRtrLdpSessionInAddrTable is a read-only table that represents all
         local addresses either sent to or received from an LDP peer for a
         single session between an LDP entity and an LDP Peer.

         In 13.0 this table has been replaced by
         TIMETRA-LDP-NG-MIB::vRtrLdpNgSessionAddrTable."
    ::= { tmnxLdpObjs 47 }

vRtrLdpSessionAddrEntry          OBJECT-TYPE
    SYNTAX      VRtrLdpSessionAddrEntry
    MAX-ACCESS  not-accessible
    STATUS      obsolete
    DESCRIPTION
        "Each row entry represents an instance of all local addresses sent to
         or received from an LDP peer."
    INDEX       {
        vRtrID,
        vRtrLdpPeerLdpId
    }
    ::= { vRtrLdpSessionAddrTable 1 }

VRtrLdpSessionAddrEntry          ::= SEQUENCE
{
    vRtrLdpSessionAddrLocalLdpId     MplsLdpIdentifier,
    vRtrLdpSessionAddrNumInAddrs     Unsigned32,
    vRtrLdpSessionAddrNumOutAddrs    Unsigned32
}

vRtrLdpSessionAddrLocalLdpId     OBJECT-TYPE
    SYNTAX      MplsLdpIdentifier
    MAX-ACCESS  read-only
    STATUS      obsolete
    DESCRIPTION
        "The value of vRtrLdpSessionAddrLocalLdpId indicates the local LDP
         identifier for this LDP session.

         This object was obsoleted in release 13.0."
    ::= { vRtrLdpSessionAddrEntry 1 }

vRtrLdpSessionAddrNumInAddrs     OBJECT-TYPE
    SYNTAX      Unsigned32
    MAX-ACCESS  read-only
    STATUS      obsolete
    DESCRIPTION
        "The value of vRtrLdpSessionAddrNumInAddrs indicates the number of
         local addresses that have been received from the peer for this
         session.

         This object was obsoleted in release 13.0."
    ::= { vRtrLdpSessionAddrEntry 2 }

vRtrLdpSessionAddrNumOutAddrs    OBJECT-TYPE
    SYNTAX      Unsigned32
    MAX-ACCESS  read-only
    STATUS      obsolete
    DESCRIPTION
        "The value of vRtrLdpSessionAddrNumOutAddrs indicates the number of
         local addresses that have been sent to the peer for this session.

         This object was obsoleted in release 13.0."
    ::= { vRtrLdpSessionAddrEntry 3 }

vRtrLdpSessionInAddrTable        OBJECT-TYPE
    SYNTAX      SEQUENCE OF VRtrLdpSessionInAddrEntry
    MAX-ACCESS  not-accessible
    STATUS      obsolete
    DESCRIPTION
        "vRtrLdpSessionInAddrTable is a read-only table that represents all
         local addresses received from an LDP peer for a single session between
         an LDP entity and an LDP Peer.

         In 13.0 this table has been replaced by
         TIMETRA-LDP-NG-MIB::vRtrLdpNgSessionInAddrTable."
    ::= { tmnxLdpObjs 48 }

vRtrLdpSessionInAddrEntry        OBJECT-TYPE
    SYNTAX      VRtrLdpSessionInAddrEntry
    MAX-ACCESS  not-accessible
    STATUS      obsolete
    DESCRIPTION
        "Each row entry represents an instance of a local address received from
         an LDP peer."
    INDEX       {
        vRtrID,
        vRtrLdpPeerLdpId,
        vRtrLdpSessionInAddrAddrType,
        vRtrLdpSessionInAddrAddress
    }
    ::= { vRtrLdpSessionInAddrTable 1 }

VRtrLdpSessionInAddrEntry        ::= SEQUENCE
{
    vRtrLdpSessionInAddrAddrType     InetAddressType,
    vRtrLdpSessionInAddrAddress      InetAddress,
    vRtrLdpSessionInAddrLocalLdpId   MplsLdpIdentifier
}

vRtrLdpSessionInAddrAddrType     OBJECT-TYPE
    SYNTAX      InetAddressType
    MAX-ACCESS  not-accessible
    STATUS      obsolete
    DESCRIPTION
        "The value of vRtrLdpSessionInAddrAddrType indicates the address type
         of vRtrLdpSessionInAddrAddress.

         This object was obsoleted in release 13.0."
    ::= { vRtrLdpSessionInAddrEntry 1 }

vRtrLdpSessionInAddrAddress      OBJECT-TYPE
    SYNTAX      InetAddress (SIZE (4|16))
    MAX-ACCESS  not-accessible
    STATUS      obsolete
    DESCRIPTION
        "The value of vRtrLdpSessionInAddrAddress indicates the IP address
         received from the peer for this LDP session.

         This object was obsoleted in release 13.0."
    ::= { vRtrLdpSessionInAddrEntry 2 }

vRtrLdpSessionInAddrLocalLdpId   OBJECT-TYPE
    SYNTAX      MplsLdpIdentifier
    MAX-ACCESS  read-only
    STATUS      obsolete
    DESCRIPTION
        "The value of vRtrLdpSessionInAddrLocalLdpId indicates the local LDP
         identifier for this LDP session.

         This object was obsoleted in release 13.0."
    ::= { vRtrLdpSessionInAddrEntry 3 }

vRtrLdpSessionOutAddrTable       OBJECT-TYPE
    SYNTAX      SEQUENCE OF VRtrLdpSessionOutAddrEntry
    MAX-ACCESS  not-accessible
    STATUS      obsolete
    DESCRIPTION
        "vRtrLdpSessionOutAddrTable is a read-only table that represents all
         local addresses sent to an LDP peer for a single session between an
         LDP entity and an LDP Peer.

         In 13.0 this table has been replaced by
         TIMETRA-LDP-NG-MIB::vRtrLdpNgSessionOutAddrTable."
    ::= { tmnxLdpObjs 49 }

vRtrLdpSessionOutAddrEntry       OBJECT-TYPE
    SYNTAX      VRtrLdpSessionOutAddrEntry
    MAX-ACCESS  not-accessible
    STATUS      obsolete
    DESCRIPTION
        "Each row entry represents an instance of a local address sent to an
         LDP peer."
    INDEX       {
        vRtrID,
        vRtrLdpPeerLdpId,
        vRtrLdpSessionOutAddrAddrType,
        vRtrLdpSessionOutAddrAddress
    }
    ::= { vRtrLdpSessionOutAddrTable 1 }

VRtrLdpSessionOutAddrEntry       ::= SEQUENCE
{
    vRtrLdpSessionOutAddrAddrType    InetAddressType,
    vRtrLdpSessionOutAddrAddress     InetAddress,
    vRtrLdpSessionOutAddrLocalLdpId  MplsLdpIdentifier
}

vRtrLdpSessionOutAddrAddrType    OBJECT-TYPE
    SYNTAX      InetAddressType
    MAX-ACCESS  not-accessible
    STATUS      obsolete
    DESCRIPTION
        "The value of vRtrLdpSessionOutAddrAddrType indicates the address type
         of vRtrLdpSessionOutAddrAddress.

         This object was obsoleted in release 13.0."
    ::= { vRtrLdpSessionOutAddrEntry 1 }

vRtrLdpSessionOutAddrAddress     OBJECT-TYPE
    SYNTAX      InetAddress (SIZE (4|16))
    MAX-ACCESS  not-accessible
    STATUS      obsolete
    DESCRIPTION
        "The value of vRtrLdpSessionOutAddrAddress indicates the IP address
         sent to the peer for this LDP session.

         This object was obsoleted in release 13.0."
    ::= { vRtrLdpSessionOutAddrEntry 2 }

vRtrLdpSessionOutAddrLocalLdpId  OBJECT-TYPE
    SYNTAX      MplsLdpIdentifier
    MAX-ACCESS  read-only
    STATUS      obsolete
    DESCRIPTION
        "The value of vRtrLdpSessionOutAddrLocalLdpId indicates the local LDP
         identifier for this LDP session.

         This object was obsoleted in release 13.0."
    ::= { vRtrLdpSessionOutAddrEntry 3 }

vRtrLdpPeerTemplTableLstChanged  OBJECT-TYPE
    SYNTAX      TimeStamp
    MAX-ACCESS  read-only
    STATUS      current
    DESCRIPTION
        "The value of vRtrLdpPeerTemplTableLstChanged indicates the last
         timestamp when an entry in the vRtrLdpPeerTemplTable was last changed."
    ::= { tmnxLdpObjs 50 }

vRtrLdpPeerTemplTable            OBJECT-TYPE
    SYNTAX      SEQUENCE OF VRtrLdpPeerTemplEntry
    MAX-ACCESS  not-accessible
    STATUS      current
    DESCRIPTION
        "vRtrLdpPeerTemplTable provides an entry for each virtual router
         targeted peer template configuration to be used with LDP."
    ::= { tmnxLdpObjs 51 }

vRtrLdpPeerTemplEntry            OBJECT-TYPE
    SYNTAX      VRtrLdpPeerTemplEntry
    MAX-ACCESS  not-accessible
    STATUS      current
    DESCRIPTION
        "Each row entry represents an targeted peer template on this virtual
         router that participates in the LDP protocol. Row entries can be
         created or deleted via SNMP SET requests. A row with default attribute
         values is created by setting vRtrLdpPeerTemplRowStatus to
         'createAndGo'. A row entry can be destroyed by setting
         vRtrLdpPeerTemplRowStatus to 'destroy'."
    INDEX       {
        vRtrID,
        vRtrLdpPeerTemplName
    }
    ::= { vRtrLdpPeerTemplTable 1 }

VRtrLdpPeerTemplEntry            ::= SEQUENCE
{
    vRtrLdpPeerTemplName             TNamedItem,
    vRtrLdpPeerTemplLastChanged      TimeStamp,
    vRtrLdpPeerTemplRowStatus        RowStatus,
    vRtrLdpPeerTemplAdminState       TmnxAdminState,
    vRtrLdpPeerTemplInheritance      Unsigned32,
    vRtrLdpPeerTemplKeepAliveFactor  TmnxLdpKeepAliveFactor,
    vRtrLdpPeerTemplKeepAliveTimeout TmnxLdpNewKeepAliveTimeout,
    vRtrLdpPeerTemplHelloFactor      TmnxLdpHelloFactor,
    vRtrLdpPeerTemplHelloTimeout     TmnxLdpNewHelloTimeout,
    vRtrLdpPeerTemplTunneling        TruthValue,
    vRtrLdpPeerTemplBfdEnabled       TruthValue,
    vRtrLdpPeerTemplLsrIfIndex       InterfaceIndexOrZero,
    vRtrLdpPeerTemplHelloReduction   TruthValue,
    vRtrLdpPeerTemplHelloReductnFctr Unsigned32,
    vRtrLdpPeerTemplCreateTime       TimeStamp,
    vRtrLdpPeerTemplIndex            Counter64,
    vRtrLdpPeerTemplLsrIdAdvert      TruthValue,
    vRtrLdpPeerTemplLsrIdCommunity   TPolicyStatementNameOrEmpty,
    vRtrLdpPeerTemplMcastTunneling   TruthValue
}

vRtrLdpPeerTemplName             OBJECT-TYPE
    SYNTAX      TNamedItem
    MAX-ACCESS  not-accessible
    STATUS      current
    DESCRIPTION
        "The value of vRtrLdpPeerTemplName uniquely identifies the name of the
         targeted peer template within a virtual router instance."
    ::= { vRtrLdpPeerTemplEntry 1 }

vRtrLdpPeerTemplLastChanged      OBJECT-TYPE
    SYNTAX      TimeStamp
    MAX-ACCESS  read-only
    STATUS      current
    DESCRIPTION
        "The value of vRtrLdpPeerTemplLastChanged indicates the sysUpTime when
         this row was last modified."
    ::= { vRtrLdpPeerTemplEntry 2 }

vRtrLdpPeerTemplRowStatus        OBJECT-TYPE
    SYNTAX      RowStatus
    MAX-ACCESS  read-create
    STATUS      current
    DESCRIPTION
        "The value of vRtrLdpPeerTemplRowStatus specifies the row status of an
         entry in vRtrLdpPeerTemplTable.It is used to control the creation and
         deletion of rows. A row can be created by setting
         vRtrLdpPeerTemplRowStatus to 'createAndGo'. A row entry can be
         destroyed by setting vRtrLdpPeerTemplRowStatus to 'destroy'."
    ::= { vRtrLdpPeerTemplEntry 3 }

vRtrLdpPeerTemplAdminState       OBJECT-TYPE
    SYNTAX      TmnxAdminState
    MAX-ACCESS  read-create
    STATUS      current
    DESCRIPTION
        "The value of vRtrLdpPeerTemplAdminState specifies administrative state
         of the targeted peer template."
    DEFVAL      { inService }
    ::= { vRtrLdpPeerTemplEntry 4 }

vRtrLdpPeerTemplInheritance      OBJECT-TYPE
    SYNTAX      Unsigned32
    MAX-ACCESS  read-create
    STATUS      current
    DESCRIPTION
        "The value of vRtrLdpPeerTemplInheritance specifies if the peer
         template entry in this row, should inherit the operational value of an
         object, or use the administratively set value. Non mask bits will
         always have value of zero, and any attempt to change the value will be
         silently discarded.

         This object is a bit-mask, with the following positions:
         vRtrLdpPeerTemplKeepAliveFactor       0x01
         vRtrLdpPeerTemplKeepAliveTimeout      0x02
         vRtrLdpPeerTemplHelloFactor           0x04
         vRtrLdpPeerTemplHelloTimeout          0x08
         vRtrLdpPeerTemplHelloReduction        0x10
         vRtrLdpPeerTemplHelloReductnFctr      0x20

         When the bit for an object has value of one, then the object's
         administrative and operational value are whatever the DEFVAL or most
         recently SET value. The mask bit(s) will be set to one when set is
         performed on the inherited object(s). Any attempt to set the mask bit
         to one will be silently discarded.

         When the bit for an object is set to zero, then the object's
         administrative and operational value are inherited from the
         corresponding targeted peer object in vRtrLdpGeneralTable."
    DEFVAL      { 0 }
    ::= { vRtrLdpPeerTemplEntry 5 }

vRtrLdpPeerTemplKeepAliveFactor  OBJECT-TYPE
    SYNTAX      TmnxLdpKeepAliveFactor
    MAX-ACCESS  read-create
    STATUS      current
    DESCRIPTION
        "The value of vRtrLdpPeerTemplKeepAliveFactor specifies the value by
         which the keepalive timeout (vRtrLdpPeerTemplKeepAliveTimeout) should
         be divided to give the keepalive time i.e. the time interval, in
         seconds, between LDP keepalive messages. LDP keepalive messages are
         sent to keep the LDP session from timing out when no other LDP traffic
         is being sent between the neighbors."
    DEFVAL      { 4 }
    ::= { vRtrLdpPeerTemplEntry 6 }

vRtrLdpPeerTemplKeepAliveTimeout OBJECT-TYPE
    SYNTAX      TmnxLdpNewKeepAliveTimeout
    UNITS       "seconds"
    MAX-ACCESS  read-create
    STATUS      current
    DESCRIPTION
        "The value of vRtrLdpPeerTemplKeepAliveTimeout specifies the time
         interval, in seconds, that LDP waits before tearing down a session. If
         no LDP messages are exchanged during this time interval, the LDP
         session is torn down. Generally the value of
         vRtrLdpPeerTemplKeepAliveTimeout is configured to be three times the
         keepalive time (the time interval between successive LDP keepalive
         messages)."
    DEFVAL      { 40 }
    ::= { vRtrLdpPeerTemplEntry 7 }

vRtrLdpPeerTemplHelloFactor      OBJECT-TYPE
    SYNTAX      TmnxLdpHelloFactor
    MAX-ACCESS  read-create
    STATUS      current
    DESCRIPTION
        "The value of vRtrLdpPeerTemplHelloFactor specifies the value by which
         the hello timeout (vRtrLdpPeerTemplHelloTimeout) should be divided to
         give the hello time i.e. the time interval, in seconds, between LDP
         Hello messages. LDP uses hello messages to discover neighbors and to
         detect loss of connectivity with its neighbors."
    DEFVAL      { 3 }
    ::= { vRtrLdpPeerTemplEntry 8 }

vRtrLdpPeerTemplHelloTimeout     OBJECT-TYPE
    SYNTAX      TmnxLdpNewHelloTimeout
    UNITS       "seconds"
    MAX-ACCESS  read-create
    STATUS      current
    DESCRIPTION
        "The value of vRtrLdpPeerTemplHelloTimeout specifies the hello time
         also known as hold time. It is the time interval, in seconds, that LDP
         waits before declaring a neighbor to be down. Hello timeout is local
         to the system and is sent in the hello messages to a neighbor. Hello
         timeout cannot be set to a value that is less than three times the
         hello time."
    DEFVAL      { 45 }
    ::= { vRtrLdpPeerTemplEntry 9 }

vRtrLdpPeerTemplTunneling        OBJECT-TYPE
    SYNTAX      TruthValue
    MAX-ACCESS  read-create
    STATUS      current
    DESCRIPTION
        "The value of vRtrLdpPeerTemplTunneling specifies whether tunneling of
         LDP over prefix tunnels is enabled. When this object has a value of
         'true', tunneling is enabled. When its value is 'false', tunneling is
         disabled."
    DEFVAL      { false }
    ::= { vRtrLdpPeerTemplEntry 10 }

vRtrLdpPeerTemplBfdEnabled       OBJECT-TYPE
    SYNTAX      TruthValue
    MAX-ACCESS  read-create
    STATUS      current
    DESCRIPTION
        "The value of vRtrLdpPeerTemplBfdEnabled specifies whether BFD tracking
         of a LDP Session is enabled for this template. When this object has a
         value of 'true', BFD tracking is enabled. When its value is 'false',
         BFD tracking is disabled."
    DEFVAL      { false }
    ::= { vRtrLdpPeerTemplEntry 11 }

vRtrLdpPeerTemplLsrIfIndex       OBJECT-TYPE
    SYNTAX      InterfaceIndexOrZero
    MAX-ACCESS  read-create
    STATUS      current
    DESCRIPTION
        "The value of vRtrLdpPeerTemplLsrIfIndex specifies the local interface
         index that is to be used as source LSR-ID to establish targeted hello
         adjacency with a LDP peer."
    DEFVAL      { 0 }
    ::= { vRtrLdpPeerTemplEntry 12 }

vRtrLdpPeerTemplHelloReduction   OBJECT-TYPE
    SYNTAX      TruthValue
    MAX-ACCESS  read-create
    STATUS      current
    DESCRIPTION
        "The value of vRtrLdpPeerTemplHelloReduction specifies whether hello
         reduction is enabled or not for this targeted peer template.If
         enabled, the sender advertises the dampened
         vRtrLdpPeerTemplHelloTimeout to the targeted peer after LDP session is
         established.

         The value of 'true' means targeted hello reduction is enabled."
    DEFVAL      { false }
    ::= { vRtrLdpPeerTemplEntry 13 }

vRtrLdpPeerTemplHelloReductnFctr OBJECT-TYPE
    SYNTAX      Unsigned32 (3..20)
    MAX-ACCESS  read-create
    STATUS      current
    DESCRIPTION
        "The value of vRtrLdpPeerTemplHelloReductnFctr specifies the number of
         hello messages that are sent at consistent
         vRtrLdpPeerTemplHelloTimeout, before advertising further dampened
         vRtrLdpPeerTemplHelloTimeout. An 'inconsistentValue' error is returned
         if this object is set when vRtrLdpPeerTemplHelloReduction is disabled."
    DEFVAL      { 3 }
    ::= { vRtrLdpPeerTemplEntry 14 }

vRtrLdpPeerTemplCreateTime       OBJECT-TYPE
    SYNTAX      TimeStamp
    MAX-ACCESS  read-only
    STATUS      current
    DESCRIPTION
        "The value of vRtrLdpPeerTemplCreateTime indicates the sysUpTime when
         this LDP peer template was created."
    ::= { vRtrLdpPeerTemplEntry 15 }

vRtrLdpPeerTemplIndex            OBJECT-TYPE
    SYNTAX      Counter64
    MAX-ACCESS  read-only
    STATUS      current
    DESCRIPTION
        "The value of vRtrLdpPeerTemplIndex indicates a unique value greater
         than zero which identifies this template for this virtual router in
         the Nokia SROS system. It is a unique value among entries within the
         same value of vRtrID.

         The value of vRtrLdpPeerTemplIndex represents the order in which the
         templates are created. This is also the order in which configuration
         will be saved. In the running system, this value may have gaps as
         templates are added and deleted. This is volatile object; hence, it is
         not persistent across reboot."
    ::= { vRtrLdpPeerTemplEntry 16 }

vRtrLdpPeerTemplLsrIdAdvert      OBJECT-TYPE
    SYNTAX      TruthValue
    MAX-ACCESS  read-create
    STATUS      current
    DESCRIPTION
        "The value of vRtrLdpPeerTemplLsrIdAdvert specifies whether  or not
         advertisement of a local-LSR ID is sent over a given  T-LDP session.

         When this object has a value of 'true', advertising is  enabled,
         otherwise it is disabled."
    DEFVAL      { false }
    ::= { vRtrLdpPeerTemplEntry 17 }

vRtrLdpPeerTemplLsrIdCommunity   OBJECT-TYPE
    SYNTAX      TPolicyStatementNameOrEmpty
    MAX-ACCESS  read-create
    STATUS      current
    DESCRIPTION
        "The value of vRtrLdpPeerTemplLsrIdCommunity defines a community string
         associated with a session to a given peer"
    DEFVAL      { ''H }
    ::= { vRtrLdpPeerTemplEntry 18 }

vRtrLdpPeerTemplMcastTunneling   OBJECT-TYPE
    SYNTAX      TruthValue
    MAX-ACCESS  read-create
    STATUS      current
    DESCRIPTION
        "The value of vRtrLdpPeerTemplMcastTunneling specifies whether
         tunneling of LDP over multicast tunnels is enabled. When this object
         has a value of 'true', tunneling is enabled. When its value is
         'false', tunneling is disabled."
    DEFVAL      { false }
    ::= { vRtrLdpPeerTemplEntry 19 }

vRtrLdpPeerTmplPlcyMpTblLstChgd  OBJECT-TYPE
    SYNTAX      TimeStamp
    MAX-ACCESS  read-only
    STATUS      current
    DESCRIPTION
        "The value of vRtrLdpPeerTmplPlcyMpTblLstChgd indicates the last
         timestamp when an entry in the vRtrLdpPeerTemplPlcyMapTable was last
         changed."
    ::= { tmnxLdpObjs 52 }

vRtrLdpPeerTemplPlcyMapTable     OBJECT-TYPE
    SYNTAX      SEQUENCE OF VRtrLdpPeerTemplPlcyMapEntry
    MAX-ACCESS  not-accessible
    STATUS      current
    DESCRIPTION
        "vRtrLdpPeerTemplPlcyMapTable maps targeted peer template entry to peer
         policy to be used with the Label Distribution Protocol (LDP)."
    ::= { tmnxLdpObjs 53 }

vRtrLdpPeerTemplPlcyMapEntry     OBJECT-TYPE
    SYNTAX      VRtrLdpPeerTemplPlcyMapEntry
    MAX-ACCESS  not-accessible
    STATUS      current
    DESCRIPTION
        "Each row entry maps a targeted peer template configuration to a set of
         policies for a virtual router in system. Row entries can be created or
         deleted via SNMP SET requests.

         A row is created by setting vRtrLdpPeerTemplPlcyMapRowStatus to
         'createAndGo' provided the corresponding LSP id exists as an MPLS lsp.
         A row entry can be destroyed by setting
         vRtrLdpPeerTemplPlcyMapRowStatus to 'destroy'."
    INDEX       {
        vRtrID,
        vRtrLdpPeerTemplName
    }
    ::= { vRtrLdpPeerTemplPlcyMapTable 1 }

VRtrLdpPeerTemplPlcyMapEntry     ::= SEQUENCE
{
    vRtrLdpPeerTemplPlcyMapLstChange TimeStamp,
    vRtrLdpPeerTemplPlcyMapRowStatus RowStatus,
    vRtrLdpPeerTemplPlcyMapPolicy1   TPolicyStatementNameOrEmpty,
    vRtrLdpPeerTemplPlcyMapPolicy2   TPolicyStatementNameOrEmpty,
    vRtrLdpPeerTemplPlcyMapPolicy3   TPolicyStatementNameOrEmpty,
    vRtrLdpPeerTemplPlcyMapPolicy4   TPolicyStatementNameOrEmpty,
    vRtrLdpPeerTemplPlcyMapPolicy5   TPolicyStatementNameOrEmpty,
    vRtrLdpPeerTemplPlcyMapIndex     Counter64,
    vRtrLdpPeerTemplPlcyMapCreateTim TimeStamp
}

vRtrLdpPeerTemplPlcyMapLstChange OBJECT-TYPE
    SYNTAX      TimeStamp
    MAX-ACCESS  read-only
    STATUS      current
    DESCRIPTION
        "The value of vRtrLdpPeerTemplPlcyMapLstChange indicates the sysUpTime
         when this row was last modified."
    ::= { vRtrLdpPeerTemplPlcyMapEntry 1 }

vRtrLdpPeerTemplPlcyMapRowStatus OBJECT-TYPE
    SYNTAX      RowStatus
    MAX-ACCESS  read-create
    STATUS      current
    DESCRIPTION
        "The value of vRtrLdpPeerTemplPlcyMapRowStatus specifies the row status
         of an entry in vRtrLdpPeerTemplPlcyMapTable. A row can be created by
         setting vRtrLdpPeerTemplPlcyMapRowStatus to 'createAndGo'. A row entry
         can be destroyed by setting vRtrLdpPeerTemplPlcyMapRowStatus to
         'destroy'."
    ::= { vRtrLdpPeerTemplPlcyMapEntry 2 }

vRtrLdpPeerTemplPlcyMapPolicy1   OBJECT-TYPE
    SYNTAX      TPolicyStatementNameOrEmpty
    MAX-ACCESS  read-create
    STATUS      current
    DESCRIPTION
        "The value of vRtrLdpPeerTemplPlcyMapPolicy1 specifies the first
         targeted peer template policy."
    DEFVAL      { ''H }
    ::= { vRtrLdpPeerTemplPlcyMapEntry 3 }

vRtrLdpPeerTemplPlcyMapPolicy2   OBJECT-TYPE
    SYNTAX      TPolicyStatementNameOrEmpty
    MAX-ACCESS  read-create
    STATUS      current
    DESCRIPTION
        "The value of vRtrLdpPeerTemplPlcyMapPolicy2 specifies the second
         targeted peer template policy."
    DEFVAL      { ''H }
    ::= { vRtrLdpPeerTemplPlcyMapEntry 4 }

vRtrLdpPeerTemplPlcyMapPolicy3   OBJECT-TYPE
    SYNTAX      TPolicyStatementNameOrEmpty
    MAX-ACCESS  read-create
    STATUS      current
    DESCRIPTION
        "The value of vRtrLdpPeerTemplPlcyMapPolicy3 specifies the third
         targeted peer template policy."
    DEFVAL      { ''H }
    ::= { vRtrLdpPeerTemplPlcyMapEntry 5 }

vRtrLdpPeerTemplPlcyMapPolicy4   OBJECT-TYPE
    SYNTAX      TPolicyStatementNameOrEmpty
    MAX-ACCESS  read-create
    STATUS      current
    DESCRIPTION
        "The value of vRtrLdpPeerTemplPlcyMapPolicy4 specifies the fourth
         targeted peer template policy."
    DEFVAL      { ''H }
    ::= { vRtrLdpPeerTemplPlcyMapEntry 6 }

vRtrLdpPeerTemplPlcyMapPolicy5   OBJECT-TYPE
    SYNTAX      TPolicyStatementNameOrEmpty
    MAX-ACCESS  read-create
    STATUS      current
    DESCRIPTION
        "The value of vRtrLdpPeerTemplPlcyMapPolicy5 specifies the fifth
         targeted peer template policy."
    DEFVAL      { ''H }
    ::= { vRtrLdpPeerTemplPlcyMapEntry 7 }

vRtrLdpPeerTemplPlcyMapIndex     OBJECT-TYPE
    SYNTAX      Counter64
    MAX-ACCESS  read-only
    STATUS      current
    DESCRIPTION
        "The value of vRtrLdpPeerTemplPlcyMapIndex indicates a unique value
         greater than zero which identifies this template policy map for this
         virtual router in the Nokia SROS system. It is a unique value among
         entries within the same value of vRtrID.

         The value of vRtrLdpPeerTemplPlcyMapIndex represents the order in
         which the template policy map are created. This is also the order in
         which configuration will be saved. In the running system, this value
         may have gaps as template policy maps are added and deleted. This is
         volatile object; hence, it is not persistent across reboot."
    ::= { vRtrLdpPeerTemplPlcyMapEntry 8 }

vRtrLdpPeerTemplPlcyMapCreateTim OBJECT-TYPE
    SYNTAX      TimeStamp
    MAX-ACCESS  read-only
    STATUS      current
    DESCRIPTION
        "The value of vRtrLdpPeerTemplPlcyMapCreateTim indicates the sysUpTime
         when this LDP peer template policy map was created."
    ::= { vRtrLdpPeerTemplPlcyMapEntry 9 }

vRtrLdpPeerTemplPeerTable        OBJECT-TYPE
    SYNTAX      SEQUENCE OF VRtrLdpPeerTemplPeerEntry
    MAX-ACCESS  not-accessible
    STATUS      current
    DESCRIPTION
        "vRtrLdpPeerTemplPeerTable is a read-only table that represents all
         auto discovered peers for a peer template."
    ::= { tmnxLdpObjs 54 }

vRtrLdpPeerTemplPeerEntry        OBJECT-TYPE
    SYNTAX      VRtrLdpPeerTemplPeerEntry
    MAX-ACCESS  not-accessible
    STATUS      current
    DESCRIPTION
        "Each row entry represents an auto discovered peer for a peer template."
    INDEX       {
        vRtrID,
        vRtrLdpPeerTemplName,
        vRtrLdpPeerTemplPeerAddrType,
        vRtrLdpPeerTemplPeerAddress
    }
    ::= { vRtrLdpPeerTemplPeerTable 1 }

VRtrLdpPeerTemplPeerEntry        ::= SEQUENCE
{
    vRtrLdpPeerTemplPeerAddrType     InetAddressType,
    vRtrLdpPeerTemplPeerAddress      InetAddress,
    vRtrLdpPeerTemplPeerCreateTime   TimeStamp
}

vRtrLdpPeerTemplPeerAddrType     OBJECT-TYPE
    SYNTAX      InetAddressType
    MAX-ACCESS  not-accessible
    STATUS      current
    DESCRIPTION
        "The value of vRtrLdpPeerTemplPeerAddrType indicates the address type
         of vRtrLdpPeerTemplPeerAddress."
    ::= { vRtrLdpPeerTemplPeerEntry 1 }

vRtrLdpPeerTemplPeerAddress      OBJECT-TYPE
    SYNTAX      InetAddress (SIZE (4|16))
    MAX-ACCESS  not-accessible
    STATUS      current
    DESCRIPTION
        "The value of vRtrLdpPeerTemplPeerAddress indicates the peer IP
         address."
    ::= { vRtrLdpPeerTemplPeerEntry 2 }

vRtrLdpPeerTemplPeerCreateTime   OBJECT-TYPE
    SYNTAX      TimeStamp
    MAX-ACCESS  read-only
    STATUS      current
    DESCRIPTION
        "The value of vRtrLdpPeerTemplPeerCreateTime indicates the peer create
         time."
    ::= { vRtrLdpPeerTemplPeerEntry 3 }

tmnxLdpConformance               OBJECT IDENTIFIER ::= { tmnxSRConfs 8 }

tmnxLdpCompliances               OBJECT IDENTIFIER ::= { tmnxLdpConformance 1 }

tmnxLdpV4v0Compliance            MODULE-COMPLIANCE
    STATUS      obsolete
    DESCRIPTION
        "The compliance statement for management of extended LDP on Nokia SROS
         series systems 4.0 release."
    MODULE
        MANDATORY-GROUPS {
            tmnxLdpGlobalV3v0Group,
            tmnxLdpIfV3v0Group,
            tmnxLdpAdjR2r1Group,
            tmnxLdpSessionR2r1Group,
            tmnxLdpServFecV4v0Group,
            tmnxLdpAddrFecGroup,
            tmnxLdpNotificationGroup,
            tmnxLdpStaticFecV3v0Group
        }
    ::= { tmnxLdpCompliances 4 }

tmnxLdpV5v0Compliance            MODULE-COMPLIANCE
    STATUS      obsolete
    DESCRIPTION
        "The compliance statement for management of extended LDP on Nokia SROS
         series systems 5.0 release."
    MODULE
        MANDATORY-GROUPS {
            tmnxLdpGlobalV5v0Group,
            tmnxLdpIfV5v0Group,
            tmnxLdpAdjR2r1Group,
            tmnxLdpSessionV5v0Group,
            tmnxLdpServFecV5v0Group,
            tmnxLdpAddrFecV5v0Group,
            tmnxLdpNotificationGroup,
            tmnxLdpStaticFecV3v0Group,
            tmnxLdpGenExtGlobalV5v0Group
        }
    ::= { tmnxLdpCompliances 5 }

tmnxLdpV6v0Compliance            MODULE-COMPLIANCE
    STATUS      obsolete
    DESCRIPTION
        "The compliance statement for management of extended LDP on Nokia SROS
         series systems 6.0 release."
    MODULE
        MANDATORY-GROUPS {
            tmnxLdpGlobalV5v0Group,
            tmnxLdpIfV5v0Group,
            tmnxLdpAdjR2r1Group,
            tmnxLdpSessionV5v0Group,
            tmnxLdpServFecV6v0Group,
            tmnxLdpServFec129V6v0Group,
            tmnxLdpAddrFecV5v0Group,
            tmnxLdpNotificationGroup,
            tmnxLdpStaticFecV3v0Group,
            tmnxLdpCepTdmFecV6v0Group,
            tmnxLdpGenExtGlobalV5v0Group
        }
    ::= { tmnxLdpCompliances 6 }

tmnxLdpV7v0Compliance            MODULE-COMPLIANCE
    STATUS      obsolete
    DESCRIPTION
        "The compliance statement for management of extended LDP on Nokia SROS
         series systems 7.0 release."
    MODULE
        MANDATORY-GROUPS {
            tmnxLdpGlobalV5v0Group,
            tmnxLdpIfV5v0Group,
            tmnxLdpAdjR2r1Group,
            tmnxLdpSessionV5v0Group,
            tmnxLdpServFecV6v0Group,
            tmnxLdpServFec129V6v0Group,
            tmnxLdpAddrFecV5v0Group,
            tmnxLdpNotificationGroup,
            tmnxLdpStaticFecV3v0Group,
            tmnxLdpAggrPreMatchV7v0Group,
            tmnxLdpStatsV7v0Group,
            tmnxLdpCepTdmFecV6v0Group,
            tmnxLdpGenExtGlobalV5v0Group
        }
    ::= { tmnxLdpCompliances 7 }

tmnxLdpV8v0Compliance            MODULE-COMPLIANCE
    STATUS      obsolete
    DESCRIPTION
        "The compliance statement for management of extended LDP on Nokia SROS
         series systems 8.0 release."
    MODULE
        MANDATORY-GROUPS {
            tmnxLdpGlobalV5v0Group,
            tmnxLdpIfV5v0Group,
            tmnxLdpAdjR2r1Group,
            tmnxLdpSessionV5v0Group,
            tmnxLdpServFecV6v0Group,
            tmnxLdpServFec129V6v0Group,
            tmnxLdpAddrFecV5v0Group,
            tmnxLdpNotificationGroup,
            tmnxLdpStaticFecV3v0Group,
            tmnxLdpAggrPreMatchV7v0Group,
            tmnxLdpStatsV7v0Group,
            tmnxLdpCepTdmFecV6v0Group,
            tmnxLdpGenExtGlobalV5v0Group,
            tmnxLdpGlobalV8v0Group,
            tmnxLdpSessionV8v0Group,
            tmnxLdpP2MPFecV8v0Group,
            tmnxLdpStatsV8v0Group,
            tmnxLdpPeerV7v0Group,
            tmnxLdpServFecV8v0Group,
            tmnxLdpServFec129V8v0Group,
            tmnxLdpAddrFecV8v0Group,
            tmnxLdpGlobalV8v0R4Group,
            tmnxLdpAddrFecV7v0Group
        }
    ::= { tmnxLdpCompliances 8 }

tmnxLdpV9v0Compliance            MODULE-COMPLIANCE
    STATUS      obsolete
    DESCRIPTION
        "The compliance statement for management of extended LDP on Nokia SROS
         series systems 9.0 release."
    MODULE
        MANDATORY-GROUPS {
            tmnxLdpGlobalV5v0Group,
            tmnxLdpIfV5v0Group,
            tmnxLdpAdjR2r1Group,
            tmnxLdpSessionV5v0Group,
            tmnxLdpServFecV6v0Group,
            tmnxLdpServFec129V6v0Group,
            tmnxLdpAddrFecV5v0Group,
            tmnxLdpNotificationGroup,
            tmnxLdpStaticFecV3v0Group,
            tmnxLdpAggrPreMatchV7v0Group,
            tmnxLdpStatsV7v0Group,
            tmnxLdpAdjBackoffGroup,
            tmnxLdpCepTdmFecV6v0Group,
            tmnxLdpGenExtGlobalV5v0Group,
            tmnxLdpGlobalV8v0Group,
            tmnxLdpSessionV8v0Group,
            tmnxLdpP2MPFecV8v0Group,
            tmnxLdpStatsV8v0Group,
            tmnxLdpPeerV7v0Group,
            tmnxLdpServFecV8v0Group,
            tmnxLdpServFec129V8v0Group,
            tmnxLdpAddrFecV8v0Group,
            tmnxLdpGlobalV8v0R4Group,
            tmnxLdpAddrFecV7v0Group,
            tmnxLdpGlobalV9v0Group,
            tmnxLdpGlobalV9v0R4Group
        }
    ::= { tmnxLdpCompliances 9 }

tmnxLdpV10v0Compliance           MODULE-COMPLIANCE
    STATUS      obsolete
    DESCRIPTION
        "The compliance statement for management of extended LDP on Nokia SROS
         series systems 10.0 release."
    MODULE
        MANDATORY-GROUPS {
            tmnxLdpGlobalV5v0Group,
            tmnxLdpIfV5v0Group,
            tmnxLdpAdjR2r1Group,
            tmnxLdpSessionV5v0Group,
            tmnxLdpServFecV6v0Group,
            tmnxLdpServFec129V6v0Group,
            tmnxLdpNotificationGroup,
            tmnxLdpStaticFecV3v0Group,
            tmnxLdpAggrPreMatchV7v0Group,
            tmnxLdpStatsV7v0Group,
            tmnxLdpAdjBackoffGroup,
            tmnxLdpCepTdmFecV6v0Group,
            tmnxLdpGenExtGlobalV5v0Group,
            tmnxLdpGlobalV8v0Group,
            tmnxLdpSessionV8v0Group,
            tmnxLdpStatsV8v0Group,
            tmnxLdpPeerV7v0Group,
            tmnxLdpServFecV8v0Group,
            tmnxLdpServFec129V8v0Group,
            tmnxLdpGlobalV8v0R4Group,
            tmnxLdpGlobalV9v0Group,
            tmnxLdpGlobalV9v0R4Group,
            tmnxLdpP2MPFecV10v0Group,
            tmnxLdpAddressFecV10v0Group,
            tmnxLdpAddrActiveFecV10v0Group
        }
    ::= { tmnxLdpCompliances 10 }

tmnxLdpV11v0Compliance           MODULE-COMPLIANCE
    STATUS      obsolete
    DESCRIPTION
        "The compliance statement for management of extended LDP on Nokia SROS
         series systems 11.0 release."
    MODULE
        MANDATORY-GROUPS {
            tmnxLdpGlobalV5v0Group,
            tmnxLdpIfV5v0Group,
            tmnxLdpAdjR2r1Group,
            tmnxLdpSessionV5v0Group,
            tmnxLdpServFecV6v0Group,
            tmnxLdpServFec129V6v0Group,
            tmnxLdpNotificationGroup,
            tmnxLdpStaticFecV3v0Group,
            tmnxLdpAggrPreMatchV7v0Group,
            tmnxLdpStatsV7v0Group,
            tmnxLdpAdjBackoffGroup,
            tmnxLdpCepTdmFecV6v0Group,
            tmnxLdpGenExtGlobalV5v0Group,
            tmnxLdpGlobalV8v0Group,
            tmnxLdpSessionV8v0Group,
            tmnxLdpStatsV8v0Group,
            tmnxLdpPeerV7v0Group,
            tmnxLdpServFecV8v0Group,
            tmnxLdpServFec129V8v0Group,
            tmnxLdpGlobalV8v0R4Group,
            tmnxLdpGlobalV9v0Group,
            tmnxLdpGlobalV9v0R4Group,
            tmnxLdpP2MPFecV10v0Group,
            tmnxLdpAddressFecV10v0Group,
            tmnxLdpAddrActiveFecV10v0Group,
            tmnxLdpHelloReductionV11v0Group,
            tmnxLdpGlobalV11v0Group,
            tmnxLdpLsrOverloadV11v0Group,
            tmnxLdpTLDPAutoCreateV11v0Group,
            tmnxLdpLsrOvrloadNotify,
            tmnxLdpLsrOvrloadNotifyObjs
        }
    ::= { tmnxLdpCompliances 11 }

tmnxLdpV12v0Compliance           MODULE-COMPLIANCE
    STATUS      obsolete
    DESCRIPTION
        "The compliance statement for management of extended LDP on Nokia SROS
         series systems 12.0 release."
    MODULE
        MANDATORY-GROUPS {
            tmnxLdpGlobalV5v0Group,
            tmnxLdpIfV5v0Group,
            tmnxLdpAdjR2r1Group,
            tmnxLdpSessionV5v0Group,
            tmnxLdpServFecV6v0Group,
            tmnxLdpServFec129V6v0Group,
            tmnxLdpNotificationGroup,
            tmnxLdpStaticFecV3v0Group,
            tmnxLdpAggrPreMatchV7v0Group,
            tmnxLdpStatsV7v0Group,
            tmnxLdpAdjBackoffGroup,
            tmnxLdpCepTdmFecV6v0Group,
            tmnxLdpGenExtGlobalV5v0Group,
            tmnxLdpGlobalV8v0Group,
            tmnxLdpSessionV8v0Group,
            tmnxLdpStatsV8v0Group,
            tmnxLdpPeerV7v0Group,
            tmnxLdpServFecV8v0Group,
            tmnxLdpServFec129V8v0Group,
            tmnxLdpGlobalV8v0R4Group,
            tmnxLdpGlobalV9v0Group,
            tmnxLdpGlobalV9v0R4Group,
            tmnxLdpP2MPFecV10v0Group,
            tmnxLdpAddressFecV10v0Group,
            tmnxLdpAddrActiveFecV10v0Group,
            tmnxLdpHelloReductionV11v0Group,
            tmnxLdpGlobalV11v0Group,
            tmnxLdpLsrOverloadV11v0Group,
            tmnxLdpTLDPAutoCreateV11v0Group,
            tmnxLdpLsrOvrloadNotify,
            tmnxLdpLsrOvrloadNotifyObjs,
            tmnxLdpFecLimitPerPeerV13v0Group,
            tmnxLdpFecLimitPerPeerNotify,
            tmnxLdpFecLimitNotifyObjs
        }
    ::= { tmnxLdpCompliances 12 }

tmnxLdpV13v0Compliance           MODULE-COMPLIANCE
    STATUS      current
    DESCRIPTION
        "The compliance statement for management of extended LDP on Nokia SROS
         series systems 13.0 release."
    MODULE
        MANDATORY-GROUPS {
            tmnxLdpStatsV7v0Group,
            tmnxLdpObsoletedV13V0Group,
            tmnxLdpTLDPAutoCreateV13v0Group,
            tmnxLdpNotifyObjsV13v0Group,
            tmnxLdpObsoletedNotifyObjGroup,
            tmnxLdpObsoletedNtfnV13v0Group,
            tmnxLdpNotificationV13v0Group
        }
    ::= { tmnxLdpCompliances 13 }

tmnxLdpV15v0Compliance           MODULE-COMPLIANCE
    STATUS      current
    DESCRIPTION
        "The compliance statement for management of extended LDP on Nokia SROS
         series systems 15.0 release."
    MODULE
        MANDATORY-GROUPS {
            tmnxLdpLocalLsrIdAdvertGroup,
            tmnxLdpLocalLsrIdCommunityGroup
        }
    ::= { tmnxLdpCompliances 14 }

tmnxLdpV16v0Compliance           MODULE-COMPLIANCE
    STATUS      current
    DESCRIPTION
        "The compliance statement for management of extended LDP on Nokia SROS
         series systems release 16.0."
    MODULE
        MANDATORY-GROUPS {
            tmnxLdpAggrEgrStatsV16v0Group
        }
    ::= { tmnxLdpCompliances 15 }

tmnxLdpV20v0Compliance           MODULE-COMPLIANCE
    STATUS      current
    DESCRIPTION
        "The compliance statement for management of extended LDP on Nokia SROS
         series systems release 20.0."
    MODULE
        MANDATORY-GROUPS {
            tmnxLdpPeerMcastTunnelingGroup
        }
    ::= { tmnxLdpCompliances 16 }

tmnxLdpGroups                    OBJECT IDENTIFIER ::= { tmnxLdpConformance 2 }

tmnxLdpAddrFecGroup              OBJECT-GROUP
    OBJECTS     {
        vRtrLdpAddrFecFlags,
        vRtrLdpAddrFecNumInLabels,
        vRtrLdpAddrFecNumOutLabels,
        vRtrLdpAddrFecInLabel1,
        vRtrLdpAddrFecInLabelStatus1,
        vRtrLdpAddrFecInLabelIfIndex1,
        vRtrLdpAddrFecInLabel2,
        vRtrLdpAddrFecInLabelStatus2,
        vRtrLdpAddrFecInLabelIfIndex2,
        vRtrLdpAddrFecInLabel3,
        vRtrLdpAddrFecInLabelStatus3,
        vRtrLdpAddrFecInLabelIfIndex3,
        vRtrLdpAddrFecInLabel4,
        vRtrLdpAddrFecInLabelStatus4,
        vRtrLdpAddrFecInLabelIfIndex4,
        vRtrLdpAddrFecInLabel5,
        vRtrLdpAddrFecInLabelStatus5,
        vRtrLdpAddrFecInLabelIfIndex5,
        vRtrLdpAddrFecOutLabel1,
        vRtrLdpAddrFecOutLabelStatus1,
        vRtrLdpAddrFecOutLabelIfIndex1,
        vRtrLdpAddrFecOutLabelNextHop1,
        vRtrLdpAddrFecOutLabel2,
        vRtrLdpAddrFecOutLabelStatus2,
        vRtrLdpAddrFecOutLabelIfIndex2,
        vRtrLdpAddrFecOutLabelNextHop2,
        vRtrLdpAddrFecOutLabel3,
        vRtrLdpAddrFecOutLabelStatus3,
        vRtrLdpAddrFecOutLabelIfIndex3,
        vRtrLdpAddrFecOutLabelNextHop3,
        vRtrLdpAddrFecOutLabel4,
        vRtrLdpAddrFecOutLabelStatus4,
        vRtrLdpAddrFecOutLabelIfIndex4,
        vRtrLdpAddrFecOutLabelNextHop4,
        vRtrLdpAddrFecOutLabel5,
        vRtrLdpAddrFecOutLabelStatus5,
        vRtrLdpAddrFecOutLabelIfIndex5,
        vRtrLdpAddrFecOutLabelNextHop5,
        vRtrLdpAddrFecMapFecType,
        vRtrLdpAddrFecMapIpPrefix,
        vRtrLdpAddrFecMapIpMask
    }
    STATUS      obsolete
    DESCRIPTION
        "The group of objects supporting management of extended LDP address
         FECs sent to or received from an LDP peer on Nokia SROS series
         systems."
    ::= { tmnxLdpGroups 6 }

tmnxLdpNotifyObjsGroup           OBJECT-GROUP
    OBJECTS     {
        vRtrLdpInstanceNotifyReasonCode,
        vRtrLdpIfNotifyReasonCode,
        vRtrLdpNotifyLocalGroupID,
        vRtrLdpNotifyRemoteGroupID
    }
    STATUS      obsolete
    DESCRIPTION
        "The group of objects supporting extended LDP notifications on Nokia
         SROS series systems."
    ::= { tmnxLdpGroups 7 }

tmnxLdpNotificationGroup         NOTIFICATION-GROUP
    NOTIFICATIONS {
        vRtrLdpStateChange,
        vRtrLdpInstanceStateChange,
        vRtrLdpIfStateChange,
        vRtrLdpGroupIdMismatch
    }
    STATUS      obsolete
    DESCRIPTION
        "The group of notifications supporting the extended LDP feature on
         Nokia SROS series systems."
    ::= { tmnxLdpGroups 8 }

tmnxLdpAdjBackoffGroup           OBJECT-GROUP
    OBJECTS     {
        vRtrLdpAdjInitBackoff,
        vRtrLdpAdjMaxBackoff,
        vRtrLdpAdjCurrentBackoff,
        vRtrLdpAdjWaitingTime,
        vRtrLdpAdjBackoffStatus
    }
    STATUS      obsolete
    DESCRIPTION
        "The group of objects supporting general management of extended LDP
         adjacency backoff on Nokia SROS series systems. The
         vRtrLdpAdjBackoffTable is not yet supported by a TiMOS release."
    ::= { tmnxLdpGroups 10 }

tmnxLdpObsoleteObjsGroup         OBJECT-GROUP
    OBJECTS     {
        vRtrLdpNotifyLocalServiceID,
        vRtrLdpNotifyRemoteServiceID,
        vRtrLdpPolicyRowStatus,
        vRtrLdpPolicyName
    }
    STATUS      current
    DESCRIPTION
        "The group of obsolete objects for the extended LDP feature on Nokia
         SROS series systems."
    ::= { tmnxLdpGroups 11 }

tmnxLdpObsoleteNotificationGroup NOTIFICATION-GROUP
    NOTIFICATIONS {
        vRtrLdpSvcIdMismatch
    }
    STATUS      current
    DESCRIPTION
        "The group of obsolete notifications for the extended LDP feature on
         Nokia SROS series systems."
    ::= { tmnxLdpGroups 12 }

tmnxLdpAdjR2r1Group              OBJECT-GROUP
    OBJECTS     {
        vRtrLdpHelloAdjMapLdpId,
        vRtrLdpHelloAdjLocalLdpId,
        vRtrLdpHelloAdjEntityIndex,
        vRtrLdpHelloAdjIndex,
        vRtrLdpHelloAdjHoldTimeRemaining,
        vRtrLdpHelloAdjType,
        vRtrLdpHelloAdjRemoteConfSeqNum,
        vRtrLdpHelloAdjRemoteIpAddress,
        vRtrLdpHelloAdjUpTime,
        vRtrLdpHelloAdjLocalConfSeqNum,
        vRtrLdpHelloAdjLocalIpAddress,
        vRtrLdpHelloAdjInHelloMsgCount,
        vRtrLdpHelloAdjOutHelloMsgCount,
        vRtrLdpHelloAdjLocalHelloTimeout,
        vRtrLdpHelloAdjRemoteHelloTimeout
    }
    STATUS      obsolete
    DESCRIPTION
        "The group of objects supporting management of extended LDP Adjacencies
         for LDP sessions on Nokia SROS series systems 2.1 Release."
    ::= { tmnxLdpGroups 15 }

tmnxLdpSessionR2r1Group          OBJECT-GROUP
    OBJECTS     {
        vRtrLdpSessLocalLdpId,
        vRtrLdpSessEntityIndex,
        vRtrLdpSessLabelDistMethod,
        vRtrLdpSessLoopDetectForPV,
        vRtrLdpSessPathVectorLimit,
        vRtrLdpSessState,
        vRtrLdpSessAdjacencyType,
        vRtrLdpSessProtocolVersion,
        vRtrLdpSessLocalUdpPort,
        vRtrLdpSessPeerUdpPort,
        vRtrLdpSessLocalTcpPort,
        vRtrLdpSessPeerTcpPort,
        vRtrLdpSessLocalAddress,
        vRtrLdpSessPeerAddress,
        vRtrLdpSessKAHoldTimeRemaining,
        vRtrLdpSessMaxPduLength,
        vRtrLdpSessUpTime,
        vRtrLdpSessLocalKATimeout,
        vRtrLdpSessPeerKATimeout,
        vRtrLdpSessStatsTargAdj,
        vRtrLdpSessStatsLinkAdj,
        vRtrLdpSessStatsFECRecv,
        vRtrLdpSessStatsFECSent,
        vRtrLdpSessStatsHelloIn,
        vRtrLdpSessStatsHelloOut,
        vRtrLdpSessStatsKeepaliveIn,
        vRtrLdpSessStatsKeepaliveOut,
        vRtrLdpSessStatsInitIn,
        vRtrLdpSessStatsInitOut,
        vRtrLdpSessStatsLabelMappingIn,
        vRtrLdpSessStatsLabelMappingOut,
        vRtrLdpSessStatsLabelRequestIn,
        vRtrLdpSessStatsLabelRequestOut,
        vRtrLdpSessStatsLabelReleaseIn,
        vRtrLdpSessStatsLabelReleaseOut,
        vRtrLdpSessStatsLabelWithdrawIn,
        vRtrLdpSessStatsLabelWithdrawOut,
        vRtrLdpSessStatsLabelAbortIn,
        vRtrLdpSessStatsLabelAbortOut,
        vRtrLdpSessStatsAddrIn,
        vRtrLdpSessStatsAddrOut,
        vRtrLdpSessStatsAddrWithdrawIn,
        vRtrLdpSessStatsAddrWithdrawOut,
        vRtrLdpSessStatsNotificationIn,
        vRtrLdpSessStatsNotificationOut
    }
    STATUS      obsolete
    DESCRIPTION
        "The group of objects supporting management of extended LDP Sessions on
         Nokia SROS series systems 2.1 Release."
    ::= { tmnxLdpGroups 16 }

tmnxLdpStaticFecV3v0Group        OBJECT-GROUP
    OBJECTS     {
        vRtrLdpStaticFecRowStatus,
        vRtrLdpStaticFecNextNHIndex,
        vRtrLdpStaticFecIngLabel,
        vRtrLdpStaticFecNumNH,
        vRtrLdpStaticFecOperIngLabel,
        vRtrLdpStaticFecNHRowStatus,
        vRtrLdpStaticFecNHType,
        vRtrLdpStaticFecNHIpAddr,
        vRtrLdpStaticFecNHEgrLabel
    }
    STATUS      obsolete
    DESCRIPTION
        "The group of objects supporting management of LDP Static FECs on Nokia
         SROS series systems 3.0 release."
    ::= { tmnxLdpGroups 17 }

tmnxLdpIfV3v0Group               OBJECT-GROUP
    OBJECTS     {
        vRtrLdpIfTableSpinlock,
        vRtrLdpIfRowStatus,
        vRtrLdpIfLastChange,
        vRtrLdpIfAdminState,
        vRtrLdpIfOperState,
        vRtrLdpIfInheritance,
        vRtrLdpIfKeepAliveFactor,
        vRtrLdpIfKeepAliveTimeout,
        vRtrLdpIfHelloFactor,
        vRtrLdpIfHelloTimeout,
        vRtrLdpIfBackoffTime,
        vRtrLdpIfMaxBackoffTime,
        vRtrLdpIfTransportAddrType,
        vRtrLdpIfPassiveMode,
        vRtrLdpIfAutoCreate,
        vRtrLdpIfOperDownReason,
        vRtrLdpIfExistingAdjacencies,
        vRtrLdpPeerRowStatus,
        vRtrLdpPeerAuth,
        vRtrLdpPeerAuthKey,
        vRtrLdpPeerMinTTLValue,
        vRtrLdpPeerTTLLogId
    }
    STATUS      obsolete
    DESCRIPTION
        "The group of objects supporting management of extended LDP interfaces
         and targeted peers on Nokia SROS series systems 3.0 release."
    ::= { tmnxLdpGroups 19 }

tmnxLdpGlobalV3v0Group           OBJECT-GROUP
    OBJECTS     {
        vRtrLdpGenLastChange,
        vRtrLdpGenAdminState,
        vRtrLdpGenOperState,
        vRtrLdpGenLdpLsrId,
        vRtrLdpGenProtocolVersion,
        vRtrLdpGenDeaggregateFec,
        vRtrLdpGenKeepAliveFactor,
        vRtrLdpGenKeepAliveTimeout,
        vRtrLdpGenHelloFactor,
        vRtrLdpGenHelloTimeout,
        vRtrLdpGenRoutePreference,
        vRtrLdpGenControlMode,
        vRtrLdpGenDistMethod,
        vRtrLdpGenRetentionMode,
        vRtrLdpGenTransportAddrType,
        vRtrLdpGenPropagatePolicy,
        vRtrLdpGenLoopDetectCapable,
        vRtrLdpGenHopLimit,
        vRtrLdpGenPathVectorLimit,
        vRtrLdpGenBackoffTime,
        vRtrLdpGenMaxBackoffTime,
        vRtrLdpGenTargKeepAliveFactor,
        vRtrLdpGenTargKeepAliveTimeout,
        vRtrLdpGenTargHelloFactor,
        vRtrLdpGenTargHelloTimeout,
        vRtrLdpGenTargPassiveMode,
        vRtrLdpGenTargetedSessions,
        vRtrLdpGenCreateTime,
        vRtrLdpGenUpTime,
        vRtrLdpGenImportPolicy1,
        vRtrLdpGenImportPolicy2,
        vRtrLdpGenImportPolicy3,
        vRtrLdpGenImportPolicy4,
        vRtrLdpGenImportPolicy5,
        vRtrLdpGenExportPolicy1,
        vRtrLdpGenExportPolicy2,
        vRtrLdpGenExportPolicy3,
        vRtrLdpGenExportPolicy4,
        vRtrLdpGenExportPolicy5,
        vRtrLdpGenTunnelDownDampTime,
        vRtrLdpGenOperDownReason,
        vRtrLdpGenTrustList,
        vRtrLdpStatsOperDownEvents,
        vRtrLdpStatsActiveSessions,
        vRtrLdpStatsActiveAdjacencies,
        vRtrLdpStatsActiveInterfaces,
        vRtrLdpStatsInactiveInterfaces,
        vRtrLdpStatsActiveTargSessions,
        vRtrLdpStatsInactiveTargSessions,
        vRtrLdpStatsAddrFECRecv,
        vRtrLdpStatsAddrFECSent,
        vRtrLdpStatsSvcFECRecv,
        vRtrLdpStatsSvcFECSent,
        vRtrLdpStatsAttemptedSessions,
        vRtrLdpStatsSessRejNoHelloErrors,
        vRtrLdpStatsSessRejAdvErrors,
        vRtrLdpStatsSessRejMaxPduErrors,
        vRtrLdpStatsSessRejLabelRangeErrors,
        vRtrLdpStatsBadLdpIdentifierErrors,
        vRtrLdpStatsBadPduLengthErrors,
        vRtrLdpStatsBadMessageLengthErrors,
        vRtrLdpStatsBadTlvLengthErrors,
        vRtrLdpStatsMalformedTlvValueErrors,
        vRtrLdpStatsKeepAliveExpiredErrors,
        vRtrLdpStatsShutdownNotifRecv,
        vRtrLdpStatsShutdownNotifSent
    }
    STATUS      obsolete
    DESCRIPTION
        "The group of objects supporting general management of extended LDP on
         Nokia SROS series systems 3.0 release."
    ::= { tmnxLdpGroups 20 }

tmnxLdpServFecV4v0Group          OBJECT-GROUP
    OBJECTS     {
        vRtrLdpServFecServType,
        vRtrLdpServFecServId,
        vRtrLdpServFecVpnId,
        vRtrLdpServFecFlags,
        vRtrLdpServFecNumInLabels,
        vRtrLdpServFecNumOutLabels,
        vRtrLdpServFecInLabel1,
        vRtrLdpServFecInLabelStatus1,
        vRtrLdpServFecInLabel2,
        vRtrLdpServFecInLabelStatus2,
        vRtrLdpServFecInLabel3,
        vRtrLdpServFecInLabelStatus3,
        vRtrLdpServFecInLabel4,
        vRtrLdpServFecInLabelStatus4,
        vRtrLdpServFecInLabel5,
        vRtrLdpServFecInLabelStatus5,
        vRtrLdpServFecOutLabel1,
        vRtrLdpServFecOutLabelStatus1,
        vRtrLdpServFecOutLabel2,
        vRtrLdpServFecOutLabelStatus2,
        vRtrLdpServFecOutLabel3,
        vRtrLdpServFecOutLabelStatus3,
        vRtrLdpServFecOutLabel4,
        vRtrLdpServFecOutLabelStatus4,
        vRtrLdpServFecOutLabel5,
        vRtrLdpServFecOutLabelStatus5,
        vRtrLdpServFecSdpId,
        vRtrLdpServFecLocalMTU,
        vRtrLdpServFecRemoteMTU,
        vRtrLdpServFecLocalVlanTag,
        vRtrLdpServFecRemoteVlanTag,
        vRtrLdpServFecLocalMaxCellConcat,
        vRtrLdpServFecRemoteMaxCellConcat,
        vRtrLdpServFecMapFecType,
        vRtrLdpServFecMapVcType,
        vRtrLdpServFecMapVcId,
        vRtrLdpServFecInLabelSigStatus1,
        vRtrLdpServFecInLabelSigStatus2,
        vRtrLdpServFecInLabelSigStatus3,
        vRtrLdpServFecInLabelSigStatus4,
        vRtrLdpServFecInLabelSigStatus5,
        vRtrLdpServFecOutLabelSigStatus1,
        vRtrLdpServFecOutLabelSigStatus2,
        vRtrLdpServFecOutLabelSigStatus3,
        vRtrLdpServFecOutLabelSigStatus4,
        vRtrLdpServFecOutLabelSigStatus5
    }
    STATUS      obsolete
    DESCRIPTION
        "The group of objects supporting management of extended LDP service
         FECs sent to or received from an LDP peer on Nokia SROS series systems
         release 4.0."
    ::= { tmnxLdpGroups 21 }

tmnxLdpGlobalV5v0Group           OBJECT-GROUP
    OBJECTS     {
        vRtrLdpGenLastChange,
        vRtrLdpGenAdminState,
        vRtrLdpGenOperState,
        vRtrLdpGenLdpLsrId,
        vRtrLdpGenProtocolVersion,
        vRtrLdpGenDeaggregateFec,
        vRtrLdpGenKeepAliveFactor,
        vRtrLdpGenKeepAliveTimeout,
        vRtrLdpGenHelloFactor,
        vRtrLdpGenHelloTimeout,
        vRtrLdpGenRoutePreference,
        vRtrLdpGenControlMode,
        vRtrLdpGenDistMethod,
        vRtrLdpGenRetentionMode,
        vRtrLdpGenTransportAddrType,
        vRtrLdpGenPropagatePolicy,
        vRtrLdpGenLoopDetectCapable,
        vRtrLdpGenHopLimit,
        vRtrLdpGenPathVectorLimit,
        vRtrLdpGenBackoffTime,
        vRtrLdpGenMaxBackoffTime,
        vRtrLdpGenTargKeepAliveFactor,
        vRtrLdpGenTargKeepAliveTimeout,
        vRtrLdpGenTargHelloFactor,
        vRtrLdpGenTargHelloTimeout,
        vRtrLdpGenTargPassiveMode,
        vRtrLdpGenTargetedSessions,
        vRtrLdpGenCreateTime,
        vRtrLdpGenUpTime,
        vRtrLdpGenImportPolicy1,
        vRtrLdpGenImportPolicy2,
        vRtrLdpGenImportPolicy3,
        vRtrLdpGenImportPolicy4,
        vRtrLdpGenImportPolicy5,
        vRtrLdpGenExportPolicy1,
        vRtrLdpGenExportPolicy2,
        vRtrLdpGenExportPolicy3,
        vRtrLdpGenExportPolicy4,
        vRtrLdpGenExportPolicy5,
        vRtrLdpGenTunnelDownDampTime,
        vRtrLdpGenOperDownReason,
        vRtrLdpGenGracefulRestart,
        vRtrLdpGenGRNbrLiveTime,
        vRtrLdpGenGRMaxRecoveryTime,
        vRtrLdpTargImportPolicy1,
        vRtrLdpTargImportPolicy2,
        vRtrLdpTargImportPolicy3,
        vRtrLdpTargImportPolicy4,
        vRtrLdpTargImportPolicy5,
        vRtrLdpTargExportPolicy1,
        vRtrLdpTargExportPolicy2,
        vRtrLdpTargExportPolicy3,
        vRtrLdpTargExportPolicy4,
        vRtrLdpTargExportPolicy5,
        vRtrLdpTargTunnelPreference,
        vRtrLdpStatsOperDownEvents,
        vRtrLdpStatsActiveSessions,
        vRtrLdpStatsActiveAdjacencies,
        vRtrLdpStatsActiveInterfaces,
        vRtrLdpStatsInactiveInterfaces,
        vRtrLdpStatsActiveTargSessions,
        vRtrLdpStatsInactiveTargSessions,
        vRtrLdpStatsAddrFECRecv,
        vRtrLdpStatsAddrFECSent,
        vRtrLdpStatsSvcFECRecv,
        vRtrLdpStatsSvcFECSent,
        vRtrLdpStatsAttemptedSessions,
        vRtrLdpStatsSessRejNoHelloErrors,
        vRtrLdpStatsSessRejAdvErrors,
        vRtrLdpStatsSessRejMaxPduErrors,
        vRtrLdpStatsSessRejLabelRangeErrors,
        vRtrLdpStatsBadLdpIdentifierErrors,
        vRtrLdpStatsBadPduLengthErrors,
        vRtrLdpStatsBadMessageLengthErrors,
        vRtrLdpStatsBadTlvLengthErrors,
        vRtrLdpStatsMalformedTlvValueErrors,
        vRtrLdpStatsKeepAliveExpiredErrors,
        vRtrLdpStatsShutdownNotifRecv,
        vRtrLdpStatsShutdownNotifSent,
        vRtrLdpStatsEgrFecPfxCount
    }
    STATUS      obsolete
    DESCRIPTION
        "The group of objects supporting general management of extended LDP on
         Nokia SROS series systems 5.0 release."
    ::= { tmnxLdpGroups 22 }

tmnxLdpIfV5v0Group               OBJECT-GROUP
    OBJECTS     {
        vRtrLdpIfTableSpinlock,
        vRtrLdpIfRowStatus,
        vRtrLdpIfLastChange,
        vRtrLdpIfAdminState,
        vRtrLdpIfOperState,
        vRtrLdpIfInheritance,
        vRtrLdpIfKeepAliveFactor,
        vRtrLdpIfKeepAliveTimeout,
        vRtrLdpIfHelloFactor,
        vRtrLdpIfHelloTimeout,
        vRtrLdpIfBackoffTime,
        vRtrLdpIfMaxBackoffTime,
        vRtrLdpIfTransportAddrType,
        vRtrLdpIfPassiveMode,
        vRtrLdpIfAutoCreate,
        vRtrLdpIfOperDownReason,
        vRtrLdpIfExistingAdjacencies,
        vRtrLdpIfTunneling,
        vRtrLdpIfLspRowStatus,
        vRtrLdpPeerRowStatus,
        vRtrLdpPeerAuth,
        vRtrLdpPeerAuthKey,
        vRtrLdpPeerMinTTLValue,
        vRtrLdpPeerTTLLogId,
        vRtrLdpPeerAuthKeyChain
    }
    STATUS      obsolete
    DESCRIPTION
        "The group of objects supporting management of extended LDP interfaces
         and targeted peers on Nokia SROS series systems 5.0 release."
    ::= { tmnxLdpGroups 23 }

tmnxLdpServFecV5v0Group          OBJECT-GROUP
    OBJECTS     {
        vRtrLdpServFecServType,
        vRtrLdpServFecServId,
        vRtrLdpServFecVpnId,
        vRtrLdpServFecFlags,
        vRtrLdpServFecNumInLabels,
        vRtrLdpServFecNumOutLabels,
        vRtrLdpServFecInLabel1,
        vRtrLdpServFecInLabelStatus1,
        vRtrLdpServFecInLabel2,
        vRtrLdpServFecInLabelStatus2,
        vRtrLdpServFecInLabel3,
        vRtrLdpServFecInLabelStatus3,
        vRtrLdpServFecInLabel4,
        vRtrLdpServFecInLabelStatus4,
        vRtrLdpServFecInLabel5,
        vRtrLdpServFecInLabelStatus5,
        vRtrLdpServFecOutLabel1,
        vRtrLdpServFecOutLabelStatus1,
        vRtrLdpServFecOutLabel2,
        vRtrLdpServFecOutLabelStatus2,
        vRtrLdpServFecOutLabel3,
        vRtrLdpServFecOutLabelStatus3,
        vRtrLdpServFecOutLabel4,
        vRtrLdpServFecOutLabelStatus4,
        vRtrLdpServFecOutLabel5,
        vRtrLdpServFecOutLabelStatus5,
        vRtrLdpServFecSdpId,
        vRtrLdpServFecLocalMTU,
        vRtrLdpServFecRemoteMTU,
        vRtrLdpServFecLocalVlanTag,
        vRtrLdpServFecRemoteVlanTag,
        vRtrLdpServFecLocalMaxCellConcat,
        vRtrLdpServFecRemoteMaxCellConcat,
        vRtrLdpServFecMapFecType,
        vRtrLdpServFecMapVcType,
        vRtrLdpServFecMapVcId,
        vRtrLdpServFecInLabelSigStatus1,
        vRtrLdpServFecInLabelSigStatus2,
        vRtrLdpServFecInLabelSigStatus3,
        vRtrLdpServFecInLabelSigStatus4,
        vRtrLdpServFecInLabelSigStatus5,
        vRtrLdpServFecOutLabelSigStatus1,
        vRtrLdpServFecOutLabelSigStatus2,
        vRtrLdpServFecOutLabelSigStatus3,
        vRtrLdpServFecOutLabelSigStatus4,
        vRtrLdpServFecOutLabelSigStatus5,
        vRtrLdpServFecMateEndpointVcId,
        vRtrLdpServFecMateEndpointSdpId
    }
    STATUS      obsolete
    DESCRIPTION
        "The group of objects supporting management of extended LDP service
         FECs sent to or received from an LDP peer on Nokia SROS series systems
         release 5.0."
    ::= { tmnxLdpGroups 24 }

tmnxLdpAddrFecV5v0Group          OBJECT-GROUP
    OBJECTS     {
        vRtrLdpAddrFecFlags,
        vRtrLdpAddrFecNumInLabels,
        vRtrLdpAddrFecNumOutLabels,
        vRtrLdpAddrFecInLabel1,
        vRtrLdpAddrFecInLabelStatus1,
        vRtrLdpAddrFecInLabelIfIndex1,
        vRtrLdpAddrFecInLabel2,
        vRtrLdpAddrFecInLabelStatus2,
        vRtrLdpAddrFecInLabelIfIndex2,
        vRtrLdpAddrFecInLabel3,
        vRtrLdpAddrFecInLabelStatus3,
        vRtrLdpAddrFecInLabelIfIndex3,
        vRtrLdpAddrFecInLabel4,
        vRtrLdpAddrFecInLabelStatus4,
        vRtrLdpAddrFecInLabelIfIndex4,
        vRtrLdpAddrFecInLabel5,
        vRtrLdpAddrFecInLabelStatus5,
        vRtrLdpAddrFecInLabelIfIndex5,
        vRtrLdpAddrFecOutLabel1,
        vRtrLdpAddrFecOutLabelStatus1,
        vRtrLdpAddrFecOutLabelIfIndex1,
        vRtrLdpAddrFecOutLabelNextHop1,
        vRtrLdpAddrFecOutLabel2,
        vRtrLdpAddrFecOutLabelStatus2,
        vRtrLdpAddrFecOutLabelIfIndex2,
        vRtrLdpAddrFecOutLabelNextHop2,
        vRtrLdpAddrFecOutLabel3,
        vRtrLdpAddrFecOutLabelStatus3,
        vRtrLdpAddrFecOutLabelIfIndex3,
        vRtrLdpAddrFecOutLabelNextHop3,
        vRtrLdpAddrFecOutLabel4,
        vRtrLdpAddrFecOutLabelStatus4,
        vRtrLdpAddrFecOutLabelIfIndex4,
        vRtrLdpAddrFecOutLabelNextHop4,
        vRtrLdpAddrFecOutLabel5,
        vRtrLdpAddrFecOutLabelStatus5,
        vRtrLdpAddrFecOutLabelIfIndex5,
        vRtrLdpAddrFecOutLabelNextHop5,
        vRtrLdpAddrFecLspId,
        vRtrLdpAddrFecMapFecType,
        vRtrLdpAddrFecMapIpPrefix,
        vRtrLdpAddrFecMapIpMask,
        vRtrLdpAddrFecOutLabelNextHop5
    }
    STATUS      obsolete
    DESCRIPTION
        "The group of objects supporting management of extended LDP address
         FECs sent to or received from an LDP peer on Nokia SROS series systems
         for release 5.0."
    ::= { tmnxLdpGroups 25 }

tmnxLdpSessionV5v0Group          OBJECT-GROUP
    OBJECTS     {
        vRtrLdpSessLocalLdpId,
        vRtrLdpSessEntityIndex,
        vRtrLdpSessLabelDistMethod,
        vRtrLdpSessLoopDetectForPV,
        vRtrLdpSessPathVectorLimit,
        vRtrLdpSessState,
        vRtrLdpSessAdjacencyType,
        vRtrLdpSessProtocolVersion,
        vRtrLdpSessLocalUdpPort,
        vRtrLdpSessPeerUdpPort,
        vRtrLdpSessLocalTcpPort,
        vRtrLdpSessPeerTcpPort,
        vRtrLdpSessLocalAddress,
        vRtrLdpSessPeerAddress,
        vRtrLdpSessKAHoldTimeRemaining,
        vRtrLdpSessMaxPduLength,
        vRtrLdpSessUpTime,
        vRtrLdpSessLocalKATimeout,
        vRtrLdpSessPeerKATimeout,
        vRtrLdpSessAdvertise,
        vRtrLdpSessRestartHelperState,
        vRtrLdpSessPeerNumRestart,
        vRtrLdpSessLastRestartTime,
        vRtrLdpSessFtReconnectTimeNego,
        vRtrLdpSessFtRecoveryTimeNego,
        vRtrLdpSessFtReconTimeRemaining,
        vRtrLdpSessFtRecovTimeRemaining,
        vRtrLdpSessStatsTargAdj,
        vRtrLdpSessStatsLinkAdj,
        vRtrLdpSessStatsFECRecv,
        vRtrLdpSessStatsFECSent,
        vRtrLdpSessStatsHelloIn,
        vRtrLdpSessStatsHelloOut,
        vRtrLdpSessStatsKeepaliveIn,
        vRtrLdpSessStatsKeepaliveOut,
        vRtrLdpSessStatsInitIn,
        vRtrLdpSessStatsInitOut,
        vRtrLdpSessStatsLabelMappingIn,
        vRtrLdpSessStatsLabelMappingOut,
        vRtrLdpSessStatsLabelRequestIn,
        vRtrLdpSessStatsLabelRequestOut,
        vRtrLdpSessStatsLabelReleaseIn,
        vRtrLdpSessStatsLabelReleaseOut,
        vRtrLdpSessStatsLabelWithdrawIn,
        vRtrLdpSessStatsLabelWithdrawOut,
        vRtrLdpSessStatsLabelAbortIn,
        vRtrLdpSessStatsLabelAbortOut,
        vRtrLdpSessStatsAddrIn,
        vRtrLdpSessStatsAddrOut,
        vRtrLdpSessStatsAddrWithdrawIn,
        vRtrLdpSessStatsAddrWithdrawOut,
        vRtrLdpSessStatsNotificationIn,
        vRtrLdpSessStatsNotificationOut
    }
    STATUS      obsolete
    DESCRIPTION
        "The group of objects supporting management of extended LDP Sessions on
         Nokia SROS series systems 5.0 Release."
    ::= { tmnxLdpGroups 26 }

tmnxLdpObsoletedV5v0Group        OBJECT-GROUP
    OBJECTS     {
        vRtrLdpGenTrustList
    }
    STATUS      current
    DESCRIPTION
        "The group of objects obsoleted on Nokia SROS series systems 5.0
         Release."
    ::= { tmnxLdpGroups 27 }

tmnxLdpCepTdmFecV6v0Group        OBJECT-GROUP
    OBJECTS     {
        vRtrLdpCepTdmLocalPayloadSize,
        vRtrLdpCepTdmRemotePayloadSize,
        vRtrLdpCepTdmLocalBitrate,
        vRtrLdpCepTdmRemoteBitrate,
        vRtrLdpCepTdmLocalRtpHeader,
        vRtrLdpCepTdmRemoteRtpHeader,
        vRtrLdpCepTdmLocalDiffTimestamp,
        vRtrLdpCepTdmRemoteDiffTimestamp,
        vRtrLdpCepTdmLocalSigPkts,
        vRtrLdpCepTdmRemoteSigPkts,
        vRtrLdpCepTdmLocalCasTrunk,
        vRtrLdpCepTdmRemoteCasTrunk,
        vRtrLdpCepTdmLocalTimestampFreq,
        vRtrLdpCepTdmRemoteTimestampFreq,
        vRtrLdpCepTdmLocalPayloadType,
        vRtrLdpCepTdmRemotePayloadType,
        vRtrLdpCepTdmLocalSsrcId,
        vRtrLdpCepTdmRemoteSsrcId,
        vLdpCepTdmFec129LocalPayloadSize,
        vLdpCepTdmFec129RemotePayloadSize,
        vLdpCepTdmFec129LocalBitrate,
        vLdpCepTdmFec129RemoteBitrate,
        vLdpCepTdmFec129LocalRtpHeader,
        vLdpCepTdmFec129RemoteRtpHeader,
        vLdpCepTdmFec129LocalDiffTimestamp,
        vLdpCepTdmFec129RemoteDiffTimestamp,
        vLdpCepTdmFec129LocalSigPkts,
        vLdpCepTdmFec129RemoteSigPkts,
        vLdpCepTdmFec129LocalCasTrunk,
        vLdpCepTdmFec129RemoteCasTrunk,
        vLdpCepTdmFec129LocalTimestampFreq,
        vLdpCepTdmFec129RemoteTimestampFreq,
        vLdpCepTdmFec129LocalPayloadType,
        vLdpCepTdmFec129RemotePayloadType,
        vLdpCepTdmFec129LocalSsrcId,
        vLdpCepTdmFec129RemoteSsrcId
    }
    STATUS      obsolete
    DESCRIPTION
        "The group of objects supporting management of extended LDP CEP/TDM
         FECs sent to or received from an LDP peer on Nokia SROS series systems
         release 6.0."
    ::= { tmnxLdpGroups 28 }

tmnxLdpServFecV6v0Group          OBJECT-GROUP
    OBJECTS     {
        vRtrLdpServFecServType,
        vRtrLdpServFecServId,
        vRtrLdpServFecVpnId,
        vRtrLdpServFecFlags,
        vRtrLdpServFecNumInLabels,
        vRtrLdpServFecNumOutLabels,
        vRtrLdpServFecInLabel1,
        vRtrLdpServFecInLabelStatus1,
        vRtrLdpServFecInLabel2,
        vRtrLdpServFecInLabelStatus2,
        vRtrLdpServFecInLabel3,
        vRtrLdpServFecInLabelStatus3,
        vRtrLdpServFecInLabel4,
        vRtrLdpServFecInLabelStatus4,
        vRtrLdpServFecInLabel5,
        vRtrLdpServFecInLabelStatus5,
        vRtrLdpServFecOutLabel1,
        vRtrLdpServFecOutLabelStatus1,
        vRtrLdpServFecOutLabel2,
        vRtrLdpServFecOutLabelStatus2,
        vRtrLdpServFecOutLabel3,
        vRtrLdpServFecOutLabelStatus3,
        vRtrLdpServFecOutLabel4,
        vRtrLdpServFecOutLabelStatus4,
        vRtrLdpServFecOutLabel5,
        vRtrLdpServFecOutLabelStatus5,
        vRtrLdpServFecSdpId,
        vRtrLdpServFecLocalMTU,
        vRtrLdpServFecRemoteMTU,
        vRtrLdpServFecLocalVlanTag,
        vRtrLdpServFecRemoteVlanTag,
        vRtrLdpServFecLocalMaxCellConcat,
        vRtrLdpServFecRemoteMaxCellConcat,
        vRtrLdpServFecInLabelSigStatus1,
        vRtrLdpServFecInLabelSigStatus2,
        vRtrLdpServFecInLabelSigStatus3,
        vRtrLdpServFecInLabelSigStatus4,
        vRtrLdpServFecInLabelSigStatus5,
        vRtrLdpServFecOutLabelSigStatus1,
        vRtrLdpServFecOutLabelSigStatus2,
        vRtrLdpServFecOutLabelSigStatus3,
        vRtrLdpServFecOutLabelSigStatus4,
        vRtrLdpServFecOutLabelSigStatus5,
        vRtrLdpServFecMateEndpointVcId,
        vRtrLdpServFecMateEndpointSdpId
    }
    STATUS      obsolete
    DESCRIPTION
        "The group of objects supporting management of extended LDP service
         FECs sent to or received from an LDP peer on Nokia SROS series systems
         release 6.0."
    ::= { tmnxLdpGroups 29 }

tmnxLdpServFec129V6v0Group       OBJECT-GROUP
    OBJECTS     {
        vLdpServFec129ServType,
        vLdpServFec129ServId,
        vLdpServFec129VpnId,
        vLdpServFec129Flags,
        vLdpServFec129NumInLabels,
        vLdpServFec129NumOutLabels,
        vLdpServFec129InLabel1,
        vLdpServFec129InLabelStatus1,
        vLdpServFec129OutLabel1,
        vLdpServFec129OutLabelStatus1,
        vLdpServFec129SdpId,
        vLdpServFec129LocalMTU,
        vLdpServFec129RemoteMTU,
        vLdpServFec129LocalVlanTag,
        vLdpServFec129RemoteVlanTag,
        vLdpServFec129LocalMaxCellConcat,
        vLdpServFec129RemoteMaxCellConcat,
        vLdpServFec129InLabelSigStatus1,
        vLdpServFec129OutLabelSigStatus1
    }
    STATUS      obsolete
    DESCRIPTION
        "The group of objects supporting management of LDP FEC-129s sent to or
         received from an LDP peer on Nokia SROS series systems release 6.0."
    ::= { tmnxLdpGroups 30 }

tmnxLdpServFecObsoletedV6v0Group OBJECT-GROUP
    OBJECTS     {
        vRtrLdpServFecMapFecType,
        vRtrLdpServFecMapVcType,
        vRtrLdpServFecMapVcId,
        vLdpServFec129MapVcType,
        vLdpServFec129MapAgiTlv,
        vLdpServFec129MapSrcAiiTlv,
        vLdpServFec129MapTgtAiiTlv
    }
    STATUS      current
    DESCRIPTION
        "The group of objects supporting management of obsoleted LDP FEC
         objects on Nokia SROS series systems release 6.0."
    ::= { tmnxLdpGroups 31 }

tmnxLdpAggrPreMatchV7v0Group     OBJECT-GROUP
    OBJECTS     {
        vRtrLdpAggrPreMatchAdminState,
        vRtrLdpAggrPreMatchEnabled,
        vRtrLdpAggrPreMatchPreExcPolicy1,
        vRtrLdpAggrPreMatchPreExcPolicy2,
        vRtrLdpAggrPreMatchPreExcPolicy3,
        vRtrLdpAggrPreMatchPreExcPolicy4,
        vRtrLdpAggrPreMatchPreExcPolicy5
    }
    STATUS      obsolete
    DESCRIPTION
        "The group of objects supporting management of aggregate prefix match
         procedures on Nokia SROS series systems release 7.0."
    ::= { tmnxLdpGroups 32 }

tmnxLdpObsoletedV4v0Group        OBJECT-GROUP
    OBJECTS     {
        vRtrLdpIfNotifyReasonCode
    }
    STATUS      current
    DESCRIPTION
        "The group of objects obsoleted on Nokia SROS series systems 7.0
         Release."
    ::= { tmnxLdpGroups 33 }

tmnxLdpNotifyObjsV4v0Group       OBJECT-GROUP
    OBJECTS     {
        vRtrLdpInstanceNotifyReasonCode,
        vRtrLdpNotifyLocalGroupID,
        vRtrLdpNotifyRemoteGroupID
    }
    STATUS      obsolete
    DESCRIPTION
        "The group of objects supporting extended LDP notifications on Nokia
         SROS series systems."
    ::= { tmnxLdpGroups 34 }

tmnxLdpStatsV7v0Group            OBJECT-GROUP
    OBJECTS     {
        vRtrLdpEgrStatFecPfxTblLastChgd,
        vRtrLdpEgrStatFecPfxLastChgd,
        vRtrLdpEgrStatFecPfxRowStatus,
        vRtrLdpEgrStatFecPfxActgPol,
        vRtrLdpEgrStatFecPfxCollStats,
        vRtrLdpEgrStatFecPfxAdminState,
        vRtrLdpInProfileOctetsFc0,
        vRtrLdpInProfileOctetsFc0High32,
        vRtrLdpInProfileOctetsFc0Low32,
        vRtrLdpInProfileOctetsFc1,
        vRtrLdpInProfileOctetsFc1High32,
        vRtrLdpInProfileOctetsFc1Low32,
        vRtrLdpInProfileOctetsFc2,
        vRtrLdpInProfileOctetsFc2High32,
        vRtrLdpInProfileOctetsFc2Low32,
        vRtrLdpInProfileOctetsFc3,
        vRtrLdpInProfileOctetsFc3High32,
        vRtrLdpInProfileOctetsFc3Low32,
        vRtrLdpInProfileOctetsFc4,
        vRtrLdpInProfileOctetsFc4High32,
        vRtrLdpInProfileOctetsFc4Low32,
        vRtrLdpInProfileOctetsFc5,
        vRtrLdpInProfileOctetsFc5High32,
        vRtrLdpInProfileOctetsFc5Low32,
        vRtrLdpInProfileOctetsFc6,
        vRtrLdpInProfileOctetsFc6High32,
        vRtrLdpInProfileOctetsFc6Low32,
        vRtrLdpInProfileOctetsFc7,
        vRtrLdpInProfileOctetsFc7High32,
        vRtrLdpInProfileOctetsFc7Low32,
        vRtrLdpInProfilePktsFc0,
        vRtrLdpInProfilePktsFc0High32,
        vRtrLdpInProfilePktsFc0Low32,
        vRtrLdpInProfilePktsFc1,
        vRtrLdpInProfilePktsFc1High32,
        vRtrLdpInProfilePktsFc1Low32,
        vRtrLdpInProfilePktsFc2,
        vRtrLdpInProfilePktsFc2High32,
        vRtrLdpInProfilePktsFc2Low32,
        vRtrLdpInProfilePktsFc3,
        vRtrLdpInProfilePktsFc3High32,
        vRtrLdpInProfilePktsFc3Low32,
        vRtrLdpInProfilePktsFc4,
        vRtrLdpInProfilePktsFc4High32,
        vRtrLdpInProfilePktsFc4Low32,
        vRtrLdpInProfilePktsFc5,
        vRtrLdpInProfilePktsFc5High32,
        vRtrLdpInProfilePktsFc5Low32,
        vRtrLdpInProfilePktsFc6,
        vRtrLdpInProfilePktsFc6High32,
        vRtrLdpInProfilePktsFc6Low32,
        vRtrLdpInProfilePktsFc7,
        vRtrLdpInProfilePktsFc7High32,
        vRtrLdpInProfilePktsFc7Low32,
        vRtrLdpOutOfProfOctetsFc0,
        vRtrLdpOutOfProfOctetsFc0High32,
        vRtrLdpOutOfProfOctetsFc0Low32,
        vRtrLdpOutOfProfOctetsFc1,
        vRtrLdpOutOfProfOctetsFc1High32,
        vRtrLdpOutOfProfOctetsFc1Low32,
        vRtrLdpOutOfProfOctetsFc2,
        vRtrLdpOutOfProfOctetsFc2High32,
        vRtrLdpOutOfProfOctetsFc2Low32,
        vRtrLdpOutOfProfOctetsFc3,
        vRtrLdpOutOfProfOctetsFc3High32,
        vRtrLdpOutOfProfOctetsFc3Low32,
        vRtrLdpOutOfProfOctetsFc4,
        vRtrLdpOutOfProfOctetsFc4High32,
        vRtrLdpOutOfProfOctetsFc4Low32,
        vRtrLdpOutOfProfOctetsFc5,
        vRtrLdpOutOfProfOctetsFc5High32,
        vRtrLdpOutOfProfOctetsFc5Low32,
        vRtrLdpOutOfProfOctetsFc6,
        vRtrLdpOutOfProfOctetsFc6High32,
        vRtrLdpOutOfProfOctetsFc6Low32,
        vRtrLdpOutOfProfOctetsFc7,
        vRtrLdpOutOfProfOctetsFc7High32,
        vRtrLdpOutOfProfOctetsFc7Low32,
        vRtrLdpOutOfProfPktsFc0,
        vRtrLdpOutOfProfPktsFc0High32,
        vRtrLdpOutOfProfPktsFc0Low32,
        vRtrLdpOutOfProfPktsFc1,
        vRtrLdpOutOfProfPktsFc1High32,
        vRtrLdpOutOfProfPktsFc1Low32,
        vRtrLdpOutOfProfPktsFc2,
        vRtrLdpOutOfProfPktsFc2High32,
        vRtrLdpOutOfProfPktsFc2Low32,
        vRtrLdpOutOfProfPktsFc3,
        vRtrLdpOutOfProfPktsFc3High32,
        vRtrLdpOutOfProfPktsFc3Low32,
        vRtrLdpOutOfProfPktsFc4,
        vRtrLdpOutOfProfPktsFc4High32,
        vRtrLdpOutOfProfPktsFc4Low32,
        vRtrLdpOutOfProfPktsFc5,
        vRtrLdpOutOfProfPktsFc5High32,
        vRtrLdpOutOfProfPktsFc5Low32,
        vRtrLdpOutOfProfPktsFc6,
        vRtrLdpOutOfProfPktsFc6High32,
        vRtrLdpOutOfProfPktsFc6Low32,
        vRtrLdpOutOfProfPktsFc7,
        vRtrLdpOutOfProfPktsFc7High32,
        vRtrLdpOutOfProfPktsFc7Low32
    }
    STATUS      current
    DESCRIPTION
        "The group of objects supporting management of LDP statistics on Nokia
         SROS series systems release 7.0."
    ::= { tmnxLdpGroups 35 }

tmnxLdpAddrFecV7v0Group          OBJECT-GROUP
    OBJECTS     {
        vRtrLdpAddrFecLspId2,
        vRtrLdpAddrFecLspId3,
        vRtrLdpAddrFecLspId4,
        vRtrLdpAddrFecLspId5,
        vRtrLdpAddrFecLspId6,
        vRtrLdpAddrFecLspId7,
        vRtrLdpAddrFecLspId8,
        vRtrLdpAddrFecLspId9,
        vRtrLdpAddrFecLspId10,
        vRtrLdpAddrFecLspId11,
        vRtrLdpAddrFecLspId12,
        vRtrLdpAddrFecLspId13,
        vRtrLdpAddrFecLspId14,
        vRtrLdpAddrFecLspId15,
        vRtrLdpAddrFecLspId16,
        vRtrLdpAddrFecOutLbl6,
        vRtrLdpAddrFecOutLbl7,
        vRtrLdpAddrFecOutLbl8,
        vRtrLdpAddrFecOutLbl9,
        vRtrLdpAddrFecOutLbl10,
        vRtrLdpAddrFecOutLbl11,
        vRtrLdpAddrFecOutLbl12,
        vRtrLdpAddrFecOutLbl13,
        vRtrLdpAddrFecOutLbl14,
        vRtrLdpAddrFecOutLbl15,
        vRtrLdpAddrFecOutLbl16,
        vRtrLdpAddrFecOutLblIfIndex6,
        vRtrLdpAddrFecOutLblIfIndex7,
        vRtrLdpAddrFecOutLblIfIndex8,
        vRtrLdpAddrFecOutLblIfIndex9,
        vRtrLdpAddrFecOutLblIfIndex10,
        vRtrLdpAddrFecOutLblIfIndex11,
        vRtrLdpAddrFecOutLblIfIndex12,
        vRtrLdpAddrFecOutLblIfIndex13,
        vRtrLdpAddrFecOutLblIfIndex14,
        vRtrLdpAddrFecOutLblIfIndex15,
        vRtrLdpAddrFecOutLblIfIndex16,
        vRtrLdpAddrFecOutLblNxtHopAddr6,
        vRtrLdpAddrFecOutLblNxtHopAddr7,
        vRtrLdpAddrFecOutLblNxtHopAddr8,
        vRtrLdpAddrFecOutLblNxtHopAddr9,
        vRtrLdpAddrFecOutLblNxtHopAddr10,
        vRtrLdpAddrFecOutLblNxtHopAddr11,
        vRtrLdpAddrFecOutLblNxtHopAddr12,
        vRtrLdpAddrFecOutLblNxtHopAddr13,
        vRtrLdpAddrFecOutLblNxtHopAddr14,
        vRtrLdpAddrFecOutLblNxtHopAddr15,
        vRtrLdpAddrFecOutLblNxtHopAddr16,
        vRtrLdpAddrFecOutLblNxtHopType6,
        vRtrLdpAddrFecOutLblNxtHopType7,
        vRtrLdpAddrFecOutLblNxtHopType8,
        vRtrLdpAddrFecOutLblNxtHopType9,
        vRtrLdpAddrFecOutLblNxtHopType10,
        vRtrLdpAddrFecOutLblNxtHopType11,
        vRtrLdpAddrFecOutLblNxtHopType12,
        vRtrLdpAddrFecOutLblNxtHopType13,
        vRtrLdpAddrFecOutLblNxtHopType14,
        vRtrLdpAddrFecOutLblNxtHopType15,
        vRtrLdpAddrFecOutLblNxtHopType16,
        vRtrLdpAddrFecOutLblStatus6,
        vRtrLdpAddrFecOutLblStatus7,
        vRtrLdpAddrFecOutLblStatus8,
        vRtrLdpAddrFecOutLblStatus9,
        vRtrLdpAddrFecOutLblStatus10,
        vRtrLdpAddrFecOutLblStatus11,
        vRtrLdpAddrFecOutLblStatus12,
        vRtrLdpAddrFecOutLblStatus13,
        vRtrLdpAddrFecOutLblStatus14,
        vRtrLdpAddrFecOutLblStatus15,
        vRtrLdpAddrFecOutLblStatus16
    }
    STATUS      obsolete
    DESCRIPTION
        "The group of objects supporting management of extended LDP address
         FECs sent to or received from an LDP peer on Nokia SROS series systems
         for release 7.0."
    ::= { tmnxLdpGroups 36 }

tmnxLdpGenExtGlobalV5v0Group     OBJECT-GROUP
    OBJECTS     {
        vRtrLdpGenLabelWithdrawalDelay
    }
    STATUS      obsolete
    DESCRIPTION
        "The group of objects supporting general management of extended LDP on
         Nokia SROS series systems release 5.0."
    ::= { tmnxLdpGroups 37 }

tmnxLdpGlobalV8v0Group           OBJECT-GROUP
    OBJECTS     {
        vRtrLdpIfBfdEnabled,
        vRtrLdpIfLinkLsrIfType,
        vRtrLdpIfTargLsrIfIndex,
        vRtrLdpGenImplicitNull,
        vRtrLdpGenShortTTLPropLocal,
        vRtrLdpGenShortTTLPropTransit,
        vRtrLdpPeerDODLabelDistribution,
        vRtrLdpIfMulticast,
        vRtrLdpGenMPMBBTime,
        vRtrLdpPeerImportPolicy1,
        vRtrLdpPeerImportPolicy2,
        vRtrLdpPeerImportPolicy3,
        vRtrLdpPeerImportPolicy4,
        vRtrLdpPeerImportPolicy5,
        vRtrLdpPeerExportPolicy1,
        vRtrLdpPeerExportPolicy2,
        vRtrLdpPeerExportPolicy3,
        vRtrLdpPeerExportPolicy4,
        vRtrLdpPeerExportPolicy5
    }
    STATUS      obsolete
    DESCRIPTION
        "The group of objects supporting general management of LDP Objects on
         Nokia SROS series systems release 8.0."
    ::= { tmnxLdpGroups 38 }

tmnxLdpSessionV8v0Group          OBJECT-GROUP
    OBJECTS     {
        vRtrLdpSessBfdStatus,
        vRtrLdpSessP2MPCapabilityNego,
        vRtrLdpSessMPMBBCapabilityNego,
        vRtrLdpSessDynamicCapabilityNego
    }
    STATUS      obsolete
    DESCRIPTION
        "The group of objects supporting management of extended LDP Sessions on
         Nokia SROS series systems 8.0 Release."
    ::= { tmnxLdpGroups 39 }

tmnxLdpP2MPFecV8v0Group          OBJECT-GROUP
    OBJECTS     {
        vRtrLdpP2MPFecFlags,
        vRtrLdpP2MPFecNumInLabels,
        vRtrLdpP2MPFecNumOutLabels,
        vRtrLdpP2MPFecInLbl,
        vRtrLdpP2MPFecInLblStatus,
        vRtrLdpP2MPFecInLblIfIndex,
        vRtrLdpP2MPFecOutLbl,
        vRtrLdpP2MPFecOutLblStatus,
        vRtrLdpP2MPFecOutLblNxtHopType,
        vRtrLdpP2MPFecOutLblNxtHopAddr,
        vRtrLdpP2MPFecOutLblIfIndex,
        vRtrLdpP2MPFecOutLblLspId,
        vRtrLdpP2MPFecMapFecType,
        vRtrLdpP2MPFecMapId,
        vRtrLdpP2MPFecTunnelIfId,
        vRtrLdpP2MPFecMetric,
        vRtrLdpP2MPFecMTU
    }
    STATUS      obsolete
    DESCRIPTION
        "The group of objects supporting P2MP FECs on Nokia SROS series systems
         8.0 Release."
    ::= { tmnxLdpGroups 40 }

tmnxLdpStatsV8v0Group            OBJECT-GROUP
    OBJECTS     {
        vRtrLdpStatsUnknownTlvErrors,
        vRtrLdpStatsP2MPFECSent,
        vRtrLdpStatsP2MPFECRecv
    }
    STATUS      obsolete
    DESCRIPTION
        "The group of objects supporting management of LDP statistics on Nokia
         SROS series systems release 8.0."
    ::= { tmnxLdpGroups 41 }

tmnxLdpPeerV7v0Group             OBJECT-GROUP
    OBJECTS     {
        vRtrLdpPeerFec129CiscoInterop
    }
    STATUS      obsolete
    DESCRIPTION
        "The group of objects supporting management of extended LDP peers on
         Nokia SROS series systems 7.0 release."
    ::= { tmnxLdpGroups 42 }

tmnxLdpServFecV8v0Group          OBJECT-GROUP
    OBJECTS     {
        vRtrLdpServFecLocalIpv4Capblty,
        vRtrLdpServFecRemoteIpv4Capblty,
        vRtrLdpServFecLocalIpv6Capblty,
        vRtrLdpServFecRemoteIpv6Capblty,
        vRtrLdpServFecLocalIpv4CeIpAddr,
        vRtrLdpServFecRemoteIpv4CeIpAddr,
        vRtrLdpServFecInLbl1WdwReason
    }
    STATUS      obsolete
    DESCRIPTION
        "The group of objects supporting management of extended LDP service
         FECs sent to or received from an LDP peer on Nokia SROS series systems
         release 8.0."
    ::= { tmnxLdpGroups 43 }

tmnxLdpServFec129V8v0Group       OBJECT-GROUP
    OBJECTS     {
        vLdpServFec129LocalIpv4Capblty,
        vLdpServFec129RemoteIpv4Capblty,
        vLdpServFec129LocalIpv6Capblty,
        vLdpServFec129RemoteIpv6Capblty,
        vLdpServFec129LocalIpv4CeIpAddr,
        vLdpServFec129RemoteIpv4CeIpAddr,
        vLdpServFec129InLbl1WdwReason
    }
    STATUS      obsolete
    DESCRIPTION
        "The group of objects supporting management of LDP FEC-129s sent to or
         received from an LDP peer on Nokia SROS series systems release 8.0."
    ::= { tmnxLdpGroups 44 }

tmnxLdpAddrFecV8v0Group          OBJECT-GROUP
    OBJECTS     {
        vRtrLdpAddrFecOutLblId,
        vRtrLdpAddrFecOutLblMetric,
        vRtrLdpAddrFecOutLblMtu
    }
    STATUS      obsolete
    DESCRIPTION
        "The group of objects supporting management of extended LDP address
         FECs sent to or received from an LDP peer on Nokia SROS series systems
         for release 8.0."
    ::= { tmnxLdpGroups 45 }

tmnxLdpGlobalV8v0R4Group         OBJECT-GROUP
    OBJECTS     {
        vRtrLdpGenTunlTblExportPolicy1,
        vRtrLdpGenTunlTblExportPolicy2,
        vRtrLdpGenTunlTblExportPolicy3,
        vRtrLdpGenTunlTblExportPolicy4,
        vRtrLdpGenTunlTblExportPolicy5,
        vRtrLdpPeerPMTUDiscovery,
        vRtrLdpGenP2MPCapability,
        vRtrLdpGenMPMBBCapability,
        vRtrLdpGenDynamicCapability
    }
    STATUS      obsolete
    DESCRIPTION
        "The group of objects supporting general management of LDP Objects on
         Nokia SROS series systems release 8.0R4."
    ::= { tmnxLdpGroups 46 }

tmnxLdpGlobalV9v0Group           OBJECT-GROUP
    OBJECTS     {
        vLdpServFec129MateAgiTlv,
        vLdpServFec129MateSdpId,
        vLdpServFec129MateSrcAiiTlv,
        vLdpServFec129MateTgtAiiTlv,
        vRtrLdpPeerPMTUDiscovery,
        vRtrLdpServFecLocalFLTxCapblty,
        vRtrLdpServFecLocalFLRxCapblty,
        vRtrLdpServFecRemoteFLTxCapblty,
        vRtrLdpServFecRemoteFLRxCapblty,
        vLdpServFec129LocalFLTxCapblty,
        vLdpServFec129LocalFLRxCapblty,
        vLdpServFec129RemoteFLTxCapblty,
        vLdpServFec129RemoteFLRxCapblty,
        vRtrLdpPeerAdvAdjAddrOnly,
        vRtrLdpSessionAddrLocalLdpId,
        vRtrLdpSessionAddrNumInAddrs,
        vRtrLdpSessionAddrNumOutAddrs,
        vRtrLdpSessionInAddrLocalLdpId,
        vRtrLdpSessionOutAddrLocalLdpId,
        vRtrLdpSessStatsAddrRecv,
        vRtrLdpSessStatsAddrSent
    }
    STATUS      obsolete
    DESCRIPTION
        "The group of objects supporting general management of LDP Objects on
         Nokia SROS series systems release 9.0."
    ::= { tmnxLdpGroups 47 }

tmnxLdpGlobalV9v0R4Group         OBJECT-GROUP
    OBJECTS     {
        vRtrLdpGenLdpFrr,
        vRtrLdpHelloAdjBfdStatus
    }
    STATUS      obsolete
    DESCRIPTION
        "The group of objects supporting general management of LDP Objects on
         Nokia SROS series systems release 9.0R4."
    ::= { tmnxLdpGroups 48 }

tmnxLdpP2MPFecV10v0Group         OBJECT-GROUP
    OBJECTS     {
        vRtrLdpNgP2MPFecFlags,
        vRtrLdpNgP2MPFecNumInLabels,
        vRtrLdpNgP2MPFecNumOutLabels,
        vRtrLdpNgP2MPFecTunnelIfId,
        vRtrLdpNgP2MPFecMetric,
        vRtrLdpNgP2MPFecMTU,
        vRtrLdpNgP2MPFecInLbl,
        vRtrLdpNgP2MPFecInLblStatus,
        vRtrLdpNgP2MPFecInLblIfIndex,
        vRtrLdpNgP2MPFecOutLbl,
        vRtrLdpNgP2MPFecOutLblStatus,
        vRtrLdpNgP2MPFecOutLblNxtHopType,
        vRtrLdpNgP2MPFecOutLblNxtHopAddr,
        vRtrLdpNgP2MPFecOutLblIfIndex,
        vRtrLdpNgP2MPFecOutLblLspId,
        vRtrLdpNgP2MPFecMapFlags,
        vRtrLdpNgP2MPFecMapNumInLabels,
        vRtrLdpNgP2MPFecMapNumOutLabels,
        vRtrLdpNgP2MPFecMapTunnelIfId,
        vRtrLdpNgP2MPFecMapMetric,
        vRtrLdpNgP2MPFecMapMTU
    }
    STATUS      obsolete
    DESCRIPTION
        "The group of objects supporting P2MP FECs on Nokia SROS series systems
         10.0 Release."
    ::= { tmnxLdpGroups 49 }

tmnxLdpAddressFecV10v0Group      OBJECT-GROUP
    OBJECTS     {
        vRtrLdpAddressFecFlags,
        vRtrLdpAddressFecNumInLabels,
        vRtrLdpAddressFecNumOutLabels,
        vRtrLdpAddressFecInLbl,
        vRtrLdpAddressFecInLblStatus,
        vRtrLdpAddressFecInLblIfIndex,
        vRtrLdpAddressFecOutLbl,
        vRtrLdpAddressFecOutLblStatus,
        vRtrLdpAddressFecOutLblIfIndex,
        vRtrLdpAddressFecOutLblNHType,
        vRtrLdpAddressFecOutLblNHAddr,
        vRtrLdpAddressFecOutLblMetric,
        vRtrLdpAddressFecOutLblMtu,
        vRtrLdpAddressFecOutLblLspId,
        vRtrLdpAddressFecMapFlags,
        vRtrLdpAddressFecMapNumInLabels,
        vRtrLdpAddressFecMapNumOutLabels
    }
    STATUS      obsolete
    DESCRIPTION
        "The group of objects supporting Address FECs on Nokia SROS series
         systems 10.0 Release."
    ::= { tmnxLdpGroups 50 }

tmnxLdpAddrActiveFecV10v0Group   OBJECT-GROUP
    OBJECTS     {
        vRtrLdpAddrActiveFecFecFlags,
        vRtrLdpAddrActiveFecNumInLbls,
        vRtrLdpAddrActiveFecNumOutLbls,
        vRtrLdpAddrActiveFecInLbl,
        vRtrLdpAddrActiveFecInLblIfIndex,
        vRtrLdpAddrActiveFecOutLbl,
        vRtrLdpAddrActiveFecOutLblStatus,
        vRtrLdpAddrActiveFecOutLblIfIdx,
        vRtrLdpAddrActiveFecOutLblNHType,
        vRtrLdpAddrActiveFecOutLblNHAddr,
        vRtrLdpAddrActiveFecOutLblMetric,
        vRtrLdpAddrActiveFecOutLblMtu,
        vRtrLdpAddrActiveFecOutLblLspId
    }
    STATUS      obsolete
    DESCRIPTION
        "The group of objects supporting Active Address FECs on Nokia SROS
         series systems 10.0 Release."
    ::= { tmnxLdpGroups 51 }

tmnxLdpAddrFecObsoletedGroup     OBJECT-GROUP
    OBJECTS     {
        vRtrLdpAddrFecFlags,
        vRtrLdpAddrFecNumInLabels,
        vRtrLdpAddrFecNumOutLabels,
        vRtrLdpAddrFecInLabel1,
        vRtrLdpAddrFecInLabelStatus1,
        vRtrLdpAddrFecInLabelIfIndex1,
        vRtrLdpAddrFecInLabel2,
        vRtrLdpAddrFecInLabelStatus2,
        vRtrLdpAddrFecInLabelIfIndex2,
        vRtrLdpAddrFecInLabel3,
        vRtrLdpAddrFecInLabelStatus3,
        vRtrLdpAddrFecInLabelIfIndex3,
        vRtrLdpAddrFecInLabel4,
        vRtrLdpAddrFecInLabelStatus4,
        vRtrLdpAddrFecInLabelIfIndex4,
        vRtrLdpAddrFecInLabel5,
        vRtrLdpAddrFecInLabelStatus5,
        vRtrLdpAddrFecInLabelIfIndex5,
        vRtrLdpAddrFecOutLabel1,
        vRtrLdpAddrFecOutLabelStatus1,
        vRtrLdpAddrFecOutLabelIfIndex1,
        vRtrLdpAddrFecOutLabelNextHop1,
        vRtrLdpAddrFecOutLabel2,
        vRtrLdpAddrFecOutLabelStatus2,
        vRtrLdpAddrFecOutLabelIfIndex2,
        vRtrLdpAddrFecOutLabelNextHop2,
        vRtrLdpAddrFecOutLabel3,
        vRtrLdpAddrFecOutLabelStatus3,
        vRtrLdpAddrFecOutLabelIfIndex3,
        vRtrLdpAddrFecOutLabelNextHop3,
        vRtrLdpAddrFecOutLabel4,
        vRtrLdpAddrFecOutLabelStatus4,
        vRtrLdpAddrFecOutLabelIfIndex4,
        vRtrLdpAddrFecOutLabelNextHop4,
        vRtrLdpAddrFecOutLabel5,
        vRtrLdpAddrFecOutLabelStatus5,
        vRtrLdpAddrFecOutLabelIfIndex5,
        vRtrLdpAddrFecOutLabelNextHop5,
        vRtrLdpAddrFecLspId,
        vRtrLdpAddrFecLspId2,
        vRtrLdpAddrFecLspId3,
        vRtrLdpAddrFecLspId4,
        vRtrLdpAddrFecLspId5,
        vRtrLdpAddrFecMapFecType,
        vRtrLdpAddrFecMapIpPrefix,
        vRtrLdpAddrFecMapIpMask,
        vRtrLdpAddrFecOutLbl6,
        vRtrLdpAddrFecOutLblStatus6,
        vRtrLdpAddrFecOutLblIfIndex6,
        vRtrLdpAddrFecOutLblNxtHopType6,
        vRtrLdpAddrFecOutLblNxtHopAddr6,
        vRtrLdpAddrFecLspId6,
        vRtrLdpAddrFecOutLbl7,
        vRtrLdpAddrFecOutLblStatus7,
        vRtrLdpAddrFecOutLblIfIndex7,
        vRtrLdpAddrFecOutLblNxtHopType7,
        vRtrLdpAddrFecOutLblNxtHopAddr7,
        vRtrLdpAddrFecLspId7,
        vRtrLdpAddrFecOutLbl8,
        vRtrLdpAddrFecOutLblStatus8,
        vRtrLdpAddrFecOutLblIfIndex8,
        vRtrLdpAddrFecOutLblNxtHopType8,
        vRtrLdpAddrFecOutLblNxtHopAddr8,
        vRtrLdpAddrFecLspId8,
        vRtrLdpAddrFecOutLbl9,
        vRtrLdpAddrFecOutLblStatus9,
        vRtrLdpAddrFecOutLblIfIndex9,
        vRtrLdpAddrFecOutLblNxtHopType9,
        vRtrLdpAddrFecOutLblNxtHopAddr9,
        vRtrLdpAddrFecLspId9,
        vRtrLdpAddrFecOutLbl10,
        vRtrLdpAddrFecOutLblStatus10,
        vRtrLdpAddrFecOutLblIfIndex10,
        vRtrLdpAddrFecOutLblNxtHopType10,
        vRtrLdpAddrFecOutLblNxtHopAddr10,
        vRtrLdpAddrFecLspId10,
        vRtrLdpAddrFecOutLbl11,
        vRtrLdpAddrFecOutLblStatus11,
        vRtrLdpAddrFecOutLblIfIndex11,
        vRtrLdpAddrFecOutLblNxtHopType11,
        vRtrLdpAddrFecOutLblNxtHopAddr11,
        vRtrLdpAddrFecLspId11,
        vRtrLdpAddrFecOutLbl12,
        vRtrLdpAddrFecOutLblStatus12,
        vRtrLdpAddrFecOutLblIfIndex12,
        vRtrLdpAddrFecOutLblNxtHopType12,
        vRtrLdpAddrFecOutLblNxtHopAddr12,
        vRtrLdpAddrFecLspId12,
        vRtrLdpAddrFecOutLbl13,
        vRtrLdpAddrFecOutLblStatus13,
        vRtrLdpAddrFecOutLblIfIndex13,
        vRtrLdpAddrFecOutLblNxtHopType13,
        vRtrLdpAddrFecOutLblNxtHopAddr13,
        vRtrLdpAddrFecLspId13,
        vRtrLdpAddrFecOutLbl14,
        vRtrLdpAddrFecOutLblStatus14,
        vRtrLdpAddrFecOutLblIfIndex14,
        vRtrLdpAddrFecOutLblNxtHopType14,
        vRtrLdpAddrFecOutLblNxtHopAddr14,
        vRtrLdpAddrFecLspId14,
        vRtrLdpAddrFecOutLbl15,
        vRtrLdpAddrFecOutLblStatus15,
        vRtrLdpAddrFecOutLblIfIndex15,
        vRtrLdpAddrFecOutLblNxtHopType15,
        vRtrLdpAddrFecOutLblNxtHopAddr15,
        vRtrLdpAddrFecLspId15,
        vRtrLdpAddrFecOutLbl16,
        vRtrLdpAddrFecOutLblStatus16,
        vRtrLdpAddrFecOutLblIfIndex16,
        vRtrLdpAddrFecOutLblNxtHopType16,
        vRtrLdpAddrFecOutLblNxtHopAddr16,
        vRtrLdpAddrFecLspId16,
        vRtrLdpAddrFecOutLblId,
        vRtrLdpAddrFecOutLblMetric,
        vRtrLdpAddrFecOutLblMtu
    }
    STATUS      current
    DESCRIPTION
        "The group of obsolete objects for the LDP address fec feature on Nokia
         SROS series systems 10.0 Release."
    ::= { tmnxLdpGroups 52 }

tmnxLdpP2MPFecObsoletedGroup     OBJECT-GROUP
    OBJECTS     {
        vRtrLdpP2MPFecFlags,
        vRtrLdpP2MPFecNumInLabels,
        vRtrLdpP2MPFecNumOutLabels,
        vRtrLdpP2MPFecInLbl,
        vRtrLdpP2MPFecInLblStatus,
        vRtrLdpP2MPFecInLblIfIndex,
        vRtrLdpP2MPFecOutLbl,
        vRtrLdpP2MPFecOutLblStatus,
        vRtrLdpP2MPFecOutLblNxtHopType,
        vRtrLdpP2MPFecOutLblNxtHopAddr,
        vRtrLdpP2MPFecOutLblIfIndex,
        vRtrLdpP2MPFecOutLblLspId,
        vRtrLdpP2MPFecMapFecType,
        vRtrLdpP2MPFecMapId,
        vRtrLdpP2MPFecTunnelIfId,
        vRtrLdpP2MPFecMetric,
        vRtrLdpP2MPFecMTU
    }
    STATUS      current
    DESCRIPTION
        "The group of obsolete objects for the LDP P2MP fec feature on Nokia
         SROS series systems 10.0 Release."
    ::= { tmnxLdpGroups 53 }

tmnxLdpHelloReductionV11v0Group  OBJECT-GROUP
    OBJECTS     {
        vRtrLdpGenTargHelloReduction,
        vRtrLdpGenTargHelloReductionFctr,
        vRtrLdpIfHelloReduction,
        vRtrLdpIfHelloReductionFactor,
        vRtrLdpIfOperHelloTimeout
    }
    STATUS      obsolete
    DESCRIPTION
        "The group of objects supporting TLDP Hello Reduction feature on
         interfaces and targeted peers on Nokia SROS series systems 11.0
         release."
    ::= { tmnxLdpGroups 54 }

tmnxLdpGlobalV11v0Group          OBJECT-GROUP
    OBJECTS     {
        vRtrLdpIfLinkLsrIfIndex,
        vRtrLdpStaticFecNHIfName,
        vRtrLdpGenMcastUpstreamFrr,
        vRtrLdpPeerPeIDMacFlushInterop
    }
    STATUS      obsolete
    DESCRIPTION
        "The group of all global objects in LDP supporting management of LDP
         features on Nokia SROS series systems 11.0 release."
    ::= { tmnxLdpGroups 55 }

tmnxLdpLsrOverloadV11v0Group     OBJECT-GROUP
    OBJECTS     {
        vRtrLdpGenOverloadCapability,
        vRtrLdpSessOvrloadCapabltyNego,
        vRtrLdpSessAddrFecOverloadSent,
        vRtrLdpSessAddrFecOverloadRecv,
        vRtrLdpSessMcastFecOverloadSent,
        vRtrLdpSessMcastFecOverloadRecv,
        vRtrLdpSessServFecOverloadSent,
        vRtrLdpSessServFecOverloadRecv
    }
    STATUS      obsolete
    DESCRIPTION
        "The group of all global objects in LDP supporting LSR Overload feature
         on Nokia SROS series systems 11.0 release."
    ::= { tmnxLdpGroups 56 }

tmnxLdpTLDPAutoCreateV11v0Group  OBJECT-GROUP
    OBJECTS     {
        vRtrLdpPeerTemplRowStatus,
        vRtrLdpPeerTemplLastChanged,
        vRtrLdpPeerTemplAdminState,
        vRtrLdpPeerTemplInheritance,
        vRtrLdpPeerTemplKeepAliveFactor,
        vRtrLdpPeerTemplKeepAliveTimeout,
        vRtrLdpPeerTemplHelloFactor,
        vRtrLdpPeerTemplHelloTimeout,
        vRtrLdpPeerTemplTunneling,
        vRtrLdpPeerTemplBfdEnabled,
        vRtrLdpPeerTemplLsrIfIndex,
        vRtrLdpPeerTemplHelloReduction,
        vRtrLdpPeerTemplHelloReductnFctr,
        vRtrLdpPeerTemplCreateTime,
        vRtrLdpPeerTemplIndex,
        vRtrLdpPeerTemplPlcyMapPolicy1,
        vRtrLdpPeerTemplPlcyMapPolicy2,
        vRtrLdpPeerTemplPlcyMapPolicy3,
        vRtrLdpPeerTemplPlcyMapPolicy4,
        vRtrLdpPeerTemplPlcyMapPolicy5,
        vRtrLdpPeerTemplPlcyMapIndex,
        vRtrLdpPeerTemplPlcyMapCreateTim,
        vRtrLdpPeerTemplPlcyMapLstChange,
        vRtrLdpPeerTemplPlcyMapRowStatus,
        vRtrLdpPeerTemplTableLstChanged,
        vRtrLdpPeerTmplPlcyMpTblLstChgd,
        vRtrLdpPeerTemplPeerCreateTime,
        vRtrLdpIfCreator,
        vRtrLdpIfTemplName,
        vRtrLdpIfUpTime
    }
    STATUS      obsolete
    DESCRIPTION
        "The group of all global objects in LDP supporting T-LDP Auto Creation
         feature on Nokia SROS series systems 11.0 release."
    ::= { tmnxLdpGroups 57 }

tmnxLdpLsrOvrloadNotifyObjs      OBJECT-GROUP
    OBJECTS     {
        vRtrLdpSessOverloadState,
        vRtrLdpSessOverloadDirection,
        vRtrLdpSessOverloadFecType
    }
    STATUS      obsolete
    DESCRIPTION
        "The group of objects supporting LSR Overload feature notifications on
         Nokia SROS series systems."
    ::= { tmnxLdpGroups 58 }

tmnxLdpLsrOvrloadNotify          NOTIFICATION-GROUP
    NOTIFICATIONS {
        vRtrLdpSessionStateChange
    }
    STATUS      obsolete
    DESCRIPTION
        "The group of notifications supporting LSR Overload feature on Nokia
         SROS series systems."
    ::= { tmnxLdpGroups 59 }

tmnxLdpFecLimitPerPeerV13v0Group OBJECT-GROUP
    OBJECTS     {
        vRtrLdpPeerMaxFec,
        vRtrLdpPeerMaxFecLogOnly,
        vRtrLdpPeerMaxFecThreshold,
        vRtrLdpSessOperMaxFecThreshold
    }
    STATUS      obsolete
    DESCRIPTION
        "The group of notifications supporting LSR FEC limit per LDP peer
         feature on Nokia SROS series systems."
    ::= { tmnxLdpGroups 60 }

tmnxLdpFecLimitPerPeerNotify     NOTIFICATION-GROUP
    NOTIFICATIONS {
        vRtrLdpSessMaxFecThresChanged,
        vRtrLdpSessMaxFecLimitReached
    }
    STATUS      obsolete
    DESCRIPTION
        "The group of notifications supporting LSR FEC limit per LDP peer
         feature on Nokia SROS series systems."
    ::= { tmnxLdpGroups 61 }

tmnxLdpFecLimitNotifyObjs        OBJECT-GROUP
    OBJECTS     {
        vRtrLdpSessOperThresLevel
    }
    STATUS      obsolete
    DESCRIPTION
        "The group of objects supporting LDP fec-limit notification on Nokia
         SROS series systems."
    ::= { tmnxLdpGroups 62 }

tmnxLdpObsoletedV13V0Group       OBJECT-GROUP
    OBJECTS     {
        vRtrLdpAdjInitBackoff,
        vRtrLdpAdjMaxBackoff,
        vRtrLdpAdjCurrentBackoff,
        vRtrLdpAdjWaitingTime,
        vRtrLdpAdjBackoffStatus,
        vRtrLdpHelloAdjMapLdpId,
        vRtrLdpHelloAdjLocalLdpId,
        vRtrLdpHelloAdjEntityIndex,
        vRtrLdpHelloAdjIndex,
        vRtrLdpHelloAdjHoldTimeRemaining,
        vRtrLdpHelloAdjType,
        vRtrLdpHelloAdjRemoteConfSeqNum,
        vRtrLdpHelloAdjRemoteIpAddress,
        vRtrLdpHelloAdjUpTime,
        vRtrLdpHelloAdjLocalConfSeqNum,
        vRtrLdpHelloAdjLocalIpAddress,
        vRtrLdpHelloAdjInHelloMsgCount,
        vRtrLdpHelloAdjOutHelloMsgCount,
        vRtrLdpHelloAdjLocalHelloTimeout,
        vRtrLdpHelloAdjRemoteHelloTimeout,
        vRtrLdpStaticFecRowStatus,
        vRtrLdpStaticFecNextNHIndex,
        vRtrLdpStaticFecIngLabel,
        vRtrLdpStaticFecNumNH,
        vRtrLdpStaticFecOperIngLabel,
        vRtrLdpStaticFecNHRowStatus,
        vRtrLdpStaticFecNHType,
        vRtrLdpStaticFecNHIpAddr,
        vRtrLdpStaticFecNHEgrLabel,
        vRtrLdpGenLastChange,
        vRtrLdpGenAdminState,
        vRtrLdpGenOperState,
        vRtrLdpGenLdpLsrId,
        vRtrLdpGenProtocolVersion,
        vRtrLdpGenDeaggregateFec,
        vRtrLdpGenKeepAliveFactor,
        vRtrLdpGenKeepAliveTimeout,
        vRtrLdpGenHelloFactor,
        vRtrLdpGenHelloTimeout,
        vRtrLdpGenRoutePreference,
        vRtrLdpGenControlMode,
        vRtrLdpGenDistMethod,
        vRtrLdpGenRetentionMode,
        vRtrLdpGenTransportAddrType,
        vRtrLdpGenPropagatePolicy,
        vRtrLdpGenLoopDetectCapable,
        vRtrLdpGenHopLimit,
        vRtrLdpGenPathVectorLimit,
        vRtrLdpGenBackoffTime,
        vRtrLdpGenMaxBackoffTime,
        vRtrLdpGenTargKeepAliveFactor,
        vRtrLdpGenTargKeepAliveTimeout,
        vRtrLdpGenTargHelloFactor,
        vRtrLdpGenTargHelloTimeout,
        vRtrLdpGenTargPassiveMode,
        vRtrLdpGenTargetedSessions,
        vRtrLdpGenCreateTime,
        vRtrLdpGenUpTime,
        vRtrLdpGenImportPolicy1,
        vRtrLdpGenImportPolicy2,
        vRtrLdpGenImportPolicy3,
        vRtrLdpGenImportPolicy4,
        vRtrLdpGenImportPolicy5,
        vRtrLdpGenExportPolicy1,
        vRtrLdpGenExportPolicy2,
        vRtrLdpGenExportPolicy3,
        vRtrLdpGenExportPolicy4,
        vRtrLdpGenExportPolicy5,
        vRtrLdpGenTunnelDownDampTime,
        vRtrLdpGenOperDownReason,
        vRtrLdpGenGracefulRestart,
        vRtrLdpGenGRNbrLiveTime,
        vRtrLdpGenGRMaxRecoveryTime,
        vRtrLdpTargImportPolicy1,
        vRtrLdpTargImportPolicy2,
        vRtrLdpTargImportPolicy3,
        vRtrLdpTargImportPolicy4,
        vRtrLdpTargImportPolicy5,
        vRtrLdpTargExportPolicy1,
        vRtrLdpTargExportPolicy2,
        vRtrLdpTargExportPolicy3,
        vRtrLdpTargExportPolicy4,
        vRtrLdpTargExportPolicy5,
        vRtrLdpTargTunnelPreference,
        vRtrLdpStatsOperDownEvents,
        vRtrLdpStatsActiveSessions,
        vRtrLdpStatsActiveAdjacencies,
        vRtrLdpStatsActiveInterfaces,
        vRtrLdpStatsInactiveInterfaces,
        vRtrLdpStatsActiveTargSessions,
        vRtrLdpStatsInactiveTargSessions,
        vRtrLdpStatsAddrFECRecv,
        vRtrLdpStatsAddrFECSent,
        vRtrLdpStatsSvcFECRecv,
        vRtrLdpStatsSvcFECSent,
        vRtrLdpStatsAttemptedSessions,
        vRtrLdpStatsSessRejNoHelloErrors,
        vRtrLdpStatsSessRejAdvErrors,
        vRtrLdpStatsSessRejMaxPduErrors,
        vRtrLdpStatsSessRejLabelRangeErrors,
        vRtrLdpStatsBadLdpIdentifierErrors,
        vRtrLdpStatsBadPduLengthErrors,
        vRtrLdpStatsBadMessageLengthErrors,
        vRtrLdpStatsBadTlvLengthErrors,
        vRtrLdpStatsMalformedTlvValueErrors,
        vRtrLdpStatsKeepAliveExpiredErrors,
        vRtrLdpStatsShutdownNotifRecv,
        vRtrLdpStatsShutdownNotifSent,
        vRtrLdpStatsEgrFecPfxCount,
        vRtrLdpIfTableSpinlock,
        vRtrLdpIfRowStatus,
        vRtrLdpIfLastChange,
        vRtrLdpIfAdminState,
        vRtrLdpIfOperState,
        vRtrLdpIfInheritance,
        vRtrLdpIfKeepAliveFactor,
        vRtrLdpIfKeepAliveTimeout,
        vRtrLdpIfHelloFactor,
        vRtrLdpIfHelloTimeout,
        vRtrLdpIfBackoffTime,
        vRtrLdpIfMaxBackoffTime,
        vRtrLdpIfTransportAddrType,
        vRtrLdpIfPassiveMode,
        vRtrLdpIfAutoCreate,
        vRtrLdpIfOperDownReason,
        vRtrLdpIfExistingAdjacencies,
        vRtrLdpIfTunneling,
        vRtrLdpIfLspRowStatus,
        vRtrLdpPeerRowStatus,
        vRtrLdpPeerAuth,
        vRtrLdpPeerAuthKey,
        vRtrLdpPeerMinTTLValue,
        vRtrLdpPeerTTLLogId,
        vRtrLdpPeerAuthKeyChain,
        vRtrLdpSessLocalLdpId,
        vRtrLdpSessEntityIndex,
        vRtrLdpSessLabelDistMethod,
        vRtrLdpSessLoopDetectForPV,
        vRtrLdpSessPathVectorLimit,
        vRtrLdpSessState,
        vRtrLdpSessAdjacencyType,
        vRtrLdpSessProtocolVersion,
        vRtrLdpSessLocalUdpPort,
        vRtrLdpSessPeerUdpPort,
        vRtrLdpSessLocalTcpPort,
        vRtrLdpSessPeerTcpPort,
        vRtrLdpSessLocalAddress,
        vRtrLdpSessPeerAddress,
        vRtrLdpSessKAHoldTimeRemaining,
        vRtrLdpSessMaxPduLength,
        vRtrLdpSessUpTime,
        vRtrLdpSessLocalKATimeout,
        vRtrLdpSessPeerKATimeout,
        vRtrLdpSessAdvertise,
        vRtrLdpSessRestartHelperState,
        vRtrLdpSessPeerNumRestart,
        vRtrLdpSessLastRestartTime,
        vRtrLdpSessFtReconnectTimeNego,
        vRtrLdpSessFtRecoveryTimeNego,
        vRtrLdpSessFtReconTimeRemaining,
        vRtrLdpSessFtRecovTimeRemaining,
        vRtrLdpSessStatsTargAdj,
        vRtrLdpSessStatsLinkAdj,
        vRtrLdpSessStatsFECRecv,
        vRtrLdpSessStatsFECSent,
        vRtrLdpSessStatsHelloIn,
        vRtrLdpSessStatsHelloOut,
        vRtrLdpSessStatsKeepaliveIn,
        vRtrLdpSessStatsKeepaliveOut,
        vRtrLdpSessStatsInitIn,
        vRtrLdpSessStatsInitOut,
        vRtrLdpSessStatsLabelMappingIn,
        vRtrLdpSessStatsLabelMappingOut,
        vRtrLdpSessStatsLabelRequestIn,
        vRtrLdpSessStatsLabelRequestOut,
        vRtrLdpSessStatsLabelReleaseIn,
        vRtrLdpSessStatsLabelReleaseOut,
        vRtrLdpSessStatsLabelWithdrawIn,
        vRtrLdpSessStatsLabelWithdrawOut,
        vRtrLdpSessStatsLabelAbortIn,
        vRtrLdpSessStatsLabelAbortOut,
        vRtrLdpSessStatsAddrIn,
        vRtrLdpSessStatsAddrOut,
        vRtrLdpSessStatsAddrWithdrawIn,
        vRtrLdpSessStatsAddrWithdrawOut,
        vRtrLdpSessStatsNotificationIn,
        vRtrLdpSessStatsNotificationOut,
        vRtrLdpCepTdmLocalPayloadSize,
        vRtrLdpCepTdmRemotePayloadSize,
        vRtrLdpCepTdmLocalBitrate,
        vRtrLdpCepTdmRemoteBitrate,
        vRtrLdpCepTdmLocalRtpHeader,
        vRtrLdpCepTdmRemoteRtpHeader,
        vRtrLdpCepTdmLocalDiffTimestamp,
        vRtrLdpCepTdmRemoteDiffTimestamp,
        vRtrLdpCepTdmLocalSigPkts,
        vRtrLdpCepTdmRemoteSigPkts,
        vRtrLdpCepTdmLocalCasTrunk,
        vRtrLdpCepTdmRemoteCasTrunk,
        vRtrLdpCepTdmLocalTimestampFreq,
        vRtrLdpCepTdmRemoteTimestampFreq,
        vRtrLdpCepTdmLocalPayloadType,
        vRtrLdpCepTdmRemotePayloadType,
        vRtrLdpCepTdmLocalSsrcId,
        vRtrLdpCepTdmRemoteSsrcId,
        vLdpCepTdmFec129LocalPayloadSize,
        vLdpCepTdmFec129RemotePayloadSize,
        vLdpCepTdmFec129LocalBitrate,
        vLdpCepTdmFec129RemoteBitrate,
        vLdpCepTdmFec129LocalRtpHeader,
        vLdpCepTdmFec129RemoteRtpHeader,
        vLdpCepTdmFec129LocalDiffTimestamp,
        vLdpCepTdmFec129RemoteDiffTimestamp,
        vLdpCepTdmFec129LocalSigPkts,
        vLdpCepTdmFec129RemoteSigPkts,
        vLdpCepTdmFec129LocalCasTrunk,
        vLdpCepTdmFec129RemoteCasTrunk,
        vLdpCepTdmFec129LocalTimestampFreq,
        vLdpCepTdmFec129RemoteTimestampFreq,
        vLdpCepTdmFec129LocalPayloadType,
        vLdpCepTdmFec129RemotePayloadType,
        vLdpCepTdmFec129LocalSsrcId,
        vLdpCepTdmFec129RemoteSsrcId,
        vRtrLdpServFecServType,
        vRtrLdpServFecServId,
        vRtrLdpServFecVpnId,
        vRtrLdpServFecFlags,
        vRtrLdpServFecNumInLabels,
        vRtrLdpServFecNumOutLabels,
        vRtrLdpServFecInLabel1,
        vRtrLdpServFecInLabelStatus1,
        vRtrLdpServFecInLabel2,
        vRtrLdpServFecInLabelStatus2,
        vRtrLdpServFecInLabel3,
        vRtrLdpServFecInLabelStatus3,
        vRtrLdpServFecInLabel4,
        vRtrLdpServFecInLabelStatus4,
        vRtrLdpServFecInLabel5,
        vRtrLdpServFecInLabelStatus5,
        vRtrLdpServFecOutLabel1,
        vRtrLdpServFecOutLabelStatus1,
        vRtrLdpServFecOutLabel2,
        vRtrLdpServFecOutLabelStatus2,
        vRtrLdpServFecOutLabel3,
        vRtrLdpServFecOutLabelStatus3,
        vRtrLdpServFecOutLabel4,
        vRtrLdpServFecOutLabelStatus4,
        vRtrLdpServFecOutLabel5,
        vRtrLdpServFecOutLabelStatus5,
        vRtrLdpServFecSdpId,
        vRtrLdpServFecLocalMTU,
        vRtrLdpServFecRemoteMTU,
        vRtrLdpServFecLocalVlanTag,
        vRtrLdpServFecRemoteVlanTag,
        vRtrLdpServFecLocalMaxCellConcat,
        vRtrLdpServFecRemoteMaxCellConcat,
        vRtrLdpServFecInLabelSigStatus1,
        vRtrLdpServFecInLabelSigStatus2,
        vRtrLdpServFecInLabelSigStatus3,
        vRtrLdpServFecInLabelSigStatus4,
        vRtrLdpServFecInLabelSigStatus5,
        vRtrLdpServFecOutLabelSigStatus1,
        vRtrLdpServFecOutLabelSigStatus2,
        vRtrLdpServFecOutLabelSigStatus3,
        vRtrLdpServFecOutLabelSigStatus4,
        vRtrLdpServFecOutLabelSigStatus5,
        vRtrLdpServFecMateEndpointVcId,
        vRtrLdpServFecMateEndpointSdpId,
        vLdpServFec129ServType,
        vLdpServFec129ServId,
        vLdpServFec129VpnId,
        vLdpServFec129Flags,
        vLdpServFec129NumInLabels,
        vLdpServFec129NumOutLabels,
        vLdpServFec129InLabel1,
        vLdpServFec129InLabelStatus1,
        vLdpServFec129OutLabel1,
        vLdpServFec129OutLabelStatus1,
        vLdpServFec129SdpId,
        vLdpServFec129LocalMTU,
        vLdpServFec129RemoteMTU,
        vLdpServFec129LocalVlanTag,
        vLdpServFec129RemoteVlanTag,
        vLdpServFec129LocalMaxCellConcat,
        vLdpServFec129RemoteMaxCellConcat,
        vLdpServFec129InLabelSigStatus1,
        vLdpServFec129OutLabelSigStatus1,
        vRtrLdpAggrPreMatchAdminState,
        vRtrLdpAggrPreMatchEnabled,
        vRtrLdpAggrPreMatchPreExcPolicy1,
        vRtrLdpAggrPreMatchPreExcPolicy2,
        vRtrLdpAggrPreMatchPreExcPolicy3,
        vRtrLdpAggrPreMatchPreExcPolicy4,
        vRtrLdpAggrPreMatchPreExcPolicy5,
        vRtrLdpGenLabelWithdrawalDelay,
        vRtrLdpIfBfdEnabled,
        vRtrLdpIfLinkLsrIfType,
        vRtrLdpIfTargLsrIfIndex,
        vRtrLdpGenImplicitNull,
        vRtrLdpGenShortTTLPropLocal,
        vRtrLdpGenShortTTLPropTransit,
        vRtrLdpPeerDODLabelDistribution,
        vRtrLdpIfMulticast,
        vRtrLdpGenMPMBBTime,
        vRtrLdpPeerImportPolicy1,
        vRtrLdpPeerImportPolicy2,
        vRtrLdpPeerImportPolicy3,
        vRtrLdpPeerImportPolicy4,
        vRtrLdpPeerImportPolicy5,
        vRtrLdpPeerExportPolicy1,
        vRtrLdpPeerExportPolicy2,
        vRtrLdpPeerExportPolicy3,
        vRtrLdpPeerExportPolicy4,
        vRtrLdpPeerExportPolicy5,
        vRtrLdpSessBfdStatus,
        vRtrLdpSessP2MPCapabilityNego,
        vRtrLdpSessMPMBBCapabilityNego,
        vRtrLdpSessDynamicCapabilityNego,
        vRtrLdpStatsUnknownTlvErrors,
        vRtrLdpStatsP2MPFECSent,
        vRtrLdpStatsP2MPFECRecv,
        vRtrLdpPeerFec129CiscoInterop,
        vRtrLdpServFecLocalIpv4Capblty,
        vRtrLdpServFecRemoteIpv4Capblty,
        vRtrLdpServFecLocalIpv6Capblty,
        vRtrLdpServFecRemoteIpv6Capblty,
        vRtrLdpServFecLocalIpv4CeIpAddr,
        vRtrLdpServFecRemoteIpv4CeIpAddr,
        vRtrLdpServFecInLbl1WdwReason,
        vLdpServFec129LocalIpv4Capblty,
        vLdpServFec129RemoteIpv4Capblty,
        vLdpServFec129LocalIpv6Capblty,
        vLdpServFec129RemoteIpv6Capblty,
        vLdpServFec129LocalIpv4CeIpAddr,
        vLdpServFec129RemoteIpv4CeIpAddr,
        vLdpServFec129InLbl1WdwReason,
        vRtrLdpGenTunlTblExportPolicy1,
        vRtrLdpGenTunlTblExportPolicy2,
        vRtrLdpGenTunlTblExportPolicy3,
        vRtrLdpGenTunlTblExportPolicy4,
        vRtrLdpGenTunlTblExportPolicy5,
        vRtrLdpPeerPMTUDiscovery,
        vRtrLdpGenP2MPCapability,
        vRtrLdpGenMPMBBCapability,
        vRtrLdpGenDynamicCapability,
        vLdpServFec129MateAgiTlv,
        vLdpServFec129MateSdpId,
        vLdpServFec129MateSrcAiiTlv,
        vLdpServFec129MateTgtAiiTlv,
        vRtrLdpPeerPMTUDiscovery,
        vRtrLdpServFecLocalFLTxCapblty,
        vRtrLdpServFecLocalFLRxCapblty,
        vRtrLdpServFecRemoteFLTxCapblty,
        vRtrLdpServFecRemoteFLRxCapblty,
        vLdpServFec129LocalFLTxCapblty,
        vLdpServFec129LocalFLRxCapblty,
        vLdpServFec129RemoteFLTxCapblty,
        vLdpServFec129RemoteFLRxCapblty,
        vRtrLdpPeerAdvAdjAddrOnly,
        vRtrLdpSessionAddrLocalLdpId,
        vRtrLdpSessionAddrNumInAddrs,
        vRtrLdpSessionAddrNumOutAddrs,
        vRtrLdpSessionInAddrLocalLdpId,
        vRtrLdpSessionOutAddrLocalLdpId,
        vRtrLdpSessStatsAddrRecv,
        vRtrLdpSessStatsAddrSent,
        vRtrLdpGenLdpFrr,
        vRtrLdpHelloAdjBfdStatus,
        vRtrLdpNgP2MPFecFlags,
        vRtrLdpNgP2MPFecNumInLabels,
        vRtrLdpNgP2MPFecNumOutLabels,
        vRtrLdpNgP2MPFecTunnelIfId,
        vRtrLdpNgP2MPFecMetric,
        vRtrLdpNgP2MPFecMTU,
        vRtrLdpNgP2MPFecInLbl,
        vRtrLdpNgP2MPFecInLblStatus,
        vRtrLdpNgP2MPFecInLblIfIndex,
        vRtrLdpNgP2MPFecOutLbl,
        vRtrLdpNgP2MPFecOutLblStatus,
        vRtrLdpNgP2MPFecOutLblNxtHopType,
        vRtrLdpNgP2MPFecOutLblNxtHopAddr,
        vRtrLdpNgP2MPFecOutLblIfIndex,
        vRtrLdpNgP2MPFecOutLblLspId,
        vRtrLdpNgP2MPFecMapFlags,
        vRtrLdpNgP2MPFecMapNumInLabels,
        vRtrLdpNgP2MPFecMapNumOutLabels,
        vRtrLdpNgP2MPFecMapTunnelIfId,
        vRtrLdpNgP2MPFecMapMetric,
        vRtrLdpNgP2MPFecMapMTU,
        vRtrLdpAddressFecFlags,
        vRtrLdpAddressFecNumInLabels,
        vRtrLdpAddressFecNumOutLabels,
        vRtrLdpAddressFecInLbl,
        vRtrLdpAddressFecInLblStatus,
        vRtrLdpAddressFecInLblIfIndex,
        vRtrLdpAddressFecOutLbl,
        vRtrLdpAddressFecOutLblStatus,
        vRtrLdpAddressFecOutLblIfIndex,
        vRtrLdpAddressFecOutLblNHType,
        vRtrLdpAddressFecOutLblNHAddr,
        vRtrLdpAddressFecOutLblMetric,
        vRtrLdpAddressFecOutLblMtu,
        vRtrLdpAddressFecOutLblLspId,
        vRtrLdpAddressFecMapFlags,
        vRtrLdpAddressFecMapNumInLabels,
        vRtrLdpAddressFecMapNumOutLabels,
        vRtrLdpAddrActiveFecFecFlags,
        vRtrLdpAddrActiveFecNumInLbls,
        vRtrLdpAddrActiveFecNumOutLbls,
        vRtrLdpAddrActiveFecInLbl,
        vRtrLdpAddrActiveFecInLblIfIndex,
        vRtrLdpAddrActiveFecOutLbl,
        vRtrLdpAddrActiveFecOutLblStatus,
        vRtrLdpAddrActiveFecOutLblIfIdx,
        vRtrLdpAddrActiveFecOutLblNHType,
        vRtrLdpAddrActiveFecOutLblNHAddr,
        vRtrLdpAddrActiveFecOutLblMetric,
        vRtrLdpAddrActiveFecOutLblMtu,
        vRtrLdpAddrActiveFecOutLblLspId,
        vRtrLdpGenTargHelloReduction,
        vRtrLdpGenTargHelloReductionFctr,
        vRtrLdpIfHelloReduction,
        vRtrLdpIfHelloReductionFactor,
        vRtrLdpIfOperHelloTimeout,
        vRtrLdpIfLinkLsrIfIndex,
        vRtrLdpStaticFecNHIfName,
        vRtrLdpGenMcastUpstreamFrr,
        vRtrLdpPeerPeIDMacFlushInterop,
        vRtrLdpGenOverloadCapability,
        vRtrLdpSessOvrloadCapabltyNego,
        vRtrLdpSessAddrFecOverloadSent,
        vRtrLdpSessAddrFecOverloadRecv,
        vRtrLdpSessMcastFecOverloadSent,
        vRtrLdpSessMcastFecOverloadRecv,
        vRtrLdpSessServFecOverloadSent,
        vRtrLdpSessServFecOverloadRecv,
        vRtrLdpIfCreator,
        vRtrLdpIfTemplName,
        vRtrLdpIfUpTime,
        vRtrLdpPeerMaxFec,
        vRtrLdpPeerMaxFecLogOnly,
        vRtrLdpPeerMaxFecThreshold,
        vRtrLdpSessOperMaxFecThreshold
    }
    STATUS      current
    DESCRIPTION
        "The group of obsoleted objects for the LDP feature on Nokia SROS
         series systems 13.0 Release."
    ::= { tmnxLdpGroups 63 }

tmnxLdpTLDPAutoCreateV13v0Group  OBJECT-GROUP
    OBJECTS     {
        vRtrLdpPeerTemplRowStatus,
        vRtrLdpPeerTemplLastChanged,
        vRtrLdpPeerTemplAdminState,
        vRtrLdpPeerTemplInheritance,
        vRtrLdpPeerTemplKeepAliveFactor,
        vRtrLdpPeerTemplKeepAliveTimeout,
        vRtrLdpPeerTemplHelloFactor,
        vRtrLdpPeerTemplHelloTimeout,
        vRtrLdpPeerTemplTunneling,
        vRtrLdpPeerTemplBfdEnabled,
        vRtrLdpPeerTemplLsrIfIndex,
        vRtrLdpPeerTemplHelloReduction,
        vRtrLdpPeerTemplHelloReductnFctr,
        vRtrLdpPeerTemplCreateTime,
        vRtrLdpPeerTemplIndex,
        vRtrLdpPeerTemplPlcyMapPolicy1,
        vRtrLdpPeerTemplPlcyMapPolicy2,
        vRtrLdpPeerTemplPlcyMapPolicy3,
        vRtrLdpPeerTemplPlcyMapPolicy4,
        vRtrLdpPeerTemplPlcyMapPolicy5,
        vRtrLdpPeerTemplPlcyMapIndex,
        vRtrLdpPeerTemplPlcyMapCreateTim,
        vRtrLdpPeerTemplPlcyMapLstChange,
        vRtrLdpPeerTemplPlcyMapRowStatus,
        vRtrLdpPeerTemplTableLstChanged,
        vRtrLdpPeerTmplPlcyMpTblLstChgd,
        vRtrLdpPeerTemplPeerCreateTime
    }
    STATUS      current
    DESCRIPTION
        "The group of all global objects in LDP supporting T-LDP Auto Creation
         feature on Nokia SROS series systems 13.0 release."
    ::= { tmnxLdpGroups 64 }

tmnxLdpNotifyObjsV13v0Group      OBJECT-GROUP
    OBJECTS     {
        vRtrLdpNotifyLocalGroupID,
        vRtrLdpNotifyRemoteGroupID
    }
    STATUS      current
    DESCRIPTION
        "The group of objects supporting extended LDP notifications on Nokia
         SROS series systems 13.0 release."
    ::= { tmnxLdpGroups 65 }

tmnxLdpObsoletedNotifyObjGroup   OBJECT-GROUP
    OBJECTS     {
        vRtrLdpInstanceNotifyReasonCode,
        vRtrLdpSessOverloadState,
        vRtrLdpSessOverloadDirection,
        vRtrLdpSessOverloadFecType,
        vRtrLdpSessOperThresLevel
    }
    STATUS      current
    DESCRIPTION
        "The group of obsoleted objects supporting extended LDP notifications
         on Nokia SROS series systems 13.0 release."
    ::= { tmnxLdpGroups 66 }

tmnxLdpObsoletedNtfnV13v0Group   NOTIFICATION-GROUP
    NOTIFICATIONS {
        vRtrLdpInstanceStateChange,
        vRtrLdpIfStateChange,
        vRtrLdpSessionStateChange,
        vRtrLdpSessMaxFecThresChanged,
        vRtrLdpSessMaxFecLimitReached
    }
    STATUS      current
    DESCRIPTION
        "The group of notifications which are obsoleted in Nokia SROS series
         systems release 13.0. release."
    ::= { tmnxLdpGroups 67 }

tmnxLdpNotificationV13v0Group    NOTIFICATION-GROUP
    NOTIFICATIONS {
        vRtrLdpStateChange,
        vRtrLdpGroupIdMismatch
    }
    STATUS      current
    DESCRIPTION
        "The group of notifications supporting the extended LDP feature on
         Nokia SROS series systems 13.0 release."
    ::= { tmnxLdpGroups 68 }

tmnxLdpLocalLsrIdAdvertGroup     OBJECT-GROUP
    OBJECTS     {
        vRtrLdpPeerTemplLsrIdAdvert
    }
    STATUS      current
    DESCRIPTION
        "The group of objects supports local LSR Id feature on Nokia  SROS
         series systems release 15.0."
    ::= { tmnxLdpGroups 69 }

tmnxLdpLocalLsrIdCommunityGroup  OBJECT-GROUP
    OBJECTS     {
        vRtrLdpPeerTemplLsrIdCommunity
    }
    STATUS      current
    DESCRIPTION
        "The group of objects supports local LSR Id feature on Nokia SROS
         series systems release 15.0."
    ::= { tmnxLdpGroups 70 }

tmnxLdpAggrEgrStatsV16v0Group    OBJECT-GROUP
    OBJECTS     {
        vRtrLdpAggregatePkts,
        vRtrLdpAggregatePktsLow32,
        vRtrLdpAggregatePktsHigh32,
        vRtrLdpAggregateOctets,
        vRtrLdpAggregateOctetsLow32,
        vRtrLdpAggregateOctetsHigh32
    }
    STATUS      current
    DESCRIPTION
        "The group of all global objects in LDP supporting LDP egress statistic
         aggregation feature on Nokia SROS series systems 16.0 release."
    ::= { tmnxLdpGroups 71 }

tmnxLdpPeerMcastTunnelingGroup   OBJECT-GROUP
    OBJECTS     {
        vRtrLdpPeerTemplMcastTunneling
    }
    STATUS      current
    DESCRIPTION
        "The group of objects in LDP supporting multicast tunneling feature on
         Nokia SROS series systems 20.0 release."
    ::= { tmnxLdpGroups 72 }

tmnxLdpNotifyPrefix              OBJECT IDENTIFIER ::= { tmnxSRNotifyPrefix 8 }

tmnxLdpNotifications             OBJECT IDENTIFIER ::= { tmnxLdpNotifyPrefix 0 }

vRtrLdpStateChange               NOTIFICATION-TYPE
    OBJECTS     {
        vRtrLdpStatus
    }
    STATUS      current
    DESCRIPTION
        "The vRtrLdpStateChange notification is generated when the LDP protocol
         is created or deleted in the router."
    ::= { tmnxLdpNotifications 1 }

vRtrLdpInstanceStateChange       NOTIFICATION-TYPE
    OBJECTS     {
        vRtrLdpGenAdminState,
        vRtrLdpGenOperState,
        vRtrLdpInstanceNotifyReasonCode,
        vRtrLdpGenOperDownReason
    }
    STATUS      obsolete
    DESCRIPTION
        "[CAUSE] The vRtrLdpInstanceStateChange notification may be triggered
         for the following reasons:

         1) The LDP instance changes state operationally.
         2) vRtrLdpGenOperState remains 'inService' but internal event described
         by vRtrLdpGenOperDownReason has changed.  New notification will not be
         generated if multiple internal event change occurs during 10 minute
         interval.

         [EFFECT] Based on the vRtrLdpGenOperDownReason reason code, system may
         not be able to accept new request from peers.

         [RECOVERY] Based on the vRtrLdpGenOperDownReason reason code,
         appropriate configuration changes in LDP may be required.

         This notification was obsoleted in release 13.0."
    ::= { tmnxLdpNotifications 2 }

vRtrLdpIfStateChange             NOTIFICATION-TYPE
    OBJECTS     {
        vRtrLdpIfAdminState,
        vRtrLdpIfOperState,
        vRtrLdpIfOperDownReason
    }
    STATUS      obsolete
    DESCRIPTION
        "The vRtrLdpIfStateChange notification is generated when the LDP
         interface changes state either administratively or operationally.

         This notification was obsoleted in release 13.0."
    ::= { tmnxLdpNotifications 3 }

vRtrLdpSvcIdMismatch             NOTIFICATION-TYPE
    OBJECTS     {
        vRtrLdpNotifyLocalServiceID,
        vRtrLdpNotifyRemoteServiceID
    }
    STATUS      obsolete
    DESCRIPTION
        "The vRtrLdpSvcIdMismatch notification is generated when there is a
         mismatch of local and remote service IDs."
    ::= { tmnxLdpNotifications 4 }

vRtrLdpGroupIdMismatch           NOTIFICATION-TYPE
    OBJECTS     {
        vRtrLdpNotifyLocalGroupID,
        vRtrLdpNotifyRemoteGroupID
    }
    STATUS      current
    DESCRIPTION
        "The vRtrLdpGroupIdMismatch notification is generated when there is a
         mismatch of local and remote group IDs."
    ::= { tmnxLdpNotifications 5 }

vRtrLdpSessionStateChange        NOTIFICATION-TYPE
    OBJECTS     {
        vRtrLdpSessState,
        vRtrLdpSessOverloadState,
        vRtrLdpSessOverloadDirection,
        vRtrLdpSessOverloadFecType
    }
    STATUS      obsolete
    DESCRIPTION
        "[CAUSE] The vRtrLdpSessionStateChange notification is generated when
         an Overload Notification is sent to or received from the peer
         vRtrLdpPeerLdpId for a fec type of vRtrLdpSessOverloadFecType when
         vRtrLdpSessState remains 'operational'.

         [EFFECT] Once the Local LSR has sent the Overload Notification to the
         peer vRtrLdpPeerLdpId for the fec type  of vRtrLdpSessOverloadFecType
         and vRtrLdpSessOverloadState has the value of 'true', then new Label
         Mapping Messages received from the peer vRtrLdpPeerLdpId for the fec
         type of vRtrLdpSessOverloadFecType is returned with a Label Release
         Message.

         If the Local LSR has received an Overload Notification from the peer
         vRtrLdpPeerLdpId for the fec type of vRtrLdpSessOverloadFecType and
         vRtrLdpSessOverloadState has the value of 'true', no new Label Mapping
         Message for the fec type of vRtrLdpSessOverloadFecType will be sent to
         the peer vRtrLdpPeerLdpId.

         If the Local LSR has received an Overload Notification from the peer
         vRtrLdpPeerLdpId for the fec type  of vRtrLdpSessOverloadFecType and
         vRtrLdpSessOverloadState has the value of 'false', then the Local LSR
         will send all pending and any new Label Mapping Message for the fec type
         of vRtrLdpSessOverloadFecType to the peer vRtrLdpPeerLdpId.

         [RECOVERY] In case the Local LSR sent the Overload Notification to the
         peer vRtrLdpPeerLdpId and vRtrLdpSessOverloadState has the value of
         'true' for fec type vRtrLdpSessOverloadFecType, then appropriate LDP
         configuration changes may be required on the Local and/or Remote LSR.

         Once the Local LSR is not overloaded anymore, an Overload Notification
         is sent to the peer vRtrLdpPeerLdpId and vRtrLdpSessOverloadState has
         the value of 'false' for fec type vRtrLdpSessOverloadFecType.

         This notification was obsoleted in release 13.0."
    ::= { tmnxLdpNotifications 6 }

vRtrLdpSessMaxFecThresChanged    NOTIFICATION-TYPE
    OBJECTS     {
        vRtrLdpPeerMaxFec,
        vRtrLdpSessOperThresLevel,
        vRtrLdpSessOperMaxFecThreshold
    }
    STATUS      obsolete
    DESCRIPTION
        "[CAUSE] A vRtrLdpSessMaxFecThresChanged notification is generated when
         the number of FECs accepted from the peer has exceeded or drops below
         vRtrLdpPeerMaxFecThreshold percent of the value specified by
         vRtrLdpPeerMaxFec.

         New notification will not be generated if multiple internal event
         change occurs for the same level indicated by
         vRtrLdpSessOperThresLevel during a 2 minute interval.

         If any parameter in FEC limit configuration changes then we would
         always raise this trap if current number of FECs are above the
         configured threshold or has crossed the threshold downwards. If we
         remain on or below the configured threshold before and after the
         configuration changes then no trap would be generated.

         [EFFECT] No direct effect but if the peer LSR continues to send
         further Label Mapping Message, then the number of FECs may exceed the
         configured maximum (vRtrLdpPeerMaxFec) resulting in the generation of
         vRtrLdpSessMaxFecLimitReached notification.

         [RECOVERY] Appropriate Configuration changes in local or peer LSR will
         be required.

         This notification was obsoleted in release 13.0."
    ::= { tmnxLdpNotifications 7 }

vRtrLdpSessMaxFecLimitReached    NOTIFICATION-TYPE
    OBJECTS     {
        vRtrLdpPeerMaxFec,
        vRtrLdpSessOperMaxFecThreshold
    }
    STATUS      obsolete
    DESCRIPTION
        "[CAUSE] A vRtrLdpSessMaxFecLimitReached notification is generated when
         the number of FECs accepted from the peer has reached the value
         specified by vRtrLdpPeerMaxFec.

         If the current number of FECs go below the limit but higher than the
         configured threshold and again start to increase and hit the limit a
         second time, we will raise a trap if 2 or more minutes have elapsed
         since the first vRtrLdpSessMaxFecLimitReached trap was sent.

         If any parameter in FEC limit configuration changes and the current
         number of FECs are equal to or higher than the limit specified by
         vRtrLdpPeerMaxFec, then we would always raise the
         vRtrLdpSessMaxFecLimitReached trap.

         [EFFECT] When the number of FECs exceed the configured maximum
         (vRtrLdpPeerMaxFec) it results in any of the following:

         (1) If vRtrLdpPeerMaxFecLogOnly is set to 'false' and LSR Overload
         Capability is supported, then Overload procedure will take place.

         (2) If vRtrLdpPeerMaxFecLogOnly is set to 'false' and LSR Overload
         Capability is not supported, Label Mapping Message will be returned
         with Label Release Message.

         (3) If vRtrLdpPeerMaxFecLogOnly is set to 'true', no action will be
         taken.

         [RECOVERY] Appropriate Configuration changes in local or peer LSR will
         be required.

         This notification was obsoleted in release 13.0."
    ::= { tmnxLdpNotifications 8 }

END
