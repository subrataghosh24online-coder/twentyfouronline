TROPIC-STATISTICS-MIB DEFINITIONS ::= BEGIN

-- (c) Copyright 2023 Nokia Networks.  All rights reserved.
-- This software is the confidential and proprietary property of
-- Nokia and may only be used in accordance with the terms of the
-- license agreement provided with this software.

IMPORTS
      SnmpAdminString                         FROM SNMP-FRAMEWORK-MIB
      OBJECT-TYPE, MODULE-IDENTITY,
      Unsigned32, Integer32,
      Counter32, Counter64                    FROM SNMPv2-SMI
      MODULE-COMPLIANCE, OBJECT-GROUP         FROM SNMPv2-CONF
      TEXTUAL-CONVENTION,
      DateAndTime                             FROM SNMPv2-TC
      ifIndex                                 FROM IF-MIB
      tnShelfIndex                            FROM TROPIC-SHELF-MIB
      tnSlotIndex                             FROM TROPIC-SLOT-MIB
      TnStatsProfileId,
      TnCommand                               FROM TROPIC-TC
      tnOthIfIndex,
      tnOthIfIndexLo,
      tnOthOdukTcmIfIndex,
      tnOthOdukTcmIfIndexLo                   FROM TROPIC-OTH-MIB
      tnSystemModules, tnStatisticsMIB        FROM TROPIC-GLOBAL-REG
      tnSyncELineRefIndex                     FROM TROPIC-SYNCE-MIB;

  tnStatisticsMibModule MODULE-IDENTITY
      LAST-UPDATED    "202211111200Z"
      ORGANIZATION    "Nokia"
      CONTACT-INFO    "Nokia
                       Attn: Jeff Donnelly
                       600 Mountain Avenue
                       New Providence, NJ 07974

                       Phone: +1 732 221 6408
                       Email: jeff.donnelly@nokia.com"

      DESCRIPTION "The statistics MIB, including binned counts, raw
                   counts and TCA configuration."


      REVISION    "202211111200Z"
      DESCRIPTION "Added the following to tnOthOdukStatsTcmConfigTable:
                   tnOthOdukStatsTcmConfigIntervalLength."

      REVISION    "202208121200Z"
      DESCRIPTION "1) Added the following to tnPhyCodeSublayerStatsTable:
                      tnPhyCodeSublayerStatsRxBIP8
                      tnPhyCodeSublayerStatsTxBIP8
                      tnPhyCodeSublayerStatsRxUAS
                      tnPhyCodeSublayerStatsTxUAS.
                   2) Added the following to tnFECPMStatsTable:
                      tnFECPMStatRxSUS.
                   3) Added the following to tnETHFECPMStatsTable:
                      tnETHFECPMStatBERpreFECCnt."

      REVISION    "202207081200Z"
      DESCRIPTION "1) Added the following to TnStatsGroupId:
                      fcPktStats(61).
                   2) Added the following tables:
                      tnFcPktStatsTable
                      tnFcPktRawCountStatsTable.
                   3) Added the following Scalars:
                      tnStatisticsFcPktScalars."

      REVISION    "202201211200Z"
      DESCRIPTION "1) Added the following to TnStatsGroupId:
                      ochopr(60).
                   2) Added the following tables:
                      tnOchOprStatsTable
                      tnOchOprRawCountStatsTable."

      REVISION    "202110221200Z"
      DESCRIPTION "1) Added the following to TnStatsGroupId:
                      oplineoutc(54)
                      to
                      qfactorStats(59).
                   2) Added the following tables:
                      tnOsnrRxStatsTable
                      tnQfactorStatsTable
                      tnOsnrRxRawCountStatsTable
                      tnQfactorRawCountStatsTable."

      REVISION    "202110051200Z"
      DESCRIPTION "1) Added the following to tnStatisticsOdukRxScalars:
                      tnOthOdutc1StatRxNeBIP8ErrCnt15MinTr
                      tnOthOdutc1StatRxNeBIP8ErrCnt15MinRtr
                      tnOthOdutc1StatRxNeBIP8ErrCnt1DayTr
                      tnOthOdutc1StatRxFeBIP8ErrCnt15MinTr
                      tnOthOdutc1StatRxFeBIP8ErrCnt15MinRtr
                      tnOthOdutc1StatRxFeBIP8ErrCnt1DayTr
                      tnOthOdutc4StatRxNeBIP8ErrCnt15MinTr
                      tnOthOdutc4StatRxNeBIP8ErrCnt15MinRtr
                      tnOthOdutc4StatRxNeBIP8ErrCnt1DayTr
                      tnOthOdutc4StatRxFeBIP8ErrCnt15MinTr
                      tnOthOdutc4StatRxFeBIP8ErrCnt15MinRtr
                      tnOthOdutc4StatRxFeBIP8ErrCnt1DayTr.
                   2) Added the following to tnStatisticsOdukTxScalars:
                      tnOthOdutc1StatTxNeBIP8ErrCnt15MinTr
                      tnOthOdutc1StatTxNeBIP8ErrCnt15MinRtr
                      tnOthOdutc1StatTxNeBIP8ErrCnt1DayTr
                      tnOthOdutc1StatTxFeBIP8ErrCnt15MinTr
                      tnOthOdutc1StatTxFeBIP8ErrCnt15MinRtr
                      tnOthOdutc1StatTxFeBIP8ErrCnt1DayTr
                      tnOthOdutc4StatTxNeBIP8ErrCnt15MinTr
                      tnOthOdutc4StatTxNeBIP8ErrCnt15MinRtr
                      tnOthOdutc4StatTxNeBIP8ErrCnt1DayTr
                      tnOthOdutc4StatTxFeBIP8ErrCnt15MinTr
                      tnOthOdutc4StatTxFeBIP8ErrCnt15MinRtr
                      tnOthOdutc4StatTxFeBIP8ErrCnt1DayTr.
                   3) Added the following to tnStatisticsOtukScalars:
                      tnOthOtutc1StatRxNeSMBIP8ErrCnt15MinTr
                      tnOthOtutc1StatRxNeSMBIP8ErrCnt15MinRtr
                      tnOthOtutc1StatRxNeSMBIP8ErrCnt1DayTr
                      tnOthOtutc1StatRxFeSMBIP8ErrCnt15MinTr
                      tnOthOtutc1StatRxFeSMBIP8ErrCnt15MinRtr
                      tnOthOtutc1StatRxFeSMBIP8ErrCnt1DayTr
                      tnOthOtutc4StatRxNeSMBIP8ErrCnt15MinTr
                      tnOthOtutc4StatRxNeSMBIP8ErrCnt15MinRtr
                      tnOthOtutc4StatRxNeSMBIP8ErrCnt1DayTr
                      tnOthOtutc4StatRxFeSMBIP8ErrCnt15MinTr
                      tnOthOtutc4StatRxFeSMBIP8ErrCnt15MinRtr
                      tnOthOtutc4StatRxFeSMBIP8ErrCnt1DayTr."

      REVISION    "202109171200Z"
      DESCRIPTION "1) Added the following to tnETHFECPMStatsTable:
                      tnETHFECPMStatRxBERpreFEC
                      tnETHFECPMStatRxBERPostFEC
                   2) Added the following to tnETHFECPMRawCountStatsTable:
                      tnETHFECPMRawCountStatRxBERpreFEC
                      tnETHFECPMRawCountStatRxBERPostFEC."

      REVISION    "202107301200Z"
      DESCRIPTION "1) Added the following to tnStatisticsOdukRxScalars:
                      tnOthOduflexFC3200RxNeBIP8ErrCnt15MinTr
                      tnOthOduflexFC3200RxNeBIP8ErrCnt15MinRtr
                      tnOthOduflexFC3200RxNeBIP8ErrCnt1DayTr
                      tnOthOduflexFC3200RxFeBIP8ErrCnt15MinTr
                      tnOthOduflexFC3200RxFeBIP8ErrCnt15MinRtr
                      tnOthOduflexFC3200RxFeBIP8ErrCnt1DayTr.
                   2) Added the following to tnStatisticsOdukTxScalars:
                      tnOthOduflexFC3200TxNeBIP8ErrCnt15MinTr
                      tnOthOduflexFC3200TxNeBIP8ErrCnt15MinRtr
                      tnOthOduflexFC3200TxNeBIP8ErrCnt1DayTr
                      tnOthOduflexFC3200TxFeBIP8ErrCnt15MinTr
                      tnOthOduflexFC3200TxFeBIP8ErrCnt15MinRtr
                      tnOthOduflexFC3200TxFeBIP8ErrCnt1DayTr.
                   3) Added the following to tnStatisticsPcsScalars:
                      tnPcsStats32GFCRxCV15MinTr
                      tnPcsStats32GFCTxCV15MinTr
                      tnPcsStats32GFCRxCV1DayTr
                      tnPcsStats32GFCTxCV1DayTr
                      tnPcsStats32GFCRxCV15MinRtr
                      tnPcsStats32GFCTxCV15MinRtr."

      REVISION    "202105281200Z"
      DESCRIPTION "1) Added the following to TnStatsGroupId:
                      evmStats(53).
                   2) Added the following tables:
                      tnEvmStatsTable
                      tnEvmRawCountStatsTable."

      REVISION    "202104301200Z"
      DESCRIPTION "1) Added the following to tnOpOchInStatsTable:
                      tnOpOchInStatWidth.
                   2) Added the following to tnOpOchOutStatsTable:
                      tnOpOchOutStatWidth.
                   3) Added the following to tnOpSupChInStatsTable:
                      tnOpSupChInStatWidth.
                   4) Added the following to tnOpSupChOutStatsTable:
                      tnOpSupChOutStatWidth.
                   5) Added the following to tnOpOchInRawCountStatsTable:
                      tnOpOchInRawCountStatWidth.
                   6) Added the following to tnOpOchOutRawCountStatsTable:
                      tnOpOchOutRawCountStatWidth.
                   7) Added the following to tnOpSupChInRawCountStatsTable:
                      tnOpSupChInRawCountStatWidth.
                   8) Added the following to tnOpSupChOutRawCountStatsTable:
                      tnOpSupChOutRawCountStatWidth."

      REVISION    "202103121200Z"
      DESCRIPTION "1) Added the following to TnStatsGroupId:
                      opSupChIn(51)
                      opSupChOut(52).
                   2) Added the following tables:
                      tnOpSupChInStatsTable
                      tnOpSupChOutStatsTable
                      tnOpSupChInRawCountStatsTable
                      tnOpSupChOutRawCountStatsTable."

      REVISION    "202008281200Z"
      DESCRIPTION "Added the following tables:
                   tnPdlStatsTable
                   tnSoprStatsTable
                   tnEsnrStatsTable
                   tnPdlRawCountStatsTable
                   tnSoprRawCountStatsTable
                   tnEsnrRawCountStatsTable."

      REVISION    "202008211200Z"
      DESCRIPTION "1) Added the following to TnStatsGroupId:
                      ePdlStats(48)
                      eSoprStats(49)
                      eEsnrStats(50).
                   2) Added the following to tnStatisticsOdukRxScalars:
                      tnOthOducStatRxNeBIP8ErrCnt15MinTr
                      tnOthOducStatRxNeBIP8ErrCnt15MinRtr
                      tnOthOducStatRxNeBIP8ErrCnt1DayTr
                      tnOthOducStatRxFeBIP8ErrCnt15MinTr
                      tnOthOducStatRxFeBIP8ErrCnt15MinRtr
                      tnOthOducStatRxFeBIP8ErrCnt1DayTr
                      tnOthOduflex400GBERxNeBIP8ErrCnt15MinTr
                      tnOthOduflex400GBERxNeBIP8ErrCnt15MinRtr
                      tnOthOduflex400GBERxNeBIP8ErrCnt1DayTr
                      tnOthOduflex400GBERxFeBIP8ErrCnt15MinTr
                      tnOthOduflex400GBERxFeBIP8ErrCnt15MinRtr
                      tnOthOduflex400GBERxFeBIP8ErrCnt1DayTr.
                   3) Added the following to tnStatisticsOdukTxScalars:
                      tnOthOducStatTxNeBIP8ErrCnt15MinTr
                      tnOthOducStatTxNeBIP8ErrCnt15MinRtr
                      tnOthOducStatTxNeBIP8ErrCnt1DayTr
                      tnOthOducStatTxFeBIP8ErrCnt15MinTr
                      tnOthOducStatTxFeBIP8ErrCnt15MinRtr
                      tnOthOducStatTxFeBIP8ErrCnt1DayTr
                      tnOthOduflex400GBETxNeBIP8ErrCnt15MinTr
                      tnOthOduflex400GBETxNeBIP8ErrCnt15MinRtr
                      tnOthOduflex400GBETxNeBIP8ErrCnt1DayTr
                      tnOthOduflex400GBETxFeBIP8ErrCnt15MinTr
                      tnOthOduflex400GBETxFeBIP8ErrCnt15MinRtr
                      tnOthOduflex400GBETxFeBIP8ErrCnt1DayTr.
                   4) Added the following to tnStatisticsOtukScalars:
                      tnOthOtucStatRxNeSMBIP8ErrCnt15MinTr
                      tnOthOtucStatRxNeSMBIP8ErrCnt15MinRtr
                      tnOthOtucStatRxNeSMBIP8ErrCnt1DayTr
                      tnOthOtucStatRxFeSMBIP8ErrCnt15MinTr
                      tnOthOtucStatRxFeSMBIP8ErrCnt15MinRtr
                      tnOthOtucStatRxFeSMBIP8ErrCnt1DayTr.
                   5) Added the following to tnStatisticsPcsScalars:
                      tnPcsStats400GBERxCV15MinTr
                      tnPcsStats400GBETxCV15MinTr
                      tnPcsStats400GBERxCV1DayTr
                      tnPcsStats400GBETxCV1DayTr
                      tnPcsStats400GBERxCV15MinRtr
                      tnPcsStats400GBETxCV15MinRtr.
                   6) Added the following to tnStatisticsOthOduTcmScalars:
                      tnOthOducStatsTcmNeRxBIP8ErrCnt15MinTr
                      tnOthOducStatsTcmNeRxBIP8ErrCnt15MinRtr
                      tnOthOducStatsTcmNeRxBIP8ErrCnt1DayTr
                      tnOthOducStatsTcmFeRxBIP8ErrCnt15MinTr
                      tnOthOducStatsTcmFeRxBIP8ErrCnt15MinRtr
                      tnOthOducStatsTcmFeRxBIP8ErrCnt1DayTr
                      tnOthOduflex400GBEStatsTcmNeRxBIP8ErrCnt15MinTr
                      tnOthOduflex400GBEStatsTcmNeRxBIP8ErrCnt15MinRtr
                      tnOthOduflex400GBEStatsTcmNeRxBIP8ErrCnt1DayTr
                      tnOthOduflex400GBEStatsTcmFeRxBIP8ErrCnt15MinTr
                      tnOthOduflex400GBEStatsTcmFeRxBIP8ErrCnt15MinRtr
                      tnOthOduflex400GBEStatsTcmFeRxBIP8ErrCnt1DayTr."

      REVISION    "202005081200Z"
      DESCRIPTION "Added the following to tnQmarginStatsTable:
                   tnQmarginStatMin15MinTr
                   tnQmarginStatMin15MinRtr
                   tnQmarginStatMin1DayTr."

      REVISION    "201907191200Z"
      DESCRIPTION "Modified the range from (SIZE(0..50)) to (SIZE(0..255))
                   for the following attribute:
                   tnStatsTCAProfileDescr."

      REVISION    "201905101200Z"
      DESCRIPTION "1) Added the following to TnStatsGroupId:
                      csrStats(46)
                      qmarginStats(47).
                   2) Added the following tables:
                      tnCsrStatsTable
                      tnQmarginStatsTable
                      tnCsrRawCountStatsTable
                      tnQmarginRawCountStatsTable."

      REVISION    "201904191200Z"
      DESCRIPTION "Updated DESCRIPTION of the following:
                   tnSyncEStatsOffsetMin
                   tnSyncEStatsOffsetMax
                   tnSyncEStatsOffsetAverage
                   tnSyncStatsOffsetAverage."

      REVISION    "201811161200Z"
      DESCRIPTION "Added the following table:
                   tnPktWanifStatsControlTable."

      REVISION    "201810121200Z"
      DESCRIPTION "Added the following to TnStatsGroupId:
                   packetWanifStats(45)."

      REVISION    "201808031200Z"
      DESCRIPTION "Updated DESCRIPTION of the following:
                   tnSyncEStatsOffsetMin
                   tnSyncEStatsOffsetMax
                   tnSyncEStatsOffsetAverage
                   tnSyncStatsOffsetMin
                   tnSyncStatsOffsetMax
                   tnSyncStatsOffsetAverage
                   tnSyncERawCountStatsOffsetMin
                   tnSyncERawCountStatsOffsetMax
                   tnSyncERawCountStatsOffsetAverage."

      REVISION    "201806291200Z"
      DESCRIPTION "Added the following table:
                   tnStatsPTPClearAllTable."

      REVISION    "201806221200Z"
      DESCRIPTION "Added the following to TnStatsGroupId:
                   ptpTimeOffset(39)
                   to
                   ptpTimeOffsetAccumulation(44)."

      REVISION    "201806111200Z"
      DESCRIPTION "Added the following tables:
                   tnPTOFFTable
                   tnPTMSDLYTable
                   tnPTSMDLYTable
                   tnPTMPDLYTable
                   tnPTERREFTable
                   tnPTOFFACUMTable
                   tnPTOFFRawCountTable
                   tnPTMSDLYRawCountTable
                   tnPTSMDLYRawCountTable
                   tnPTMPDLYRawCountTable
                   tnPTERREFRawCountTable
                   tnPTOFFACUMRawCountTable
                   tnPTOFFStatsConfigTable
                   tnPTMSDLYStatsConfigTable
                   tnPTSMDLYStatsConfigTable
                   tnPTMPDLYStatsConfigTable
                   tnPTERREFStatsConfigTable
                   tnPTOFFACUMStatsConfigTable."

      REVISION    "201803021200Z"
      DESCRIPTION "Marked the following as obsolete:
                   tnETHPHYFECPMStatRxRsCorrCnt
                   tnETHPHYFECPMStatRxRsUncorrCnt."

      REVISION    "201802231200Z"
      DESCRIPTION "1) Added the following to TnStatsGroupId:
                      syncEStats(38).
                   2) Updated the contact info."

      REVISION    "201802161200Z"
      DESCRIPTION "1) Marked the following as deprecated:
                      tnETHPHYFECPMStatRxRsCorrCnt
                      tnETHPHYFECPMStatRxRsUncorrCnt.
                   2) Added the following to tnETHFECPMStatsTable:
                      tnETHFECPMStatRxRsCorrCnt
                      tnETHFECPMStatRxRsUncorrCnt."

      REVISION    "201801191200Z"
      DESCRIPTION "Added the following tables:
                   tnSyncStatsTable
                   tnSyncRawCountStatsTable
                   tnSyncStatsConfigTable."

      REVISION    "201712261200Z"
      DESCRIPTION "1) Added the following tables:
                      tnSyncEStatsTable
                      tnSyncERawCountStatsTable
                      tnSyncEStatsConfigTable.
                   2) Added the following Scalars:
                      tnSyncEStatsOffsetScalars."

      REVISION    "201707071200Z"
      DESCRIPTION "Fixed MIB compile issues."

      REVISION    "201703241200Z"
      DESCRIPTION "Added ODUflex thresholds to tnStatisticsOthOduTcmScalars."

      REVISION    "201611161200Z"
      DESCRIPTION "1) Added the following to tnETHFECPMRawCountStatsTable:
                      tnETHFECPMRawCountStatRxRsCorrCnt
                      tnETHFECPMRawCountStatRxRsUncorrCnt
                   2) Updated the contact info."

      REVISION    "201610291200Z"
      DESCRIPTION "1) Added the following tables:
                      tnETHFECPMStatsTable
                      tnETHFECPMRawCountStatsTable.
                   2) Added below to tnStatisticsCompliance:
                      tnETHFECPMStatsScalarsGroup
                      tnETHFECPMStatsGroup
                      tnETHFECPMRawCountStatsScalarsGroup
                      tnETHFECPMRawCountStatsGroup"

      REVISION    "201610131200Z"
      DESCRIPTION "Added the following tables:
                   tnOpInLStatsTable
                   tnOpOutLStatsTable
                   tnOpInLRawCountStatsTable
                   tnOpOutLRawCountStatsTable."

      REVISION    "201609231200Z"
      DESCRIPTION "1) Added 54 ODUFLEX thresholds in tnStatisticsOdukRxScalars.
                   2) Added 54 ODUFLEX thresholds in tnStatisticsOdukTxScalars."

      REVISION    "201608241200Z"
      DESCRIPTION "Added the following tables:
                   tnOpInCStatsTable
                   tnOpOutCStatsTable."

      REVISION    "201608101200Z"
      DESCRIPTION "Added the following tables:
                   tnOpInCRawCountStatsTable
                   tnOpOutCRawCountStatsTable."

      REVISION    "201608081200Z"
      DESCRIPTION "Added the following table:
                   tnStreamingPmThresholdTable."

      REVISION    "201606231200Z"
      DESCRIPTION "Added the following scalars:
                   tnStatisticsStreamingPMScalars."

      REVISION    "201604181200Z"
      DESCRIPTION "Added the following to tnStatisticsFECPMScalars:
                   tnFECPMRSFECRxBERPreFEC15MinTr,
                   tnFECPMRSFECRxBERPreFEC15MinRtr,
                   tnFECPMRSFECRxBERPreFEC1DayTr."

      REVISION    "201602221200Z"
      DESCRIPTION "1) Added the following table:
                      tnpreFECBERRawCountStatsTable.
                   2) Added the following to TnStatsGroupId:
                      prefecberstats(11)."

      REVISION    "201602111200Z"
      DESCRIPTION "Changed the following from tnOtuStatsPortIntervalTable to
                   tnOtuStatsPortTable:
                   tnOtuStatsPortEnable"

      REVISION    "201601211200Z"
      DESCRIPTION "1) Added the following table:
                      tnpreFECBERStatsTable
                   2) Added the following Scalars:
                      tnStatisticspreFECBERScalars."

      REVISION    "201512231200Z"
      DESCRIPTION "Added the following to tnStatsPortIntervalTable:
                   tnStatPortEnable."

      REVISION    "201512011200Z"
      DESCRIPTION "Added the following to tnOtuStatsPortIntervalTable:
                   tnOtuStatsPortEnable."

      REVISION    "201511021200Z"
      DESCRIPTION "Added the following to tnOtuStatsPortTable:
                   tnOtuStatsPortIntervalLength1day,
                   tnOtuStatsPortNumberOfBins1day,
                   tnOtuStatsPortProfileId1day."

      REVISION    "201510071200Z"
      DESCRIPTION "Added the following to tnStatisticsFECPMScalars:
                   tnSDFECPMRxBERPreFEC15MinTr,
                   tnSDFECPMRxBERPreFEC15MinRtr,
                   tnSDFECPMRxBERPreFEC1DayTr."

      REVISION    "201510011200Z"
      DESCRIPTION "1) Added the following to tables:
                      tnOtuStatsPortIntervalTable
                      tnOtuStatsPortTable.
                   2) Added below to tnStatisticsCompliance:
                      tnOtuStatsPortIntervalGroup
                      tnOtuStatsPortGroup."

      REVISION    "201507201200Z"
      DESCRIPTION "1) Added the following tables:
                      tnFECPMStatsTable
                      tnFECPMRawCountStatsTable
                   2) Added the following Scalar:
                      tnStatisticsFECPMScalars
                   3) Added below to tnStatisticsCompliance:
                      tnFECPMStatsScalarsGroup
                      tnFECPMStatsGroup
                      tnFECPMStatsThresholdScalarsGroup
                      tnFECPMRawCountStatsScalarsGroup
                      tnFECPMRawCountStatsGroup"

      REVISION    "201408291200Z"
      DESCRIPTION "Added the following scalars:
                   tnStatisticsEncryptRxFTDScalars."

      REVISION    "201312101200Z"
      DESCRIPTION "Changed the following in TnStatsGroupId:
                   Added invalidGroup(0)
                   Deleted l1pStats(11) and fibreChannelStats(19)
                   Replaced pathSummaryStats(18) with opticalLanePwrStats(18)."

      REVISION    "201312061200Z"
      DESCRIPTION "1) Added the following to TnStatsBinStatus:
                      disabled(10).
                   2) Added the following table and scalars:
                      tnStatsLanePwrsConfigTable
                      tnStatisticsLanePowerScalars."

      REVISION    "201311221200Z"
      DESCRIPTION "1) Added the following to tnOthOtukStatsTable:
                      tnOthOtukStatNeRxBIAESErrCnt.
                   2) Added the following to tnOthOtukRawCountStatsTable:
                      tnOthOtukRawCountStatRxNeBIAES.
                   3) Marked the following tables as obsolete:
                      tnL1ProtStatsTable
                      tnL1ProtRawCountStatsTable
                      tnFibreChannelStatsTable
                      tnPathSummaryStatsTable
                      tnFibreChannelRawCountStatsTable
                      tnPathSummaryRawCountStatsTable."

      REVISION    "201308051200Z"
      DESCRIPTION "Added the following tables and scalars:
                   tnOthOdukStatsTcmConfigTable
                   tnOthOdukStatsTcmEnableTable
                   tnOthOdukStatsTcmTable
                   tnStatisticsOthOduTcmScalars
                   tnOthOdukTcmRawCountStatsTable."

      REVISION    "201305241200Z"
      DESCRIPTION "Updated DESCRIPTION of TnStatsGroupId."

      REVISION    "201211121200Z"
      DESCRIPTION "Marked the following attributes as obsolete:
                   tnSonetStat*Tr
                   tnSonetStat*Rtr
                   tnSdhStat*Tr
                   tnSdhStat*Rtr
                   tnDw64BitStat*Tr
                   tnDw64BitStat*Rtr
                   tnDwRx*Tr
                   tnDwRx*Rtr
                   tnPhyCodeSublayerStat*Tr
                   tnPhyCodeSublayerStat*Rtr."

      REVISION    "201211051200Z"
      DESCRIPTION "1) Added the following to tnOthOdukRawCountStatsDMTable:
                      tnOthOdukRawCountStatsDMStartTime.
                   2) Added the following to TnStatsGroupId:
                      dmStats (30)."

      REVISION    "201210221200Z"
      DESCRIPTION "Added the following tables:
                   tnOthOdukStatsDMConfigTable
                   tnOthOdukStatsDMTable
                   tnOthOdukRawCountStatsDMTable."

      REVISION    "201210161200Z"
      DESCRIPTION "Added the following scalar groups:
                   tnStatisticsSonetScalars
                   tnStatisticsSdhScalars
                   tnStatisticsDwScalars
                   tnStatisticsPcsScalars."

      REVISION    "201208311200Z"
      DESCRIPTION "Marked the following as obsolete:
                   tnStatsTCAItuVariable
                   tnStatsTCAItuValue."

      REVISION    "201208281200Z"
      DESCRIPTION "Added the following tables:
                   tnOsnrStatsTable
                   tnOsnrRawCountStatsTable."

      REVISION    "201208221200Z"
      DESCRIPTION "Added the following to TnStatsGroupId:
                   osnrStats (27)
                   to
                   oduStatsTx (29)."

      REVISION    "201208211200Z"
      DESCRIPTION "1) Added the following to TnStatsGroupId:
                      otuStats (26).
                   2) Added the following tables:
                      tnOthOdukStatsRxConfigTable
                      tnOthOdukStatsTxConfigTable
                      tnOthOdukStatsControlTable
                      tnOthOdukStatsRxTable
                      tnOthOdukStatsTxTable
                      tnOthOtukStatsTable
                      tnOthOdukRawCountStatsRxTable
                      tnOthOdukRawCountStatsTxTable
                      tnOthOtukRawCountStatsTable
                      tnOthOdukStatsRxScalars
                      tnOthOdukStatsTxScalars
                      tnOthOtukStatsScalars."

      REVISION    "201207241200Z"
      DESCRIPTION "Marked the following as obsolete:
                   tnStatsTcmTCATable
                   tnStatsTcmTCAProfileTable
                   tnStatsTcmPortTable
                   tnTcm64BitStatsTable
                   tnTcm64BitRawCountStatsTable."

      REVISION    "201203101200Z"
      DESCRIPTION "1) Added the following to TnStatsGroupId:
                      encryptStats (25).
                   2) Added the following tables for encryption:
                      tnEncrypt64BitStatsTable
                      tnEncrypt64BitRawCountStatsTable."

      REVISION    "201105021200Z"
      DESCRIPTION "1) Added the following to TnStatsGroupId:
                      tcmStats (24).
                   2) Added the following tables for Tandem Connection
                      Monitoring (TCM):
                      tnStatsTcmTCATable
                      tnStatsTcmTCAProfileTable
                      tnStatsTcmPortTable
                      tnTcm64BitStatsTable
                      tnTcm64BitRawCountStatsTable."

      REVISION    "201011281200Z"
      DESCRIPTION "Added the following to TnStatsGroupId:
                   preFecBitsStats (23)."

      REVISION    "201011231200Z"
      DESCRIPTION "Added the following MIB tables:
                   tnPreFECBitsStatsTable
                   tnPreFECBitsRawCountStatsTable."

      REVISION    "201010181200Z"
      DESCRIPTION "Marked the following as obsolete:
                   tnDw64BitStatRxSMBEIErrCnt
                   tnDw64BitStatRxPMBEIErrCnt
                   tnDw64BitStatRxRSSES
                   tnDigitalWrapperStatsTable
                   tnDigitalWrapperRawCountStatsTable."

      REVISION    "201010141200Z"
      DESCRIPTION "Added new stats attributes to the following tables:
                   tnSonetStatsTable
                   tnSdhStatsTable
                   tnSonetRawCountStatsTable
                   tnSdhRawCountStatsTable."

      REVISION    "201008261200Z"
      DESCRIPTION "Added 48 stats attributes to
                   tnDigitalWrapper64BitStatsTable."

      REVISION    "201008051200Z"
      DESCRIPTION "Removed the 48 recently added stats attributes from
                   tnDigitalWrapper64BitStatsTable."

      REVISION    "201008021200Z"
      DESCRIPTION "Added new Digital Wrapper stats attributes."

      REVISION    "201007291200Z"
      DESCRIPTION "1) Renamed tnDw64BitRawCountStatRxSMFEBEIErrCnt to
                      tnDw64BitRawCountStatRxSMBIAESErrCnt,
                      tnDw64BitRawCountStatRxPMFEBEIErrCnt to
                      tnDw64BitRawCountStatRxSMIAESErrCnt,
                      tnDw64BitStatRxSMFEBEIErrCnt to
                      tnDw64BitStatRxSMBIAESErrCnt,
                      tnDw64BitStatRxPMFEBEIErrCnt to
                      tnDw64BitStatRxSMIAESErrCnt.
                   2) Removed the following:
                      tnDw64BitStatRxRSFESES
                      tnDw64BitRawCountStatRxRSFESES."

      REVISION    "201006301200Z"
      DESCRIPTION "Added new Digital Wrapper stats attributes."

      REVISION    "201006071200Z"
      DESCRIPTION "Added E1 PM attributes."

      REVISION    "201005171200Z"
      DESCRIPTION "Added new PM attributes for R3.0."

      REVISION    "201003051200Z"
      DESCRIPTION "1) Added Chromatic Dispersion received stats.
                   2) Added Differential Group Delay received stats.
                   3) Added Frequency Offset received stats."

      REVISION    "200912081200Z"
      DESCRIPTION "Added start time attributes to raw PM count tables."

      REVISION    "200909011200Z"
      DESCRIPTION "Updated descriptions of the following:
                   tnOpOchOutRawCountStatsClear
                   tnOpOchInRawCountStatsClear."

      REVISION    "200907071200Z"
      DESCRIPTION "Changed index for tnPhyCodeSublayerStatsEntry
                   from tnFibreChannelStatsBin to tnPhyCodeSublayerStatsBin."

      REVISION    "200902261200Z"
      DESCRIPTION "Updated the description of tnStatsPortClear."

      REVISION    "200811061200Z"
      DESCRIPTION "Marked the following as deprecated:
                   tnDw64BitStatRxSMBEIErrCnt
                   tnDw64BitStatRxPMBEIErrCnt
                   tnDw64BitStatRxRSSES."

      REVISION    "200804081200Z"
      DESCRIPTION "Added tnStatsBaselineTable."

      REVISION    "200804051200Z"
      DESCRIPTION "Updated the textual convention descriptions."

      REVISION    "200804031200Z"
      DESCRIPTION "Created a new digital wrapper PM group that
                   is based on 64-bit counters."

      REVISION    "200803281200Z"
      DESCRIPTION "Added data complete to the new bin status values."

      REVISION    "200803171200Z"
      DESCRIPTION "1) Updated the MIB file description.
                   2) Added the Physical Coding Sublayer group.
                   3) Added new bin status values.
                   4) Added new Sonet/SDH stats attributes.
                   5) Added new Digital Wrapper stats attributes.
                   6) Added new Ethernet stats attributes.
                   7) Added new Physical Coding Sublayer stats group."

      ::= { tnSystemModules 5 }

  tnStatisticsConf                 OBJECT IDENTIFIER ::= { tnStatisticsMIB  1 }
  tnStatisticsGroups               OBJECT IDENTIFIER ::= { tnStatisticsConf 1 }
  tnStatisticsCompliances          OBJECT IDENTIFIER ::= { tnStatisticsConf 2 }
  tnStatisticsObjs                 OBJECT IDENTIFIER ::= { tnStatisticsMIB  2 }
  tnStatisticsTCA                  OBJECT IDENTIFIER ::= { tnStatisticsObjs 1 }
  tnStatisticsGrouping             OBJECT IDENTIFIER ::= { tnStatisticsObjs 2 }
  tnStatisticsRawCounts            OBJECT IDENTIFIER ::= { tnStatisticsObjs 3 }
  tnStatisticsBaseline             OBJECT IDENTIFIER ::= { tnStatisticsObjs 4 }
  tnStatisticsOdukRxScalars        OBJECT IDENTIFIER ::= { tnStatisticsObjs 5 }
  tnStatisticsOdukTxScalars        OBJECT IDENTIFIER ::= { tnStatisticsObjs 6 }
  tnStatisticsOtukScalars          OBJECT IDENTIFIER ::= { tnStatisticsObjs 7 }
  tnStatisticsSonetScalars         OBJECT IDENTIFIER ::= { tnStatisticsObjs 8 }
  tnStatisticsSdhScalars           OBJECT IDENTIFIER ::= { tnStatisticsObjs 9 }
  tnStatisticsDwScalars            OBJECT IDENTIFIER ::= { tnStatisticsObjs 10 }
  tnStatisticsPcsScalars           OBJECT IDENTIFIER ::= { tnStatisticsObjs 11 }
  tnStatisticsOthOduTcmScalars     OBJECT IDENTIFIER ::= { tnStatisticsObjs 12 }
  tnStatisticsLanePowerScalars     OBJECT IDENTIFIER ::= { tnStatisticsObjs 13 }
  tnStatisticsEncryptRxFTDScalars  OBJECT IDENTIFIER ::= { tnStatisticsObjs 14 }
  tnStatisticsFECPMScalars         OBJECT IDENTIFIER ::= { tnStatisticsObjs 15 }
  tnStatisticspreFECBERScalars     OBJECT IDENTIFIER ::= { tnStatisticsObjs 16 }
  tnStatisticsStreamingPMScalars   OBJECT IDENTIFIER ::= { tnStatisticsObjs 17 }
  tnSyncEStatsOffsetScalars        OBJECT IDENTIFIER ::= { tnStatisticsObjs 18 }
  tnStatisticsFcPktScalars         OBJECT IDENTIFIER ::= { tnStatisticsObjs 19 }

--------------------------------------------------------------------------------
-- Statistics Textual Conventions
--------------------------------------------------------------------------------
    TnStatsGroupId ::= TEXTUAL-CONVENTION
        STATUS      current
        DESCRIPTION "------------------------------
                     | invalidGroup  ---------------------- 0  |
                     | ethernetStats ---------------------- 1  |
                     | dataStats -------------------------- 2  |
                     | sonetStats/sdhStats ---------------- 3  |
                     | opticalDcPwrInStats ---------------- 4  |
                     | systemStats ------------------------ 5  |
                     | opticalDcPwrTxStats ---------------- 6  |
                     | opticalDcPwrRxStats ---------------- 7  |
                     | opticalWtPwrOutStats --------------- 8  |
                     | interfaceStats --------------------- 9  |
                     | opticalWtPwrInStats ---------------- 10 |
                     | prefecberstats --------------------- 11 |
                     | opticalDcPwrOutStats --------------- 12 |
                     | digitalWrapperStats ---------------- 13 |
                     | lbcStats --------------------------- 14 |
                     | laserTempStats --------------------- 15 |
                     | cdStats ---------------------------- 16 |
                     | dgdStats --------------------------- 17 |
                     | opticalLanePwrStats ---------------- 18 |
                     | fecpmStats-------------------------- 19 |
                     | phyCodeSubLayerStats --------------- 20 |
                     | foffStats -------------------------- 21 |
                     | e1Stats ---------------------------- 22 |
                     | preFecBitsStats -------------------- 23 |
                     | tcmStats --------------------------- 24 |
                     | encryptStats ----------------------- 25 |
                     | otuStats --------------------------- 26 |
                     | osnrStats -------------------------- 27 |
                     | oduStatsRx ------------------------- 28 |
                     | oduStatsTx ------------------------- 29 |
                     | dmStats ---------------------------- 30 |
                     | fecStats --------------------------- 31 |
                     | opinC ------------------------------ 32 |
                     | opinL ------------------------------ 33 |
                     | opoutC ----------------------------- 34 |
                     | opoutL ----------------------------- 35 |
                     | flexChannels ----------------------- 36 |
                     | ethFecPmStats ---------------------- 37 |
                     | syncEStats ------------------------- 38 |
                     | ptpTimeOffset ---------------------- 39 |
                     | ptpTMSDelay ------------------------ 40 |
                     | ptpTSMDelay ------------------------ 41 |
                     | ptpMeanPathDelay ------------------- 42 |
                     | ptpTimeErrorbyReferenceComparison -- 43 |
                     | ptpTimeOffsetAccumulation ---------- 44 |
                     | packetWanifStats ------------------- 45 |
                     | csrStats --------------------------- 46 |
                     | qmarginStats ----------------------- 47 |
                     | pdlStats --------------------------- 48 |
                     | soprStats -------------------------- 49 |
                     | esnrStats -------------------------- 50 |
                     | opSupChIn -------------------------- 51 |
                     | opSupChOut ------------------------- 52 |
                     | evmStats --------------------------  53 |
                     | oplineoutc ------------------------- 54 |
                     | oplineoutl ------------------------- 55 |
                     | opochlineoutc ---------------------- 56 |
                     | opochlineoutl ---------------------- 57 |
                     | qsnrRxStats ------------------------ 58 |
                     | qfactorStats ----------------------- 59 |
                     | ochopr ----------------------------- 60 |
                     | fcPktStats ------------------------- 61 |
                     -------------------------------------------"
        SYNTAX      Unsigned32 (1..2147483647)

    TnStatsIntervalType ::= TEXTUAL-CONVENTION
        STATUS      current
        DESCRIPTION "Valid value include:

                     0 - 15-minute bin
                     1 - 1-day bin"
        SYNTAX      Unsigned32 (0..2147483647)

    TnStatsBinType ::= TEXTUAL-CONVENTION
        STATUS      current
        DESCRIPTION "Current range: 0 to 50."
        SYNTAX      Unsigned32 (0..2147483647)

    TnStatsBinStatus ::= TEXTUAL-CONVENTION
        STATUS      current
        DESCRIPTION "The bin status."
        SYNTAX      INTEGER {
                      valid(1),
                      rxValid(2),
                      txValid(3),
                      invalid(4),
                      dataNotAvailable(5),
                      partial(6),
                      adjusted(7),
                      dataLong(8),
                      dataComplete(9),
                      disabled(10)
                    }

--------------------------------------------------------------------------------
-- Statistics Port Interval Table
--------------------------------------------------------------------------------
    tnStatsPortIntervalTable OBJECT-TYPE
        SYNTAX      SEQUENCE OF TnStatsPortIntervalEntry
        MAX-ACCESS  not-accessible
        STATUS      current
        DESCRIPTION "."
        ::= { tnStatisticsTCA 1 }

    tnStatsPortIntervalEntry OBJECT-TYPE
        SYNTAX      TnStatsPortIntervalEntry
        MAX-ACCESS  not-accessible
        STATUS      current
        DESCRIPTION "."
        INDEX   { ifIndex,
                  tnStatsGroupId }
        ::= { tnStatsPortIntervalTable 1 }

    TnStatsPortIntervalEntry ::=
        SEQUENCE {
            tnStatsPortNumberOfIntervals TnStatsIntervalType,
            tnStatPortEnable             INTEGER
        }

    tnStatsPortNumberOfIntervals OBJECT-TYPE
        SYNTAX      TnStatsIntervalType
        MAX-ACCESS  read-create
        STATUS      current
        DESCRIPTION "The number of collection intervals
                     assigned to a particular interface and
                     group."
        ::= { tnStatsPortIntervalEntry 1 }

    tnStatPortEnable OBJECT-TYPE
        SYNTAX      INTEGER {
                      enable(1),
                      disable(2)
                    }
        MAX-ACCESS  read-create
        STATUS      current
        DESCRIPTION "."
        ::= { tnStatsPortIntervalEntry 2 }

--------------------------------------------------------------------------------
-- Statistics Card Interval Table
--------------------------------------------------------------------------------
    tnStatsCardIntervalTable OBJECT-TYPE
        SYNTAX      SEQUENCE OF TnStatsCardIntervalEntry
        MAX-ACCESS  not-accessible
        STATUS      current
        DESCRIPTION "."
        ::= { tnStatisticsTCA 2 }

    tnStatsCardIntervalEntry OBJECT-TYPE
        SYNTAX      TnStatsCardIntervalEntry
        MAX-ACCESS  not-accessible
        STATUS      current
        DESCRIPTION "."
        INDEX   { tnShelfIndex,
                  tnSlotIndex,
                  tnStatsGroupId }
        ::= { tnStatsCardIntervalTable 1 }

    TnStatsCardIntervalEntry ::=
        SEQUENCE {
            tnStatsCardNumberOfIntervals TnStatsIntervalType
        }

    tnStatsCardNumberOfIntervals OBJECT-TYPE
        SYNTAX      TnStatsIntervalType
        MAX-ACCESS  read-create
        STATUS      current
        DESCRIPTION "The number of collection intervals
                     assigned to a particular card and
                     group."
        ::= { tnStatsCardIntervalEntry 1 }

--------------------------------------------------------------------------------
-- Statistics Port Configuration Table
--------------------------------------------------------------------------------
    tnStatsPortTable OBJECT-TYPE
        SYNTAX      SEQUENCE OF TnStatsPortEntry
        MAX-ACCESS  not-accessible
        STATUS      current
        DESCRIPTION "."
        ::= { tnStatisticsTCA 3 }

    tnStatsPortEntry OBJECT-TYPE
        SYNTAX      TnStatsPortEntry
        MAX-ACCESS  not-accessible
        STATUS      current
        DESCRIPTION "."
        INDEX   { ifIndex,
                  tnStatsGroupId,
                  tnStatsInterval }
        ::= { tnStatsPortTable 1 }

    TnStatsPortEntry ::=
        SEQUENCE {
            tnStatsInterval            TnStatsIntervalType,
            tnStatsPortIntervalLength  Unsigned32,
            tnStatsPortNumberOfBins    TnStatsBinType,
            tnStatsPortProfileId       TnStatsProfileId,
            tnStatsPortClear           TnCommand
        }

    tnStatsInterval OBJECT-TYPE
        SYNTAX      TnStatsIntervalType
        MAX-ACCESS  not-accessible
        STATUS      current
        DESCRIPTION "The collection interval."
        ::= { tnStatsPortEntry 1 }

    tnStatsPortIntervalLength OBJECT-TYPE
        SYNTAX      Unsigned32
        UNITS       "seconds"
        MAX-ACCESS  read-create
        STATUS      current
        DESCRIPTION "The collection interval length in seconds.
                     Sets to this attribute are currently not supported."
        ::= { tnStatsPortEntry 2 }

    tnStatsPortNumberOfBins OBJECT-TYPE
        SYNTAX      TnStatsBinType
        MAX-ACCESS  read-create
        STATUS      current
        DESCRIPTION "The number of collection bins in the
                     interval."
        ::= { tnStatsPortEntry 3 }

    tnStatsPortProfileId OBJECT-TYPE
        SYNTAX      TnStatsProfileId
        MAX-ACCESS  read-create
        STATUS      current
        DESCRIPTION "The profile identifier associated with an
                     interval on a particular interface and group."
        ::= { tnStatsPortEntry 4 }

    tnStatsPortClear OBJECT-TYPE
        SYNTAX      TnCommand
        MAX-ACCESS  read-create
        STATUS      current
        DESCRIPTION "This attribute is used to clear the current bin
                     in an interval on a particular interface
                     and group."
        ::= { tnStatsPortEntry 5 }

--------------------------------------------------------------------------------
-- Statistics Card Configuration Table
--------------------------------------------------------------------------------
    tnStatsCardTable OBJECT-TYPE
        SYNTAX      SEQUENCE OF TnStatsCardEntry
        MAX-ACCESS  not-accessible
        STATUS      current
        DESCRIPTION "."
        ::= { tnStatisticsTCA 4 }

    tnStatsCardEntry OBJECT-TYPE
        SYNTAX      TnStatsCardEntry
        MAX-ACCESS  not-accessible
        STATUS      current
        DESCRIPTION "."
        INDEX   { tnShelfIndex,
                  tnSlotIndex,
                  tnStatsGroupId,
                  tnStatsInterval }
        ::= { tnStatsCardTable 1 }

    TnStatsCardEntry ::=
        SEQUENCE {
            tnStatsCardIntervalLength  Unsigned32,
            tnStatsCardNumberOfBins    TnStatsBinType,
            tnStatsCardProfileId       TnStatsProfileId,
            tnStatsCardClear           TnCommand
        }

    tnStatsCardIntervalLength OBJECT-TYPE
        SYNTAX      Unsigned32
        UNITS       "seconds"
        MAX-ACCESS  read-create
        STATUS      current
        DESCRIPTION "The collection interval length in seconds.
                     Sets to this attribute are currently not supported."
        ::= { tnStatsCardEntry 1 }

    tnStatsCardNumberOfBins OBJECT-TYPE
        SYNTAX      TnStatsBinType
        MAX-ACCESS  read-create
        STATUS      current
        DESCRIPTION "The number of collection bins in the
                     interval."
        ::= { tnStatsCardEntry 2 }

    tnStatsCardProfileId OBJECT-TYPE
        SYNTAX      TnStatsProfileId
        MAX-ACCESS  read-create
        STATUS      current
        DESCRIPTION "The profile identifier associated with an
                     interval on a particular card and group."
        ::= { tnStatsCardEntry 3 }

    tnStatsCardClear OBJECT-TYPE
        SYNTAX      TnCommand
        MAX-ACCESS  read-create
        STATUS      current
        DESCRIPTION "This attribute is used to clear all the
                     bins in an interval on a particular card
                     and group."
        ::= { tnStatsCardEntry 4 }

--------------------------------------------------------------------------------
-- Statistics TCA Profile Table
--------------------------------------------------------------------------------
    tnStatsTCAProfileTable OBJECT-TYPE
        SYNTAX      SEQUENCE OF TnStatsTCAProfileEntry
        MAX-ACCESS  not-accessible
        STATUS      current
        DESCRIPTION "."
        ::= { tnStatisticsTCA 5 }

    tnStatsTCAProfileEntry OBJECT-TYPE
        SYNTAX      TnStatsTCAProfileEntry
        MAX-ACCESS  not-accessible
        STATUS      current
        DESCRIPTION "."
        INDEX   { tnStatsGroupId,
                  tnStatsTCAProfileId }
        ::= { tnStatsTCAProfileTable 1 }

    TnStatsTCAProfileEntry ::=
        SEQUENCE {
            tnStatsGroupId         TnStatsGroupId,
            tnStatsTCAProfileId    TnStatsProfileId,
            tnStatsTCAProfileDescr SnmpAdminString
        }

    tnStatsGroupId OBJECT-TYPE
        SYNTAX      TnStatsGroupId
        MAX-ACCESS  not-accessible
        STATUS      current
        DESCRIPTION "The group identifier."
        ::= { tnStatsTCAProfileEntry 1 }

    tnStatsTCAProfileId OBJECT-TYPE
        SYNTAX      TnStatsProfileId
        MAX-ACCESS  not-accessible
        STATUS      current
        DESCRIPTION "The profile identifier."
        ::= { tnStatsTCAProfileEntry 2 }

    tnStatsTCAProfileDescr OBJECT-TYPE
        SYNTAX      SnmpAdminString (SIZE(0..255))
        MAX-ACCESS  read-create
        STATUS      current
        DESCRIPTION "The description of the profile."
        ::= { tnStatsTCAProfileEntry 3 }

--------------------------------------------------------------------------------
-- Statistics TCA Table
--------------------------------------------------------------------------------
    tnStatsTCATable OBJECT-TYPE
        SYNTAX      SEQUENCE OF TnStatsTCAEntry
        MAX-ACCESS  not-accessible
        STATUS      current
        DESCRIPTION "."
        ::= { tnStatisticsTCA 6 }

    tnStatsTCAEntry OBJECT-TYPE
        SYNTAX      TnStatsTCAEntry
        MAX-ACCESS  not-accessible
        STATUS      current
        DESCRIPTION "."
        INDEX   { tnStatsGroupId,
                  tnStatsTCAProfileId,
                  tnStatsTCAVariableId }
        ::= { tnStatsTCATable 1 }

    TnStatsTCAEntry ::=
        SEQUENCE {
            tnStatsTCAVariableId       Unsigned32,
            tnStatsTCAVariable         OBJECT IDENTIFIER,
--            obsolete
--            tnStatsTCACriticalInterval SnmpAdminString,
--            tnStatsTCAMajorInterval    SnmpAdminString,
--            tnStatsTCAMinorInterval    SnmpAdminString,
--            tnStatsTCAWarningInterval  SnmpAdminString,
            tnStatsTCAValue            SnmpAdminString
        }

    tnStatsTCAVariableId OBJECT-TYPE
        SYNTAX      Unsigned32
        MAX-ACCESS  not-accessible
        STATUS      current
        DESCRIPTION "The integer representation of the variable."
        ::= { tnStatsTCAEntry 1 }

    tnStatsTCAVariable OBJECT-TYPE
        SYNTAX      OBJECT IDENTIFIER
        MAX-ACCESS  read-only
        STATUS      current
        DESCRIPTION "The value of this attribute is the object
                     identifier of a member of a binned
                     statistics group table."
        ::= { tnStatsTCAEntry 2 }

--    obsolete
--    tnStatsTCACriticalInterval OBJECT-TYPE ::= { tnStatsTCAEntry 3 }
--    tnStatsTCAMajorInterval    OBJECT-TYPE ::= { tnStatsTCAEntry 4 }
--    tnStatsTCAMinorInterval    OBJECT-TYPE ::= { tnStatsTCAEntry 5 }
--    tnStatsTCAWarningInterval  OBJECT-TYPE ::= { tnStatsTCAEntry 6 }

    tnStatsTCAValue OBJECT-TYPE
        SYNTAX      SnmpAdminString (SIZE(1..20))
        MAX-ACCESS  read-create
        STATUS      current
        DESCRIPTION "The threshold crossing value.

                     For the card group:
                     Current configurable range: 0 to 100.

                     For optical power related groups:
                     Current configurable range: -4000 to 3500."
        ::= { tnStatsTCAEntry 7 }

--------------------------------------------------------------------------------
-- Statistics TCA ITU Table
--
-- This table is no longer needed but cannot be marked as obsolete
-- because tnOpticalStatsITUChannel is still being used as an index in
-- other tables in this MIB file.
--
--------------------------------------------------------------------------------
    tnStatsTCAItuTable OBJECT-TYPE
        SYNTAX      SEQUENCE OF TnStatsTCAItuEntry
        MAX-ACCESS  not-accessible
        STATUS      current
        DESCRIPTION "."
        ::= { tnStatisticsTCA 7 }

    tnStatsTCAItuEntry OBJECT-TYPE
        SYNTAX      TnStatsTCAItuEntry
        MAX-ACCESS  not-accessible
        STATUS      current
        DESCRIPTION "."
        INDEX   { tnStatsGroupId,
                  tnStatsTCAProfileId,
                  tnOpticalStatsITUChannel,
                  tnStatsTCAVariableId }
        ::= { tnStatsTCAItuTable 1 }

    TnStatsTCAItuEntry ::=
        SEQUENCE {
            tnOpticalStatsITUChannel      Unsigned32
--            obsolete
--            tnStatsTCAItuVariable         OBJECT IDENTIFIER,
--            tnStatsTCAItuCriticalInterval SnmpAdminString,
--            tnStatsTCAItuMajorInterval    SnmpAdminString,
--            tnStatsTCAItuMinorInterval    SnmpAdminString,
--            tnStatsTCAItuWarningInterval  SnmpAdminString,
--            tnStatsTCAItuValue            SnmpAdminString
        }

--------------------------------------------------------------------------------
-- Statistics ITU Channel Scalar
--------------------------------------------------------------------------------
    tnOpticalStatsITUChannel OBJECT-TYPE
        SYNTAX      Unsigned32
        MAX-ACCESS  not-accessible
        STATUS      current
        DESCRIPTION "The ITU channel."
        ::= { tnStatsTCAItuEntry 1 }

--    obsolete
--    tnStatsTCAItuVariable         OBJECT-TYPE ::= { tnStatsTCAItuEntry 2 }
--    tnStatsTCAItuCriticalInterval OBJECT-TYPE ::= { tnStatsTCAItuEntry 3 }
--    tnStatsTCAItuMajorInterval    OBJECT-TYPE ::= { tnStatsTCAItuEntry 4 }
--    tnStatsTCAItuMinorInterval    OBJECT-TYPE ::= { tnStatsTCAItuEntry 5 }
--    tnStatsTCAItuWarningInterval  OBJECT-TYPE ::= { tnStatsTCAItuEntry 6 }
--    tnStatsTCAItuValue            OBJECT-TYPE ::= { tnStatsTCAItuEntry 7 }

--------------------------------------------------------------------------------
-- Statistics Port Clear All Table
--------------------------------------------------------------------------------
    tnStatsPortClearAllTable OBJECT-TYPE
        SYNTAX      SEQUENCE OF TnStatsPortClearAllEntry
        MAX-ACCESS  not-accessible
        STATUS      current
        DESCRIPTION "."
        ::= { tnStatisticsTCA 8 }

    tnStatsPortClearAllEntry OBJECT-TYPE
        SYNTAX      TnStatsPortClearAllEntry
        MAX-ACCESS  not-accessible
        STATUS      current
        DESCRIPTION "."
        INDEX   { ifIndex }
        ::= { tnStatsPortClearAllTable 1 }

    TnStatsPortClearAllEntry ::=
        SEQUENCE {
            tnStatsPortClearAll  TnCommand
        }

    tnStatsPortClearAll OBJECT-TYPE
        SYNTAX      TnCommand
        MAX-ACCESS  read-create
        STATUS      current
        DESCRIPTION "This attribute is used to clear all the bins
                     in all intervals in all groups on a particular
                     interface."
        ::= { tnStatsPortClearAllEntry 1 }

--------------------------------------------------------------------------------
-- Card Statistics TCA Scalar
--------------------------------------------------------------------------------
    tnStatsClearAll OBJECT-TYPE
        SYNTAX      TnCommand
        MAX-ACCESS  read-write
        STATUS      current
        DESCRIPTION "This attribute is used to clear all the bins
                     in all intervals in all groups on all cards and
                     interfaces in the network element."
        ::= { tnStatisticsTCA 9 }

--    obsolete
--    tnStatsTcmTCAAttributeTotal        OBJECT-TYPE ::= { tnStatisticsTCA 10 }
--    tnStatsTcmTCATable                 OBJECT-TYPE ::= { tnStatisticsTCA 11 }
--    tnStatsTcmTCAProfileAttributeTotal OBJECT-TYPE ::= { tnStatisticsTCA 12 }
--    tnStatsTcmTCAProfileTable          OBJECT-TYPE ::= { tnStatisticsTCA 13 }
--    tnStatsTcmPortAttributeTotal       OBJECT-TYPE ::= { tnStatisticsTCA 14 }
--    tnStatsTcmPortTable                OBJECT-TYPE ::= { tnStatisticsTCA 15 }

--------------------------------------------------------------------------------
-- RX Statistics ODUk Configuration Scalar
--------------------------------------------------------------------------------
    tnOthOdukStatsRxConfigAttributeTotal OBJECT-TYPE
        SYNTAX      Integer32
        MAX-ACCESS  read-only
        STATUS      current
        DESCRIPTION "."
        ::= { tnStatisticsTCA 16 }

--------------------------------------------------------------------------------
-- RX Statistics ODUk Configuration Table
--------------------------------------------------------------------------------
    tnOthOdukStatsRxConfigTable OBJECT-TYPE
        SYNTAX      SEQUENCE OF TnOthOdukStatsRxConfigEntry
        MAX-ACCESS  not-accessible
        STATUS      current
        DESCRIPTION "."
        ::= { tnStatisticsTCA 17 }

    tnOthOdukStatsRxConfigEntry OBJECT-TYPE
        SYNTAX      TnOthOdukStatsRxConfigEntry
        MAX-ACCESS  not-accessible
        STATUS      current
        DESCRIPTION "."
        INDEX   { tnOthIfIndex,
                  tnOthIfIndexLo,
                  tnStatsInterval }
        ::= { tnOthOdukStatsRxConfigTable 1 }

    TnOthOdukStatsRxConfigEntry ::=
        SEQUENCE {
            tnOthOdukStatsRxNumberofBins       TnStatsBinType,
            tnOthOdukStatsRxProfileid          TnStatsProfileId,
            tnOthOdukStatsRxClear              TnCommand,
            tnOthOdukStatsRxIntervalLength     Unsigned32
        }

    tnOthOdukStatsRxNumberofBins OBJECT-TYPE
        SYNTAX      TnStatsBinType
        MAX-ACCESS  read-create
        STATUS      current
        DESCRIPTION "The number of collection bins in the interval."
        ::= { tnOthOdukStatsRxConfigEntry 1 }

    tnOthOdukStatsRxProfileid OBJECT-TYPE
        SYNTAX      TnStatsProfileId
        MAX-ACCESS  read-create
        STATUS      current
        DESCRIPTION "The profile identifier associated with an interval
                     on a particular ODU entity and group."
        ::= { tnOthOdukStatsRxConfigEntry 2 }

    tnOthOdukStatsRxClear OBJECT-TYPE
        SYNTAX      TnCommand
        MAX-ACCESS  read-create
        STATUS      current
        DESCRIPTION "This attribute is used to clear the current bin in
                     an interval on a particular entity and group."
        ::= { tnOthOdukStatsRxConfigEntry 3 }

    tnOthOdukStatsRxIntervalLength OBJECT-TYPE
        SYNTAX      Unsigned32
        UNITS       "seconds"
        MAX-ACCESS  read-create
        STATUS      current
        DESCRIPTION "The collection interval length in seconds.
                     Sets to this attribute are currently not supported."
        ::= { tnOthOdukStatsRxConfigEntry 4 }

--------------------------------------------------------------------------------
-- TX Statistics ODUk Configuration Scalar
--------------------------------------------------------------------------------
    tnOthOdukStatsTxConfigAttributeTotal OBJECT-TYPE
        SYNTAX      Integer32
        MAX-ACCESS  read-only
        STATUS      current
        DESCRIPTION "."
        ::= { tnStatisticsTCA 18 }

--------------------------------------------------------------------------------
-- TX Statistics ODUk Configuration Table
--------------------------------------------------------------------------------
    tnOthOdukStatsTxConfigTable OBJECT-TYPE
        SYNTAX      SEQUENCE OF TnOthOdukStatsTxConfigEntry
        MAX-ACCESS  not-accessible
        STATUS      current
        DESCRIPTION "."
        ::= { tnStatisticsTCA 19 }

    tnOthOdukStatsTxConfigEntry OBJECT-TYPE
        SYNTAX      TnOthOdukStatsTxConfigEntry
        MAX-ACCESS  not-accessible
        STATUS      current
        DESCRIPTION "."
        INDEX   { tnOthIfIndex,
                  tnOthIfIndexLo,
                  tnStatsInterval }
        ::= { tnOthOdukStatsTxConfigTable 1 }

    TnOthOdukStatsTxConfigEntry ::=
        SEQUENCE {
            tnOthOdukStatsTxNumberofBins       TnStatsBinType,
            tnOthOdukStatsTxProfileid          TnStatsProfileId,
            tnOthOdukStatsTxClear              TnCommand,
            tnOthOdukStatsTxIntervalLength     Unsigned32
        }

    tnOthOdukStatsTxNumberofBins OBJECT-TYPE
        SYNTAX      TnStatsBinType
        MAX-ACCESS  read-create
        STATUS      current
        DESCRIPTION "The number of collection bins in the interval."
        ::= { tnOthOdukStatsTxConfigEntry 1 }

    tnOthOdukStatsTxProfileid OBJECT-TYPE
        SYNTAX      TnStatsProfileId
        MAX-ACCESS  read-create
        STATUS      current
        DESCRIPTION "The profile identifier associated with an interval
                     on a particular ODU entity and group."
        ::= { tnOthOdukStatsTxConfigEntry 2 }

    tnOthOdukStatsTxClear OBJECT-TYPE
        SYNTAX      TnCommand
        MAX-ACCESS  read-create
        STATUS      current
        DESCRIPTION "This attribute is used to clear the current bin in
                     an interval on a particular entity and group."
        ::= { tnOthOdukStatsTxConfigEntry 3 }

    tnOthOdukStatsTxIntervalLength OBJECT-TYPE
        SYNTAX      Unsigned32
        UNITS       "seconds"
        MAX-ACCESS  read-create
        STATUS      current
        DESCRIPTION "The collection interval length in seconds.
                     Sets to this attribute are currently not supported."
        ::= { tnOthOdukStatsTxConfigEntry 4 }

--------------------------------------------------------------------------------
-- Statistics ODUk Control Scalar
--------------------------------------------------------------------------------
    tnOthOdukStatsControlAttributeTotal OBJECT-TYPE
        SYNTAX      Integer32
        MAX-ACCESS  read-only
        STATUS      current
        DESCRIPTION "."
        ::= { tnStatisticsTCA 20 }

--------------------------------------------------------------------------------
-- Statistics ODUk Control Table
--------------------------------------------------------------------------------
    tnOthOdukStatsControlTable OBJECT-TYPE
        SYNTAX      SEQUENCE OF TnOthOdukStatsControlEntry
        MAX-ACCESS  not-accessible
        STATUS      current
        DESCRIPTION "."
        ::= { tnStatisticsTCA 21 }

    tnOthOdukStatsControlEntry OBJECT-TYPE
        SYNTAX      TnOthOdukStatsControlEntry
        MAX-ACCESS  not-accessible
        STATUS      current
        DESCRIPTION "."
        INDEX   { tnOthIfIndex,
                  tnOthIfIndexLo }
        ::= { tnOthOdukStatsControlTable 1 }

    TnOthOdukStatsControlEntry ::=
        SEQUENCE {
            tnOthOdukStatsClearAll     TnCommand,
            tnOthOdukStatsRxEnable     INTEGER,
            tnOthOdukStatsTxEnable     INTEGER
        }

    tnOthOdukStatsClearAll OBJECT-TYPE
        SYNTAX      TnCommand
        MAX-ACCESS  read-create
        STATUS      current
        DESCRIPTION "This attribute is used to clear all ODURx and ODUTx
                     PMs in both current 15 minute bin and the current
                     1 day interval."
        ::= { tnOthOdukStatsControlEntry 1 }

    tnOthOdukStatsRxEnable OBJECT-TYPE
        SYNTAX      INTEGER {
                      enable(1),
                      disable(2)
                    }
        MAX-ACCESS  read-create
        STATUS      current
        DESCRIPTION "This attribute is used to enable and disable the
                     ODURx PM."
        ::= { tnOthOdukStatsControlEntry 2 }

    tnOthOdukStatsTxEnable OBJECT-TYPE
        SYNTAX      INTEGER {
                      enable(1),
                      disable(2)
                    }
        MAX-ACCESS  read-create
        STATUS      current
        DESCRIPTION "This attribute is used to enable and disable the
                     ODUTx PM."
        ::= { tnOthOdukStatsControlEntry 3 }

--------------------------------------------------------------------------------
-- Delay Measurement (DM) Statistics ODUk Configuration Scalar
--------------------------------------------------------------------------------
    tnOthOdukStatsDMConfigAttributeTotal OBJECT-TYPE
        SYNTAX      Integer32
        MAX-ACCESS  read-only
        STATUS      current
        DESCRIPTION "."
        ::= { tnStatisticsTCA 22 }

--------------------------------------------------------------------------------
-- Delay Measurement (DM) Statistics ODUk Configuration Table
--------------------------------------------------------------------------------
    tnOthOdukStatsDMConfigTable OBJECT-TYPE
        SYNTAX      SEQUENCE OF TnOthOdukStatsDMConfigEntry
        MAX-ACCESS  not-accessible
        STATUS      current
        DESCRIPTION "."
        ::= { tnStatisticsTCA 23 }

    tnOthOdukStatsDMConfigEntry OBJECT-TYPE
        SYNTAX      TnOthOdukStatsDMConfigEntry
        MAX-ACCESS  not-accessible
        STATUS      current
        DESCRIPTION "."
        INDEX   { tnOthIfIndex,
                  tnOthIfIndexLo,
                  tnStatsInterval }
        ::= { tnOthOdukStatsDMConfigTable 1 }

    TnOthOdukStatsDMConfigEntry ::=
        SEQUENCE {
            tnOthOdukStatsDMNumberofBins       TnStatsBinType,
            tnOthOdukStatsDMProfileid          TnStatsProfileId,
            tnOthOdukStatsDMClear              TnCommand,
            tnOthOdukStatsDMIntervalLength     Unsigned32
        }

    tnOthOdukStatsDMNumberofBins OBJECT-TYPE
        SYNTAX      TnStatsBinType
        MAX-ACCESS  read-create
        STATUS      current
        DESCRIPTION "The number of collection bins in the interval."
        ::= { tnOthOdukStatsDMConfigEntry 1 }

    tnOthOdukStatsDMProfileid OBJECT-TYPE
        SYNTAX      TnStatsProfileId
        MAX-ACCESS  read-create
        STATUS      current
        DESCRIPTION "The profile identifier associated with an interval
                     on a particular ODU entity and group."
        ::= { tnOthOdukStatsDMConfigEntry 2 }

    tnOthOdukStatsDMClear OBJECT-TYPE
        SYNTAX      TnCommand
        MAX-ACCESS  read-create
        STATUS      current
        DESCRIPTION "This attribute is used to clear the current bin in
                     an interval on a particular entity and group."
        ::= { tnOthOdukStatsDMConfigEntry 3 }

    tnOthOdukStatsDMIntervalLength OBJECT-TYPE
        SYNTAX      Unsigned32
        UNITS       "seconds"
        MAX-ACCESS  read-create
        STATUS      current
        DESCRIPTION "The collection interval length in seconds.
                     Sets to this attribute are currently not supported."
        ::= { tnOthOdukStatsDMConfigEntry 4 }

--------------------------------------------------------------------------------
-- Tandem Connection Monitoring (TCM) Configuration Scalar
--------------------------------------------------------------------------------
    tnOthOdukStatsTcmConfigAttributeTotal OBJECT-TYPE
        SYNTAX      Integer32
        MAX-ACCESS  read-only
        STATUS      current
        DESCRIPTION "."
        ::= { tnStatisticsTCA 24 }

--------------------------------------------------------------------------------
-- Tandem Connection Monitoring (TCM) Configuration Table
--------------------------------------------------------------------------------
    tnOthOdukStatsTcmConfigTable OBJECT-TYPE
        SYNTAX      SEQUENCE OF TnOthOdukStatsTcmConfigEntry
        MAX-ACCESS  not-accessible
        STATUS      current
        DESCRIPTION "."
        ::= { tnStatisticsTCA 25 }

    tnOthOdukStatsTcmConfigEntry OBJECT-TYPE
        SYNTAX      TnOthOdukStatsTcmConfigEntry
        MAX-ACCESS  not-accessible
        STATUS      current
        DESCRIPTION "."
        INDEX   { tnOthOdukTcmIfIndex,
                  tnOthOdukTcmIfIndexLo,
                  tnStatsInterval }
        ::= { tnOthOdukStatsTcmConfigTable 1 }

    TnOthOdukStatsTcmConfigEntry ::=
        SEQUENCE {
            tnOthOdukStatsTcmConfigNumberOfBins           TnStatsBinType,
            tnOthOdukStatsTcmConfigProfileId              TnStatsProfileId,
            tnOthOdukStatsTcmConfigClear                  TnCommand,
            tnOthOdukStatsTcmConfigIntervalLength         Unsigned32
        }

    tnOthOdukStatsTcmConfigNumberOfBins OBJECT-TYPE
        SYNTAX      TnStatsBinType
        MAX-ACCESS  read-create
        STATUS      current
        DESCRIPTION "The number of collection bins in the interval."
        ::= { tnOthOdukStatsTcmConfigEntry 1 }

    tnOthOdukStatsTcmConfigProfileId OBJECT-TYPE
        SYNTAX      TnStatsProfileId
        MAX-ACCESS  read-create
        STATUS      current
        DESCRIPTION "The profile identifier associated with an
                     interval on a particular ODU entity and group."
        ::= { tnOthOdukStatsTcmConfigEntry 2 }

    tnOthOdukStatsTcmConfigClear OBJECT-TYPE
        SYNTAX      TnCommand
        MAX-ACCESS  read-create
        STATUS      current
        DESCRIPTION "This attribute is used to clear the current bin
                     in an interval on a particular ODU entity
                     and group."
        ::= { tnOthOdukStatsTcmConfigEntry 3 }

    tnOthOdukStatsTcmConfigIntervalLength OBJECT-TYPE
        SYNTAX      Unsigned32
        MAX-ACCESS  read-create
        STATUS      current
        DESCRIPTION "."
        ::= { tnOthOdukStatsTcmConfigEntry 4 }

--------------------------------------------------------------------------------
-- Tandem Connection Monitoring (TCM) Enable Scalar
--------------------------------------------------------------------------------
    tnOthOdukStatsTcmEnableAttributeTotal OBJECT-TYPE
        SYNTAX      Integer32
        MAX-ACCESS  read-only
        STATUS      current
        DESCRIPTION "."
        ::= { tnStatisticsTCA 26 }

--------------------------------------------------------------------------------
-- Tandem Connection Monitoring (TCM) Enable Table
--------------------------------------------------------------------------------
    tnOthOdukStatsTcmEnableTable OBJECT-TYPE
        SYNTAX      SEQUENCE OF TnOthOdukStatsTcmEnableEntry
        MAX-ACCESS  not-accessible
        STATUS      current
        DESCRIPTION "."
        ::= { tnStatisticsTCA 27 }

    tnOthOdukStatsTcmEnableEntry OBJECT-TYPE
        SYNTAX      TnOthOdukStatsTcmEnableEntry
        MAX-ACCESS  not-accessible
        STATUS      current
        DESCRIPTION "."
        INDEX   { tnOthOdukTcmIfIndex,
                  tnOthOdukTcmIfIndexLo }
        ::= { tnOthOdukStatsTcmEnableTable 1 }

    TnOthOdukStatsTcmEnableEntry ::=
        SEQUENCE {
            tnOthOdukStatsTcmClearAll  TnCommand,
            tnOthOdukStatsTcmEnable    INTEGER
        }

    tnOthOdukStatsTcmClearAll OBJECT-TYPE
        SYNTAX      TnCommand
        MAX-ACCESS  read-create
        STATUS      current
        DESCRIPTION "This attribute is used to clear all TCM PMs in both
                     current 15 minute bin and the current 1 day interval."
        ::= { tnOthOdukStatsTcmEnableEntry 1 }

    tnOthOdukStatsTcmEnable OBJECT-TYPE
        SYNTAX      INTEGER {
                      enable(1),
                      disable(2)
                    }
        MAX-ACCESS  read-create
        STATUS      current
        DESCRIPTION "This attribute is used to enable and disable the
                     TCM PM."
        ::= { tnOthOdukStatsTcmEnableEntry 2 }

--------------------------------------------------------------------------------
-- Lane Powers Configuration Scalar
--------------------------------------------------------------------------------
    tnStatsLanePwrsConfigAttributeTotal OBJECT-TYPE
        SYNTAX      Integer32
        MAX-ACCESS  read-only
        STATUS      current
        DESCRIPTION "."
        ::= { tnStatisticsTCA 28 }

--------------------------------------------------------------------------------
-- Lane Powers Configuration Table
--------------------------------------------------------------------------------
    tnStatsLanePwrsConfigTable OBJECT-TYPE
        SYNTAX      SEQUENCE OF TnStatsLanePwrsConfigEntry
        MAX-ACCESS  not-accessible
        STATUS      current
        DESCRIPTION "."
        ::= { tnStatisticsTCA 29 }

    tnStatsLanePwrsConfigEntry OBJECT-TYPE
        SYNTAX      TnStatsLanePwrsConfigEntry
        MAX-ACCESS  not-accessible
        STATUS      current
        DESCRIPTION "."
        INDEX   { ifIndex }
        ::= { tnStatsLanePwrsConfigTable 1 }

    TnStatsLanePwrsConfigEntry ::=
        SEQUENCE {
            tnStatsLanePwrsConfigProfileId     TnStatsProfileId
        }

    tnStatsLanePwrsConfigProfileId OBJECT-TYPE
        SYNTAX      TnStatsProfileId
        MAX-ACCESS  read-create
        STATUS      current
        DESCRIPTION "The profile identifier associated with Optical Lane Powers
                     on a particular port."
        ::= { tnStatsLanePwrsConfigEntry 1 }

--------------------------------------------------------------------------------
-- Otu Statistics Port Interval Table
--------------------------------------------------------------------------------
    tnOtuStatsPortIntervalTable OBJECT-TYPE
        SYNTAX      SEQUENCE OF TnOtuStatsPortIntervalEntry
        MAX-ACCESS  not-accessible
        STATUS      current
        DESCRIPTION "."
        ::= { tnStatisticsTCA 30 }

    tnOtuStatsPortIntervalEntry OBJECT-TYPE
        SYNTAX      TnOtuStatsPortIntervalEntry
        MAX-ACCESS  not-accessible
        STATUS      current
        DESCRIPTION "."
        INDEX   { ifIndex,
                  tnStatsGroupId }
        ::= { tnOtuStatsPortIntervalTable 1 }

    TnOtuStatsPortIntervalEntry ::=
        SEQUENCE {
            tnOtuStatsPortNumberOfIntervals TnStatsIntervalType
        }

    tnOtuStatsPortNumberOfIntervals OBJECT-TYPE
        SYNTAX      TnStatsIntervalType
        MAX-ACCESS  read-create
        STATUS      current
        DESCRIPTION "The number of collection intervals
                     assigned to a particular interface and
                     group."
        ::= { tnOtuStatsPortIntervalEntry 1 }

--------------------------------------------------------------------------------
-- OTU Statistics Port Configuration Table
--------------------------------------------------------------------------------
    tnOtuStatsPortTable OBJECT-TYPE
        SYNTAX      SEQUENCE OF TnOtuStatsPortEntry
        MAX-ACCESS  not-accessible
        STATUS      current
        DESCRIPTION "."
        ::= { tnStatisticsTCA 31 }

    tnOtuStatsPortEntry OBJECT-TYPE
        SYNTAX      TnOtuStatsPortEntry
        MAX-ACCESS  not-accessible
        STATUS      current
        DESCRIPTION "."
        INDEX   { ifIndex,
                  tnStatsGroupId,
                  tnStatsInterval }
        ::= { tnOtuStatsPortTable 1 }

    TnOtuStatsPortEntry ::=
        SEQUENCE {
            tnOtuStatsPortIntervalLength      Unsigned32,
            tnOtuStatsPortNumberOfBins        TnStatsBinType,
            tnOtuStatsPortProfileId           TnStatsProfileId,
            tnOtuStatsPortClear               TnCommand,
            tnOtuStatsPortIntervalLength1day  Unsigned32,
            tnOtuStatsPortNumberOfBins1day    TnStatsBinType,
            tnOtuStatsPortProfileId1day       TnStatsProfileId,
            tnOtuStatsPortEnable              INTEGER
        }

    tnOtuStatsPortIntervalLength OBJECT-TYPE
        SYNTAX      Unsigned32
        UNITS       "seconds"
        MAX-ACCESS  read-create
        STATUS      current
        DESCRIPTION "The collection interval length in seconds.
                     Sets to this attribute are currently not supported."
        ::= { tnOtuStatsPortEntry 1 }

    tnOtuStatsPortNumberOfBins OBJECT-TYPE
        SYNTAX      TnStatsBinType
        MAX-ACCESS  read-create
        STATUS      current
        DESCRIPTION "The number of collection bins in the
                     interval."
        ::= { tnOtuStatsPortEntry 2 }

    tnOtuStatsPortProfileId OBJECT-TYPE
        SYNTAX      TnStatsProfileId
        MAX-ACCESS  read-create
        STATUS      current
        DESCRIPTION "The profile identifier associated with an
                     interval on a particular interface and group."
        ::= { tnOtuStatsPortEntry 3 }

    tnOtuStatsPortClear OBJECT-TYPE
        SYNTAX      TnCommand
        MAX-ACCESS  read-create
        STATUS      current
        DESCRIPTION "This attribute is used to clear the current bin
                     in an interval on a particular interface
                     and group."
        ::= { tnOtuStatsPortEntry 4 }

    tnOtuStatsPortIntervalLength1day OBJECT-TYPE
        SYNTAX      Unsigned32
        UNITS       "seconds"
        MAX-ACCESS  read-create
        STATUS      current
        DESCRIPTION "The collection interval length in seconds.
                     Sets to this attribute are currently not supported."
        ::= { tnOtuStatsPortEntry 5 }

    tnOtuStatsPortNumberOfBins1day OBJECT-TYPE
        SYNTAX      TnStatsBinType
        MAX-ACCESS  read-create
        STATUS      current
        DESCRIPTION "The number of collection bins in the
                     interval."
        ::= { tnOtuStatsPortEntry 6 }

    tnOtuStatsPortProfileId1day OBJECT-TYPE
        SYNTAX      TnStatsProfileId
        MAX-ACCESS  read-create
        STATUS      current
        DESCRIPTION "The profile identifier associated with an
                     interval on a particular interface and group."
        ::= { tnOtuStatsPortEntry 7 }

    tnOtuStatsPortEnable OBJECT-TYPE
        SYNTAX      INTEGER {
                      enable(1),
                      disable(2)
                    }
        MAX-ACCESS  read-create
        STATUS      current
        DESCRIPTION "."
        ::= { tnOtuStatsPortEntry 8 }


--------------------------------------------------------------------------------
-- Statistics Groups
--------------------------------------------------------------------------------

--------------------------------------------------------------------------------
-- Card Statistics Scalar
--------------------------------------------------------------------------------
    tnCardStatsTotalMembers OBJECT-TYPE
        SYNTAX      Integer32
        MAX-ACCESS  read-only
        STATUS      current
        DESCRIPTION "The total number of members in the card stats table."
        ::= { tnStatisticsGrouping 1 }

--------------------------------------------------------------------------------
-- Card Statistics Table
--------------------------------------------------------------------------------
    tnCardStatsTable OBJECT-TYPE
        SYNTAX      SEQUENCE OF TnCardStatsEntry
        MAX-ACCESS  not-accessible
        STATUS      current
        DESCRIPTION "."
        ::= { tnStatisticsGrouping 2 }

    tnCardStatsEntry OBJECT-TYPE
        SYNTAX      TnCardStatsEntry
        MAX-ACCESS  not-accessible
        STATUS      current
        DESCRIPTION "."
        INDEX   { tnShelfIndex,
                  tnSlotIndex,
                  tnCardStatsProcessor,
                  tnStatsInterval,
                  tnCardStatsBin }
        ::= { tnCardStatsTable 1 }

    TnCardStatsEntry ::=
        SEQUENCE {
            tnCardStatsProcessor  Unsigned32,
            tnCardStatsBin        TnStatsBinType,
            tnCardStatsBinStatus  TnStatsBinStatus,
            tnCardStatsStartTime  DateAndTime,
            tnCardStatCpuAverage  Counter32,
            tnCardStatHeapUsage   Counter32,
            tnCardStatPoolUsage   Counter32
        }

    tnCardStatsProcessor OBJECT-TYPE
        SYNTAX      Unsigned32
        MAX-ACCESS  not-accessible
        STATUS      current
        DESCRIPTION "The processor.  Currently, the value
                     is always 1."
        ::= { tnCardStatsEntry 1 }

    tnCardStatsBin OBJECT-TYPE
        SYNTAX      TnStatsBinType
        MAX-ACCESS  not-accessible
        STATUS      current
        DESCRIPTION "The bin number, starting with bin 0."
        ::= { tnCardStatsEntry 2 }

    tnCardStatsBinStatus OBJECT-TYPE
        SYNTAX      TnStatsBinStatus
        MAX-ACCESS  read-only
        STATUS      current
        DESCRIPTION "This attribute indicates the validity of the bin."
        ::= { tnCardStatsEntry 3 }

    tnCardStatsStartTime OBJECT-TYPE
        SYNTAX      DateAndTime
        MAX-ACCESS  read-only
        STATUS      current
        DESCRIPTION "This attribute is the bin collection start date
                     and time."
        ::= { tnCardStatsEntry 4 }

    tnCardStatCpuAverage OBJECT-TYPE
        SYNTAX      Counter32
        MAX-ACCESS  read-only
        STATUS      current
        DESCRIPTION "The average CPU usage as a percentage."
        ::= { tnCardStatsEntry 5 }

    tnCardStatHeapUsage OBJECT-TYPE
        SYNTAX      Counter32
        MAX-ACCESS  read-only
        STATUS      current
        DESCRIPTION "The heap usage as a percentage."
        ::= { tnCardStatsEntry 6 }

    tnCardStatPoolUsage OBJECT-TYPE
        SYNTAX      Counter32
        MAX-ACCESS  read-only
        STATUS      current
        DESCRIPTION "The pool usage as a percentage."
        ::= { tnCardStatsEntry 7 }

--------------------------------------------------------------------------------
-- Interface Statistics Scalar
--------------------------------------------------------------------------------
    tnInterfaceStatsTotalMembers OBJECT-TYPE
        SYNTAX      Integer32
        MAX-ACCESS  read-only
        STATUS      current
        DESCRIPTION "The total number of members in the interface stats table."
        ::= { tnStatisticsGrouping 3 }

--------------------------------------------------------------------------------
-- Interface Statistics Table
--------------------------------------------------------------------------------
    tnInterfaceStatsTable OBJECT-TYPE
        SYNTAX      SEQUENCE OF TnInterfaceStatsEntry
        MAX-ACCESS  not-accessible
        STATUS      current
        DESCRIPTION "."
        ::= { tnStatisticsGrouping 4 }

    tnInterfaceStatsEntry OBJECT-TYPE
        SYNTAX      TnInterfaceStatsEntry
        MAX-ACCESS  not-accessible
        STATUS      current
        DESCRIPTION "."
        INDEX   { ifIndex,
                  tnStatsInterval,
                  tnIfStatsBin }
        ::= { tnInterfaceStatsTable 1 }

    TnInterfaceStatsEntry ::=
        SEQUENCE {
            tnIfStatsBin                    TnStatsBinType,
            tnIfStatsBinStatus              TnStatsBinStatus,
            tnIfStatsStartTime              DateAndTime,
            tnIfStatInOctets                Counter64,
            tnIfStatInUcastPkts             Counter64,
            tnIfStatInDiscards              Counter64,
            tnIfStatInErrors                Counter64,
            tnIfStatInUnknownProtos         Counter64,
            tnIfStatOutOctets               Counter64,
            tnIfStatOutUcastPkts            Counter64,
            tnIfStatOutDiscards             Counter64,
            tnIfStatOutErrors               Counter64,
            tnIfStatInMulticastPkts         Counter64,
            tnIfStatInBroadcastPkts         Counter64,
            tnIfStatOutMulticastPkts        Counter64,
            tnIfStatOutBroadcastPkts        Counter64,
            tnIfStatInPacketsNotClassified  Counter64
        }

    tnIfStatsBin OBJECT-TYPE
        SYNTAX      TnStatsBinType
        MAX-ACCESS  not-accessible
        STATUS      current
        DESCRIPTION "The bin number, starting with bin 0."
        ::= { tnInterfaceStatsEntry 1 }

    tnIfStatsBinStatus OBJECT-TYPE
        SYNTAX      TnStatsBinStatus
        MAX-ACCESS  read-only
        STATUS      current
        DESCRIPTION "This attribute indicates the validity of the bin."
        ::= { tnInterfaceStatsEntry 2 }

    tnIfStatsStartTime OBJECT-TYPE
        SYNTAX      DateAndTime
        MAX-ACCESS  read-only
        STATUS      current
        DESCRIPTION "This attribute is the bin collection start date
                     and time."
        ::= { tnInterfaceStatsEntry 3 }

    tnIfStatInOctets OBJECT-TYPE
        SYNTAX      Counter64
        MAX-ACCESS  read-only
        STATUS      current
        DESCRIPTION "Provides a count of the number of octets that
                     passed through the IN port of the interface."
        ::= { tnInterfaceStatsEntry 4 }

    tnIfStatInUcastPkts OBJECT-TYPE
        SYNTAX      Counter64
        MAX-ACCESS  read-only
        STATUS      current
        DESCRIPTION "Provides a count of the number of unicast packets
                     that passed through the IN port of the interface."
        ::= { tnInterfaceStatsEntry 5 }

    tnIfStatInDiscards OBJECT-TYPE
        SYNTAX      Counter64
        MAX-ACCESS  read-only
        STATUS      current
        DESCRIPTION "Provides a count of the number of packets
                     discarded at the IN port of the interface."
        ::= { tnInterfaceStatsEntry 6 }

    tnIfStatInErrors OBJECT-TYPE
        SYNTAX      Counter64
        MAX-ACCESS  read-only
        STATUS      current
        DESCRIPTION "Provides a count of the errored frames detected
                     at the IN port of the interface. For Ethernet
                     traffic, this value is a sum of the following
                     counts:

                     tnEtherStatRxCrcAlignErrs
                     tnEtherStatRxOversizedPkts
                     tnEtherStatRxUndersizedPkts
                     tnEtherStatRxFragments"
        ::= { tnInterfaceStatsEntry 7 }

    tnIfStatInUnknownProtos OBJECT-TYPE
        SYNTAX      Counter64
        MAX-ACCESS  read-only
        STATUS      current
        DESCRIPTION "Provides a count of the number of packets
                     received at the IN port of the interface
                     for which the protocol is unknown."
        ::= { tnInterfaceStatsEntry 8 }

    tnIfStatOutOctets OBJECT-TYPE
        SYNTAX      Counter64
        MAX-ACCESS  read-only
        STATUS      current
        DESCRIPTION "Provides a count of the number of octets
                     that passed through the OUT port
                     of the interface."
        ::= { tnInterfaceStatsEntry 9 }

    tnIfStatOutUcastPkts OBJECT-TYPE
        SYNTAX      Counter64
        MAX-ACCESS  read-only
        STATUS      current
        DESCRIPTION "Provides a count of the number of unicast
                     packets that passed through the OUT port
                     of the interface."
        ::= { tnInterfaceStatsEntry 10 }

    tnIfStatOutDiscards OBJECT-TYPE
        SYNTAX      Counter64
        MAX-ACCESS  read-only
        STATUS      current
        DESCRIPTION "Provides a count of the number of packets
                     discarded at the OUT port of the interface."
        ::= { tnInterfaceStatsEntry 11 }

    tnIfStatOutErrors OBJECT-TYPE
        SYNTAX      Counter64
        MAX-ACCESS  read-only
        STATUS      current
        DESCRIPTION "Provides a count of the errored frames detected
                     at the OUT port of the interface. For Ethernet
                     traffic, this value is a sum of the following
                     counts:

                     tnEtherStatTxCrcAlignErrs
                     tnEtherStatTxOversizedPkts
                     tnEtherStatTxUndersizedPkts
                     tnEtherStatTxFragments"
        ::= { tnInterfaceStatsEntry 12 }

    tnIfStatInMulticastPkts OBJECT-TYPE
        SYNTAX      Counter64
        MAX-ACCESS  read-only
        STATUS      current
        DESCRIPTION "Provides a count of the total number of good
                     packets detected at the IN port of the
                     interface that were directed to a multicast
                     address. Does not include packets directed to
                     the broadcast."
        ::= { tnInterfaceStatsEntry 13 }

    tnIfStatInBroadcastPkts OBJECT-TYPE
        SYNTAX      Counter64
        MAX-ACCESS  read-only
        STATUS      current
        DESCRIPTION "Provides a count of the total number of good
                     packets detected at the IN port of the
                     interface that were directed to the broadcast
                     address. Does not include multicast packets."
        ::= { tnInterfaceStatsEntry 14 }

    tnIfStatOutMulticastPkts OBJECT-TYPE
        SYNTAX      Counter64
        MAX-ACCESS  read-only
        STATUS      current
        DESCRIPTION "Provides a count of the total number of good
                     packets detected at the OUT port of the
                     interface that were directed to a multicast
                     address. Does not include packets directed to
                     the broadcast."
        ::= { tnInterfaceStatsEntry 15 }

    tnIfStatOutBroadcastPkts OBJECT-TYPE
        SYNTAX      Counter64
        MAX-ACCESS  read-only
        STATUS      current
        DESCRIPTION "Provides a count of the total number of good
                     packets detected at the OUT port of the
                     interface that were directed to the broadcast
                     address. Does not include multicast packets."
        ::= { tnInterfaceStatsEntry 16 }

    tnIfStatInPacketsNotClassified OBJECT-TYPE
        SYNTAX      Counter64
        MAX-ACCESS  read-only
        STATUS      current
        DESCRIPTION "Provides a count of the number of unclassified
                     packets received at the IN port of the
                     interface."
        ::= { tnInterfaceStatsEntry 17 }

--------------------------------------------------------------------------------
-- Ethernet Statistics Scalar
--------------------------------------------------------------------------------
    tnEtherStatsTotalMembers OBJECT-TYPE
        SYNTAX      Integer32
        MAX-ACCESS  read-only
        STATUS      current
        DESCRIPTION "The total number of members in the ethernet stats table."
        ::= { tnStatisticsGrouping 5 }

--------------------------------------------------------------------------------
-- Ethernet Statistics Table
--------------------------------------------------------------------------------
    tnEtherStatsTable OBJECT-TYPE
        SYNTAX      SEQUENCE OF TnEtherStatsEntry
        MAX-ACCESS  not-accessible
        STATUS      current
        DESCRIPTION "."
        ::= { tnStatisticsGrouping 6 }

    tnEtherStatsEntry OBJECT-TYPE
        SYNTAX      TnEtherStatsEntry
        MAX-ACCESS  not-accessible
        STATUS      current
        DESCRIPTION "."
        INDEX   { ifIndex,
                  tnStatsInterval,
                  tnEtherStatsBin }
        ::= { tnEtherStatsTable 1 }

    TnEtherStatsEntry ::=
        SEQUENCE {
            tnEtherStatsBin                   TnStatsBinType,
            tnEtherStatsBinStatus             TnStatsBinStatus,
            tnEtherStatsStartTime             DateAndTime,
            tnEtherStatRxDropEvents           Counter64,
            tnEtherStatRxFragments            Counter64,
            tnEtherStatRxJabbers              Counter64,
            tnEtherStatRxMcastPkts            Counter64,
            tnEtherStatRxOctets               Counter64,
            tnEtherStatRxOversizedPkts        Counter64,
            tnEtherStatRxPkts                 Counter64,
            tnEtherStatRxPktsSize1024to1518   Counter64,
            tnEtherStatRxPktsSize128to255     Counter64,
            tnEtherStatRxPktsSize256to511     Counter64,
            tnEtherStatRxPktsSize512to1023    Counter64,
--            obsolete
--            tnEtherStatRxPktsSize64orLess     Counter64,
            tnEtherStatRxPktsSize65to127      Counter64,
            tnEtherStatRxUndersizedPkts       Counter64,
            tnEtherStatTxBcastPkts            Counter64,
            tnEtherStatTxCrcAlignErrs         Counter64,
            tnEtherStatTxDropEvents           Counter64,
            tnEtherStatTxFragments            Counter64,
            tnEtherStatTxJabbers              Counter64,
            tnEtherStatTxMcastPkts            Counter64,
            tnEtherStatTxOctets               Counter64,
            tnEtherStatTxOversizedPkts        Counter64,
            tnEtherStatTxPkts                 Counter64,
            tnEtherStatTxPktsSize1024to1518   Counter64,
            tnEtherStatTxPktsSize128to255     Counter64,
            tnEtherStatTxPktsSize256to511     Counter64,
            tnEtherStatTxPktsSize512to1023    Counter64,
--            obsolete
--            tnEtherStatTxPktsSize64orLess     Counter64,
            tnEtherStatTxPktsSize65to127      Counter64,
            tnEtherStatTxUndersizedPkts       Counter64,
            tnEtherStatRxBcastPkts            Counter64,
            tnEtherStatRxCrcAlignErrs         Counter64,
            tnEtherStatRxCollisions           Counter64,
            tnEtherStatRxJumboPkts            Counter64,
            tnEtherStatTxCollisions           Counter64,
            tnEtherStatTxJumboPkts            Counter64,
            tnEtherStatRxPktsSize64           Counter64,
            tnEtherStatTxPktsSize64           Counter64,
            tnEtherStatRxPktErrRatio          Counter64,
            tnEtherStatTxPktErrRatio          Counter64,
            tnEtherStatRxPktErrRatio15MinTr    Counter64,
            tnEtherStatTxPktErrRatio15MinTr    Counter64,
            tnEtherStatRxPktErrRatio1DayTr     Counter64,
            tnEtherStatTxPktErrRatio1DayTr     Counter64,
            tnEtherStatRxPktErrRatio15MinRtr   Counter64,
            tnEtherStatTxPktErrRatio15MinRtr   Counter64
        }

    tnEtherStatsBin OBJECT-TYPE
        SYNTAX      TnStatsBinType
        MAX-ACCESS  not-accessible
        STATUS      current
        DESCRIPTION "The bin number, starting with bin 0."
        ::= { tnEtherStatsEntry 1 }

    tnEtherStatsBinStatus OBJECT-TYPE
        SYNTAX      TnStatsBinStatus
        MAX-ACCESS  read-only
        STATUS      current
        DESCRIPTION "This attribute indicates the validity of the bin."
        ::= { tnEtherStatsEntry 2 }

    tnEtherStatsStartTime OBJECT-TYPE
        SYNTAX      DateAndTime
        MAX-ACCESS  read-only
        STATUS      current
        DESCRIPTION "This attribute is the bin collection start date
                     and time."
        ::= { tnEtherStatsEntry 3 }

    tnEtherStatRxDropEvents OBJECT-TYPE
        SYNTAX      Counter64
        MAX-ACCESS  read-only
        STATUS      current
        DESCRIPTION "Provides a count of the total number of events
                     in which packets were dropped by the monitoring
                     entity due to a lack of resources. This value is
                     not necessarily the number of packets dropped;
                     it can be the number of times this condition has
                     been detected."
        ::= { tnEtherStatsEntry 4 }

    tnEtherStatRxFragments OBJECT-TYPE
        SYNTAX      Counter64
        MAX-ACCESS  read-only
        STATUS      current
        DESCRIPTION "Provides a count of the total number of packets
                     sent or received that were less than 64 octets in
                     length (excluding framing bits but including FCS
                     octets) and had either a bad FCS with an integral
                     number of octets (FCS Error) or a bad FCS with a
                     non-integral number of octets (Alignment Error)."
        ::= { tnEtherStatsEntry 5 }

    tnEtherStatRxJabbers OBJECT-TYPE
        SYNTAX      Counter64
        MAX-ACCESS  read-only
        STATUS      current
        DESCRIPTION "Provides a count of the total number of packets sent
                     or received that were longer than 1518 octets
                     (excluding framing bits, but including FCS octets)
                     and had either a bad FCS with an integral number of
                     octets (FCS Error) or a bad FCS with a non-integral
                     number of octets (Alignment Error)."
        ::= { tnEtherStatsEntry 6 }

    tnEtherStatRxMcastPkts OBJECT-TYPE
        SYNTAX      Counter64
        MAX-ACCESS  read-only
        STATUS      current
        DESCRIPTION "Provides a count of the total number of good packets
                     received that were directed to a multicast address.
                     This does not include packets directed to the
                     broadcast."
        ::= { tnEtherStatsEntry 7 }

    tnEtherStatRxOctets OBJECT-TYPE
        SYNTAX      Counter64
        MAX-ACCESS  read-only
        STATUS      current
        DESCRIPTION "Provides a count of the total number of octets of
                     data (including the bad packets) received on the
                     port. Excludes framing bits. Includes Frame Check
                     Sequence (FCS) octets."
        ::= { tnEtherStatsEntry 8 }

    tnEtherStatRxOversizedPkts OBJECT-TYPE
        SYNTAX      Counter64
        MAX-ACCESS  read-only
        STATUS      current
        DESCRIPTION "Provides a count of the total number of packets
                     received that were longer than 1518 octets and
                     were otherwise well formed. The packet length
                     excludes framing bits and includes FCS octets."
        ::= { tnEtherStatsEntry 9 }

    tnEtherStatRxPkts OBJECT-TYPE
        SYNTAX      Counter64
        MAX-ACCESS  read-only
        STATUS      current
        DESCRIPTION "Provides a count of the total number of packets
                     (including bad packet, broadcast packets, and
                     multicast packets) received."
        ::= { tnEtherStatsEntry 10 }

    tnEtherStatRxPktsSize1024to1518 OBJECT-TYPE
        SYNTAX      Counter64
        MAX-ACCESS  read-only
        STATUS      current
        DESCRIPTION "Provides a count of the total number of packets
                     (including bad packets) received that were
                     between 1024 and 1518 octets in length inclusive.
                     The packet length excludes framing bits and
                     includes FCS octets."
        ::= { tnEtherStatsEntry 11 }

    tnEtherStatRxPktsSize128to255 OBJECT-TYPE
        SYNTAX      Counter64
        MAX-ACCESS  read-only
        STATUS      current
        DESCRIPTION "Provides a count of the total number of packets
                     (including bad packets) received that were between
                     128 and 255 octets in length inclusive. The packet
                     length excludes framing bits and includes FCS
                     octets."
        ::= { tnEtherStatsEntry 12 }

    tnEtherStatRxPktsSize256to511 OBJECT-TYPE
        SYNTAX      Counter64
        MAX-ACCESS  read-only
        STATUS      current
        DESCRIPTION "Provides a count of the total number of packets
                     (including bad packets) received that were between
                     256 and 511 octets in length inclusive. The packet
                     length excludes framing bits and includes FCS
                     octets."
        ::= { tnEtherStatsEntry 13 }

    tnEtherStatRxPktsSize512to1023 OBJECT-TYPE
        SYNTAX      Counter64
        MAX-ACCESS  read-only
        STATUS      current
        DESCRIPTION "Provides a count of the total number of packets
                     (including bad packets) received that were
                     between 512 and 1023 octets in length inclusive.
                     The packet length excludes framing bits and
                     includes FCS octets."
        ::= { tnEtherStatsEntry 14 }

--    obsolete
--    tnEtherStatRxPktsSize64orLess OBJECT-TYPE ::= { tnEtherStatsEntry 15 }

    tnEtherStatRxPktsSize65to127 OBJECT-TYPE
        SYNTAX      Counter64
        MAX-ACCESS  read-only
        STATUS      current
        DESCRIPTION "Provides a count of the total number of packets
                     (including bad packets) received that were
                     between 65 and 127 octets in length inclusive.
                     The packet length excludes framing bits and
                     includes FCS octets."
        ::= { tnEtherStatsEntry 16 }

    tnEtherStatRxUndersizedPkts OBJECT-TYPE
        SYNTAX      Counter64
        MAX-ACCESS  read-only
        STATUS      current
        DESCRIPTION "Provides a count of the total number of packets
                     received that were less than 64 octets long
                     and were otherwise well formed. The packet
                     length excludes framing bits and includes
                     FCS octets."
        ::= { tnEtherStatsEntry 17 }

    tnEtherStatTxBcastPkts OBJECT-TYPE
        SYNTAX      Counter64
        MAX-ACCESS  read-only
        STATUS      current
        DESCRIPTION "Provides a count of the total number of good
                     packets received that were directed to the
                     broadcast address. This does not include
                     multicast packets."
        ::= { tnEtherStatsEntry 18 }

    tnEtherStatTxCrcAlignErrs OBJECT-TYPE
        SYNTAX      Counter64
        MAX-ACCESS  read-only
        STATUS      current
        DESCRIPTION "Provides a count of the total number of packets
                     received that had a length of between 63 and
                     1518 octets, inclusive, but had either a FCS
                     with an integral number of octets (FCS error)
                     or a bad FCS with a non-integral number of
                     octets (Alignment Error). The packet length
                     excludes framing bits and includes FCS octets."
        ::= { tnEtherStatsEntry 19 }

    tnEtherStatTxDropEvents OBJECT-TYPE
        SYNTAX      Counter64
        MAX-ACCESS  read-only
        STATUS      current
        DESCRIPTION "Provides a count of the total number of events
                     in which packets were dropped by the monitoring
                     entity due to a lack of resources. This value
                     is not necessarily the number of packets dropped;
                     it can be the number of times this condition
                     has been detected."
        ::= { tnEtherStatsEntry 20 }

    tnEtherStatTxFragments OBJECT-TYPE
        SYNTAX      Counter64
        MAX-ACCESS  read-only
        STATUS      current
        DESCRIPTION "Provides a count of the total number of packets
                     sent or received that were less than 64 octets
                     in length (excluding framing bits but including
                     FCS octets) and had either a bad FCS with an
                     integral number of octets (FCS Error) or a bad
                     FCS with a non-integral number of octets
                     (Alignment Error)."
        ::= { tnEtherStatsEntry 21 }

    tnEtherStatTxJabbers OBJECT-TYPE
        SYNTAX      Counter64
        MAX-ACCESS  read-only
        STATUS      current
        DESCRIPTION "Provides a count of the total number of packets
                     sent or received that were longer than 1518
                     octets (excluding framing bits, but including
                     FCS octets) and had either a bad FCS with an
                     integral number of octets (FCS Error) or a bad
                     FCS with a non-integral number of octets
                     (Alignment Error)."
        ::= { tnEtherStatsEntry 22 }

    tnEtherStatTxMcastPkts OBJECT-TYPE
        SYNTAX      Counter64
        MAX-ACCESS  read-only
        STATUS      current
        DESCRIPTION "Provides a count of the total number of good
                     packets received that were directed to a
                     multicast address. This does not include packets
                     directed to the broadcast."
        ::= { tnEtherStatsEntry 23 }

    tnEtherStatTxOctets OBJECT-TYPE
        SYNTAX      Counter64
        MAX-ACCESS  read-only
        STATUS      current
        DESCRIPTION "Provides a count of the total number of octets
                     of data (including the bad packets) received
                     on the port. Excludes framing bits. Includes
                     Frame Check Sequence (FCS) octets."
        ::= { tnEtherStatsEntry 24 }

    tnEtherStatTxOversizedPkts OBJECT-TYPE
        SYNTAX      Counter64
        MAX-ACCESS  read-only
        STATUS      current
        DESCRIPTION "Provides a count of the total number of
                     packets received that were longer than 1518
                     octets and were otherwise well formed. The
                     packet length excludes framing bits and
                     includes FCS octets."
        ::= { tnEtherStatsEntry 25 }

    tnEtherStatTxPkts OBJECT-TYPE
        SYNTAX      Counter64
        MAX-ACCESS  read-only
        STATUS      current
        DESCRIPTION "Provides a count of the total number of packets
                     (including bad packet, broadcast packets, and
                     multicast packets) received."
        ::= { tnEtherStatsEntry 26 }

    tnEtherStatTxPktsSize1024to1518 OBJECT-TYPE
        SYNTAX      Counter64
        MAX-ACCESS  read-only
        STATUS      current
        DESCRIPTION "Provides a count of the total number of packets
                     (including bad packets) received that were
                     between 1024 and 1518 octets in length
                     inclusive. The packet length excludes framing
                     bits and includes FCS octets."
        ::= { tnEtherStatsEntry 27 }

    tnEtherStatTxPktsSize128to255 OBJECT-TYPE
        SYNTAX      Counter64
        MAX-ACCESS  read-only
        STATUS      current
        DESCRIPTION "Provides a count of the total number of packets
                     (including bad packets) received that were
                     between 128 and 255 octets in length inclusive.
                     The packet length excludes framing bits and
                     includes FCS octets."
        ::= { tnEtherStatsEntry 28 }

    tnEtherStatTxPktsSize256to511 OBJECT-TYPE
        SYNTAX      Counter64
        MAX-ACCESS  read-only
        STATUS      current
        DESCRIPTION "Provides a count of the total number of packets
                     (including bad packets) received that were
                     between 256 and 511octets in length inclusive.
                     The packet length excludes framing bits and
                     includes FCS octets."
        ::= { tnEtherStatsEntry 29 }

    tnEtherStatTxPktsSize512to1023 OBJECT-TYPE
        SYNTAX      Counter64
        MAX-ACCESS  read-only
        STATUS      current
        DESCRIPTION "Provides a count of the total number of packets
                     (including bad packets) received that were
                     between 512 and 1023 octets in length inclusive.
                     The packet length excludes framing bits and
                     includes FCS octets."
        ::= { tnEtherStatsEntry 30 }

--    obsolete
--    tnEtherStatTxPktsSize64orLess OBJECT-TYPE ::= { tnEtherStatsEntry 31 }

    tnEtherStatTxPktsSize65to127 OBJECT-TYPE
        SYNTAX      Counter64
        MAX-ACCESS  read-only
        STATUS      current
        DESCRIPTION "Provides a count of the total number of packets
                     (including bad packets) received that were
                     between 65 and 127 octets in length inclusive.
                     The packet length excludes framing bits and
                     includes FCS octets."
        ::= { tnEtherStatsEntry 32 }

    tnEtherStatTxUndersizedPkts OBJECT-TYPE
        SYNTAX      Counter64
        MAX-ACCESS  read-only
        STATUS      current
        DESCRIPTION "Provides a count of the total number of packets
                     received that were less than 64 octets long
                     and were otherwise well formed. The packet
                     length excludes framing bits and includes
                     FCS octets."
        ::= { tnEtherStatsEntry 33 }

    tnEtherStatRxBcastPkts OBJECT-TYPE
        SYNTAX      Counter64
        MAX-ACCESS  read-only
        STATUS      current
        DESCRIPTION "Provides a count of the total number of good
                     packets received that were directed to the
                     broadcast address. This does not include
                     multicast packets."
        ::= { tnEtherStatsEntry 34 }

    tnEtherStatRxCrcAlignErrs OBJECT-TYPE
        SYNTAX      Counter64
        MAX-ACCESS  read-only
        STATUS      current
        DESCRIPTION "Provides a count of the total number of packets
                     received that had a length of between 63 and
                     1518 octets, inclusive, but had either a FCS
                     with an integral number of octets (FCS error)
                     or a bad FCS with a non-integral number of
                     octets (Alignment Error). The packet length
                     excludes framing bits and includes FCS octets."
        ::= { tnEtherStatsEntry 35 }

    tnEtherStatRxCollisions OBJECT-TYPE
        SYNTAX      Counter64
        MAX-ACCESS  read-only
        STATUS      current
        DESCRIPTION "Provides a count of the total number of
                     collisions on the port."
        ::= { tnEtherStatsEntry 36 }

    tnEtherStatRxJumboPkts OBJECT-TYPE
        SYNTAX      Counter64
        MAX-ACCESS  read-only
        STATUS      current
        DESCRIPTION "Provides a count of the total number of Jumbo
                     frames sent or received on the port. Jumbo
                     frames are frames which have a packet size
                     greater than 1500 bytes."
        ::= { tnEtherStatsEntry 37 }

    tnEtherStatTxCollisions OBJECT-TYPE
        SYNTAX      Counter64
        MAX-ACCESS  read-only
        STATUS      current
        DESCRIPTION "Provides a count of the total number of
                     collisions on the port."
        ::= { tnEtherStatsEntry 38 }

    tnEtherStatTxJumboPkts OBJECT-TYPE
        SYNTAX      Counter64
        MAX-ACCESS  read-only
        STATUS      current
        DESCRIPTION "Provides a count of the total number of Jumbo
                     frames sent or received on the port. Jumbo
                     frames are frames which have a packet size
                     greater than 1500 bytes."
        ::= { tnEtherStatsEntry 39 }

    tnEtherStatRxPktsSize64 OBJECT-TYPE
        SYNTAX      Counter64
        MAX-ACCESS  read-only
        STATUS      current
        DESCRIPTION "Provides a count of the total number of packets
                     (including bad packets) received that were 64
                     octets in length inclusive. The packet length
                     excludes framing bits and includes FCS octets."
        ::= { tnEtherStatsEntry 40 }

    tnEtherStatTxPktsSize64 OBJECT-TYPE
        SYNTAX      Counter64
        MAX-ACCESS  read-only
        STATUS      current
        DESCRIPTION "Provides a count of the total number of packets
                     (including bad packets) received that were 64
                     octets in length inclusive. The packet length
                     excludes framing bits and includes FCS octets."
        ::= { tnEtherStatsEntry 41 }

    tnEtherStatRxPktErrRatio OBJECT-TYPE
        SYNTAX      Counter64
        MAX-ACCESS  read-only
        STATUS      current
        DESCRIPTION "Provides a ratio of the total number of errored
                     packets received to the total number of packets
                     received."
        ::= { tnEtherStatsEntry 42 }

    tnEtherStatTxPktErrRatio OBJECT-TYPE
        SYNTAX      Counter64
        MAX-ACCESS  read-only
        STATUS      current
        DESCRIPTION "Provides a ratio of the total number of errored
                     packets transmitted to the total number of packets
                     transmitted."
        ::= { tnEtherStatsEntry 43 }

    tnEtherStatRxPktErrRatio15MinTr OBJECT-TYPE
        SYNTAX      Counter64
        MAX-ACCESS  read-only
        STATUS      current
        DESCRIPTION "15 minute threshold value for a ratio of the total
                     number of errored packets received to the total
                     number of packets received."
        ::= { tnEtherStatsEntry 44 }

    tnEtherStatTxPktErrRatio15MinTr OBJECT-TYPE
        SYNTAX      Counter64
        MAX-ACCESS  read-only
        STATUS      current
        DESCRIPTION "15 minute threshold value for a ratio of the total
                     number of errored packets transmitted to the total
                     number of packets transmitted."
        ::= { tnEtherStatsEntry 45 }

    tnEtherStatRxPktErrRatio1DayTr OBJECT-TYPE
        SYNTAX      Counter64
        MAX-ACCESS  read-only
        STATUS      current
        DESCRIPTION "1 day threshold value for a ratio of the total
                     number of errored packets received to the total
                     number of packets received."
        ::= { tnEtherStatsEntry 46 }

    tnEtherStatTxPktErrRatio1DayTr OBJECT-TYPE
        SYNTAX      Counter64
        MAX-ACCESS  read-only
        STATUS      current
        DESCRIPTION "1 day threshold value for a ratio of the total
                     number of errored packets transmitted to the total
                     number of packets transmitted."
        ::= { tnEtherStatsEntry 47 }

    tnEtherStatRxPktErrRatio15MinRtr OBJECT-TYPE
        SYNTAX      Counter64
        MAX-ACCESS  read-only
        STATUS      current
        DESCRIPTION "15 minute reset threshold value for a ratio of the
                     total number of errored packets received to the
                     total number of packets received."
        ::= { tnEtherStatsEntry 48 }

    tnEtherStatTxPktErrRatio15MinRtr OBJECT-TYPE
        SYNTAX      Counter64
        MAX-ACCESS  read-only
        STATUS      current
        DESCRIPTION "15 minute reset threshold value for a ratio of the
                     total number of errored packets transmitted to the
                     total number of packets transmitted."
        ::= { tnEtherStatsEntry 49 }

--------------------------------------------------------------------------------
-- SONET Statistics Scalar
--------------------------------------------------------------------------------
    tnSonetStatsTotalMembers OBJECT-TYPE
        SYNTAX      Integer32
        MAX-ACCESS  read-only
        STATUS      current
        DESCRIPTION "The total number of members in the SONET stats table."
        ::= { tnStatisticsGrouping 7 }

--------------------------------------------------------------------------------
-- SONET Statistics Table
--------------------------------------------------------------------------------
    tnSonetStatsTable OBJECT-TYPE
        SYNTAX      SEQUENCE OF TnSonetStatsEntry
        MAX-ACCESS  not-accessible
        STATUS      current
        DESCRIPTION "."
        ::= { tnStatisticsGrouping 8 }

    tnSonetStatsEntry OBJECT-TYPE
        SYNTAX      TnSonetStatsEntry
        MAX-ACCESS  not-accessible
        STATUS      current
        DESCRIPTION "."
        INDEX   { ifIndex,
                  tnStatsInterval,
                  tnSonetStatsBin }
        ::= { tnSonetStatsTable 1 }

    TnSonetStatsEntry ::=
        SEQUENCE {
            tnSonetStatsBin              TnStatsBinType,
            tnSonetStatsBinStatus        TnStatsBinStatus,
            tnSonetStatsStartTime        DateAndTime,
            tnSonetStatRxCVS             Counter32,
            tnSonetStatRxESS             Counter32,
            tnSonetStatRxSESS            Counter32,
            tnSonetStatRxSEFSS           Counter32,
            tnSonetStatRxCVL             Counter32,
            tnSonetStatRxESL             Counter32,
            tnSonetStatRxSESL            Counter32,
            tnSonetStatRxUASL            Counter32,
            tnSonetStatRxFCL             Counter32,
            tnSonetStatTxCVS             Counter32,
            tnSonetStatTxESS             Counter32,
            tnSonetStatTxSESS            Counter32,
            tnSonetStatTxSEFSS           Counter32,
            tnSonetStatTxCVL             Counter32,
            tnSonetStatTxESL             Counter32,
            tnSonetStatTxSESL            Counter32,
            tnSonetStatTxUASL            Counter32,
            tnSonetStatTxFCL             Counter32,
            tnSonetStatRxUASS            Counter32,
            tnSonetStatTxUASS            Counter32,
--            obsolete
--            tnSonetStatRxCVS15MinTr      Counter32,
--            tnSonetStatRxESS15MinTr      Counter32,
--            tnSonetStatRxSESS15MinTr     Counter32,
--            tnSonetStatRxSEFSS15MinTr    Counter32,
--            tnSonetStatRxCVL15MinTr      Counter32,
--            tnSonetStatRxESL15MinTr      Counter32,
--            tnSonetStatRxSESL15MinTr     Counter32,
--            tnSonetStatRxUASL15MinTr     Counter32,
--            tnSonetStatRxFCL15MinTr      Counter32,
--            tnSonetStatTxCVS15MinTr      Counter32,
--            tnSonetStatTxESS15MinTr      Counter32,
--            tnSonetStatTxSESS15MinTr     Counter32,
--            tnSonetStatTxSEFSS15MinTr    Counter32,
--            tnSonetStatTxCVL15MinTr      Counter32,
--            tnSonetStatTxESL15MinTr      Counter32,
--            tnSonetStatTxSESL15MinTr     Counter32,
--            tnSonetStatTxUASL15MinTr     Counter32,
--            tnSonetStatTxFCL15MinTr      Counter32,
--            tnSonetStatRxUASS15MinTr     Counter32,
--            tnSonetStatTxUASS15MinTr     Counter32,
--            tnSonetStatRxCVS1DayTr       Counter32,
--            tnSonetStatRxESS1DayTr       Counter32,
--            tnSonetStatRxSESS1DayTr      Counter32,
--            tnSonetStatRxSEFSS1DayTr     Counter32,
--            tnSonetStatRxCVL1DayTr       Counter32,
--            tnSonetStatRxESL1DayTr       Counter32,
--            tnSonetStatRxSESL1DayTr      Counter32,
--            tnSonetStatRxUASL1DayTr      Counter32,
--            tnSonetStatRxFCL1DayTr       Counter32,
--            tnSonetStatTxCVS1DayTr       Counter32,
--            tnSonetStatTxESS1DayTr       Counter32,
--            tnSonetStatTxSESS1DayTr      Counter32,
--            tnSonetStatTxSEFSS1DayTr     Counter32,
--            tnSonetStatTxCVL1DayTr       Counter32,
--            tnSonetStatTxESL1DayTr       Counter32,
--            tnSonetStatTxSESL1DayTr      Counter32,
--            tnSonetStatTxUASL1DayTr      Counter32,
--            tnSonetStatTxFCL1DayTr       Counter32,
--            tnSonetStatRxUASS1DayTr      Counter32,
--            tnSonetStatTxUASS1DayTr      Counter32,
--            tnSonetStatRxCVS15MinRtr     Counter32,
--            tnSonetStatRxESS15MinRtr     Counter32,
--            tnSonetStatRxSESS15MinRtr    Counter32,
--            tnSonetStatRxSEFSS15MinRtr   Counter32,
--            tnSonetStatRxCVL15MinRtr     Counter32,
--            tnSonetStatRxESL15MinRtr     Counter32,
--            tnSonetStatRxSESL15MinRtr    Counter32,
--            tnSonetStatRxUASL15MinRtr    Counter32,
--            tnSonetStatRxFCL15MinRtr     Counter32,
--            tnSonetStatTxCVS15MinRtr     Counter32,
--            tnSonetStatTxESS15MinRtr     Counter32,
--            tnSonetStatTxSESS15MinRtr    Counter32,
--            tnSonetStatTxSEFSS15MinRtr   Counter32,
--            tnSonetStatTxCVL15MinRtr     Counter32,
--            tnSonetStatTxESL15MinRtr     Counter32,
--            tnSonetStatTxSESL15MinRtr    Counter32,
--            tnSonetStatTxUASL15MinRtr    Counter32,
--            tnSonetStatTxFCL15MinRtr     Counter32,
--            tnSonetStatRxUASS15MinRtr    Counter32,
--            tnSonetStatTxUASS15MinRtr    Counter32,
            tnSonetStatRxFECVL           Counter32,
            tnSonetStatRxFEESL           Counter32,
            tnSonetStatRxFESESL          Counter32,
            tnSonetStatRxFEUASL          Counter32
--            obsolete
--            tnSonetStatRxFECVL15MinTr    Counter32,
--            tnSonetStatRxFEESL15MinTr    Counter32,
--            tnSonetStatRxFESESL15MinTr   Counter32,
--            tnSonetStatRxFEUASL15MinTr   Counter32,
--            tnSonetStatRxFECVL1DayTr     Counter32,
--            tnSonetStatRxFEESL1DayTr     Counter32,
--            tnSonetStatRxFESESL1DayTr    Counter32,
--            tnSonetStatRxFEUASL1DayTr    Counter32,
--            tnSonetStatRxFECVL15MinRtr   Counter32,
--            tnSonetStatRxFEESL15MinRtr   Counter32,
--            tnSonetStatRxFESESL15MinRtr  Counter32,
--            tnSonetStatRxFEUASL15MinRtr  Counter32
        }

    tnSonetStatsBin OBJECT-TYPE
        SYNTAX      TnStatsBinType
        MAX-ACCESS  not-accessible
        STATUS      current
        DESCRIPTION "The bin number, starting with bin 0."
        ::= { tnSonetStatsEntry 1 }

    tnSonetStatsBinStatus OBJECT-TYPE
        SYNTAX      TnStatsBinStatus
        MAX-ACCESS  read-only
        STATUS      current
        DESCRIPTION "This attribute indicates the validity of the bin."
        ::= { tnSonetStatsEntry 2 }

    tnSonetStatsStartTime OBJECT-TYPE
        SYNTAX      DateAndTime
        MAX-ACCESS  read-only
        STATUS      current
        DESCRIPTION "This attribute is the bin collection start date
                     and time."
        ::= { tnSonetStatsEntry 3 }

    tnSonetStatRxCVS OBJECT-TYPE
        SYNTAX      Counter32
        MAX-ACCESS  read-only
        STATUS      current
        DESCRIPTION "Coding violation - section. Provides a count of
                     the number of B1 violations."
        ::= { tnSonetStatsEntry 4 }

    tnSonetStatRxESS OBJECT-TYPE
        SYNTAX      Counter32
        MAX-ACCESS  read-only
        STATUS      current
        DESCRIPTION "Errored second - section. Provides a count of
                     the number of one second intervals in which
                     any of the following conditions are true:

                     - at least one B1 BIP-8 error was detected.
                     - a loss of signal (LOS) defect was present.
                     - a severely errored frame (SEF) defect was
                       present."
        ::= { tnSonetStatsEntry 5 }

    tnSonetStatRxSESS OBJECT-TYPE
        SYNTAX      Counter32
        MAX-ACCESS  read-only
        STATUS      current
        DESCRIPTION "Severely errored second - section. Provides a
                     count of the number of one second intervals in
                     which any of the following conditions are true:

                     - the number of section layer BIP errors detected
                       exceeded the value defined in GR-253-CORE.
                     - a loss of signal (LOS) defect was present.
                     - a severely errored frame (SEF) defect was
                       present."
        ::= { tnSonetStatsEntry 6 }

    tnSonetStatRxSEFSS OBJECT-TYPE
        SYNTAX      Counter32
        MAX-ACCESS  read-only
        STATUS      current
        DESCRIPTION "Severely errored second - section. Provides a
                     count of the number of one second intervals in
                     which any of the following conditions are true:

                     - the number of section layer BIP errors detected
                       exceeded the value defined in GR-253-CORE.
                     - a loss of signal (LOS) defect was present.
                     - a severely errored frame (SEF) defect was
                       present."
        ::= { tnSonetStatsEntry 7 }

    tnSonetStatRxCVL OBJECT-TYPE
        SYNTAX      Counter32
        MAX-ACCESS  read-only
        STATUS      current
        DESCRIPTION "Coding violation - line. Provides a count of
                     the number of B2 BIP violations."
        ::= { tnSonetStatsEntry 8 }

    tnSonetStatRxESL OBJECT-TYPE
        SYNTAX      Counter32
        MAX-ACCESS  read-only
        STATUS      current
        DESCRIPTION "Errored second - line. Provides a count of the
                     number of one second intervals in which any
                     of the following conditions are true:

                     - at least one B2 BIP error was detected.
                     - an alarm indicating signal (AIS-L) defect
                       was present."
        ::= { tnSonetStatsEntry 9 }

    tnSonetStatRxSESL OBJECT-TYPE
        SYNTAX      Counter32
        MAX-ACCESS  read-only
        STATUS      current
        DESCRIPTION "Severely errored second - line. Provides a
                     count of the number of one second intervals
                     in which any of the following conditions are
                     true:

                     - the number of line layer B2 errors detected
                       exceeded the value defined in GR-253-CORE.
                     - an alarm indicating signal (AIS-L) defect
                       was present."
        ::= { tnSonetStatsEntry 10 }

    tnSonetStatRxUASL OBJECT-TYPE
        SYNTAX      Counter32
        MAX-ACCESS  read-only
        STATUS      current
        DESCRIPTION "Unavailable second - line. Provides a count
                     of the number of seconds that a line is
                     unavailable. A line is deemed to be unavailable
                     when 10 consecutive severely errored seconds
                     (SESs) are detected. The period of
                     unavailability begins at the onset the 10
                     consecutive SESs (back in time). Availability
                     is declared after a period of 10 consecutive
                     non-SESs. The period of availability begins
                     at the onset of the 10 consecutive
                     non-SESs (back in time)."
        ::= { tnSonetStatsEntry 11 }

    tnSonetStatRxFCL OBJECT-TYPE
        SYNTAX      Counter32
        MAX-ACCESS  read-only
        STATUS      current
        DESCRIPTION "Failure count - line. Provides a count of the
                     number of line failures. A failure event begins
                     when a AIS-L failure is declared and ends when
                     the failure is cleared. A failure event that
                     begins in one period and ends in another period
                     is counted only in the period where it begins."
        ::= { tnSonetStatsEntry 12 }

    tnSonetStatTxCVS OBJECT-TYPE
        SYNTAX      Counter32
        MAX-ACCESS  read-only
        STATUS      current
        DESCRIPTION "Coding violation - section. Provides a count of
                     the number of B1 violations."
        ::= { tnSonetStatsEntry 13 }

    tnSonetStatTxESS OBJECT-TYPE
        SYNTAX      Counter32
        MAX-ACCESS  read-only
        STATUS      current
        DESCRIPTION "Errored second - section. Provides a count of
                     the number of one second intervals in which
                     any of the following conditions are true:

                     - at least one B1 BIP-8 error was detected.
                     - a loss of signal (LOS) defect was present.
                     - a severely errored frame (SEF) defect was
                       present."
        ::= { tnSonetStatsEntry 14 }

    tnSonetStatTxSESS OBJECT-TYPE
        SYNTAX      Counter32
        MAX-ACCESS  read-only
        STATUS      current
        DESCRIPTION "Severely errored second - section. Provides a
                     count of the number of one second intervals in
                     which any of the following conditions are true:

                     - the number of section layer BIP errors detected
                       exceeded the value defined in GR-253-CORE.
                     - a loss of signal (LOS) defect was present.
                     - a severely errored frame (SEF) defect was
                       present."
        ::= { tnSonetStatsEntry 15 }

    tnSonetStatTxSEFSS OBJECT-TYPE
        SYNTAX      Counter32
        MAX-ACCESS  read-only
        STATUS      current
        DESCRIPTION "Severely errored frame second - section.
                     Provides a count of the number of one second
                     intervals in which any of the following
                     conditions are true:

                     - a loss of frame (LOF) defect was present.
                     - a severely errored frame (SEF) defect was
                       present."
        ::= { tnSonetStatsEntry 16 }

    tnSonetStatTxCVL OBJECT-TYPE
        SYNTAX      Counter32
        MAX-ACCESS  read-only
        STATUS      current
        DESCRIPTION "Coding violation - line. Provides a count of
                     the number of B2 BIP violations."
        ::= { tnSonetStatsEntry 17 }

    tnSonetStatTxESL OBJECT-TYPE
        SYNTAX      Counter32
        MAX-ACCESS  read-only
        STATUS      current
        DESCRIPTION "Errored second - line. Provides a count of the
                     number of one second intervals in which any
                     of the following conditions are true:

                     - at least one B2 BIP error was detected.
                     - an alarm indicating signal (AIS-L) defect
                       was present."
        ::= { tnSonetStatsEntry 18 }

    tnSonetStatTxSESL OBJECT-TYPE
        SYNTAX      Counter32
        MAX-ACCESS  read-only
        STATUS      current
        DESCRIPTION "Severely errored second - line. Provides a
                     count of the number of one second intervals
                     in which any of the following conditions are
                     true:

                     - the number of line layer B2 errors detected
                       exceeded the value defined in GR-253-CORE.
                     - an alarm indicating signal (AIS-L) defect
                       was present."
        ::= { tnSonetStatsEntry 19 }

    tnSonetStatTxUASL OBJECT-TYPE
        SYNTAX      Counter32
        MAX-ACCESS  read-only
        STATUS      current
        DESCRIPTION "Unavailable second - line. Provides a count
                     of the number of seconds that a line is
                     unavailable. A line is deemed to be unavailable
                     when 10 consecutive severely errored seconds
                     (SESs) are detected. The period of
                     unavailability begins at the onset the 10
                     consecutive SESs (back in time). Availability
                     is declared after a period of 10 consecutive
                     non-SESs. The period of availability begins
                     at the onset of the 10 consecutive
                     non-SESs (back in time)."
        ::= { tnSonetStatsEntry 20 }

    tnSonetStatTxFCL OBJECT-TYPE
        SYNTAX      Counter32
        MAX-ACCESS  read-only
        STATUS      current
        DESCRIPTION "Failure count - line. Provides a count of the
                     number of line failures. A failure event begins
                     when a AIS-L failure is declared and ends when
                     the failure is cleared. A failure event that
                     begins in one period and ends in another period
                     is counted only in the period where it begins."
        ::= { tnSonetStatsEntry 21 }

    tnSonetStatRxUASS OBJECT-TYPE
        SYNTAX      Counter32
        MAX-ACCESS  read-only
        STATUS      current
        DESCRIPTION "Unavailable second - section. Provides a count
                     of the number of seconds that a section is
                     unavailable. A section is deemed to be unavailable
                     when 10 consecutive severely errored seconds
                     (SESs) are detected. The period of
                     unavailability begins at the onset the 10
                     consecutive SESs (back in time). Availability
                     is declared after a period of 10 consecutive
                     non-SESs. The period of availability begins
                     at the onset of the 10 consecutive
                     non-SESs (back in time)."
        ::= { tnSonetStatsEntry 22 }

    tnSonetStatTxUASS OBJECT-TYPE
        SYNTAX      Counter32
        MAX-ACCESS  read-only
        STATUS      current
        DESCRIPTION "Unavailable second - section. Provides a count
                     of the number of seconds that a section is
                     unavailable. A section is deemed to be unavailable
                     when 10 consecutive severely errored seconds
                     (SESs) are detected. The period of
                     unavailability begins at the onset the 10
                     consecutive SESs (back in time). Availability
                     is declared after a period of 10 consecutive
                     non-SESs. The period of availability begins
                     at the onset of the 10 consecutive
                     non-SESs (back in time)."
        ::= { tnSonetStatsEntry 23 }

--    obsolete
--    tnSonetStatRxCVS15MinTr    OBJECT-TYPE ::= { tnSonetStatsEntry 24 }
--    tnSonetStatRxESS15MinTr    OBJECT-TYPE ::= { tnSonetStatsEntry 25 }
--    tnSonetStatRxSESS15MinTr   OBJECT-TYPE ::= { tnSonetStatsEntry 26 }
--    tnSonetStatRxSEFSS15MinTr  OBJECT-TYPE ::= { tnSonetStatsEntry 27 }
--    tnSonetStatRxCVL15MinTr    OBJECT-TYPE ::= { tnSonetStatsEntry 28 }
--    tnSonetStatRxESL15MinTr    OBJECT-TYPE ::= { tnSonetStatsEntry 29 }
--    tnSonetStatRxSESL15MinTr   OBJECT-TYPE ::= { tnSonetStatsEntry 30 }
--    tnSonetStatRxUASL15MinTr   OBJECT-TYPE ::= { tnSonetStatsEntry 31 }
--    tnSonetStatRxFCL15MinTr    OBJECT-TYPE ::= { tnSonetStatsEntry 32 }
--    tnSonetStatTxCVS15MinTr    OBJECT-TYPE ::= { tnSonetStatsEntry 33 }
--    tnSonetStatTxESS15MinTr    OBJECT-TYPE ::= { tnSonetStatsEntry 34 }
--    tnSonetStatTxSESS15MinTr   OBJECT-TYPE ::= { tnSonetStatsEntry 35 }
--    tnSonetStatTxSEFSS15MinTr  OBJECT-TYPE ::= { tnSonetStatsEntry 36 }
--    tnSonetStatTxCVL15MinTr    OBJECT-TYPE ::= { tnSonetStatsEntry 37 }
--    tnSonetStatTxESL15MinTr    OBJECT-TYPE ::= { tnSonetStatsEntry 38 }
--    tnSonetStatTxSESL15MinTr   OBJECT-TYPE ::= { tnSonetStatsEntry 39 }
--    tnSonetStatTxUASL15MinTr   OBJECT-TYPE ::= { tnSonetStatsEntry 40 }
--    tnSonetStatTxFCL15MinTr    OBJECT-TYPE ::= { tnSonetStatsEntry 41 }
--    tnSonetStatRxUASS15MinTr   OBJECT-TYPE ::= { tnSonetStatsEntry 42 }
--    tnSonetStatTxUASS15MinTr   OBJECT-TYPE ::= { tnSonetStatsEntry 43 }
--    tnSonetStatRxCVS1DayTr     OBJECT-TYPE ::= { tnSonetStatsEntry 44 }
--    tnSonetStatRxESS1DayTr     OBJECT-TYPE ::= { tnSonetStatsEntry 45 }
--    tnSonetStatRxSESS1DayTr    OBJECT-TYPE ::= { tnSonetStatsEntry 46 }
--    tnSonetStatRxSEFSS1DayTr   OBJECT-TYPE ::= { tnSonetStatsEntry 47 }
--    tnSonetStatRxCVL1DayTr     OBJECT-TYPE ::= { tnSonetStatsEntry 48 }
--    tnSonetStatRxESL1DayTr     OBJECT-TYPE ::= { tnSonetStatsEntry 49 }
--    tnSonetStatRxSESL1DayTr    OBJECT-TYPE ::= { tnSonetStatsEntry 50 }
--    tnSonetStatRxUASL1DayTr    OBJECT-TYPE ::= { tnSonetStatsEntry 51 }
--    tnSonetStatRxFCL1DayTr     OBJECT-TYPE ::= { tnSonetStatsEntry 52 }
--    tnSonetStatTxCVS1DayTr     OBJECT-TYPE ::= { tnSonetStatsEntry 53 }
--    tnSonetStatTxESS1DayTr     OBJECT-TYPE ::= { tnSonetStatsEntry 54 }
--    tnSonetStatTxSESS1DayTr    OBJECT-TYPE ::= { tnSonetStatsEntry 55 }
--    tnSonetStatTxSEFSS1DayTr   OBJECT-TYPE ::= { tnSonetStatsEntry 56 }
--    tnSonetStatTxCVL1DayTr     OBJECT-TYPE ::= { tnSonetStatsEntry 57 }
--    tnSonetStatTxESL1DayTr     OBJECT-TYPE ::= { tnSonetStatsEntry 58 }
--    tnSonetStatTxSESL1DayTr    OBJECT-TYPE ::= { tnSonetStatsEntry 59 }
--    tnSonetStatTxUASL1DayTr    OBJECT-TYPE ::= { tnSonetStatsEntry 60 }
--    tnSonetStatTxFCL1DayTr     OBJECT-TYPE ::= { tnSonetStatsEntry 61 }
--    tnSonetStatRxUASS1DayTr    OBJECT-TYPE ::= { tnSonetStatsEntry 62 }
--    tnSonetStatTxUASS1DayTr    OBJECT-TYPE ::= { tnSonetStatsEntry 63 }
--    tnSonetStatRxCVS15MinRtr   OBJECT-TYPE ::= { tnSonetStatsEntry 64 }
--    tnSonetStatRxESS15MinRtr   OBJECT-TYPE ::= { tnSonetStatsEntry 65 }
--    tnSonetStatRxSESS15MinRtr  OBJECT-TYPE ::= { tnSonetStatsEntry 66 }
--    tnSonetStatRxSEFSS15MinRtr OBJECT-TYPE ::= { tnSonetStatsEntry 67 }
--    tnSonetStatRxCVL15MinRtr   OBJECT-TYPE ::= { tnSonetStatsEntry 68 }
--    tnSonetStatRxESL15MinRtr   OBJECT-TYPE ::= { tnSonetStatsEntry 69 }
--    tnSonetStatRxSESL15MinRtr  OBJECT-TYPE ::= { tnSonetStatsEntry 70 }
--    tnSonetStatRxUASL15MinRtr  OBJECT-TYPE ::= { tnSonetStatsEntry 71 }
--    tnSonetStatRxFCL15MinRtr   OBJECT-TYPE ::= { tnSonetStatsEntry 72 }
--    tnSonetStatTxCVS15MinRtr   OBJECT-TYPE ::= { tnSonetStatsEntry 73 }
--    tnSonetStatTxESS15MinRtr   OBJECT-TYPE ::= { tnSonetStatsEntry 74 }
--    tnSonetStatTxSESS15MinRtr  OBJECT-TYPE ::= { tnSonetStatsEntry 75 }
--    tnSonetStatTxSEFSS15MinRtr OBJECT-TYPE ::= { tnSonetStatsEntry 76 }
--    tnSonetStatTxCVL15MinRtr   OBJECT-TYPE ::= { tnSonetStatsEntry 77 }
--    tnSonetStatTxESL15MinRtr   OBJECT-TYPE ::= { tnSonetStatsEntry 78 }
--    tnSonetStatTxSESL15MinRtr  OBJECT-TYPE ::= { tnSonetStatsEntry 79 }
--    tnSonetStatTxUASL15MinRtr  OBJECT-TYPE ::= { tnSonetStatsEntry 80 }
--    tnSonetStatTxFCL15MinRtr   OBJECT-TYPE ::= { tnSonetStatsEntry 81 }
--    tnSonetStatRxUASS15MinRtr  OBJECT-TYPE ::= { tnSonetStatsEntry 82 }
--    tnSonetStatTxUASS15MinRtr  OBJECT-TYPE ::= { tnSonetStatsEntry 83 }

    tnSonetStatRxFECVL OBJECT-TYPE
        SYNTAX      Counter32
        MAX-ACCESS  read-only
        STATUS      current
        DESCRIPTION "Coding violation - line. Provides a count of
                     the number of Far End B2 BIP violations."
        ::= { tnSonetStatsEntry 84 }

    tnSonetStatRxFEESL OBJECT-TYPE
        SYNTAX      Counter32
        MAX-ACCESS  read-only
        STATUS      current
        DESCRIPTION "Errored second - line. Provides a count of the
                     number of error count in one second intervals."
        ::= { tnSonetStatsEntry 85 }

    tnSonetStatRxFESESL OBJECT-TYPE
        SYNTAX      Counter32
        MAX-ACCESS  read-only
        STATUS      current
        DESCRIPTION "Severely errored second - line."
        ::= { tnSonetStatsEntry 86 }

    tnSonetStatRxFEUASL OBJECT-TYPE
        SYNTAX      Counter32
        MAX-ACCESS  read-only
        STATUS      current
        DESCRIPTION "Unavailable second - line."
        ::= { tnSonetStatsEntry 87 }

--    obsolete
--    tnSonetStatRxFECVL15MinTr         OBJECT-TYPE ::= { tnSonetStatsEntry 88 }
--    tnSonetStatRxFEESL15MinTr         OBJECT-TYPE ::= { tnSonetStatsEntry 89 }
--    tnSonetStatRxFESESL15MinTr        OBJECT-TYPE ::= { tnSonetStatsEntry 90 }
--    tnSonetStatRxFEUASL15MinTr        OBJECT-TYPE ::= { tnSonetStatsEntry 91 }
--    tnSonetStatRxFECVL1DayTr          OBJECT-TYPE ::= { tnSonetStatsEntry 92 }
--    tnSonetStatRxFEESL1DayTr          OBJECT-TYPE ::= { tnSonetStatsEntry 93 }
--    tnSonetStatRxFESESL1DayTr         OBJECT-TYPE ::= { tnSonetStatsEntry 94 }
--    tnSonetStatRxFEUASL1DayTr         OBJECT-TYPE ::= { tnSonetStatsEntry 95 }
--    tnSonetStatRxFECVL15MinRtr        OBJECT-TYPE ::= { tnSonetStatsEntry 96 }
--    tnSonetStatRxFEESL15MinRtr        OBJECT-TYPE ::= { tnSonetStatsEntry 97 }
--    tnSonetStatRxFESESL15MinRtr       OBJECT-TYPE ::= { tnSonetStatsEntry 98 }
--    tnSonetStatRxFEUASL15MinRtr       OBJECT-TYPE ::= { tnSonetStatsEntry 99 }

--    tnDigitalWrapperStatsTotalMembers OBJECT-TYPE ::= { tnStatisticsGrouping 9 }
--    tnDigitalWrapperStatsTable        OBJECT-TYPE ::= { tnStatisticsGrouping 10 }
--    tnL1ProtStatsTotalMembers         OBJECT-TYPE ::= { tnStatisticsGrouping 11 }
--    tnL1ProtStatsTable                OBJECT-TYPE ::= { tnStatisticsGrouping 12 }

--------------------------------------------------------------------------------
-- Optical DC Power TX (OPT) Statistics Scalar
--------------------------------------------------------------------------------
    tnOptStatsTotalMembers OBJECT-TYPE
        SYNTAX      Integer32
        MAX-ACCESS  read-only
        STATUS      current
        DESCRIPTION "The total number of members in the OPT stats table."
        ::= { tnStatisticsGrouping 13 }

--------------------------------------------------------------------------------
-- Optical DC Power TX (OPT) Statistics Table
--------------------------------------------------------------------------------
    tnOptStatsTable OBJECT-TYPE
        SYNTAX      SEQUENCE OF TnOptStatsEntry
        MAX-ACCESS  not-accessible
        STATUS      current
        DESCRIPTION "."
        ::= { tnStatisticsGrouping 14 }

    tnOptStatsEntry OBJECT-TYPE
        SYNTAX      TnOptStatsEntry
        MAX-ACCESS  not-accessible
        STATUS      current
        DESCRIPTION "."
        INDEX   { ifIndex,
                  tnStatsInterval,
                  tnOptStatsBin }
        ::= { tnOptStatsTable 1 }

    TnOptStatsEntry ::=
        SEQUENCE {
            tnOptStatsBin              TnStatsBinType,
            tnOptStatsBinStatus        TnStatsBinStatus,
            tnOptStatsStartTime        DateAndTime,
            tnOptStatMinPower          Integer32,
            tnOptStatMaxPower          Integer32,
            tnOptStatAveragePower      Integer32,
            tnOptStatMinPowerTr        Integer32,
            tnOptStatMaxPowerTr        Integer32,
            tnOptStatMinPowerRtr       Integer32,
            tnOptStatMaxPowerRtr       Integer32
        }

    tnOptStatsBin OBJECT-TYPE
        SYNTAX      TnStatsBinType
        MAX-ACCESS  not-accessible
        STATUS      current
        DESCRIPTION "The bin number, starting with bin 0."
        ::= { tnOptStatsEntry 1 }

    tnOptStatsBinStatus OBJECT-TYPE
        SYNTAX      TnStatsBinStatus
        MAX-ACCESS  read-only
        STATUS      current
        DESCRIPTION "This attribute indicates the validity of the bin."
        ::= { tnOptStatsEntry 2 }

    tnOptStatsStartTime OBJECT-TYPE
        SYNTAX      DateAndTime
        MAX-ACCESS  read-only
        STATUS      current
        DESCRIPTION "This attribute is the bin collection start date
                     and time."
        ::= { tnOptStatsEntry 3 }

    tnOptStatMinPower OBJECT-TYPE
        SYNTAX      Integer32
        UNITS       "mBm"
        MAX-ACCESS  read-only
        STATUS      current
        DESCRIPTION "Minimum optical DC power in the TX direction (mBm)."
        ::= { tnOptStatsEntry 4 }

    tnOptStatMaxPower OBJECT-TYPE
        SYNTAX      Integer32
        UNITS       "mBm"
        MAX-ACCESS  read-only
        STATUS      current
        DESCRIPTION "Maximum optical DC power in the TX direction (mBm)."
        ::= { tnOptStatsEntry 5 }

    tnOptStatAveragePower OBJECT-TYPE
        SYNTAX      Integer32
        UNITS       "mBm"
        MAX-ACCESS  read-only
        STATUS      current
        DESCRIPTION "Average optical DC power in the TX direction (mBm)."
        ::= { tnOptStatsEntry 6 }

    tnOptStatMinPowerTr OBJECT-TYPE
        SYNTAX      Integer32
        UNITS       "mBm"
        MAX-ACCESS  read-only
        STATUS      current
        DESCRIPTION "Low threshold for 15 minute and 1 day for minimum
                     optical DC power in the TX direction (mBm)."
        ::= { tnOptStatsEntry 7 }

    tnOptStatMaxPowerTr OBJECT-TYPE
        SYNTAX      Integer32
        UNITS       "mBm"
        MAX-ACCESS  read-only
        STATUS      current
        DESCRIPTION "High threshold for 15 minute and 1 day for maximum
                     optical DC power in the TX direction (mBm)."
        ::= { tnOptStatsEntry 8 }

    tnOptStatMinPowerRtr OBJECT-TYPE
        SYNTAX      Integer32
        UNITS       "mBm"
        MAX-ACCESS  read-only
        STATUS      current
        DESCRIPTION "Low reset threshold for 15 minute and 1 day for
                     minimum optical DC power in the TX direction (mBm)."
        ::= { tnOptStatsEntry 9 }

    tnOptStatMaxPowerRtr OBJECT-TYPE
        SYNTAX      Integer32
        UNITS       "mBm"
        MAX-ACCESS  read-only
        STATUS      current
        DESCRIPTION "High reset threshold for 15 minute and 1 day for
                     maximum optical DC power in the TX direction (mBm)."
        ::= { tnOptStatsEntry 10 }

--------------------------------------------------------------------------------
-- Optical DC Power RX (OPR) Statistics Scalar
--------------------------------------------------------------------------------
    tnOprStatsTotalMembers OBJECT-TYPE
        SYNTAX      Integer32
        MAX-ACCESS  read-only
        STATUS      current
        DESCRIPTION "The total number of members in the OPR stats table."
        ::= { tnStatisticsGrouping 15 }

--------------------------------------------------------------------------------
-- Optical DC Power RX (OPR) Statistics Table
--------------------------------------------------------------------------------
    tnOprStatsTable OBJECT-TYPE
        SYNTAX      SEQUENCE OF TnOprStatsEntry
        MAX-ACCESS  not-accessible
        STATUS      current
        DESCRIPTION "."
        ::= { tnStatisticsGrouping 16 }

    tnOprStatsEntry OBJECT-TYPE
        SYNTAX      TnOprStatsEntry
        MAX-ACCESS  not-accessible
        STATUS      current
        DESCRIPTION "."
        INDEX   { ifIndex,
                  tnStatsInterval,
                  tnOprStatsBin }
        ::= { tnOprStatsTable 1 }

    TnOprStatsEntry ::=
        SEQUENCE {
            tnOprStatsBin              TnStatsBinType,
            tnOprStatsBinStatus        TnStatsBinStatus,
            tnOprStatsStartTime        DateAndTime,
            tnOprStatMinPower          Integer32,
            tnOprStatMaxPower          Integer32,
            tnOprStatAveragePower      Integer32,
            tnOprStatMinPowerTr        Integer32,
            tnOprStatMaxPowerTr        Integer32,
            tnOprStatMinPowerRtr       Integer32,
            tnOprStatMaxPowerRtr       Integer32
        }

    tnOprStatsBin OBJECT-TYPE
        SYNTAX      TnStatsBinType
        MAX-ACCESS  not-accessible
        STATUS      current
        DESCRIPTION "The bin number, starting with bin 0."
        ::= { tnOprStatsEntry 1 }

    tnOprStatsBinStatus OBJECT-TYPE
        SYNTAX      TnStatsBinStatus
        MAX-ACCESS  read-only
        STATUS      current
        DESCRIPTION "This attribute indicates the validity of the bin."
        ::= { tnOprStatsEntry 2 }

    tnOprStatsStartTime OBJECT-TYPE
        SYNTAX      DateAndTime
        MAX-ACCESS  read-only
        STATUS      current
        DESCRIPTION "This attribute is the bin collection start date
                     and time."
        ::= { tnOprStatsEntry 3 }

    tnOprStatMinPower OBJECT-TYPE
        SYNTAX      Integer32
        UNITS       "mBm"
        MAX-ACCESS  read-only
        STATUS      current
        DESCRIPTION "Minimum optical DC power in the RX direction (mBm)."
        ::= { tnOprStatsEntry 4 }

    tnOprStatMaxPower OBJECT-TYPE
        SYNTAX      Integer32
        UNITS       "mBm"
        MAX-ACCESS  read-only
        STATUS      current
        DESCRIPTION "Maximum optical DC power in the RX direction (mBm)."
        ::= { tnOprStatsEntry 5 }

    tnOprStatAveragePower OBJECT-TYPE
        SYNTAX      Integer32
        UNITS       "mBm"
        MAX-ACCESS  read-only
        STATUS      current
        DESCRIPTION "Average optical DC power in the RX direction (mBm)."
        ::= { tnOprStatsEntry 6 }

    tnOprStatMinPowerTr OBJECT-TYPE
        SYNTAX      Integer32
        UNITS       "mBm"
        MAX-ACCESS  read-only
        STATUS      current
        DESCRIPTION "Low threshold for 15 minute and 1 day for minimum
                     optical DC power in the RX direction (mBm)."
        ::= { tnOprStatsEntry 7 }

    tnOprStatMaxPowerTr OBJECT-TYPE
        SYNTAX      Integer32
        UNITS       "mBm"
        MAX-ACCESS  read-only
        STATUS      current
        DESCRIPTION "High threshold for 15 minute and 1 day for maximum
                     optical DC power in the RX direction (mBm)."
        ::= { tnOprStatsEntry 8 }

    tnOprStatMinPowerRtr OBJECT-TYPE
        SYNTAX      Integer32
        UNITS       "mBm"
        MAX-ACCESS  read-only
        STATUS      current
        DESCRIPTION "Low reset threshold for 15 minute and 1 day for
                     minimum optical DC power in the RX direction (mBm)."
        ::= { tnOprStatsEntry 9 }

    tnOprStatMaxPowerRtr OBJECT-TYPE
        SYNTAX      Integer32
        UNITS       "mBm"
        MAX-ACCESS  read-only
        STATUS      current
        DESCRIPTION "High reset threshold for 15 minute and 1 day for
                     maximum optical DC power in the RX direction (mBm)."
        ::= { tnOprStatsEntry 10 }

--------------------------------------------------------------------------------
-- Optical DC Power Out (OPOUT) Statistics Scalar
--------------------------------------------------------------------------------
    tnOpOutStatsTotalMembers OBJECT-TYPE
        SYNTAX      Integer32
        MAX-ACCESS  read-only
        STATUS      current
        DESCRIPTION "The total number of members in the OPOUT stats table."
        ::= { tnStatisticsGrouping 17 }

--------------------------------------------------------------------------------
-- Optical DC Power Out (OPOUT) Statistics Table
--------------------------------------------------------------------------------
    tnOpOutStatsTable OBJECT-TYPE
        SYNTAX      SEQUENCE OF TnOpOutStatsEntry
        MAX-ACCESS  not-accessible
        STATUS      current
        DESCRIPTION "."
        ::= { tnStatisticsGrouping 18 }

    tnOpOutStatsEntry OBJECT-TYPE
        SYNTAX      TnOpOutStatsEntry
        MAX-ACCESS  not-accessible
        STATUS      current
        DESCRIPTION "."
        INDEX   { ifIndex,
                  tnStatsInterval,
                  tnOpOutStatsBin }
        ::= { tnOpOutStatsTable 1 }

    TnOpOutStatsEntry ::=
        SEQUENCE {
            tnOpOutStatsBin         TnStatsBinType,
            tnOpOutStatsBinStatus   TnStatsBinStatus,
            tnOpOutStatsStartTime   DateAndTime,
            tnOpOutStatMinPower     Integer32,
            tnOpOutStatMaxPower     Integer32,
            tnOpOutStatAveragePower Integer32
        }

    tnOpOutStatsBin OBJECT-TYPE
        SYNTAX      TnStatsBinType
        MAX-ACCESS  not-accessible
        STATUS      current
        DESCRIPTION "The bin number, starting with bin 0."
        ::= { tnOpOutStatsEntry 1 }

    tnOpOutStatsBinStatus OBJECT-TYPE
        SYNTAX      TnStatsBinStatus
        MAX-ACCESS  read-only
        STATUS      current
        DESCRIPTION "This attribute indicates the validity of the bin."
        ::= { tnOpOutStatsEntry 2 }

    tnOpOutStatsStartTime OBJECT-TYPE
        SYNTAX      DateAndTime
        MAX-ACCESS  read-only
        STATUS      current
        DESCRIPTION "This attribute is the bin collection start date
                     and time."
        ::= { tnOpOutStatsEntry 3 }

    tnOpOutStatMinPower OBJECT-TYPE
        SYNTAX      Integer32
        UNITS       "mBm"
        MAX-ACCESS  read-only
        STATUS      current
        DESCRIPTION "Minimum optical DC power in the
                     Out direction (mBm)."
        ::= { tnOpOutStatsEntry 4 }

    tnOpOutStatMaxPower OBJECT-TYPE
        SYNTAX      Integer32
        UNITS       "mBm"
        MAX-ACCESS  read-only
        STATUS      current
        DESCRIPTION "Maximum optical DC power in the
                     Out direction (mBm)."
        ::= { tnOpOutStatsEntry 5 }

    tnOpOutStatAveragePower OBJECT-TYPE
        SYNTAX      Integer32
        UNITS       "mBm"
        MAX-ACCESS  read-only
        STATUS      current
        DESCRIPTION "Average optical DC power in the
                     Out direction (mBm)."
        ::= { tnOpOutStatsEntry 6 }

--------------------------------------------------------------------------------
-- Optical DC Power In (OPIN) Statistics Scalar
--------------------------------------------------------------------------------
    tnOpInStatsTotalMembers OBJECT-TYPE
        SYNTAX      Integer32
        MAX-ACCESS  read-only
        STATUS      current
        DESCRIPTION "The total number of members in the OPIN stats table."
        ::= { tnStatisticsGrouping 19 }

--------------------------------------------------------------------------------
-- Optical DC Power In (OPIN) Statistics Table
--------------------------------------------------------------------------------
    tnOpInStatsTable OBJECT-TYPE
        SYNTAX      SEQUENCE OF TnOpInStatsEntry
        MAX-ACCESS  not-accessible
        STATUS      current
        DESCRIPTION "."
        ::= { tnStatisticsGrouping 20 }

    tnOpInStatsEntry OBJECT-TYPE
        SYNTAX      TnOpInStatsEntry
        MAX-ACCESS  not-accessible
        STATUS      current
        DESCRIPTION "."
        INDEX   { ifIndex,
                  tnStatsInterval,
                  tnOpInStatsBin }
        ::= { tnOpInStatsTable 1 }

    TnOpInStatsEntry ::=
        SEQUENCE {
            tnOpInStatsBin         TnStatsBinType,
            tnOpInStatsBinStatus   TnStatsBinStatus,
            tnOpInStatsStartTime   DateAndTime,
            tnOpInStatMinPower     Integer32,
            tnOpInStatMaxPower     Integer32,
            tnOpInStatAveragePower Integer32
        }

    tnOpInStatsBin OBJECT-TYPE
        SYNTAX      TnStatsBinType
        MAX-ACCESS  not-accessible
        STATUS      current
        DESCRIPTION "The bin number, starting with bin 0."
        ::= { tnOpInStatsEntry 1 }

    tnOpInStatsBinStatus OBJECT-TYPE
        SYNTAX      TnStatsBinStatus
        MAX-ACCESS  read-only
        STATUS      current
        DESCRIPTION "This attribute indicates the validity of the bin."
        ::= { tnOpInStatsEntry 2 }

    tnOpInStatsStartTime OBJECT-TYPE
        SYNTAX      DateAndTime
        MAX-ACCESS  read-only
        STATUS      current
        DESCRIPTION "This attribute is the bin collection start date
                     and time."
        ::= { tnOpInStatsEntry 3 }

    tnOpInStatMinPower OBJECT-TYPE
        SYNTAX      Integer32
        UNITS       "mBm"
        MAX-ACCESS  read-only
        STATUS      current
        DESCRIPTION "Minimum optical DC power in the
                     In direction (mBm)."
        ::= { tnOpInStatsEntry 4 }

    tnOpInStatMaxPower OBJECT-TYPE
        SYNTAX      Integer32
        UNITS       "mBm"
        MAX-ACCESS  read-only
        STATUS      current
        DESCRIPTION "Maximum optical DC power in the
                     In direction (mBm)."
        ::= { tnOpInStatsEntry 5 }

    tnOpInStatAveragePower OBJECT-TYPE
        SYNTAX      Integer32
        UNITS       "mBm"
        MAX-ACCESS  read-only
        STATUS      current
        DESCRIPTION "Average optical DC power in the
                     In direction (mBm)."
        ::= { tnOpInStatsEntry 6 }

--------------------------------------------------------------------------------
-- Optical WT Power Out (OPOCHOUT) Statistics Scalar
--------------------------------------------------------------------------------
    tnOpOchOutStatsTotalMembers OBJECT-TYPE
        SYNTAX      Integer32
        MAX-ACCESS  read-only
        STATUS      current
        DESCRIPTION "The total number of members in the OPOCHOUT stats table."
        ::= { tnStatisticsGrouping 21 }

--------------------------------------------------------------------------------
-- Optical WT Power Out (OPOCHOUT) Statistics Table
--------------------------------------------------------------------------------
    tnOpOchOutStatsTable OBJECT-TYPE
        SYNTAX      SEQUENCE OF TnOpOchOutStatsEntry
        MAX-ACCESS  not-accessible
        STATUS      current
        DESCRIPTION "."
        ::= { tnStatisticsGrouping 22 }

    tnOpOchOutStatsEntry OBJECT-TYPE
        SYNTAX      TnOpOchOutStatsEntry
        MAX-ACCESS  not-accessible
        STATUS      current
        DESCRIPTION "."
        INDEX   { ifIndex,
                  tnStatsInterval,
                  tnOpOchOutStatsBin,
                  tnOpticalStatsITUChannel }
        ::= { tnOpOchOutStatsTable 1 }

    TnOpOchOutStatsEntry ::=
        SEQUENCE {
            tnOpOchOutStatsBin         TnStatsBinType,
            tnOpOchOutStatsBinStatus   TnStatsBinStatus,
            tnOpOchOutStatsStartTime   DateAndTime,
            tnOpOchOutStatMinPower     Integer32,
            tnOpOchOutStatMaxPower     Integer32,
            tnOpOchOutStatAveragePower Integer32,
            tnOpOchOutStatWidth        Unsigned32
        }

    tnOpOchOutStatsBin OBJECT-TYPE
        SYNTAX      TnStatsBinType
        MAX-ACCESS  not-accessible
        STATUS      current
        DESCRIPTION "The bin number, starting with bin 0."
        ::= { tnOpOchOutStatsEntry 1 }

    tnOpOchOutStatsBinStatus OBJECT-TYPE
        SYNTAX      TnStatsBinStatus
        MAX-ACCESS  read-only
        STATUS      current
        DESCRIPTION "This attribute indicates the validity of the bin."
        ::= { tnOpOchOutStatsEntry 2 }

    tnOpOchOutStatsStartTime OBJECT-TYPE
        SYNTAX      DateAndTime
        MAX-ACCESS  read-only
        STATUS      current
        DESCRIPTION "This attribute is the bin collection start date
                     and time."
        ::= { tnOpOchOutStatsEntry 3 }

    tnOpOchOutStatMinPower OBJECT-TYPE
        SYNTAX      Integer32
        UNITS       "mBm"
        MAX-ACCESS  read-only
        STATUS      current
        DESCRIPTION "Minimum optical WT power in the
                     Out direction (mBm)."
        ::= { tnOpOchOutStatsEntry 4 }

    tnOpOchOutStatMaxPower OBJECT-TYPE
        SYNTAX      Integer32
        UNITS       "mBm"
        MAX-ACCESS  read-only
        STATUS      current
        DESCRIPTION "Maximum optical WT power in the
                     Out direction (mBm)."
        ::= { tnOpOchOutStatsEntry 5 }

    tnOpOchOutStatAveragePower OBJECT-TYPE
        SYNTAX      Integer32
        UNITS       "mBm"
        MAX-ACCESS  read-only
        STATUS      current
        DESCRIPTION "Average optical WT power in the
                     Out direction (mBm)."
        ::= { tnOpOchOutStatsEntry 6 }

    tnOpOchOutStatWidth OBJECT-TYPE
        SYNTAX         Unsigned32
        UNITS          "MHz"
        MAX-ACCESS     read-only
        STATUS         current
        DESCRIPTION    "Channel width."
        ::= { tnOpOchOutStatsEntry 7 }

--------------------------------------------------------------------------------
-- Optical WT Power In (OPOCHIN) Statistics Scalar
--------------------------------------------------------------------------------
    tnOpOchInStatsTotalMembers OBJECT-TYPE
        SYNTAX      Integer32
        MAX-ACCESS  read-only
        STATUS      current
        DESCRIPTION "The total number of members in the OPOCHIN stats table."
        ::= { tnStatisticsGrouping 23 }

--------------------------------------------------------------------------------
-- Optical WT Power In (OPOCHIN) Statistics Table
--------------------------------------------------------------------------------
    tnOpOchInStatsTable OBJECT-TYPE
        SYNTAX      SEQUENCE OF TnOpOchInStatsEntry
        MAX-ACCESS  not-accessible
        STATUS      current
        DESCRIPTION "."
        ::= { tnStatisticsGrouping 24 }

    tnOpOchInStatsEntry OBJECT-TYPE
        SYNTAX      TnOpOchInStatsEntry
        MAX-ACCESS  not-accessible
        STATUS      current
        DESCRIPTION "."
        INDEX   { ifIndex,
                  tnStatsInterval,
                  tnOpOchInStatsBin,
                  tnOpticalStatsITUChannel }
        ::= { tnOpOchInStatsTable 1 }

    TnOpOchInStatsEntry ::=
        SEQUENCE {
            tnOpOchInStatsBin         TnStatsBinType,
            tnOpOchInStatsBinStatus   TnStatsBinStatus,
            tnOpOchInStatsStartTime   DateAndTime,
            tnOpOchInStatMinPower     Integer32,
            tnOpOchInStatMaxPower     Integer32,
            tnOpOchInStatAveragePower Integer32,
            tnOpOchInStatWidth        Unsigned32
        }

    tnOpOchInStatsBin OBJECT-TYPE
        SYNTAX      TnStatsBinType
        MAX-ACCESS  not-accessible
        STATUS      current
        DESCRIPTION "The bin number, starting with bin 0."
        ::= { tnOpOchInStatsEntry 1 }

    tnOpOchInStatsBinStatus OBJECT-TYPE
        SYNTAX      TnStatsBinStatus
        MAX-ACCESS  read-only
        STATUS      current
        DESCRIPTION "This attribute indicates the validity of the bin."
        ::= { tnOpOchInStatsEntry 2 }

    tnOpOchInStatsStartTime OBJECT-TYPE
        SYNTAX      DateAndTime
        MAX-ACCESS  read-only
        STATUS      current
        DESCRIPTION "This attribute is the bin collection start date
                     and time."
        ::= { tnOpOchInStatsEntry 3 }

    tnOpOchInStatMinPower OBJECT-TYPE
        SYNTAX      Integer32
        UNITS       "mBm"
        MAX-ACCESS  read-only
        STATUS      current
        DESCRIPTION "Minimum optical WT power in the
                     In direction (mBm)."
        ::= { tnOpOchInStatsEntry 4 }

    tnOpOchInStatMaxPower OBJECT-TYPE
        SYNTAX      Integer32
        UNITS       "mBm"
        MAX-ACCESS  read-only
        STATUS      current
        DESCRIPTION "Maximum optical WT power in the
                     In direction (mBm)."
        ::= { tnOpOchInStatsEntry 5 }

    tnOpOchInStatAveragePower OBJECT-TYPE
        SYNTAX      Integer32
        UNITS       "mBm"
        MAX-ACCESS  read-only
        STATUS      current
        DESCRIPTION "Average optical WT power in the
                     In direction (mBm)."
        ::= { tnOpOchInStatsEntry 6 }

    tnOpOchInStatWidth OBJECT-TYPE
        SYNTAX         Unsigned32
        UNITS          "MHz"
        MAX-ACCESS     read-only
        STATUS         current
        DESCRIPTION    "Channel width."
        ::= { tnOpOchInStatsEntry 7 }

--------------------------------------------------------------------------------
-- SDH Statistics Scalar
--------------------------------------------------------------------------------
    tnSdhStatsTotalMembers OBJECT-TYPE
        SYNTAX      Integer32
        MAX-ACCESS  read-only
        STATUS      current
        DESCRIPTION "The total number of members in the SDH stats table."
        ::= { tnStatisticsGrouping 25 }

--------------------------------------------------------------------------------
-- SDH Statistics Table
--------------------------------------------------------------------------------
    tnSdhStatsTable OBJECT-TYPE
        SYNTAX      SEQUENCE OF TnSdhStatsEntry
        MAX-ACCESS  not-accessible
        STATUS      current
        DESCRIPTION "."
        ::= { tnStatisticsGrouping 26 }

    tnSdhStatsEntry OBJECT-TYPE
        SYNTAX      TnSdhStatsEntry
        MAX-ACCESS  not-accessible
        STATUS      current
        DESCRIPTION "."
        INDEX   { ifIndex,
                  tnStatsInterval,
                  tnSdhStatsBin }
        ::= { tnSdhStatsTable 1 }

    TnSdhStatsEntry ::=
        SEQUENCE {
            tnSdhStatsBin              TnStatsBinType,
            tnSdhStatsBinStatus        TnStatsBinStatus,
            tnSdhStatsStartTime        DateAndTime,
            tnSdhStatRxRSEB            Counter32,
            tnSdhStatRxRSES            Counter32,
            tnSdhStatRxRSSES           Counter32,
            tnSdhStatRxMSEB            Counter32,
            tnSdhStatRxMSES            Counter32,
            tnSdhStatRxMSSES           Counter32,
            tnSdhStatRxMSUAS           Counter32,
            tnSdhStatTxRSEB            Counter32,
            tnSdhStatTxRSES            Counter32,
            tnSdhStatTxRSSES           Counter32,
            tnSdhStatTxMSEB            Counter32,
            tnSdhStatTxMSES            Counter32,
            tnSdhStatTxMSSES           Counter32,
            tnSdhStatTxMSUAS           Counter32,
            tnSdhStatRxRSUAS           Counter32,
            tnSdhStatTxRSUAS           Counter32,
--            obsolete
--            tnSdhStatRxRSEB15MinTr     Counter32,
--            tnSdhStatRxRSES15MinTr     Counter32,
--            tnSdhStatRxRSSES15MinTr    Counter32,
--            tnSdhStatRxMSEB15MinTr     Counter32,
--            tnSdhStatRxMSES15MinTr     Counter32,
--            tnSdhStatRxMSSES15MinTr    Counter32,
--            tnSdhStatRxMSUAS15MinTr    Counter32,
--            tnSdhStatTxRSEB15MinTr     Counter32,
--            tnSdhStatTxRSES15MinTr     Counter32,
--            tnSdhStatTxRSSES15MinTr    Counter32,
--            tnSdhStatTxMSEB15MinTr     Counter32,
--            tnSdhStatTxMSES15MinTr     Counter32,
--            tnSdhStatTxMSSES15MinTr    Counter32,
--            tnSdhStatTxMSUAS15MinTr    Counter32,
--            tnSdhStatRxRSUAS15MinTr    Counter32,
--            tnSdhStatTxRSUAS15MinTr    Counter32,
--            tnSdhStatRxRSEB1DayTr      Counter32,
--            tnSdhStatRxRSES1DayTr      Counter32,
--            tnSdhStatRxRSSES1DayTr     Counter32,
--            tnSdhStatRxMSEB1DayTr      Counter32,
--            tnSdhStatRxMSES1DayTr      Counter32,
--            tnSdhStatRxMSSES1DayTr     Counter32,
--            tnSdhStatRxMSUAS1DayTr     Counter32,
--            tnSdhStatTxRSEB1DayTr      Counter32,
--            tnSdhStatTxRSES1DayTr      Counter32,
--            tnSdhStatTxRSSES1DayTr     Counter32,
--            tnSdhStatTxMSEB1DayTr      Counter32,
--            tnSdhStatTxMSES1DayTr      Counter32,
--            tnSdhStatTxMSSES1DayTr     Counter32,
--            tnSdhStatTxMSUAS1DayTr     Counter32,
--            tnSdhStatRxRSUAS1DayTr     Counter32,
--            tnSdhStatTxRSUAS1DayTr     Counter32,
--            tnSdhStatRxRSEB15MinRtr    Counter32,
--            tnSdhStatRxRSES15MinRtr    Counter32,
--            tnSdhStatRxRSSES15MinRtr   Counter32,
--            tnSdhStatRxMSEB15MinRtr    Counter32,
--            tnSdhStatRxMSES15MinRtr    Counter32,
--            tnSdhStatRxMSSES15MinRtr   Counter32,
--            tnSdhStatRxMSUAS15MinRtr   Counter32,
--            tnSdhStatTxRSEB15MinRtr    Counter32,
--            tnSdhStatTxRSES15MinRtr    Counter32,
--            tnSdhStatTxRSSES15MinRtr   Counter32,
--            tnSdhStatTxMSEB15MinRtr    Counter32,
--            tnSdhStatTxMSES15MinRtr    Counter32,
--            tnSdhStatTxMSSES15MinRtr   Counter32,
--            tnSdhStatTxMSUAS15MinRtr   Counter32,
--            tnSdhStatRxRSUAS15MinRtr   Counter32,
--            tnSdhStatTxRSUAS15MinRtr   Counter32,
            tnSdhStatRxMSFEEB          Counter32,
            tnSdhStatRxMSFEES          Counter32,
            tnSdhStatRxMSFESES         Counter32,
            tnSdhStatRxMSFEUAS         Counter32
--            obsolete
--            tnSdhStatRxMSFEEB15MinTr   Counter32,
--            tnSdhStatRxMSFEES15MinTr   Counter32,
--            tnSdhStatRxMSFESES15MinTr  Counter32,
--            tnSdhStatRxMSFEUAS15MinTr  Counter32,
--            tnSdhStatRxMSFEEB1DayTr    Counter32,
--            tnSdhStatRxMSFEES1DayTr    Counter32,
--            tnSdhStatRxMSFESES1DayTr   Counter32,
--            tnSdhStatRxMSFEUAS1DayTr   Counter32,
--            tnSdhStatRxMSFEEB15MinRtr  Counter32,
--            tnSdhStatRxMSFEES15MinRtr  Counter32,
--            tnSdhStatRxMSFESES15MinRtr Counter32,
--            tnSdhStatRxMSFEUAS15MinRtr Counter32
        }

    tnSdhStatsBin OBJECT-TYPE
        SYNTAX      TnStatsBinType
        MAX-ACCESS  not-accessible
        STATUS      current
        DESCRIPTION "The bin number, starting with bin 0."
        ::= { tnSdhStatsEntry 1 }

    tnSdhStatsBinStatus OBJECT-TYPE
        SYNTAX      TnStatsBinStatus
        MAX-ACCESS  read-only
        STATUS      current
        DESCRIPTION "This attribute indicates the validity of the bin."
        ::= { tnSdhStatsEntry 2 }

    tnSdhStatsStartTime OBJECT-TYPE
        SYNTAX      DateAndTime
        MAX-ACCESS  read-only
        STATUS      current
        DESCRIPTION "This attribute is the bin collection start date
                     and time."
        ::= { tnSdhStatsEntry 3 }

    tnSdhStatRxRSEB OBJECT-TYPE
        SYNTAX      Counter32
        MAX-ACCESS  read-only
        STATUS      current
        DESCRIPTION "Regenerator section - errored block. Provides
                     a count of the number of B1 violations."
        ::= { tnSdhStatsEntry 4 }

    tnSdhStatRxRSES OBJECT-TYPE
        SYNTAX      Counter32
        MAX-ACCESS  read-only
        STATUS      current
        DESCRIPTION "Regenerator section - errored second. Provides
                     a count of the number of one second intervals in
                     which any of the following conditions are true:

                     - at least one B1 BIP-8 error was detected.
                     - a loss of signal (LOS) defect was present.
                     - a severely errored frame (SEF) defect was
                       present."
        ::= { tnSdhStatsEntry 5 }

    tnSdhStatRxRSSES OBJECT-TYPE
        SYNTAX      Counter32
        MAX-ACCESS  read-only
        STATUS      current
        DESCRIPTION "Regenerator section - severely errored second.
                     Provides a count of the number of one second
                     intervals in which any of the following conditions
                     are true:

                     - the number of regenerator section layer BIP
                       errors detected exceeded the value defined in
                       GR-253-CORE.
                     - a loss of signal (LOS) defect was present.
                     - a severely errored frame (SEF) defect was
                       present."
        ::= { tnSdhStatsEntry 6 }

    tnSdhStatRxMSEB OBJECT-TYPE
        SYNTAX      Counter32
        MAX-ACCESS  read-only
        STATUS      current
        DESCRIPTION "Multiplex section - errored block. Provides a
                     count of the number of B2 BIP violations."
        ::= { tnSdhStatsEntry 7 }

    tnSdhStatRxMSES OBJECT-TYPE
        SYNTAX      Counter32
        MAX-ACCESS  read-only
        STATUS      current
        DESCRIPTION "Multiplex section - errored second. Provides
                     a count of the number of one second intervals
                     in which any of the following conditions are true:

                     - at least one B2 BIP error was detected.
                     - an alarm indicating signal (MS-AIS) defect
                       was present."
        ::= { tnSdhStatsEntry 8 }

    tnSdhStatRxMSSES OBJECT-TYPE
        SYNTAX      Counter32
        MAX-ACCESS  read-only
        STATUS      current
        DESCRIPTION "Multiplex section - severely errored second.
                     Provides a count of the number of one second
                     intervals in which any of the following
                     conditions are true:

                     - the number of multiplex section layer B2 errors
                       detected exceeded the value defined in
                       GR-253-CORE.
                     - an alarm indicating signal (MS-AIS) defect
                       was present."
        ::= { tnSdhStatsEntry 9 }

    tnSdhStatRxMSUAS OBJECT-TYPE
        SYNTAX      Counter32
        MAX-ACCESS  read-only
        STATUS      current
        DESCRIPTION "Multiplex section - unavailable second. Provides
                     a count of the number of seconds that a line is
                     unavailable. A multiplex section is deemed to be
                     unavailable when 10 consecutive severely errored
                     seconds (SESs) are detected. The period of
                     unavailability begins at the onset the 10
                     consecutive SESs (back in time). Availability
                     is declared after a period of 10 consecutive
                     non-SESs. The period of availability begins
                     at the onset of the 10 consecutive
                     non-SESs (back in time)."
        ::= { tnSdhStatsEntry 10 }

    tnSdhStatTxRSEB OBJECT-TYPE
        SYNTAX      Counter32
        MAX-ACCESS  read-only
        STATUS      current
        DESCRIPTION "Regenerator section - errored block. Provides a
                     count of the number of B1 violations."
        ::= { tnSdhStatsEntry 11 }

    tnSdhStatTxRSES OBJECT-TYPE
        SYNTAX      Counter32
        MAX-ACCESS  read-only
        STATUS      current
        DESCRIPTION "Regenerator section - errored second. Provides
                     a count of the number of one second intervals in
                     which any of the following conditions are true:

                     - at least one B1 BIP-8 error was detected.
                     - a loss of signal (LOS) defect was present.
                     - a severely errored frame (SEF) defect was
                       present."
        ::= { tnSdhStatsEntry 12 }

    tnSdhStatTxRSSES OBJECT-TYPE
        SYNTAX      Counter32
        MAX-ACCESS  read-only
        STATUS      current
        DESCRIPTION "Regenerator section - severely errored second.
                     Provides a count of the number of one second
                     intervals in which any of the following conditions
                     are true:

                     - the number of regenerator section layer BIP
                       errors detected exceeded the value defined in
                       GR-253-CORE.
                     - a loss of signal (LOS) defect was present.
                     - a severely errored frame (SEF) defect was
                       present."
        ::= { tnSdhStatsEntry 13 }

    tnSdhStatTxMSEB OBJECT-TYPE
        SYNTAX      Counter32
        MAX-ACCESS  read-only
        STATUS      current
        DESCRIPTION "Multiplex section - errored block. Provides a
                     count of the number of B2 BIP violations."
        ::= { tnSdhStatsEntry 14 }

    tnSdhStatTxMSES OBJECT-TYPE
        SYNTAX      Counter32
        MAX-ACCESS  read-only
        STATUS      current
        DESCRIPTION "Multiplex section - errored second. Provides
                     a count of the number of one second intervals
                     in which any of the following conditions are true:

                     - at least one B2 BIP error was detected.
                     - an alarm indicating signal (MS-AIS) defect
                       was present."
        ::= { tnSdhStatsEntry 15 }

    tnSdhStatTxMSSES OBJECT-TYPE
        SYNTAX      Counter32
        MAX-ACCESS  read-only
        STATUS      current
        DESCRIPTION "Multiplex section - severely errored second.
                     Provides a count of the number of one second
                     intervals in which any of the following
                     conditions are true:

                     - the number of multiplex section layer B2 errors
                       detected exceeded the value defined in
                       GR-253-CORE.
                     - an alarm indicating signal (MS-AIS) defect
                       was present."
        ::= { tnSdhStatsEntry 16 }

    tnSdhStatTxMSUAS OBJECT-TYPE
        SYNTAX      Counter32
        MAX-ACCESS  read-only
        STATUS      current
        DESCRIPTION "Multiplex section - unavailable second. Provides
                     a count of the number of seconds that a line is
                     unavailable. A multiplex section is deemed to be
                     unavailable when 10 consecutive severely errored
                     seconds (SESs) are detected. The period of
                     unavailability begins at the onset the 10
                     consecutive SESs (back in time). Availability
                     is declared after a period of 10 consecutive
                     non-SESs. The period of availability begins
                     at the onset of the 10 consecutive
                     non-SESs (back in time)."
        ::= { tnSdhStatsEntry 17 }

    tnSdhStatRxRSUAS OBJECT-TYPE
        SYNTAX      Counter32
        MAX-ACCESS  read-only
        STATUS      current
        DESCRIPTION "Regenerator section - unavailable second. Provides
                     a count of the number of seconds that a line is
                     unavailable. A regenerator section is deemed to be
                     unavailable when 10 consecutive severely errored
                     seconds (SESs) are detected. The period of
                     unavailability begins at the onset the 10
                     consecutive SESs (back in time). Availability
                     is declared after a period of 10 consecutive
                     non-SESs. The period of availability begins
                     at the onset of the 10 consecutive
                     non-SESs (back in time)."
        ::= { tnSdhStatsEntry 18 }

    tnSdhStatTxRSUAS OBJECT-TYPE
        SYNTAX      Counter32
        MAX-ACCESS  read-only
        STATUS      current
        DESCRIPTION "Regenerator section - unavailable second. Provides
                     a count of the number of seconds that a line is
                     unavailable. A regenerator section is deemed to be
                     unavailable when 10 consecutive severely errored
                     seconds (SESs) are detected. The period of
                     unavailability begins at the onset the 10
                     consecutive SESs (back in time). Availability
                     is declared after a period of 10 consecutive
                     non-SESs. The period of availability begins
                     at the onset of the 10 consecutive
                     non-SESs (back in time)."
        ::= { tnSdhStatsEntry 19 }

--    obsolete
--    tnSdhStatRxRSEB15MinTr   OBJECT-TYPE ::= { tnSdhStatsEntry 20 }
--    tnSdhStatRxRSES15MinTr   OBJECT-TYPE ::= { tnSdhStatsEntry 21 }
--    tnSdhStatRxRSSES15MinTr  OBJECT-TYPE ::= { tnSdhStatsEntry 22 }
--    tnSdhStatRxMSEB15MinTr   OBJECT-TYPE ::= { tnSdhStatsEntry 23 }
--    tnSdhStatRxMSES15MinTr   OBJECT-TYPE ::= { tnSdhStatsEntry 24 }
--    tnSdhStatRxMSSES15MinTr  OBJECT-TYPE ::= { tnSdhStatsEntry 25 }
--    tnSdhStatRxMSUAS15MinTr  OBJECT-TYPE ::= { tnSdhStatsEntry 26 }
--    tnSdhStatTxRSEB15MinTr   OBJECT-TYPE ::= { tnSdhStatsEntry 27 }
--    tnSdhStatTxRSES15MinTr   OBJECT-TYPE ::= { tnSdhStatsEntry 28 }
--    tnSdhStatTxRSSES15MinTr  OBJECT-TYPE ::= { tnSdhStatsEntry 29 }
--    tnSdhStatTxMSEB15MinTr   OBJECT-TYPE ::= { tnSdhStatsEntry 30 }
--    tnSdhStatTxMSES15MinTr   OBJECT-TYPE ::= { tnSdhStatsEntry 31 }
--    tnSdhStatTxMSSES15MinTr  OBJECT-TYPE ::= { tnSdhStatsEntry 32 }
--    tnSdhStatTxMSUAS15MinTr  OBJECT-TYPE ::= { tnSdhStatsEntry 33 }
--    tnSdhStatRxRSUAS15MinTr  OBJECT-TYPE ::= { tnSdhStatsEntry 34 }
--    tnSdhStatTxRSUAS15MinTr  OBJECT-TYPE ::= { tnSdhStatsEntry 35 }
--    tnSdhStatRxRSEB1DayTr    OBJECT-TYPE ::= { tnSdhStatsEntry 36 }
--    tnSdhStatRxRSES1DayTr    OBJECT-TYPE ::= { tnSdhStatsEntry 37 }
--    tnSdhStatRxRSSES1DayTr   OBJECT-TYPE ::= { tnSdhStatsEntry 38 }
--    tnSdhStatRxMSEB1DayTr    OBJECT-TYPE ::= { tnSdhStatsEntry 39 }
--    tnSdhStatRxMSES1DayTr    OBJECT-TYPE ::= { tnSdhStatsEntry 40 }
--    tnSdhStatRxMSSES1DayTr   OBJECT-TYPE ::= { tnSdhStatsEntry 41 }
--    tnSdhStatRxMSUAS1DayTr   OBJECT-TYPE ::= { tnSdhStatsEntry 42 }
--    tnSdhStatTxRSEB1DayTr    OBJECT-TYPE ::= { tnSdhStatsEntry 43 }
--    tnSdhStatTxRSES1DayTr    OBJECT-TYPE ::= { tnSdhStatsEntry 44 }
--    tnSdhStatTxRSSES1DayTr   OBJECT-TYPE ::= { tnSdhStatsEntry 45 }
--    tnSdhStatTxMSEB1DayTr    OBJECT-TYPE ::= { tnSdhStatsEntry 46 }
--    tnSdhStatTxMSES1DayTr    OBJECT-TYPE ::= { tnSdhStatsEntry 47 }
--    tnSdhStatTxMSSES1DayTr   OBJECT-TYPE ::= { tnSdhStatsEntry 48 }
--    tnSdhStatTxMSUAS1DayTr   OBJECT-TYPE ::= { tnSdhStatsEntry 49 }
--    tnSdhStatRxRSUAS1DayTr   OBJECT-TYPE ::= { tnSdhStatsEntry 50 }
--    tnSdhStatTxRSUAS1DayTr   OBJECT-TYPE ::= { tnSdhStatsEntry 51 }
--    tnSdhStatRxRSEB15MinRtr  OBJECT-TYPE ::= { tnSdhStatsEntry 52 }
--    tnSdhStatRxRSES15MinRtr  OBJECT-TYPE ::= { tnSdhStatsEntry 53 }
--    tnSdhStatRxRSSES15MinRtr OBJECT-TYPE ::= { tnSdhStatsEntry 54 }
--    tnSdhStatRxMSEB15MinRtr  OBJECT-TYPE ::= { tnSdhStatsEntry 55 }
--    tnSdhStatRxMSES15MinRtr  OBJECT-TYPE ::= { tnSdhStatsEntry 56 }
--    tnSdhStatRxMSSES15MinRtr OBJECT-TYPE ::= { tnSdhStatsEntry 57 }
--    tnSdhStatRxMSUAS15MinRtr OBJECT-TYPE ::= { tnSdhStatsEntry 58 }
--    tnSdhStatTxRSEB15MinRtr  OBJECT-TYPE ::= { tnSdhStatsEntry 59 }
--    tnSdhStatTxRSES15MinRtr  OBJECT-TYPE ::= { tnSdhStatsEntry 60 }
--    tnSdhStatTxRSSES15MinRtr OBJECT-TYPE ::= { tnSdhStatsEntry 61 }
--    tnSdhStatTxMSEB15MinRtr  OBJECT-TYPE ::= { tnSdhStatsEntry 62 }
--    tnSdhStatTxMSES15MinRtr  OBJECT-TYPE ::= { tnSdhStatsEntry 63 }
--    tnSdhStatTxMSSES15MinRtr OBJECT-TYPE ::= { tnSdhStatsEntry 64 }
--    tnSdhStatTxMSUAS15MinRtr OBJECT-TYPE ::= { tnSdhStatsEntry 65 }
--    tnSdhStatRxRSUAS15MinRtr OBJECT-TYPE ::= { tnSdhStatsEntry 66 }
--    tnSdhStatTxRSUAS15MinRtr OBJECT-TYPE ::= { tnSdhStatsEntry 67 }

    tnSdhStatRxMSFEEB OBJECT-TYPE
        SYNTAX      Counter32
        MAX-ACCESS  read-only
        STATUS      current
        DESCRIPTION "Multiplex section - errored block. Provides a
                     count of the number of B2 BIP violations."
        ::= { tnSdhStatsEntry 68 }

    tnSdhStatRxMSFEES OBJECT-TYPE
        SYNTAX      Counter32
        MAX-ACCESS  read-only
        STATUS      current
        DESCRIPTION "Multiplex section - errored second."
        ::= { tnSdhStatsEntry 69 }

    tnSdhStatRxMSFESES OBJECT-TYPE
        SYNTAX      Counter32
        MAX-ACCESS  read-only
        STATUS      current
        DESCRIPTION "Multiplex section - severely errored second."
        ::= { tnSdhStatsEntry 70 }

    tnSdhStatRxMSFEUAS OBJECT-TYPE
        SYNTAX      Counter32
        MAX-ACCESS  read-only
        STATUS      current
        DESCRIPTION "Multiplex section - unavailable second. Provides
                     a count of the number of seconds that a line is
                     unavailable."
        ::= { tnSdhStatsEntry 71 }

--    obsolete
--    tnSdhStatRxMSFEEB15MinTr        OBJECT-TYPE ::= { tnSdhStatsEntry 72 }
--    tnSdhStatRxMSFEES15MinTr        OBJECT-TYPE ::= { tnSdhStatsEntry 73 }
--    tnSdhStatRxMSFESES15MinTr       OBJECT-TYPE ::= { tnSdhStatsEntry 74 }
--    tnSdhStatRxMSFEUAS15MinTr       OBJECT-TYPE ::= { tnSdhStatsEntry 75 }
--    tnSdhStatRxMSFEEB1DayTr         OBJECT-TYPE ::= { tnSdhStatsEntry 76 }
--    tnSdhStatRxMSFEES1DayTr         OBJECT-TYPE ::= { tnSdhStatsEntry 77 }
--    tnSdhStatRxMSFESES1DayTr        OBJECT-TYPE ::= { tnSdhStatsEntry 78 }
--    tnSdhStatRxMSFEUAS1DayTr        OBJECT-TYPE ::= { tnSdhStatsEntry 79 }
--    tnSdhStatRxMSFEEB15MinRtr       OBJECT-TYPE ::= { tnSdhStatsEntry 80 }
--    tnSdhStatRxMSFEES15MinRtr       OBJECT-TYPE ::= { tnSdhStatsEntry 81 }
--    tnSdhStatRxMSFESES15MinRtr      OBJECT-TYPE ::= { tnSdhStatsEntry 82 }
--    tnSdhStatRxMSFEUAS15MinRtr      OBJECT-TYPE ::= { tnSdhStatsEntry 83 }

--    tnPathSummaryStatsTotalMembers  OBJECT-TYPE ::= { tnStatisticsGrouping 27 }
--    tnPathSummaryStatsTable         OBJECT-TYPE ::= { tnStatisticsGrouping 28 }
--    tnFibreChannelStatsTotalMembers OBJECT-TYPE ::= { tnStatisticsGrouping 29 }
--    tnFibreChannelStatsTable        OBJECT-TYPE ::= { tnStatisticsGrouping 30 }

--------------------------------------------------------------------------------
-- Physical Coding Sublayer (PCS) Statistics Scalar
--------------------------------------------------------------------------------
    tnPhyCodeSublayerStatsTotalMembers OBJECT-TYPE
        SYNTAX      Integer32
        MAX-ACCESS  read-only
        STATUS      current
        DESCRIPTION "The total number of members in the PCS stats table."
        ::= { tnStatisticsGrouping 31 }

--------------------------------------------------------------------------------
-- Physical Coding Sublayer (PCS) Statistics Table
--------------------------------------------------------------------------------
    tnPhyCodeSublayerStatsTable OBJECT-TYPE
        SYNTAX      SEQUENCE OF TnPhyCodeSublayerStatsEntry
        MAX-ACCESS  not-accessible
        STATUS      current
        DESCRIPTION "."
        ::= { tnStatisticsGrouping 32 }

    tnPhyCodeSublayerStatsEntry OBJECT-TYPE
        SYNTAX      TnPhyCodeSublayerStatsEntry
        MAX-ACCESS  not-accessible
        STATUS      current
        DESCRIPTION "."
        INDEX   { ifIndex,
                  tnStatsInterval,
                  tnPhyCodeSublayerStatsBin }
        ::= { tnPhyCodeSublayerStatsTable 1 }

    TnPhyCodeSublayerStatsEntry ::=
        SEQUENCE {
            tnPhyCodeSublayerStatsBin             TnStatsBinType,
            tnPhyCodeSublayerStatsBinStatus       TnStatsBinStatus,
            tnPhyCodeSublayerStatsStartTime       DateAndTime,
            tnPhyCodeSublayerStatRxCV             Counter32,
            tnPhyCodeSublayerStatRxES             Counter32,
            tnPhyCodeSublayerStatRxSES            Counter32,
            tnPhyCodeSublayerStatRxSEFS           Counter32,
            tnPhyCodeSublayerStatTxCV             Counter32,
            tnPhyCodeSublayerStatTxES             Counter32,
            tnPhyCodeSublayerStatTxSES            Counter32,
            tnPhyCodeSublayerStatTxSEFS           Counter32,
--            obsolete
--            tnPhyCodeSublayerStatRxCV15MinTr      Counter32,
--            tnPhyCodeSublayerStatRxES15MinTr      Counter32,
--            tnPhyCodeSublayerStatRxSES15MinTr     Counter32,
--            tnPhyCodeSublayerStatRxSEFS15MinTr    Counter32,
--            tnPhyCodeSublayerStatTxCV15MinTr      Counter32,
--            tnPhyCodeSublayerStatTxES15MinTr      Counter32,
--            tnPhyCodeSublayerStatTxSES15MinTr     Counter32,
--            tnPhyCodeSublayerStatTxSEFS15MinTr    Counter32,
--            tnPhyCodeSublayerStatRxCV1DayTr       Counter32,
--            tnPhyCodeSublayerStatRxES1DayTr       Counter32,
--            tnPhyCodeSublayerStatRxSES1DayTr      Counter32,
--            tnPhyCodeSublayerStatRxSEFS1DayTr     Counter32,
--            tnPhyCodeSublayerStatTxCV1DayTr       Counter32,
--            tnPhyCodeSublayerStatTxES1DayTr       Counter32,
--            tnPhyCodeSublayerStatTxSES1DayTr      Counter32,
--            tnPhyCodeSublayerStatTxSEFS1DayTr     Counter32,
--            tnPhyCodeSublayerStatRxCV15MinRtr     Counter32,
--            tnPhyCodeSublayerStatRxES15MinRtr     Counter32,
--            tnPhyCodeSublayerStatRxSES15MinRtr    Counter32,
--            tnPhyCodeSublayerStatRxSEFS15MinRtr   Counter32,
--            tnPhyCodeSublayerStatTxCV15MinRtr     Counter32,
--            tnPhyCodeSublayerStatTxES15MinRtr     Counter32,
--            tnPhyCodeSublayerStatTxSES15MinRtr    Counter32,
--            tnPhyCodeSublayerStatTxSEFS15MinRtr   Counter32,
            tnPhyCodeSublayerStatsRxBIP8          Counter32,
            tnPhyCodeSublayerStatsTxBIP8          Counter32,
            tnPhyCodeSublayerStatsRxUAS           Counter32,
            tnPhyCodeSublayerStatsTxUAS           Counter32
       }

    tnPhyCodeSublayerStatsBin OBJECT-TYPE
        SYNTAX      TnStatsBinType
        MAX-ACCESS  not-accessible
        STATUS      current
        DESCRIPTION "The bin number, starting with bin 0."
        ::= { tnPhyCodeSublayerStatsEntry 1 }

    tnPhyCodeSublayerStatsBinStatus OBJECT-TYPE
        SYNTAX      TnStatsBinStatus
        MAX-ACCESS  read-only
        STATUS      current
        DESCRIPTION "This attribute indicates the validity of the bin."
        ::= { tnPhyCodeSublayerStatsEntry 2 }

    tnPhyCodeSublayerStatsStartTime OBJECT-TYPE
        SYNTAX      DateAndTime
        MAX-ACCESS  read-only
        STATUS      current
        DESCRIPTION "This attribute is the bin collection start date
                     and time."
        ::= { tnPhyCodeSublayerStatsEntry 3 }

    tnPhyCodeSublayerStatRxCV OBJECT-TYPE
        SYNTAX      Counter32
        MAX-ACCESS  read-only
        STATUS      current
        DESCRIPTION "Coding violation."
        ::= { tnPhyCodeSublayerStatsEntry 4 }

    tnPhyCodeSublayerStatRxES OBJECT-TYPE
        SYNTAX      Counter32
        MAX-ACCESS  read-only
        STATUS      current
        DESCRIPTION "Errored second."
        ::= { tnPhyCodeSublayerStatsEntry 5 }

    tnPhyCodeSublayerStatRxSES OBJECT-TYPE
        SYNTAX      Counter32
        MAX-ACCESS  read-only
        STATUS      current
        DESCRIPTION "Severely errored second."
        ::= { tnPhyCodeSublayerStatsEntry 6 }

    tnPhyCodeSublayerStatRxSEFS OBJECT-TYPE
        SYNTAX      Counter32
        MAX-ACCESS  read-only
        STATUS      current
        DESCRIPTION "Severely errored frame second."
        ::= { tnPhyCodeSublayerStatsEntry 7 }

    tnPhyCodeSublayerStatTxCV OBJECT-TYPE
        SYNTAX      Counter32
        MAX-ACCESS  read-only
        STATUS      current
        DESCRIPTION "Coding violation."
        ::= { tnPhyCodeSublayerStatsEntry 8 }

    tnPhyCodeSublayerStatTxES OBJECT-TYPE
        SYNTAX      Counter32
        MAX-ACCESS  read-only
        STATUS      current
        DESCRIPTION "Errored second."
        ::= { tnPhyCodeSublayerStatsEntry 9 }

    tnPhyCodeSublayerStatTxSES OBJECT-TYPE
        SYNTAX      Counter32
        MAX-ACCESS  read-only
        STATUS      current
        DESCRIPTION "Severely errored second."
        ::= { tnPhyCodeSublayerStatsEntry 10 }

    tnPhyCodeSublayerStatTxSEFS OBJECT-TYPE
        SYNTAX      Counter32
        MAX-ACCESS  read-only
        STATUS      current
        DESCRIPTION "Severely errored frame second."
        ::= { tnPhyCodeSublayerStatsEntry 11 }

--    obsolete
--    tnPhyCodeSublayerStatRxCV15MinTr    OBJECT-TYPE ::= { tnPhyCodeSublayerStatsEntry 12 }
--    tnPhyCodeSublayerStatRxES15MinTr    OBJECT-TYPE ::= { tnPhyCodeSublayerStatsEntry 13 }
--    tnPhyCodeSublayerStatRxSES15MinTr   OBJECT-TYPE ::= { tnPhyCodeSublayerStatsEntry 14 }
--    tnPhyCodeSublayerStatRxSEFS15MinTr  OBJECT-TYPE ::= { tnPhyCodeSublayerStatsEntry 15 }
--    tnPhyCodeSublayerStatTxCV15MinTr    OBJECT-TYPE ::= { tnPhyCodeSublayerStatsEntry 16 }
--    tnPhyCodeSublayerStatTxES15MinTr    OBJECT-TYPE ::= { tnPhyCodeSublayerStatsEntry 17 }
--    tnPhyCodeSublayerStatTxSES15MinTr   OBJECT-TYPE ::= { tnPhyCodeSublayerStatsEntry 18 }
--    tnPhyCodeSublayerStatTxSEFS15MinTr  OBJECT-TYPE ::= { tnPhyCodeSublayerStatsEntry 19 }
--    tnPhyCodeSublayerStatRxCV1DayTr     OBJECT-TYPE ::= { tnPhyCodeSublayerStatsEntry 20 }
--    tnPhyCodeSublayerStatRxES1DayTr     OBJECT-TYPE ::= { tnPhyCodeSublayerStatsEntry 21 }
--    tnPhyCodeSublayerStatRxSES1DayTr    OBJECT-TYPE ::= { tnPhyCodeSublayerStatsEntry 22 }
--    tnPhyCodeSublayerStatRxSEFS1DayTr   OBJECT-TYPE ::= { tnPhyCodeSublayerStatsEntry 23 }
--    tnPhyCodeSublayerStatTxCV1DayTr     OBJECT-TYPE ::= { tnPhyCodeSublayerStatsEntry 24 }
--    tnPhyCodeSublayerStatTxES1DayTr     OBJECT-TYPE ::= { tnPhyCodeSublayerStatsEntry 25 }
--    tnPhyCodeSublayerStatTxSES1DayTr    OBJECT-TYPE ::= { tnPhyCodeSublayerStatsEntry 26 }
--    tnPhyCodeSublayerStatTxSEFS1DayTr   OBJECT-TYPE ::= { tnPhyCodeSublayerStatsEntry 27 }
--    tnPhyCodeSublayerStatRxCV15MinRtr   OBJECT-TYPE ::= { tnPhyCodeSublayerStatsEntry 28 }
--    tnPhyCodeSublayerStatRxES15MinRtr   OBJECT-TYPE ::= { tnPhyCodeSublayerStatsEntry 29 }
--    tnPhyCodeSublayerStatRxSES15MinRtr  OBJECT-TYPE ::= { tnPhyCodeSublayerStatsEntry 30 }
--    tnPhyCodeSublayerStatRxSEFS15MinRtr OBJECT-TYPE ::= { tnPhyCodeSublayerStatsEntry 31 }
--    tnPhyCodeSublayerStatTxCV15MinRtr   OBJECT-TYPE ::= { tnPhyCodeSublayerStatsEntry 32 }
--    tnPhyCodeSublayerStatTxES15MinRtr   OBJECT-TYPE ::= { tnPhyCodeSublayerStatsEntry 33 }
--    tnPhyCodeSublayerStatTxSES15MinRtr  OBJECT-TYPE ::= { tnPhyCodeSublayerStatsEntry 34 }
--    tnPhyCodeSublayerStatTxSEFS15MinRtr OBJECT-TYPE ::= { tnPhyCodeSublayerStatsEntry 35 }

    tnPhyCodeSublayerStatsRxBIP8 OBJECT-TYPE
        SYNTAX      Counter32
        MAX-ACCESS  read-only
        STATUS      current
        DESCRIPTION "Severely errored frame second."
        ::= { tnPhyCodeSublayerStatsEntry 36 }

    tnPhyCodeSublayerStatsTxBIP8 OBJECT-TYPE
        SYNTAX      Counter32
        MAX-ACCESS  read-only
        STATUS      current
        DESCRIPTION "Severely errored frame second."
        ::= { tnPhyCodeSublayerStatsEntry 37 }

    tnPhyCodeSublayerStatsRxUAS OBJECT-TYPE
        SYNTAX      Counter32
        MAX-ACCESS  read-only
        STATUS      current
        DESCRIPTION "Severely errored frame second."
        ::= { tnPhyCodeSublayerStatsEntry 38 }

    tnPhyCodeSublayerStatsTxUAS OBJECT-TYPE
        SYNTAX      Counter32
        MAX-ACCESS  read-only
        STATUS      current
        DESCRIPTION "Severely errored frame second."
        ::= { tnPhyCodeSublayerStatsEntry 39 }

--------------------------------------------------------------------------------
-- Digital Wrapper 64 Bit Statistics Scalar
--------------------------------------------------------------------------------
    tnDigitalWrapper64BitStatsTotalMembers OBJECT-TYPE
        SYNTAX      Integer32
        MAX-ACCESS  read-only
        STATUS      current
        DESCRIPTION "The total number of members in the digital wrapper stats
                     table."
        ::= { tnStatisticsGrouping 33 }

--------------------------------------------------------------------------------
-- Digital Wrapper 64 Bit Statistics Table
--------------------------------------------------------------------------------
    tnDigitalWrapper64BitStatsTable OBJECT-TYPE
        SYNTAX      SEQUENCE OF TnDigitalWrapper64BitStatsEntry
        MAX-ACCESS  not-accessible
        STATUS      current
        DESCRIPTION "."
        ::= { tnStatisticsGrouping 34 }

    tnDigitalWrapper64BitStatsEntry OBJECT-TYPE
        SYNTAX      TnDigitalWrapper64BitStatsEntry
        MAX-ACCESS  not-accessible
        STATUS      current
        DESCRIPTION "."
        INDEX   { ifIndex,
                  tnStatsInterval,
                  tnDw64BitStatsBin }
        ::= { tnDigitalWrapper64BitStatsTable 1 }

    TnDigitalWrapper64BitStatsEntry ::=
        SEQUENCE {
            tnDw64BitStatsBin                     TnStatsBinType,
            tnDw64BitStatsBinStatus               TnStatsBinStatus,
            tnDw64BitStatsStartTime               DateAndTime,
            tnDw64BitStatRxRSCorrCnt              Counter64,
            tnDw64BitStatRxRSUncorrCnt            Counter64,
            tnDw64BitStatRxSMBIP8ErrCnt           Counter64,
            tnDw64BitStatRxPMBIP8ErrCnt           Counter64,
--            obsolete
--            tnDw64BitStatRxSMBEIErrCnt            Counter64,
--            tnDw64BitStatRxPMBEIErrCnt            Counter64,
--            tnDw64BitStatRxRSSES                  Counter64,
            tnDw64BitStatRxSMES                   Counter64,
            tnDw64BitStatRxPMES                   Counter64,
            tnDw64BitStatRxSMSES                  Counter64,
            tnDw64BitStatRxPMSES                  Counter64,
            tnDw64BitStatRxSMUAS                  Counter64,
            tnDw64BitStatRxPMUAS                  Counter64,
--            obsolete
--            tnDw64BitStatRxRSCorrCnt15MinTr       Counter64,
--            tnDw64BitStatRxRSUncorrCnt15MinTr     Counter64,
--            tnDw64BitStatRxSMBIP8ErrCnt15MinTr    Counter64,
--            tnDw64BitStatRxPMBIP8ErrCnt15MinTr    Counter64,
--            tnDw64BitStatRxSMES15MinTr            Counter64,
--            tnDw64BitStatRxPMES15MinTr            Counter64,
--            tnDw64BitStatRxSMSES15MinTr           Counter64,
--            tnDw64BitStatRxPMSES15MinTr           Counter64,
--            tnDw64BitStatRxSMUAS15MinTr           Counter64,
--            tnDw64BitStatRxPMUAS15MinTr           Counter64,
--            tnDw64BitStatRxRSCorrCnt1DayTr        Counter64,
--            tnDw64BitStatRxRSUncorrCnt1DayTr      Counter64,
--            tnDw64BitStatRxSMBIP8ErrCnt1DayTr     Counter64,
--            tnDw64BitStatRxPMBIP8ErrCnt1DayTr     Counter64,
--            tnDw64BitStatRxSMES1DayTr             Counter64,
--            tnDw64BitStatRxPMES1DayTr             Counter64,
--            tnDw64BitStatRxSMSES1DayTr            Counter64,
--            tnDw64BitStatRxPMSES1DayTr            Counter64,
--            tnDw64BitStatRxSMUAS1DayTr            Counter64,
--            tnDw64BitStatRxPMUAS1DayTr            Counter64,
--            tnDw64BitStatRxRSCorrCnt15MinRtr      Counter64,
--            tnDw64BitStatRxRSUncorrCnt15MinRtr    Counter64,
--            tnDw64BitStatRxSMBIP8ErrCnt15MinRtr   Counter64,
--            tnDw64BitStatRxPMBIP8ErrCnt15MinRtr   Counter64,
--            tnDw64BitStatRxSMES15MinRtr           Counter64,
--            tnDw64BitStatRxPMES15MinRtr           Counter64,
--            tnDw64BitStatRxSMSES15MinRtr          Counter64,
--            tnDw64BitStatRxPMSES15MinRtr          Counter64,
--            tnDw64BitStatRxSMUAS15MinRtr          Counter64,
--            tnDw64BitStatRxPMUAS15MinRtr          Counter64,
            tnDw64BitStatRxBERPreFEC              Counter64,
            tnDw64BitStatRxBERPostFEC             Counter64,
            tnDw64BitStatRxSMFEBIP8ErrCnt         Counter64,
            tnDw64BitStatRxPMFEBIP8ErrCnt         Counter64,
            tnDw64BitStatRxSMBIAESErrCnt          Counter64,
            tnDw64BitStatRxSMIAESErrCnt           Counter64,
            tnDw64BitStatRxSMFEES                 Counter64,
            tnDw64BitStatRxPMFEES                 Counter64,
            tnDw64BitStatRxSMFESES                Counter64,
            tnDw64BitStatRxPMFESES                Counter64,
            tnDw64BitStatRxSMFEUAS                Counter64,
            tnDw64BitStatRxPMFEUAS                Counter64
--            obsolete
--            tnDwRxSMFEBIP8ErrCnt15MinTr           Counter64,
--            tnDwRxPMFEBIP8ErrCnt15MinTr           Counter64,
--            tnDwRxSMFEES15MinTr                   Counter64,
--            tnDwRxPMFEES15MinTr                   Counter64,
--            tnDwRxSMFESES15MinTr                  Counter64,
--            tnDwRxPMFESES15MinTr                  Counter64,
--            tnDwRxSMFEUAS15MinTr                  Counter64,
--            tnDwRxPMFEUAS15MinTr                  Counter64,
--            tnDwRxSMBIAES15MinTr                  Counter64,
--            tnDwRxSMIAES15MinTr                   Counter64,
--            tnDwRxBERPreFEC15MinTr                Counter64,
--            tnDwRxBERPostFEC15MinTr               Counter64,
--            tnDwRxSMFEBIP8ErrCnt1DayTr            Counter64,
--            tnDwRxPMFEBIP8ErrCnt1DayTr            Counter64,
--            tnDwRxSMFEES1DayTr                    Counter64,
--            tnDwRxPMFEES1DayTr                    Counter64,
--            tnDwRxSMFESES1DayTr                   Counter64,
--            tnDwRxPMFESES1DayTr                   Counter64,
--            tnDwRxSMFEUAS1DayTr                   Counter64,
--            tnDwRxPMFEUAS1DayTr                   Counter64,
--            tnDwRxSMBIAES1DayTr                   Counter64,
--            tnDwRxSMIAES1DayTr                    Counter64,
--            tnDwRxBERPreFEC1DayTr                 Counter64,
--            tnDwRxBERPostFEC1DayTr                Counter64,
--            tnDwRxSMFEBIP8ErrCnt15MinRtr          Counter64,
--            tnDwRxPMFEBIP8ErrCnt15MinRtr          Counter64,
--            tnDwRxSMFEES15MinRtr                  Counter64,
--            tnDwRxPMFEES15MinRtr                  Counter64,
--            tnDwRxSMFESES15MinRtr                 Counter64,
--            tnDwRxPMFESES15MinRtr                 Counter64,
--            tnDwRxSMFEUAS15MinRtr                 Counter64,
--            tnDwRxPMFEUAS15MinRtr                 Counter64,
--            tnDwRxSMBIAES15MinRtr                 Counter64,
--            tnDwRxSMIAES15MinRtr                  Counter64,
--            tnDwRxBERPreFEC15MinRtr               Counter64,
--            tnDwRxBERPostFEC15MinRtr              Counter64,
        }

    tnDw64BitStatsBin OBJECT-TYPE
        SYNTAX      TnStatsBinType
        MAX-ACCESS  not-accessible
        STATUS      current
        DESCRIPTION "The bin number, starting with bin 0."
        ::= { tnDigitalWrapper64BitStatsEntry 1 }

    tnDw64BitStatsBinStatus OBJECT-TYPE
        SYNTAX      TnStatsBinStatus
        MAX-ACCESS  read-only
        STATUS      current
        DESCRIPTION "This attribute indicates the validity of the bin."
        ::= { tnDigitalWrapper64BitStatsEntry 2 }

    tnDw64BitStatsStartTime OBJECT-TYPE
        SYNTAX      DateAndTime
        MAX-ACCESS  read-only
        STATUS      current
        DESCRIPTION "This attribute is the bin collection start date
                     and time."
        ::= { tnDigitalWrapper64BitStatsEntry 3 }

    tnDw64BitStatRxRSCorrCnt OBJECT-TYPE
        SYNTAX      Counter64
        MAX-ACCESS  read-only
        STATUS      current
        DESCRIPTION "Provides a count of the number of bits
                     corrected at the receiver."
        ::= { tnDigitalWrapper64BitStatsEntry 4 }

    tnDw64BitStatRxRSUncorrCnt OBJECT-TYPE
        SYNTAX      Counter64
        MAX-ACCESS  read-only
        STATUS      current
        DESCRIPTION "Provides a count of the number of blocks
                     detected at the receiver which have
                     uncorrectable errors."
        ::= { tnDigitalWrapper64BitStatsEntry 5 }

    tnDw64BitStatRxSMBIP8ErrCnt OBJECT-TYPE
        SYNTAX      Counter64
        MAX-ACCESS  read-only
        STATUS      current
        DESCRIPTION "Provides a count of the section monitor
                     bit interleaved parity (BIP-8) errors
                     detected at the receiver."
        ::= { tnDigitalWrapper64BitStatsEntry 6 }

    tnDw64BitStatRxPMBIP8ErrCnt OBJECT-TYPE
        SYNTAX      Counter64
        MAX-ACCESS  read-only
        STATUS      current
        DESCRIPTION "Provides a count of the path monitor bit
                     interleaved parity (BIP-8) errors detected
                     at the receiver."
        ::= { tnDigitalWrapper64BitStatsEntry 7 }

--    obsolete
--    tnDw64BitStatRxSMBEIErrCnt OBJECT-TYPE ::= { tnDigitalWrapper64BitStatsEntry 8 }
--    tnDw64BitStatRxPMBEIErrCnt OBJECT-TYPE ::= { tnDigitalWrapper64BitStatsEntry 9 }
--    tnDw64BitStatRxRSSES       OBJECT-TYPE ::= { tnDigitalWrapper64BitStatsEntry 10 }

    tnDw64BitStatRxSMES OBJECT-TYPE
        SYNTAX      Counter64
        MAX-ACCESS  read-only
        STATUS      current
        DESCRIPTION "Provides a count of the section monitor
                     errored seconds."
        ::= { tnDigitalWrapper64BitStatsEntry 11 }

    tnDw64BitStatRxPMES OBJECT-TYPE
        SYNTAX      Counter64
        MAX-ACCESS  read-only
        STATUS      current
        DESCRIPTION "Provides a count of the path monitor
                     errored seconds."
        ::= { tnDigitalWrapper64BitStatsEntry 12 }

    tnDw64BitStatRxSMSES OBJECT-TYPE
        SYNTAX      Counter64
        MAX-ACCESS  read-only
        STATUS      current
        DESCRIPTION "Provides a count of the section monitor
                     severely errored seconds."
        ::= { tnDigitalWrapper64BitStatsEntry 13 }

    tnDw64BitStatRxPMSES OBJECT-TYPE
        SYNTAX      Counter64
        MAX-ACCESS  read-only
        STATUS      current
        DESCRIPTION "Provides a count of the path monitor
                     severely errored seconds."
        ::= { tnDigitalWrapper64BitStatsEntry 14 }

    tnDw64BitStatRxSMUAS OBJECT-TYPE
        SYNTAX      Counter64
        MAX-ACCESS  read-only
        STATUS      current
        DESCRIPTION "Provides a count of the section monitor
                     unavailable seconds."
        ::= { tnDigitalWrapper64BitStatsEntry 15 }

    tnDw64BitStatRxPMUAS OBJECT-TYPE
        SYNTAX      Counter64
        MAX-ACCESS  read-only
        STATUS      current
        DESCRIPTION "Provides a count of the path monitor
                     unavailable seconds."
        ::= { tnDigitalWrapper64BitStatsEntry 16 }

--    obsolete
--    tnDw64BitStatRxRSCorrCnt15MinTr     OBJECT-TYPE ::= { tnDigitalWrapper64BitStatsEntry 17 }
--    tnDw64BitStatRxRSUncorrCnt15MinTr   OBJECT-TYPE ::= { tnDigitalWrapper64BitStatsEntry 18 }
--    tnDw64BitStatRxSMBIP8ErrCnt15MinTr  OBJECT-TYPE ::= { tnDigitalWrapper64BitStatsEntry 19 }
--    tnDw64BitStatRxPMBIP8ErrCnt15MinTr  OBJECT-TYPE ::= { tnDigitalWrapper64BitStatsEntry 20 }
--    tnDw64BitStatRxSMES15MinTr          OBJECT-TYPE ::= { tnDigitalWrapper64BitStatsEntry 21 }
--    tnDw64BitStatRxPMES15MinTr          OBJECT-TYPE ::= { tnDigitalWrapper64BitStatsEntry 22 }
--    tnDw64BitStatRxSMSES15MinTr         OBJECT-TYPE ::= { tnDigitalWrapper64BitStatsEntry 23 }
--    tnDw64BitStatRxPMSES15MinTr         OBJECT-TYPE ::= { tnDigitalWrapper64BitStatsEntry 24 }
--    tnDw64BitStatRxSMUAS15MinTr         OBJECT-TYPE ::= { tnDigitalWrapper64BitStatsEntry 25 }
--    tnDw64BitStatRxPMUAS15MinTr         OBJECT-TYPE ::= { tnDigitalWrapper64BitStatsEntry 26 }
--    tnDw64BitStatRxRSCorrCnt1DayTr      OBJECT-TYPE ::= { tnDigitalWrapper64BitStatsEntry 27 }
--    tnDw64BitStatRxRSUncorrCnt1DayTr    OBJECT-TYPE ::= { tnDigitalWrapper64BitStatsEntry 28 }
--    tnDw64BitStatRxSMBIP8ErrCnt1DayTr   OBJECT-TYPE ::= { tnDigitalWrapper64BitStatsEntry 29 }
--    tnDw64BitStatRxPMBIP8ErrCnt1DayTr   OBJECT-TYPE ::= { tnDigitalWrapper64BitStatsEntry 30 }
--    tnDw64BitStatRxSMES1DayTr           OBJECT-TYPE ::= { tnDigitalWrapper64BitStatsEntry 31 }
--    tnDw64BitStatRxPMES1DayTr           OBJECT-TYPE ::= { tnDigitalWrapper64BitStatsEntry 32 }
--    tnDw64BitStatRxSMSES1DayTr          OBJECT-TYPE ::= { tnDigitalWrapper64BitStatsEntry 33 }
--    tnDw64BitStatRxPMSES1DayTr          OBJECT-TYPE ::= { tnDigitalWrapper64BitStatsEntry 34 }
--    tnDw64BitStatRxSMUAS1DayTr          OBJECT-TYPE ::= { tnDigitalWrapper64BitStatsEntry 35 }
--    tnDw64BitStatRxPMUAS1DayTr          OBJECT-TYPE ::= { tnDigitalWrapper64BitStatsEntry 36 }
--    tnDw64BitStatRxRSCorrCnt15MinRtr    OBJECT-TYPE ::= { tnDigitalWrapper64BitStatsEntry 37 }
--    tnDw64BitStatRxRSUncorrCnt15MinRtr  OBJECT-TYPE ::= { tnDigitalWrapper64BitStatsEntry 38 }
--    tnDw64BitStatRxSMBIP8ErrCnt15MinRtr OBJECT-TYPE ::= { tnDigitalWrapper64BitStatsEntry 39 }
--    tnDw64BitStatRxPMBIP8ErrCnt15MinRtr OBJECT-TYPE ::= { tnDigitalWrapper64BitStatsEntry 40 }
--    tnDw64BitStatRxSMES15MinRtr         OBJECT-TYPE ::= { tnDigitalWrapper64BitStatsEntry 41 }
--    tnDw64BitStatRxPMES15MinRtr         OBJECT-TYPE ::= { tnDigitalWrapper64BitStatsEntry 42 }
--    tnDw64BitStatRxSMSES15MinRtr        OBJECT-TYPE ::= { tnDigitalWrapper64BitStatsEntry 43 }
--    tnDw64BitStatRxPMSES15MinRtr        OBJECT-TYPE ::= { tnDigitalWrapper64BitStatsEntry 44 }
--    tnDw64BitStatRxSMUAS15MinRtr        OBJECT-TYPE ::= { tnDigitalWrapper64BitStatsEntry 45 }
--    tnDw64BitStatRxPMUAS15MinRtr        OBJECT-TYPE ::= { tnDigitalWrapper64BitStatsEntry 46 }

    tnDw64BitStatRxBERPreFEC OBJECT-TYPE
        SYNTAX      Counter64
        MAX-ACCESS  read-only
        STATUS      current
        DESCRIPTION "Provides the error bit rate of pre-FEC
                     (Forward Error Correction)."
        ::= { tnDigitalWrapper64BitStatsEntry 47 }

    tnDw64BitStatRxBERPostFEC OBJECT-TYPE
        SYNTAX      Counter64
        MAX-ACCESS  read-only
        STATUS      current
        DESCRIPTION "Provides error bit rate of post-FEC
                     (Forward Error Correction)."
        ::= { tnDigitalWrapper64BitStatsEntry 48 }

    tnDw64BitStatRxSMFEBIP8ErrCnt OBJECT-TYPE
        SYNTAX      Counter64
        MAX-ACCESS  read-only
        STATUS      current
        DESCRIPTION "Provides a count of the far end section monitor
                     bit interleaved parity (BIP-8) errors detected
                     at the receiver."
        ::= { tnDigitalWrapper64BitStatsEntry 49 }

    tnDw64BitStatRxPMFEBIP8ErrCnt OBJECT-TYPE
        SYNTAX      Counter64
        MAX-ACCESS  read-only
        STATUS      current
        DESCRIPTION "Provides a count of the far end bit interleaved
                     parity (BIP-8) errors detected at the receiver."
        ::= { tnDigitalWrapper64BitStatsEntry 50 }

    tnDw64BitStatRxSMBIAESErrCnt OBJECT-TYPE
        SYNTAX      Counter64
        MAX-ACCESS  read-only
        STATUS      current
        DESCRIPTION "Provides a count of the section monitor
                     backward error indication (BEI)errors."
        ::= { tnDigitalWrapper64BitStatsEntry 51 }

    tnDw64BitStatRxSMIAESErrCnt OBJECT-TYPE
        SYNTAX      Counter64
        MAX-ACCESS  read-only
        STATUS      current
        DESCRIPTION "Provides a count of the backward error
                     indication (BEI) errors."
        ::= { tnDigitalWrapper64BitStatsEntry 52 }

    tnDw64BitStatRxSMFEES OBJECT-TYPE
        SYNTAX      Counter64
        MAX-ACCESS  read-only
        STATUS      current
        DESCRIPTION "Provides a count of section monitoring far end
                     errored seconds."
        ::= { tnDigitalWrapper64BitStatsEntry 53 }

    tnDw64BitStatRxPMFEES OBJECT-TYPE
        SYNTAX      Counter64
        MAX-ACCESS  read-only
        STATUS      current
        DESCRIPTION "Provides a count of far end errored seconds."
        ::= { tnDigitalWrapper64BitStatsEntry 54 }

    tnDw64BitStatRxSMFESES OBJECT-TYPE
        SYNTAX      Counter64
        MAX-ACCESS  read-only
        STATUS      current
        DESCRIPTION "Provides a count of section monitoring far end
                     severely errored seconds."
        ::= { tnDigitalWrapper64BitStatsEntry 55 }

    tnDw64BitStatRxPMFESES OBJECT-TYPE
        SYNTAX      Counter64
        MAX-ACCESS  read-only
        STATUS      current
        DESCRIPTION "Provides a count of far end severely errored
                     seconds."
        ::= { tnDigitalWrapper64BitStatsEntry 56 }

    tnDw64BitStatRxSMFEUAS OBJECT-TYPE
        SYNTAX      Counter64
        MAX-ACCESS  read-only
        STATUS      current
        DESCRIPTION "Provides a count of section monitoring far end
                     unavailable seconds."
        ::= { tnDigitalWrapper64BitStatsEntry 57 }

    tnDw64BitStatRxPMFEUAS OBJECT-TYPE
        SYNTAX      Counter64
        MAX-ACCESS  read-only
        STATUS      current
        DESCRIPTION "Provides a count of far end unavailable seconds."
        ::= { tnDigitalWrapper64BitStatsEntry 58 }

--    obsolete
--    tnDwRxSMFEBIP8ErrCnt15MinTr  OBJECT-TYPE ::= { tnDigitalWrapper64BitStatsEntry 59 }
--    tnDwRxPMFEBIP8ErrCnt15MinTr  OBJECT-TYPE ::= { tnDigitalWrapper64BitStatsEntry 60 }
--    tnDwRxSMFEES15MinTr          OBJECT-TYPE ::= { tnDigitalWrapper64BitStatsEntry 61 }
--    tnDwRxPMFEES15MinTr          OBJECT-TYPE ::= { tnDigitalWrapper64BitStatsEntry 62 }
--    tnDwRxSMFESES15MinTr         OBJECT-TYPE ::= { tnDigitalWrapper64BitStatsEntry 63 }
--    tnDwRxPMFESES15MinTr         OBJECT-TYPE ::= { tnDigitalWrapper64BitStatsEntry 64 }
--    tnDwRxSMFEUAS15MinTr         OBJECT-TYPE ::= { tnDigitalWrapper64BitStatsEntry 65 }
--    tnDwRxPMFEUAS15MinTr         OBJECT-TYPE ::= { tnDigitalWrapper64BitStatsEntry 66 }
--    tnDwRxSMBIAES15MinTr         OBJECT-TYPE ::= { tnDigitalWrapper64BitStatsEntry 67 }
--    tnDwRxSMIAES15MinTr          OBJECT-TYPE ::= { tnDigitalWrapper64BitStatsEntry 68 }
--    tnDwRxBERPreFEC15MinTr       OBJECT-TYPE ::= { tnDigitalWrapper64BitStatsEntry 69 }
--    tnDwRxBERPostFEC15MinTr      OBJECT-TYPE ::= { tnDigitalWrapper64BitStatsEntry 70 }
--    tnDwRxSMFEBIP8ErrCnt1DayTr   OBJECT-TYPE ::= { tnDigitalWrapper64BitStatsEntry 71 }
--    tnDwRxPMFEBIP8ErrCnt1DayTr   OBJECT-TYPE ::= { tnDigitalWrapper64BitStatsEntry 72 }
--    tnDwRxSMFEES1DayTr           OBJECT-TYPE ::= { tnDigitalWrapper64BitStatsEntry 73 }
--    tnDwRxPMFEES1DayTr           OBJECT-TYPE ::= { tnDigitalWrapper64BitStatsEntry 74 }
--    tnDwRxSMFESES1DayTr          OBJECT-TYPE ::= { tnDigitalWrapper64BitStatsEntry 75 }
--    tnDwRxPMFESES1DayTr          OBJECT-TYPE ::= { tnDigitalWrapper64BitStatsEntry 76 }
--    tnDwRxSMFEUAS1DayTr          OBJECT-TYPE ::= { tnDigitalWrapper64BitStatsEntry 77 }
--    tnDwRxPMFEUAS1DayTr          OBJECT-TYPE ::= { tnDigitalWrapper64BitStatsEntry 78 }
--    tnDwRxSMBIAES1DayTr          OBJECT-TYPE ::= { tnDigitalWrapper64BitStatsEntry 79 }
--    tnDwRxSMIAES1DayTr           OBJECT-TYPE ::= { tnDigitalWrapper64BitStatsEntry 80 }
--    tnDwRxBERPreFEC1DayTr        OBJECT-TYPE ::= { tnDigitalWrapper64BitStatsEntry 81 }
--    tnDwRxBERPostFEC1DayTr       OBJECT-TYPE ::= { tnDigitalWrapper64BitStatsEntry 82 }
--    tnDwRxSMFEBIP8ErrCnt15MinRtr OBJECT-TYPE ::= { tnDigitalWrapper64BitStatsEntry 83 }
--    tnDwRxPMFEBIP8ErrCnt15MinRtr OBJECT-TYPE ::= { tnDigitalWrapper64BitStatsEntry 84 }
--    tnDwRxSMFEES15MinRtr         OBJECT-TYPE ::= { tnDigitalWrapper64BitStatsEntry 85 }
--    tnDwRxPMFEES15MinRtr         OBJECT-TYPE ::= { tnDigitalWrapper64BitStatsEntry 86 }
--    tnDwRxSMFESES15MinRtr        OBJECT-TYPE ::= { tnDigitalWrapper64BitStatsEntry 87 }
--    tnDwRxPMFESES15MinRtr        OBJECT-TYPE ::= { tnDigitalWrapper64BitStatsEntry 88 }
--    tnDwRxSMFEUAS15MinRtr        OBJECT-TYPE ::= { tnDigitalWrapper64BitStatsEntry 89 }
--    tnDwRxPMFEUAS15MinRtr        OBJECT-TYPE ::= { tnDigitalWrapper64BitStatsEntry 90 }
--    tnDwRxSMBIAES15MinRtr        OBJECT-TYPE ::= { tnDigitalWrapper64BitStatsEntry 91 }
--    tnDwRxSMIAES15MinRtr         OBJECT-TYPE ::= { tnDigitalWrapper64BitStatsEntry 92 }
--    tnDwRxBERPreFEC15MinRtr      OBJECT-TYPE ::= { tnDigitalWrapper64BitStatsEntry 93 }
--    tnDwRxBERPostFEC15MinRtr     OBJECT-TYPE ::= { tnDigitalWrapper64BitStatsEntry 94 }

--------------------------------------------------------------------------------
-- Chromatic Dispersion received (CDR) Statistics Scalar
--------------------------------------------------------------------------------
    tnCdrStatsTotalMembers OBJECT-TYPE
        SYNTAX      Integer32
        MAX-ACCESS  read-only
        STATUS      current
        DESCRIPTION "The total number of members in the CDR received stats table."
        ::= { tnStatisticsGrouping 35 }

--------------------------------------------------------------------------------
-- Chromatic Dispersion received (CDR) Statistics Table
--------------------------------------------------------------------------------
    tnCdrStatsTable OBJECT-TYPE
        SYNTAX      SEQUENCE OF TnCdrStatsEntry
        MAX-ACCESS  not-accessible
        STATUS      current
        DESCRIPTION "."
        ::= { tnStatisticsGrouping 36 }

    tnCdrStatsEntry OBJECT-TYPE
        SYNTAX      TnCdrStatsEntry
        MAX-ACCESS  not-accessible
        STATUS      current
        DESCRIPTION "."
        INDEX   { ifIndex,
                  tnStatsInterval,
                  tnCdrStatsBin }
        ::= { tnCdrStatsTable 1 }

    TnCdrStatsEntry ::=
        SEQUENCE {
            tnCdrStatsBin         TnStatsBinType,
            tnCdrStatsBinStatus   TnStatsBinStatus,
            tnCdrStatsStartTime   DateAndTime,
            tnCdrStatMin          Integer32,
            tnCdrStatMax          Integer32,
            tnCdrStatAverage      Integer32
        }

    tnCdrStatsBin OBJECT-TYPE
        SYNTAX      TnStatsBinType
        MAX-ACCESS  not-accessible
        STATUS      current
        DESCRIPTION "The bin number, starting with bin 0."
        ::= { tnCdrStatsEntry 1 }

    tnCdrStatsBinStatus OBJECT-TYPE
        SYNTAX      TnStatsBinStatus
        MAX-ACCESS  read-only
        STATUS      current
        DESCRIPTION "This attribute indicates the validity of the bin."
        ::= { tnCdrStatsEntry 2 }

    tnCdrStatsStartTime OBJECT-TYPE
        SYNTAX      DateAndTime
        MAX-ACCESS  read-only
        STATUS      current
        DESCRIPTION "This attribute is the bin collection start date
                     and time."
        ::= { tnCdrStatsEntry 3 }

    tnCdrStatMin OBJECT-TYPE
        SYNTAX      Integer32
        UNITS       "ps/nm"
        MAX-ACCESS  read-only
        STATUS      current
        DESCRIPTION "Minimum chromatic dispersion received (ps/nm)."
        ::= { tnCdrStatsEntry 4 }

    tnCdrStatMax OBJECT-TYPE
        SYNTAX      Integer32
        UNITS       "ps/nm"
        MAX-ACCESS  read-only
        STATUS      current
        DESCRIPTION "Maximum chromatic dispersion received (ps/nm)."
        ::= { tnCdrStatsEntry 5 }

    tnCdrStatAverage OBJECT-TYPE
        SYNTAX      Integer32
        UNITS       "ps/nm"
        MAX-ACCESS  read-only
        STATUS      current
        DESCRIPTION "Average chromatic dispersion received (ps/nm)."
        ::= { tnCdrStatsEntry 6 }

--------------------------------------------------------------------------------
-- Differential Group Delay received (DGDR) Statistics Scalar
--------------------------------------------------------------------------------
    tnDgdrStatsTotalMembers OBJECT-TYPE
        SYNTAX      Integer32
        MAX-ACCESS  read-only
        STATUS      current
        DESCRIPTION "The total number of members in the DGDR stats table."
        ::= { tnStatisticsGrouping 37 }

--------------------------------------------------------------------------------
-- Differential Group Delay received (DGDR) Statistics Table
--------------------------------------------------------------------------------
    tnDgdrStatsTable OBJECT-TYPE
        SYNTAX      SEQUENCE OF TnDgdrStatsEntry
        MAX-ACCESS  not-accessible
        STATUS      current
        DESCRIPTION "."
        ::= { tnStatisticsGrouping 38 }

    tnDgdrStatsEntry OBJECT-TYPE
        SYNTAX      TnDgdrStatsEntry
        MAX-ACCESS  not-accessible
        STATUS      current
        DESCRIPTION "."
        INDEX   { ifIndex,
                  tnStatsInterval,
                  tnDgdrStatsBin }
        ::= { tnDgdrStatsTable 1 }

    TnDgdrStatsEntry ::=
        SEQUENCE {
            tnDgdrStatsBin         TnStatsBinType,
            tnDgdrStatsBinStatus   TnStatsBinStatus,
            tnDgdrStatsStartTime   DateAndTime,
            tnDgdrStatMin          Integer32,
            tnDgdrStatMax          Integer32,
            tnDgdrStatAverage      Integer32
        }

    tnDgdrStatsBin OBJECT-TYPE
        SYNTAX      TnStatsBinType
        MAX-ACCESS  not-accessible
        STATUS      current
        DESCRIPTION "The bin number, starting with bin 0."
        ::= { tnDgdrStatsEntry 1 }

    tnDgdrStatsBinStatus OBJECT-TYPE
        SYNTAX      TnStatsBinStatus
        MAX-ACCESS  read-only
        STATUS      current
        DESCRIPTION "This attribute indicates the validity of the bin."
        ::= { tnDgdrStatsEntry 2 }

    tnDgdrStatsStartTime OBJECT-TYPE
        SYNTAX      DateAndTime
        MAX-ACCESS  read-only
        STATUS      current
        DESCRIPTION "This attribute is the bin collection start date
                     and time."
        ::= { tnDgdrStatsEntry 3 }

    tnDgdrStatMin OBJECT-TYPE
        SYNTAX      Integer32
        UNITS       "ps"
        MAX-ACCESS  read-only
        STATUS      current
        DESCRIPTION "Minimum differential group delay received (ps)."
        ::= { tnDgdrStatsEntry 4 }

    tnDgdrStatMax OBJECT-TYPE
        SYNTAX      Integer32
        UNITS       "ps"
        MAX-ACCESS  read-only
        STATUS      current
        DESCRIPTION "Maximum differential group delay received (ps)."
        ::= { tnDgdrStatsEntry 5 }

    tnDgdrStatAverage OBJECT-TYPE
        SYNTAX      Integer32
        UNITS       "ps"
        MAX-ACCESS  read-only
        STATUS      current
        DESCRIPTION "Average differential group delay received (ps)."
        ::= { tnDgdrStatsEntry 6 }

--------------------------------------------------------------------------------
-- Frequency Offset received (FOFFR) Statistics Scalar
--------------------------------------------------------------------------------
    tnFoffrStatsTotalMembers OBJECT-TYPE
        SYNTAX      Integer32
        MAX-ACCESS  read-only
        STATUS      current
        DESCRIPTION "The total number of members in the FOFFR stats table."
        ::= { tnStatisticsGrouping 39 }

--------------------------------------------------------------------------------
-- Frequency Offset received (FOFFR) Statistics Table
--------------------------------------------------------------------------------
    tnFoffrStatsTable OBJECT-TYPE
        SYNTAX      SEQUENCE OF TnFoffrStatsEntry
        MAX-ACCESS  not-accessible
        STATUS      current
        DESCRIPTION "."
        ::= { tnStatisticsGrouping 40 }

    tnFoffrStatsEntry OBJECT-TYPE
        SYNTAX      TnFoffrStatsEntry
        MAX-ACCESS  not-accessible
        STATUS      current
        DESCRIPTION "."
        INDEX   { ifIndex,
                  tnStatsInterval,
                  tnFoffrStatsBin }
        ::= { tnFoffrStatsTable 1 }

    TnFoffrStatsEntry ::=
        SEQUENCE {
            tnFoffrStatsBin         TnStatsBinType,
            tnFoffrStatsBinStatus   TnStatsBinStatus,
            tnFoffrStatsStartTime   DateAndTime,
            tnFoffrStatMin          Integer32,
            tnFoffrStatMax          Integer32,
            tnFoffrStatAverage      Integer32
        }

    tnFoffrStatsBin OBJECT-TYPE
        SYNTAX      TnStatsBinType
        MAX-ACCESS  not-accessible
        STATUS      current
        DESCRIPTION "The bin number, starting with bin 0."
        ::= { tnFoffrStatsEntry 1 }

    tnFoffrStatsBinStatus OBJECT-TYPE
        SYNTAX      TnStatsBinStatus
        MAX-ACCESS  read-only
        STATUS      current
        DESCRIPTION "This attribute indicates the validity of the bin."
        ::= { tnFoffrStatsEntry 2 }

    tnFoffrStatsStartTime OBJECT-TYPE
        SYNTAX      DateAndTime
        MAX-ACCESS  read-only
        STATUS      current
        DESCRIPTION "This attribute is the bin collection start date
                     and time."
        ::= { tnFoffrStatsEntry 3 }

    tnFoffrStatMin OBJECT-TYPE
        SYNTAX      Integer32
        UNITS       "GHz"
        MAX-ACCESS  read-only
        STATUS      current
        DESCRIPTION "Minimum frequency offset received (GHz)."
        ::= { tnFoffrStatsEntry 4 }

    tnFoffrStatMax OBJECT-TYPE
        SYNTAX      Integer32
        UNITS       "GHz"
        MAX-ACCESS  read-only
        STATUS      current
        DESCRIPTION "Maximum frequency offset received (GHz)."
        ::= { tnFoffrStatsEntry 5 }

    tnFoffrStatAverage OBJECT-TYPE
        SYNTAX      Integer32
        UNITS       "GHz"
        MAX-ACCESS  read-only
        STATUS      current
        DESCRIPTION "Average frequency offset received (GHz)."
        ::= { tnFoffrStatsEntry 6 }

--------------------------------------------------------------------------------
-- E1 Statistics Scalar
--------------------------------------------------------------------------------
    tnE1StatsTotalMembers OBJECT-TYPE
        SYNTAX      Integer32
        MAX-ACCESS  read-only
        STATUS      current
        DESCRIPTION "The total number of members in the E1 stats table."
        ::= { tnStatisticsGrouping 41 }

--------------------------------------------------------------------------------
-- E1 Statistics Table
--------------------------------------------------------------------------------
    tnE1StatsTable OBJECT-TYPE
        SYNTAX      SEQUENCE OF TnE1StatsEntry
        MAX-ACCESS  not-accessible
        STATUS      current
        DESCRIPTION "."
        ::= { tnStatisticsGrouping 42 }

    tnE1StatsEntry OBJECT-TYPE
        SYNTAX      TnE1StatsEntry
        MAX-ACCESS  not-accessible
        STATUS      current
        DESCRIPTION "."
        INDEX   { ifIndex,
                  tnStatsInterval,
                  tnE1StatsBin }
        ::= { tnE1StatsTable 1 }

    TnE1StatsEntry ::=
        SEQUENCE {
            tnE1StatsBin              TnStatsBinType,
            tnE1StatsBinStatus        TnStatsBinStatus,
            tnE1StatsStartTime        DateAndTime,
            tnE1StatRxBBEP            Counter32,
            tnE1StatRxESP             Counter32,
            tnE1StatRxSESP            Counter32,
            tnE1StatRxUASP            Counter32,
            tnE1StatRxESL             Counter32,
            tnE1StatRxSESL            Counter32,
            tnE1StatTxBBEP            Counter32,
            tnE1StatTxESP             Counter32,
            tnE1StatTxSESP            Counter32,
            tnE1StatTxUASP            Counter32,
            tnE1StatRxBBEP15MinTr     Counter32,
            tnE1StatRxESP15MinTr      Counter32,
            tnE1StatRxSESP15MinTr     Counter32,
            tnE1StatRxUASP15MinTr     Counter32,
            tnE1StatRxESL15MinTr      Counter32,
            tnE1StatRxSESL15MinTr     Counter32,
            tnE1StatTxBBEP15MinTr     Counter32,
            tnE1StatTxESP15MinTr      Counter32,
            tnE1StatTxSESP15MinTr     Counter32,
            tnE1StatTxUASP15MinTr     Counter32,
            tnE1StatRxBBEP1DayTr      Counter32,
            tnE1StatRxESP1DayTr       Counter32,
            tnE1StatRxSESP1DayTr      Counter32,
            tnE1StatRxUASP1DayTr      Counter32,
            tnE1StatRxESL1DayTr       Counter32,
            tnE1StatRxSESL1DayTr      Counter32,
            tnE1StatTxBBEP1DayTr      Counter32,
            tnE1StatTxESP1DayTr       Counter32,
            tnE1StatTxSESP1DayTr      Counter32,
            tnE1StatTxUASP1DayTr      Counter32,
            tnE1StatRxBBEP15MinRtr    Counter32,
            tnE1StatRxESP15MinRtr     Counter32,
            tnE1StatRxSESP15MinRtr    Counter32,
            tnE1StatRxUASP15MinRtr    Counter32,
            tnE1StatRxESL15MinRtr     Counter32,
            tnE1StatRxSESL15MinRtr    Counter32,
            tnE1StatTxBBEP15MinRtr    Counter32,
            tnE1StatTxESP15MinRtr     Counter32,
            tnE1StatTxSESP15MinRtr    Counter32,
            tnE1StatTxUASP15MinRtr    Counter32
        }

    tnE1StatsBin OBJECT-TYPE
        SYNTAX      TnStatsBinType
        MAX-ACCESS  not-accessible
        STATUS      current
        DESCRIPTION "The bin number, starting with bin 0."
        ::= { tnE1StatsEntry 1 }

    tnE1StatsBinStatus OBJECT-TYPE
        SYNTAX      TnStatsBinStatus
        MAX-ACCESS  read-only
        STATUS      current
        DESCRIPTION "This attribute indicates the validity of the bin."
        ::= { tnE1StatsEntry 2 }

    tnE1StatsStartTime OBJECT-TYPE
        SYNTAX      DateAndTime
        MAX-ACCESS  read-only
        STATUS      current
        DESCRIPTION "This attribute is the bin collection start date
                     and time."
        ::= { tnE1StatsEntry 3 }

    tnE1StatRxBBEP OBJECT-TYPE
        SYNTAX      Counter32
        MAX-ACCESS  read-only
        STATUS      current
        DESCRIPTION "Background Block Errors - Path."
        ::= { tnE1StatsEntry 4 }

    tnE1StatRxESP OBJECT-TYPE
        SYNTAX      Counter32
        MAX-ACCESS  read-only
        STATUS      current
        DESCRIPTION "Errored second - Path."
        ::= { tnE1StatsEntry 5 }

    tnE1StatRxSESP OBJECT-TYPE
        SYNTAX      Counter32
        MAX-ACCESS  read-only
        STATUS      current
        DESCRIPTION "Severely errored second - Path."
        ::= { tnE1StatsEntry 6 }

    tnE1StatRxUASP OBJECT-TYPE
        SYNTAX      Counter32
        MAX-ACCESS  read-only
        STATUS      current
        DESCRIPTION "Unavailable Seconds - Path."
        ::= { tnE1StatsEntry 7 }

    tnE1StatRxESL OBJECT-TYPE
        SYNTAX      Counter32
        MAX-ACCESS  read-only
        STATUS      current
        DESCRIPTION "Errored second - line. Provides a count of the
                     number of one second intervals in which any
                     of the following conditions are true:

                     - at least one B2 BIP error was detected.
                     - an alarm indicating signal (AIS-L) defect
                       was present."
        ::= { tnE1StatsEntry 8 }

    tnE1StatRxSESL OBJECT-TYPE
        SYNTAX      Counter32
        MAX-ACCESS  read-only
        STATUS      current
        DESCRIPTION "Severely errored second - line. Provides a
                     count of the number of one second intervals
                     in which any of the following conditions are
                     true:

                     - the number of line layer B2 errors detected
                       exceeded the value defined in GR-253-CORE.
                     - an alarm indicating signal (AIS-L) defect
                       was present."
        ::= { tnE1StatsEntry 9 }

    tnE1StatTxBBEP OBJECT-TYPE
        SYNTAX      Counter32
        MAX-ACCESS  read-only
        STATUS      current
        DESCRIPTION "Background Block Errors - Path."
        ::= { tnE1StatsEntry 10 }

    tnE1StatTxESP OBJECT-TYPE
        SYNTAX      Counter32
        MAX-ACCESS  read-only
        STATUS      current
        DESCRIPTION "Errored second ."
        ::= { tnE1StatsEntry 11 }

    tnE1StatTxSESP OBJECT-TYPE
        SYNTAX      Counter32
        MAX-ACCESS  read-only
        STATUS      current
        DESCRIPTION "Severely errored second "
        ::= { tnE1StatsEntry 12 }

    tnE1StatTxUASP OBJECT-TYPE
        SYNTAX      Counter32
        MAX-ACCESS  read-only
        STATUS      current
        DESCRIPTION "Unavailable second."
        ::= { tnE1StatsEntry 13 }

    tnE1StatRxBBEP15MinTr OBJECT-TYPE
        SYNTAX      Counter32
        MAX-ACCESS  read-only
        STATUS      current
        DESCRIPTION "15 minute threshold value for Background Block Errors."
        ::= { tnE1StatsEntry 14 }

    tnE1StatRxESP15MinTr OBJECT-TYPE
        SYNTAX      Counter32
        MAX-ACCESS  read-only
        STATUS      current
        DESCRIPTION "15 minute threshold value for Errored second."
        ::= { tnE1StatsEntry 15 }

    tnE1StatRxSESP15MinTr OBJECT-TYPE
        SYNTAX      Counter32
        MAX-ACCESS  read-only
        STATUS      current
        DESCRIPTION "15 minute threshold value for Severely errored second."
        ::= { tnE1StatsEntry 16 }

    tnE1StatRxUASP15MinTr OBJECT-TYPE
        SYNTAX      Counter32
        MAX-ACCESS  read-only
        STATUS      current
        DESCRIPTION "15 minute threshold value for Unavailable Seconds."
        ::= { tnE1StatsEntry 17 }

    tnE1StatRxESL15MinTr OBJECT-TYPE
        SYNTAX      Counter32
        MAX-ACCESS  read-only
        STATUS      current
        DESCRIPTION "15 minute threshold value for Errored second."
        ::= { tnE1StatsEntry 18 }

    tnE1StatRxSESL15MinTr OBJECT-TYPE
        SYNTAX      Counter32
        MAX-ACCESS  read-only
        STATUS      current
        DESCRIPTION "15 minute threshold value for Severely errored second."
        ::= { tnE1StatsEntry 19 }

    tnE1StatTxBBEP15MinTr OBJECT-TYPE
        SYNTAX      Counter32
        MAX-ACCESS  read-only
        STATUS      current
        DESCRIPTION "15 minute threshold value for Background Block Errors."
        ::= { tnE1StatsEntry 20 }

    tnE1StatTxESP15MinTr OBJECT-TYPE
        SYNTAX      Counter32
        MAX-ACCESS  read-only
        STATUS      current
        DESCRIPTION "15 minute threshold value for Errored second."
        ::= { tnE1StatsEntry 21 }

    tnE1StatTxSESP15MinTr OBJECT-TYPE
        SYNTAX      Counter32
        MAX-ACCESS  read-only
        STATUS      current
        DESCRIPTION "15 minute threshold value for Severely errored second."
        ::= { tnE1StatsEntry 22 }

    tnE1StatTxUASP15MinTr OBJECT-TYPE
        SYNTAX      Counter32
        MAX-ACCESS  read-only
        STATUS      current
        DESCRIPTION "15 minute threshold value for Unavailable second."
        ::= { tnE1StatsEntry 23 }

    tnE1StatRxBBEP1DayTr OBJECT-TYPE
        SYNTAX      Counter32
        MAX-ACCESS  read-only
        STATUS      current
        DESCRIPTION "1 day threshold value for Background Block Errors."
        ::= { tnE1StatsEntry 24 }

    tnE1StatRxESP1DayTr OBJECT-TYPE
        SYNTAX      Counter32
        MAX-ACCESS  read-only
        STATUS      current
        DESCRIPTION "1 day threshold value for Errored second."
        ::= { tnE1StatsEntry 25 }

    tnE1StatRxSESP1DayTr OBJECT-TYPE
        SYNTAX      Counter32
        MAX-ACCESS  read-only
        STATUS      current
        DESCRIPTION "1 day threshold value for Severely errored second."
        ::= { tnE1StatsEntry 26 }

    tnE1StatRxUASP1DayTr OBJECT-TYPE
        SYNTAX      Counter32
        MAX-ACCESS  read-only
        STATUS      current
        DESCRIPTION "1 day threshold value for Unavailable Seconds."
        ::= { tnE1StatsEntry 27 }

    tnE1StatRxESL1DayTr OBJECT-TYPE
        SYNTAX      Counter32
        MAX-ACCESS  read-only
        STATUS      current
        DESCRIPTION "1 day threshold value for Errored second ."
        ::= { tnE1StatsEntry 28 }

    tnE1StatRxSESL1DayTr OBJECT-TYPE
        SYNTAX      Counter32
        MAX-ACCESS  read-only
        STATUS      current
        DESCRIPTION "1 day threshold value for Severely errored second."
        ::= { tnE1StatsEntry 29 }

    tnE1StatTxBBEP1DayTr OBJECT-TYPE
        SYNTAX      Counter32
        MAX-ACCESS  read-only
        STATUS      current
        DESCRIPTION "1 day threshold value for Background Block Errors."
        ::= { tnE1StatsEntry 30 }

    tnE1StatTxESP1DayTr OBJECT-TYPE
        SYNTAX      Counter32
        MAX-ACCESS  read-only
        STATUS      current
        DESCRIPTION "1 day threshold value for Errored second ."
        ::= { tnE1StatsEntry 31 }

    tnE1StatTxSESP1DayTr OBJECT-TYPE
        SYNTAX      Counter32
        MAX-ACCESS  read-only
        STATUS      current
        DESCRIPTION "1 day threshold value for Severely errored second ."
        ::= { tnE1StatsEntry 32 }

    tnE1StatTxUASP1DayTr OBJECT-TYPE
        SYNTAX      Counter32
        MAX-ACCESS  read-only
        STATUS      current
        DESCRIPTION "1 day threshold value for Unavailable second."
        ::= { tnE1StatsEntry 33 }

    tnE1StatRxBBEP15MinRtr OBJECT-TYPE
        SYNTAX      Counter32
        MAX-ACCESS  read-only
        STATUS      current
        DESCRIPTION "15 minute reset threshold value for Background Block
                     Errors."
        ::= { tnE1StatsEntry 34 }

    tnE1StatRxESP15MinRtr OBJECT-TYPE
        SYNTAX      Counter32
        MAX-ACCESS  read-only
        STATUS      current
        DESCRIPTION "15 minute reset threshold value for Errored Second."
        ::= { tnE1StatsEntry 35 }

    tnE1StatRxSESP15MinRtr OBJECT-TYPE
        SYNTAX      Counter32
        MAX-ACCESS  read-only
        STATUS      current
        DESCRIPTION "15 minute reset threshold value for Severely Errored
                     Seconds."
        ::= { tnE1StatsEntry 36 }

    tnE1StatRxUASP15MinRtr OBJECT-TYPE
        SYNTAX      Counter32
        MAX-ACCESS  read-only
        STATUS      current
        DESCRIPTION "15 minute reset threshold value for Unavailable Seconds."
        ::= { tnE1StatsEntry 37 }

    tnE1StatRxESL15MinRtr OBJECT-TYPE
        SYNTAX      Counter32
        MAX-ACCESS  read-only
        STATUS      current
        DESCRIPTION "15 minute reset threshold value for Errored second."
        ::= { tnE1StatsEntry 38 }

    tnE1StatRxSESL15MinRtr OBJECT-TYPE
        SYNTAX      Counter32
        MAX-ACCESS  read-only
        STATUS      current
        DESCRIPTION "15 minute reset threshold value for Severely Errored Second."
        ::= { tnE1StatsEntry 39 }

    tnE1StatTxBBEP15MinRtr OBJECT-TYPE
        SYNTAX      Counter32
        MAX-ACCESS  read-only
        STATUS      current
        DESCRIPTION "15 minute reset threshold value for Background Block Errors."
        ::= { tnE1StatsEntry 40 }

    tnE1StatTxESP15MinRtr OBJECT-TYPE
        SYNTAX      Counter32
        MAX-ACCESS  read-only
        STATUS      current
        DESCRIPTION "15 minute reset threshold value for Errored Seconds."
        ::= { tnE1StatsEntry 41 }

    tnE1StatTxSESP15MinRtr OBJECT-TYPE
        SYNTAX      Counter32
        MAX-ACCESS  read-only
        STATUS      current
        DESCRIPTION "15 minute reset threshold value for Severely Errored Seconds"
        ::= { tnE1StatsEntry 42 }

    tnE1StatTxUASP15MinRtr OBJECT-TYPE
        SYNTAX      Counter32
        MAX-ACCESS  read-only
        STATUS      current
        DESCRIPTION "15 minute reset threshold value for Unavailable Seconds."
        ::= { tnE1StatsEntry 43 }

--------------------------------------------------------------------------------
-- PreFECBits Statistics Scalar
--------------------------------------------------------------------------------
    tnPreFECBitsStatsTotalMembers OBJECT-TYPE
        SYNTAX      Integer32
        MAX-ACCESS  read-only
        STATUS      current
        DESCRIPTION "The total number of members in the PreFECBitsBits group
                     delay received stats table."
        ::= { tnStatisticsGrouping 43 }

--------------------------------------------------------------------------------
-- PreFECBits Statistics Table
--------------------------------------------------------------------------------
    tnPreFECBitsStatsTable OBJECT-TYPE
        SYNTAX      SEQUENCE OF TnPreFECBitsStatsEntry
        MAX-ACCESS  not-accessible
        STATUS      current
        DESCRIPTION "."
        ::= { tnStatisticsGrouping 44 }

    tnPreFECBitsStatsEntry OBJECT-TYPE
        SYNTAX      TnPreFECBitsStatsEntry
        MAX-ACCESS  not-accessible
        STATUS      current
        DESCRIPTION "."
        INDEX   { ifIndex,
                  tnStatsInterval,
                  tnPreFECBitsStatsBin }
        ::= { tnPreFECBitsStatsTable 1 }

    TnPreFECBitsStatsEntry ::=
        SEQUENCE {
            tnPreFECBitsStatsBin           TnStatsBinType,
            tnPreFECBitsStatsBinStatus     TnStatsBinStatus,
            tnPreFECBitsStatsStartTime     DateAndTime,
            tnPreFECBitsStatMin            Counter64,
            tnPreFECBitsStatMax            Counter64,
            tnPreFECBitsStatAverage        Counter64
        }

    tnPreFECBitsStatsBin OBJECT-TYPE
        SYNTAX      TnStatsBinType
        MAX-ACCESS  not-accessible
        STATUS      current
        DESCRIPTION "The bin number, starting with bin 0."
        ::= { tnPreFECBitsStatsEntry 1 }

    tnPreFECBitsStatsBinStatus OBJECT-TYPE
        SYNTAX      TnStatsBinStatus
        MAX-ACCESS  read-only
        STATUS      current
        DESCRIPTION "This attribute indicates the validity of the bin."
        ::= { tnPreFECBitsStatsEntry 2 }

    tnPreFECBitsStatsStartTime OBJECT-TYPE
        SYNTAX      DateAndTime
        MAX-ACCESS  read-only
        STATUS      current
        DESCRIPTION "Bin collection start date and time."
        ::= { tnPreFECBitsStatsEntry 3 }

    tnPreFECBitsStatMin OBJECT-TYPE
        SYNTAX      Counter64
        UNITS       "Bits in 1-second"
        MAX-ACCESS  read-only
        STATUS      current
        DESCRIPTION "Minimum PreFECBits bits received (Bits in 1-second)."
        ::= { tnPreFECBitsStatsEntry 4 }

    tnPreFECBitsStatMax OBJECT-TYPE
        SYNTAX      Counter64
        UNITS       "Bits in 1-second"
        MAX-ACCESS  read-only
        STATUS      current
        DESCRIPTION "Maximum PreFECBitsbits received (Bits in 1-second)."
        ::= { tnPreFECBitsStatsEntry 5 }

    tnPreFECBitsStatAverage OBJECT-TYPE
        SYNTAX      Counter64
        UNITS       "Bits in 1-second"
        MAX-ACCESS  read-only
        STATUS      current
        DESCRIPTION "Average PreFECBitsbits received (Bits in 1-second)."
        ::= { tnPreFECBitsStatsEntry 6 }

--    obsolete
--    tnTcm64BitStatsTotalMembers OBJECT-TYPE ::= { tnStatisticsGrouping 45 }
--    tnTcm64BitStatsTable        OBJECT-TYPE ::= { tnStatisticsGrouping 46 }

--------------------------------------------------------------------------------
-- Encryption 64 Bit Statistics Scalar
--------------------------------------------------------------------------------
    tnEncrypt64BitStatsTotalMembers OBJECT-TYPE
        SYNTAX      Integer32
        MAX-ACCESS  read-only
        STATUS      current
        DESCRIPTION "The total number of members in the encrypt raw count stats
                     table."
        ::= { tnStatisticsGrouping 47 }

--------------------------------------------------------------------------------
-- Encryption 64 Bit Statistics Table
--------------------------------------------------------------------------------
    tnEncrypt64BitStatsTable OBJECT-TYPE
        SYNTAX      SEQUENCE OF TnEncrypt64BitStatsEntry
        MAX-ACCESS  not-accessible
        STATUS      current
        DESCRIPTION "."
        ::= { tnStatisticsGrouping 48 }

    tnEncrypt64BitStatsEntry OBJECT-TYPE
        SYNTAX      TnEncrypt64BitStatsEntry
        MAX-ACCESS  not-accessible
        STATUS      current
        DESCRIPTION "."
        INDEX   { ifIndex,
                  tnStatsInterval,
                  tnEncrypt64BitStatsBin }
        ::= { tnEncrypt64BitStatsTable 1 }

    TnEncrypt64BitStatsEntry ::=
        SEQUENCE {
            tnEncrypt64BitStatsBin                   TnStatsBinType,
            tnEncrypt64BitStatsBinStatus             TnStatsBinStatus,
            tnEncrypt64BitStatsStartTime             DateAndTime,
            tnEncrypt64BitStatTx128BitBlkCnt         Counter64,
            tnEncrypt64BitStatRxFailToDecryptCnt     Counter64
        }

    tnEncrypt64BitStatsBin OBJECT-TYPE
        SYNTAX      TnStatsBinType
        MAX-ACCESS  not-accessible
        STATUS      current
        DESCRIPTION "The bin number, starting with bin 0."
        ::= { tnEncrypt64BitStatsEntry 1 }

    tnEncrypt64BitStatsBinStatus OBJECT-TYPE
        SYNTAX      TnStatsBinStatus
        MAX-ACCESS  read-only
        STATUS      current
        DESCRIPTION "This attribute indicates the validity of the bin."
        ::= { tnEncrypt64BitStatsEntry 2 }

    tnEncrypt64BitStatsStartTime OBJECT-TYPE
        SYNTAX      DateAndTime
        MAX-ACCESS  read-only
        STATUS      current
        DESCRIPTION "This attribute is the bin collection start date and
                     time."
        ::= { tnEncrypt64BitStatsEntry 3 }

    tnEncrypt64BitStatTx128BitBlkCnt OBJECT-TYPE
        SYNTAX      Counter64
        MAX-ACCESS  read-only
        STATUS      current
        DESCRIPTION "Hardware should increment a cumulative counter for
                     each 128 bit block of data that is encrypted."
        ::= { tnEncrypt64BitStatsEntry 4 }

    tnEncrypt64BitStatRxFailToDecryptCnt OBJECT-TYPE
        SYNTAX      Counter64
        MAX-ACCESS  read-only
        STATUS      current
        DESCRIPTION "Failed to decrypt 128 bit block of data counter
                     (e.g., counter could not be read, counter not
                     expected, key bank unknown)."
        ::= { tnEncrypt64BitStatsEntry 5 }

--------------------------------------------------------------------------------
-- RX Statistics ODUk Stats Scalar
--------------------------------------------------------------------------------
    tnOthOdukStatsRxTotalMembers OBJECT-TYPE
        SYNTAX      Integer32
        MAX-ACCESS  read-only
        STATUS      current
        DESCRIPTION "."
        ::= { tnStatisticsGrouping 49 }

--------------------------------------------------------------------------------
-- RX Statistics ODUk Stats Table
--------------------------------------------------------------------------------
    tnOthOdukStatsRxTable OBJECT-TYPE
        SYNTAX      SEQUENCE OF TnOthOdukStatsRxEntry
        MAX-ACCESS  not-accessible
        STATUS      current
        DESCRIPTION "."
        ::= { tnStatisticsGrouping 50 }

    tnOthOdukStatsRxEntry OBJECT-TYPE
        SYNTAX      TnOthOdukStatsRxEntry
        MAX-ACCESS  not-accessible
        STATUS      current
        DESCRIPTION "."
        INDEX   { tnOthIfIndex,
                  tnOthIfIndexLo,
                  tnStatsInterval,
                  tnOthOdukStatsBin }
        ::= { tnOthOdukStatsRxTable 1 }

    TnOthOdukStatsRxEntry ::=
        SEQUENCE {
            tnOthOdukStatsBin                TnStatsBinType,
            tnOthOdukStatsRxBinStatus        TnStatsBinStatus,
            tnOthOdukStatsRxStartTime        DateAndTime,
            tnOthOdukStatsRxNeBIP8ErrCnt     Counter64,
            tnOthOdukStatsRxNeES             Counter64,
            tnOthOdukStatsRxNeSES            Counter64,
            tnOthOdukStatsRxNeUAS            Counter64,
            tnOthOdukStatsRxFeBIP8ErrCnt     Counter64,
            tnOthOdukStatsRxFeES             Counter64,
            tnOthOdukStatsRxFeSES            Counter64,
            tnOthOdukStatsRxFeUAS            Counter64
        }

    tnOthOdukStatsBin OBJECT-TYPE
        SYNTAX      TnStatsBinType
        MAX-ACCESS  not-accessible
        STATUS      current
        DESCRIPTION "The bin number, starting with bin 0."
        ::= { tnOthOdukStatsRxEntry 1 }

    tnOthOdukStatsRxBinStatus OBJECT-TYPE
        SYNTAX      TnStatsBinStatus
        MAX-ACCESS  read-only
        STATUS      current
        DESCRIPTION "This attribute indicates the validity of the bin."
        ::= { tnOthOdukStatsRxEntry 2 }

    tnOthOdukStatsRxStartTime OBJECT-TYPE
        SYNTAX      DateAndTime
        MAX-ACCESS  read-only
        STATUS      current
        DESCRIPTION "This attribute is the bin collection start date
                     and time."
        ::= { tnOthOdukStatsRxEntry 3 }

    tnOthOdukStatsRxNeBIP8ErrCnt OBJECT-TYPE
        SYNTAX      Counter64
        MAX-ACCESS  read-only
        STATUS      current
        DESCRIPTION "Provides a count of near-end receiving direction
                     ODU BIP8 error blocks."
        ::= { tnOthOdukStatsRxEntry 4 }

    tnOthOdukStatsRxNeES OBJECT-TYPE
        SYNTAX      Counter64
        MAX-ACCESS  read-only
        STATUS      current
        DESCRIPTION "Provides a count of near-end receiving direction
                     ODU errored seconds."
        ::= { tnOthOdukStatsRxEntry 5 }

    tnOthOdukStatsRxNeSES OBJECT-TYPE
        SYNTAX      Counter64
        MAX-ACCESS  read-only
        STATUS      current
        DESCRIPTION "Provides a count of near-end receiving direction
                     ODU severely errored seconds."
        ::= { tnOthOdukStatsRxEntry 6 }

    tnOthOdukStatsRxNeUAS OBJECT-TYPE
        SYNTAX      Counter64
        MAX-ACCESS  read-only
        STATUS      current
        DESCRIPTION "Provides a count of near-end receiving direction
                     ODU unavailable seconds."
        ::= { tnOthOdukStatsRxEntry 7 }

    tnOthOdukStatsRxFeBIP8ErrCnt OBJECT-TYPE
        SYNTAX      Counter64
        MAX-ACCESS  read-only
        STATUS      current
        DESCRIPTION "Provides a count of far-end receiving direction
                     ODU BIP8 error blocks."
        ::= { tnOthOdukStatsRxEntry 8 }

    tnOthOdukStatsRxFeES OBJECT-TYPE
        SYNTAX      Counter64
        MAX-ACCESS  read-only
        STATUS      current
        DESCRIPTION "Provides a count of far-end receiving direction
                     ODU errored seconds."
        ::= { tnOthOdukStatsRxEntry 9 }

    tnOthOdukStatsRxFeSES OBJECT-TYPE
        SYNTAX      Counter64
        MAX-ACCESS  read-only
        STATUS      current
        DESCRIPTION "Provides a count of far-end receiving direction
                     ODU severely errored seconds."
        ::= { tnOthOdukStatsRxEntry 10 }

    tnOthOdukStatsRxFeUAS OBJECT-TYPE
        SYNTAX      Counter64
        MAX-ACCESS  read-only
        STATUS      current
        DESCRIPTION "Provides a count of far-end receiving direction
                     ODU unavailable seconds."
        ::= { tnOthOdukStatsRxEntry 11 }

--------------------------------------------------------------------------------
-- TX Statistics ODUk Stats Scalar
--------------------------------------------------------------------------------
    tnOthOdukStatsTxTotalMembers OBJECT-TYPE
        SYNTAX      Integer32
        MAX-ACCESS  read-only
        STATUS      current
        DESCRIPTION "."
        ::= { tnStatisticsGrouping 51 }

--------------------------------------------------------------------------------
-- TX Statistics ODUk Stats Table
--------------------------------------------------------------------------------
    tnOthOdukStatsTxTable OBJECT-TYPE
        SYNTAX      SEQUENCE OF TnOthOdukStatsTxEntry
        MAX-ACCESS  not-accessible
        STATUS      current
        DESCRIPTION "."
        ::= { tnStatisticsGrouping 52 }

    tnOthOdukStatsTxEntry OBJECT-TYPE
        SYNTAX      TnOthOdukStatsTxEntry
        MAX-ACCESS  not-accessible
        STATUS      current
        DESCRIPTION "."
        INDEX   { tnOthIfIndex,
                  tnOthIfIndexLo,
                  tnStatsInterval,
                  tnOthOdukStatsBin }
        ::= { tnOthOdukStatsTxTable 1 }

    TnOthOdukStatsTxEntry ::=
        SEQUENCE {
            tnOthOdukStatsTxBinStatus        TnStatsBinStatus,
            tnOthOdukStatsTxStartTime        DateAndTime,
            tnOthOdukStatsTxNeBIP8ErrCnt     Counter64,
            tnOthOdukStatsTxNeES             Counter64,
            tnOthOdukStatsTxNeSES            Counter64,
            tnOthOdukStatsTxNeUAS            Counter64,
            tnOthOdukStatsTxFeBIP8ErrCnt     Counter64,
            tnOthOdukStatsTxFeES             Counter64,
            tnOthOdukStatsTxFeSES            Counter64,
            tnOthOdukStatsTxFeUAS            Counter64
        }

    tnOthOdukStatsTxBinStatus OBJECT-TYPE
        SYNTAX      TnStatsBinStatus
        MAX-ACCESS  read-only
        STATUS      current
        DESCRIPTION "This attribute indicates the validity of the bin."
        ::= { tnOthOdukStatsTxEntry 1 }

    tnOthOdukStatsTxStartTime OBJECT-TYPE
        SYNTAX      DateAndTime
        MAX-ACCESS  read-only
        STATUS      current
        DESCRIPTION "This attribute is the bin collection start date
                     and time."
        ::= { tnOthOdukStatsTxEntry 2 }

    tnOthOdukStatsTxNeBIP8ErrCnt OBJECT-TYPE
        SYNTAX      Counter64
        MAX-ACCESS  read-only
        STATUS      current
        DESCRIPTION "Provides a count of near-end transmitting direction
                     ODU BIP8 error blocks."
        ::= { tnOthOdukStatsTxEntry 3 }

    tnOthOdukStatsTxNeES OBJECT-TYPE
        SYNTAX      Counter64
        MAX-ACCESS  read-only
        STATUS      current
        DESCRIPTION "Provides a count of near-end transmitting direction
                     ODU errored seconds."
        ::= { tnOthOdukStatsTxEntry 4 }

    tnOthOdukStatsTxNeSES OBJECT-TYPE
        SYNTAX      Counter64
        MAX-ACCESS  read-only
        STATUS      current
        DESCRIPTION "Provides a count of near-end transmitting direction
                     ODU severely errored seconds."
        ::= { tnOthOdukStatsTxEntry 5 }

    tnOthOdukStatsTxNeUAS OBJECT-TYPE
        SYNTAX      Counter64
        MAX-ACCESS  read-only
        STATUS      current
        DESCRIPTION "Provides a count of near-end transmitting direction
                     ODU unavailable seconds."
        ::= { tnOthOdukStatsTxEntry 6 }

    tnOthOdukStatsTxFeBIP8ErrCnt OBJECT-TYPE
        SYNTAX      Counter64
        MAX-ACCESS  read-only
        STATUS      current
        DESCRIPTION "Provides a count of far-end transmitting direction
                     ODU BIP8 error blocks."
        ::= { tnOthOdukStatsTxEntry 7 }

    tnOthOdukStatsTxFeES OBJECT-TYPE
        SYNTAX      Counter64
        MAX-ACCESS  read-only
        STATUS      current
        DESCRIPTION "Provides a count of far-end transmitting direction
                     ODU errored seconds."
        ::= { tnOthOdukStatsTxEntry 8 }

    tnOthOdukStatsTxFeSES OBJECT-TYPE
        SYNTAX      Counter64
        MAX-ACCESS  read-only
        STATUS      current
        DESCRIPTION "Provides a count of far-end transmitting direction
                     ODU severely errored seconds."
        ::= { tnOthOdukStatsTxEntry 9 }

    tnOthOdukStatsTxFeUAS OBJECT-TYPE
        SYNTAX      Counter64
        MAX-ACCESS  read-only
        STATUS      current
        DESCRIPTION "Provides a count of far-end transmitting direction
                     ODU unavailable seconds."
        ::= { tnOthOdukStatsTxEntry 10 }

--------------------------------------------------------------------------------
-- Statistics OTUk Stats Scalar
--------------------------------------------------------------------------------
    tnOthOtukStatsTotalMembers OBJECT-TYPE
        SYNTAX      Integer32
        MAX-ACCESS  read-only
        STATUS      current
        DESCRIPTION "."
        ::= { tnStatisticsGrouping 53 }

--------------------------------------------------------------------------------
-- Statistics ODUk Stats Table
--------------------------------------------------------------------------------
    tnOthOtukStatsTable OBJECT-TYPE
        SYNTAX      SEQUENCE OF TnOthOtukStatsEntry
        MAX-ACCESS  not-accessible
        STATUS      current
        DESCRIPTION "."
        ::= { tnStatisticsGrouping 54 }

    tnOthOtukStatsEntry OBJECT-TYPE
        SYNTAX      TnOthOtukStatsEntry
        MAX-ACCESS  not-accessible
        STATUS      current
        DESCRIPTION "."
        INDEX   { ifIndex,
                  tnStatsInterval,
                  tnOthOtukStatsBin }
        ::= { tnOthOtukStatsTable 1 }

    TnOthOtukStatsEntry ::=
        SEQUENCE {
            tnOthOtukStatsBin                 TnStatsBinType,
            tnOthOtukStatsBinStatus           TnStatsBinStatus,
            tnOthOtukStatsStartTime           DateAndTime,
            tnOthOtukStatRxRsCorrCnt          Counter64,
            tnOthOtukStatRxRsUncorrCnt        Counter64,
            tnOthOtukStatRxBERPreFEC          Counter64,
            tnOthOtukStatRxBERPostFEC         Counter64,
            tnOthOtukStatNeRxSMBIP8ErrCnt     Counter64,
            tnOthOtukStatNeRxBIAESErrCnt      Counter64,
            tnOthOtukStatNeRxSMES             Counter64,
            tnOthOtukStatNeRxSMSES            Counter64,
            tnOthOtukStatNeRxSMUAS            Counter64,
            tnOthOtukStatNeRxIAES             Counter64,
            tnOthOtukStatFeRxSMBIP8ErrCnt     Counter64,
            tnOthOtukStatFeRxSMES             Counter64,
            tnOthOtukStatFeRxSMSES            Counter64,
            tnOthOtukStatFeRxSMUAS            Counter64,
            tnOthOtukStatFeRxIAES             Counter64
        }

    tnOthOtukStatsBin OBJECT-TYPE
        SYNTAX      TnStatsBinType
        MAX-ACCESS  not-accessible
        STATUS      current
        DESCRIPTION "The bin number, starting with bin 0."
        ::= { tnOthOtukStatsEntry 1 }

    tnOthOtukStatsBinStatus OBJECT-TYPE
        SYNTAX      TnStatsBinStatus
        MAX-ACCESS  read-only
        STATUS      current
        DESCRIPTION "This attribute indicates the validity of the bin."
        ::= { tnOthOtukStatsEntry 2 }

    tnOthOtukStatsStartTime OBJECT-TYPE
        SYNTAX      DateAndTime
        MAX-ACCESS  read-only
        STATUS      current
        DESCRIPTION "This attribute is the bin collection start date
                     and time."
        ::= { tnOthOtukStatsEntry 3 }

    tnOthOtukStatRxRsCorrCnt OBJECT-TYPE
        SYNTAX      Counter64
        MAX-ACCESS  read-only
        STATUS      current
        DESCRIPTION "Provides a count of the number of FEC (Forward
                     Error Correction) error bits corrected at the
                     receiver."
        ::= { tnOthOtukStatsEntry 4 }

    tnOthOtukStatRxRsUncorrCnt OBJECT-TYPE
        SYNTAX      Counter64
        MAX-ACCESS  read-only
        STATUS      current
        DESCRIPTION "Provides a count of the number of FEC blocks
                     detected at the receiver which have uncorrectable
                     errors."
        ::= { tnOthOtukStatsEntry 5 }

    tnOthOtukStatRxBERPreFEC OBJECT-TYPE
        SYNTAX      Counter64
        MAX-ACCESS  read-only
        STATUS      current
        DESCRIPTION "Provides a count of the error bit rate of pre-FEC."
        ::= { tnOthOtukStatsEntry 6 }

    tnOthOtukStatRxBERPostFEC OBJECT-TYPE
        SYNTAX      Counter64
        MAX-ACCESS  read-only
        STATUS      current
        DESCRIPTION "Provides a count of the error bit rate of post-FEC."
        ::= { tnOthOtukStatsEntry 7 }

    tnOthOtukStatNeRxSMBIP8ErrCnt OBJECT-TYPE
        SYNTAX      Counter64
        MAX-ACCESS  read-only
        STATUS      current
        DESCRIPTION "Provides a count of near-end section monitor bit
                     interleaved parity (BIP-8) errors detected at the
                     receiver."
        ::= { tnOthOtukStatsEntry 8 }

    tnOthOtukStatNeRxBIAESErrCnt OBJECT-TYPE
        SYNTAX      Counter64
        MAX-ACCESS  read-only
        STATUS      current
        DESCRIPTION "Provides a count of the section monitor backward
                     error indication (BEI) errors."
        ::= { tnOthOtukStatsEntry 9 }

    tnOthOtukStatNeRxSMES OBJECT-TYPE
        SYNTAX      Counter64
        MAX-ACCESS  read-only
        STATUS      current
        DESCRIPTION "Provides a count of near-end section monitor errored
                     seconds detected at the receiver."
        ::= { tnOthOtukStatsEntry 10 }

    tnOthOtukStatNeRxSMSES OBJECT-TYPE
        SYNTAX      Counter64
        MAX-ACCESS  read-only
        STATUS      current
        DESCRIPTION "Provides a count of near-end  section monitor
                     severely errored seconds  detected at the receiver."
        ::= { tnOthOtukStatsEntry 11 }

    tnOthOtukStatNeRxSMUAS OBJECT-TYPE
        SYNTAX      Counter64
        MAX-ACCESS  read-only
        STATUS      current
        DESCRIPTION "Provides a count of near-end  section monitor severely
                     errored seconds  detected at the receiver."
        ::= { tnOthOtukStatsEntry 12 }

    tnOthOtukStatNeRxIAES OBJECT-TYPE
        SYNTAX      Counter64
        MAX-ACCESS  read-only
        STATUS      current
        DESCRIPTION "Provides a count of near-end IAE defect seconds
                     detected at the receiver."
        ::= { tnOthOtukStatsEntry 13 }

    tnOthOtukStatFeRxSMBIP8ErrCnt OBJECT-TYPE
        SYNTAX      Counter64
        MAX-ACCESS  read-only
        STATUS      current
        DESCRIPTION "Provides a count of the backward error indication
                     (BEI) errors, i.e. the far-end  section monitor bit
                     interleaved parity (BIP-8) errors detected at the
                     receiver."
        ::= { tnOthOtukStatsEntry 14 }

    tnOthOtukStatFeRxSMES OBJECT-TYPE
        SYNTAX      Counter64
        MAX-ACCESS  read-only
        STATUS      current
        DESCRIPTION "Provides a count of far-end  section monitor errored
                     seconds detected at the receiver."
        ::= { tnOthOtukStatsEntry 15 }

    tnOthOtukStatFeRxSMSES OBJECT-TYPE
        SYNTAX      Counter64
        MAX-ACCESS  read-only
        STATUS      current
        DESCRIPTION "Provides a count of near-end  section monitor severely
                     errored seconds  detected at the receiver."
        ::= { tnOthOtukStatsEntry 16 }

    tnOthOtukStatFeRxSMUAS OBJECT-TYPE
        SYNTAX      Counter64
        MAX-ACCESS  read-only
        STATUS      current
        DESCRIPTION "Provides a count of near-end section monitor
                     unavailable seconds detected at the receiver."
        ::= { tnOthOtukStatsEntry 17 }

    tnOthOtukStatFeRxIAES OBJECT-TYPE
        SYNTAX      Counter64
        MAX-ACCESS  read-only
        STATUS      current
        DESCRIPTION "Provides a count of the backward IAE defect seconds,
                     i.e., the far-end IAE defect seconds at the receiver."
        ::= { tnOthOtukStatsEntry 18 }

--------------------------------------------------------------------------------
-- Optical Signal Noise Ratio (OSNR) Statistics Scalar
--------------------------------------------------------------------------------
    tnOsnrStatsTotalMembers OBJECT-TYPE
        SYNTAX      Integer32
        MAX-ACCESS  read-only
        STATUS      current
        DESCRIPTION "The total number of members in the OSNR stats table."
        ::= { tnStatisticsGrouping 55 }

--------------------------------------------------------------------------------
-- Optical Signal Noise Ratio (OSNR) Statistics Table
--------------------------------------------------------------------------------
    tnOsnrStatsTable OBJECT-TYPE
        SYNTAX      SEQUENCE OF TnOsnrStatsEntry
        MAX-ACCESS  not-accessible
        STATUS      current
        DESCRIPTION "."
        ::= { tnStatisticsGrouping 56 }

    tnOsnrStatsEntry OBJECT-TYPE
        SYNTAX      TnOsnrStatsEntry
        MAX-ACCESS  not-accessible
        STATUS      current
        DESCRIPTION "."
        INDEX   { ifIndex,
                  tnStatsInterval,
                  tnOsnrStatsBin,
                  tnOpticalStatsITUChannel }
        ::= { tnOsnrStatsTable 1 }

    TnOsnrStatsEntry ::=
        SEQUENCE {
            tnOsnrStatsBin           TnStatsBinType,
            tnOsnrStatsBinStatus     TnStatsBinStatus,
            tnOsnrStatsStartTime     DateAndTime,
            tnOsnrStatMinOSNR        Integer32,
            tnOsnrStatMaxOSNR        Integer32,
            tnOsnrStatAverageOSNR    Integer32,
            tnOsnrStatStatusOSNR     INTEGER
        }

    tnOsnrStatsBin OBJECT-TYPE
        SYNTAX      TnStatsBinType
        MAX-ACCESS  not-accessible
        STATUS      current
        DESCRIPTION "The bin number, starting with bin 0."
        ::= { tnOsnrStatsEntry 1 }

    tnOsnrStatsBinStatus OBJECT-TYPE
        SYNTAX      TnStatsBinStatus
        MAX-ACCESS  read-only
        STATUS      current
        DESCRIPTION "This attribute indicates the validity of the bin."
        ::= { tnOsnrStatsEntry 2 }

    tnOsnrStatsStartTime OBJECT-TYPE
        SYNTAX      DateAndTime
        MAX-ACCESS  read-only
        STATUS      current
        DESCRIPTION "This attribute is the bin collection start date
                     and time."
        ::= { tnOsnrStatsEntry 3 }

    tnOsnrStatMinOSNR OBJECT-TYPE
        SYNTAX      Integer32
        UNITS       "mB"
        MAX-ACCESS  read-only
        STATUS      current
        DESCRIPTION "Minimum OSNR (mB)."
        ::= { tnOsnrStatsEntry 4 }

    tnOsnrStatMaxOSNR OBJECT-TYPE
        SYNTAX      Integer32
        UNITS       "mB"
        MAX-ACCESS  read-only
        STATUS      current
        DESCRIPTION "Maximum OSNR (mB)."
        ::= { tnOsnrStatsEntry 5 }

    tnOsnrStatAverageOSNR OBJECT-TYPE
        SYNTAX      Integer32
        UNITS       "mB"
        MAX-ACCESS  read-only
        STATUS      current
        DESCRIPTION "Average OSNR (mB)."
        ::= { tnOsnrStatsEntry 6 }

    tnOsnrStatStatusOSNR OBJECT-TYPE
        SYNTAX      INTEGER {
                      update(1),
                      noUpdate(2)
                    }
        MAX-ACCESS  read-only
        STATUS      current
        DESCRIPTION "OSNR updating Status."
        ::= { tnOsnrStatsEntry 7 }

--------------------------------------------------------------------------------
-- Delay Measurement (DM) Statistics ODUk Stats Scalar
--------------------------------------------------------------------------------
    tnOthOdukStatsDMTotalMembers OBJECT-TYPE
        SYNTAX      Integer32
        MAX-ACCESS  read-only
        STATUS      current
        DESCRIPTION "."
        ::= { tnStatisticsGrouping 57 }

--------------------------------------------------------------------------------
-- Delay Measurement (DM) Statistics ODUk Stats Table
--------------------------------------------------------------------------------
    tnOthOdukStatsDMTable OBJECT-TYPE
        SYNTAX      SEQUENCE OF TnOthOdukStatsDMEntry
        MAX-ACCESS  not-accessible
        STATUS      current
        DESCRIPTION "."
        ::= { tnStatisticsGrouping 58 }

    tnOthOdukStatsDMEntry OBJECT-TYPE
        SYNTAX      TnOthOdukStatsDMEntry
        MAX-ACCESS  not-accessible
        STATUS      current
        DESCRIPTION "."
        INDEX   { tnOthIfIndex,
                  tnOthIfIndexLo,
                  tnStatsInterval,
                  tnOthOdukStatsBin }
        ::= { tnOthOdukStatsDMTable 1 }

    TnOthOdukStatsDMEntry ::=
        SEQUENCE {
            tnOthOdukStatsDMBinStatus     TnStatsBinStatus,
            tnOthOdukStatsDMStartTime     DateAndTime,
            tnOthOdukStatsDMMinDm         Integer32,
            tnOthOdukStatsDMMaxDm         Integer32,
            tnOthOdukStatsDMAverageDm     Integer32
        }

    tnOthOdukStatsDMBinStatus OBJECT-TYPE
        SYNTAX      TnStatsBinStatus
        MAX-ACCESS  read-only
        STATUS      current
        DESCRIPTION "This attribute indicates the validity of the bin."
        ::= { tnOthOdukStatsDMEntry 1 }

    tnOthOdukStatsDMStartTime OBJECT-TYPE
        SYNTAX      DateAndTime
        MAX-ACCESS  read-only
        STATUS      current
        DESCRIPTION "This attribute is the bin collection start date
                     and time."
        ::= { tnOthOdukStatsDMEntry 2 }

    tnOthOdukStatsDMMinDm OBJECT-TYPE
        SYNTAX      Integer32
        UNITS       "us"
        MAX-ACCESS  read-only
        STATUS      current
        DESCRIPTION "Minimum Dm (micro-seconds)."
        ::= { tnOthOdukStatsDMEntry 3 }

    tnOthOdukStatsDMMaxDm OBJECT-TYPE
        SYNTAX      Integer32
        UNITS       "us"
        MAX-ACCESS  read-only
        STATUS      current
        DESCRIPTION "Maximum Dm (micro-seconds)."
        ::= { tnOthOdukStatsDMEntry 4 }

    tnOthOdukStatsDMAverageDm OBJECT-TYPE
        SYNTAX      Integer32
        UNITS       "us"
        MAX-ACCESS  read-only
        STATUS      current
        DESCRIPTION "Average Dm (micro-seconds)."
        ::= { tnOthOdukStatsDMEntry 5 }

--------------------------------------------------------------------------------
-- Statistics Tandem Connection Monitoring (TCM) Scalar
--------------------------------------------------------------------------------
    tnOthOdukStatsTcmTotalMembers OBJECT-TYPE
        SYNTAX      Integer32
        MAX-ACCESS  read-only
        STATUS      current
        DESCRIPTION "The total number of members in the TCM stats table."
        ::= { tnStatisticsGrouping 59 }

--------------------------------------------------------------------------------
-- Statistics Tandem Connection Monitoring (TCM) Table
--------------------------------------------------------------------------------
    tnOthOdukStatsTcmTable OBJECT-TYPE
        SYNTAX      SEQUENCE OF TnOthOdukStatsTcmEntry
        MAX-ACCESS  not-accessible
        STATUS      current
        DESCRIPTION "."
        ::= { tnStatisticsGrouping 60 }

    tnOthOdukStatsTcmEntry OBJECT-TYPE
        SYNTAX      TnOthOdukStatsTcmEntry
        MAX-ACCESS  not-accessible
        STATUS      current
        DESCRIPTION "."
        INDEX   { tnOthOdukTcmIfIndex,
                  tnOthOdukTcmIfIndexLo,
                  tnStatsInterval,
                  tnOthOdukStatsTcmBin }
        ::= { tnOthOdukStatsTcmTable 1 }

    TnOthOdukStatsTcmEntry ::=
        SEQUENCE {
            tnOthOdukStatsTcmBin              TnStatsBinType,
            tnOthOdukStatsTcmBinStatus        TnStatsBinStatus,
            tnOthOdukStatsTcmStartTime        DateAndTime,
            tnOthOdukStatsTcmNeRxBIP8ErrCnt   Counter64,
            tnOthOdukStatsTcmNeRxIAESErrCnt   Counter64,
            tnOthOdukStatsTcmNeRxES           Counter64,
            tnOthOdukStatsTcmNeRxSES          Counter64,
            tnOthOdukStatsTcmNeRxUAS          Counter64,
            tnOthOdukStatsTcmFeRxBIP8ErrCnt   Counter64,
            tnOthOdukStatsTcmFeRxBIAESErrCnt  Counter64,
            tnOthOdukStatsTcmFeRxES           Counter64,
            tnOthOdukStatsTcmFeRxSES          Counter64,
            tnOthOdukStatsTcmFeRxUAS          Counter64
        }

    tnOthOdukStatsTcmBin OBJECT-TYPE
        SYNTAX      TnStatsBinType
        MAX-ACCESS  not-accessible
        STATUS      current
        DESCRIPTION "bin number, starting with bin 0."
        ::= { tnOthOdukStatsTcmEntry 1 }

    tnOthOdukStatsTcmBinStatus OBJECT-TYPE
        SYNTAX      TnStatsBinStatus
        MAX-ACCESS  read-only
        STATUS      current
        DESCRIPTION "This attribute indicates the validity of the bin."
        ::= { tnOthOdukStatsTcmEntry 2 }

    tnOthOdukStatsTcmStartTime OBJECT-TYPE
        SYNTAX      DateAndTime
        MAX-ACCESS  read-only
        STATUS      current
        DESCRIPTION "This attribute is the bin collection start date
                     and time."
        ::= { tnOthOdukStatsTcmEntry 3 }

    tnOthOdukStatsTcmNeRxBIP8ErrCnt OBJECT-TYPE
        SYNTAX      Counter64
        MAX-ACCESS  read-only
        STATUS      current
        DESCRIPTION "Provides a count of near-end Receiving direction
                     TCM BIP8 error blocks."
        ::= { tnOthOdukStatsTcmEntry 4 }

    tnOthOdukStatsTcmNeRxIAESErrCnt OBJECT-TYPE
        SYNTAX      Counter64
        MAX-ACCESS  read-only
        STATUS      current
        DESCRIPTION "Provides a count of near-end IAE defect seconds
                     detected at the receiver."
        ::= { tnOthOdukStatsTcmEntry 5 }

    tnOthOdukStatsTcmNeRxES OBJECT-TYPE
        SYNTAX      Counter64
        MAX-ACCESS  read-only
        STATUS      current
        DESCRIPTION "Provides a count of near-end Receiving direction
                     TCM errored seconds."
        ::= { tnOthOdukStatsTcmEntry 6 }

    tnOthOdukStatsTcmNeRxSES OBJECT-TYPE
        SYNTAX      Counter64
        MAX-ACCESS  read-only
        STATUS      current
        DESCRIPTION "Provides a count of near-end Receiving direction
                     TCM severely errored seconds."
        ::= { tnOthOdukStatsTcmEntry 7 }

    tnOthOdukStatsTcmNeRxUAS OBJECT-TYPE
        SYNTAX      Counter64
        MAX-ACCESS  read-only
        STATUS      current
        DESCRIPTION "Provides a count of near-end Receiving direction
                     TCM unavailable seconds."
        ::= { tnOthOdukStatsTcmEntry 8 }

    tnOthOdukStatsTcmFeRxBIP8ErrCnt OBJECT-TYPE
        SYNTAX      Counter64
        MAX-ACCESS  read-only
        STATUS      current
        DESCRIPTION "Provides a count of receiving direction TCM BEI
                     counts, i.e., Far-End receiving direction error
                     blocks "
        ::= { tnOthOdukStatsTcmEntry 9 }

    tnOthOdukStatsTcmFeRxBIAESErrCnt OBJECT-TYPE
        SYNTAX      Counter64
        MAX-ACCESS  read-only
        STATUS      current
        DESCRIPTION "Provides a count of the backward IAE defect seconds,
                     i.e., the far-end IAE defect seconds at the receiver."
        ::= { tnOthOdukStatsTcmEntry 10 }

    tnOthOdukStatsTcmFeRxES OBJECT-TYPE
        SYNTAX      Counter64
        MAX-ACCESS  read-only
        STATUS      current
        DESCRIPTION "Provides a count of Far-End Receiving direction
                     TCM errored seconds."
        ::= { tnOthOdukStatsTcmEntry 11 }

    tnOthOdukStatsTcmFeRxSES OBJECT-TYPE
        SYNTAX      Counter64
        MAX-ACCESS  read-only
        STATUS      current
        DESCRIPTION "Provides a count of Far-End Receiving direction
                     TCM severely errored seconds."
        ::= { tnOthOdukStatsTcmEntry 12 }

    tnOthOdukStatsTcmFeRxUAS OBJECT-TYPE
        SYNTAX      Counter64
        MAX-ACCESS  read-only
        STATUS      current
        DESCRIPTION "Provides a count of Far-End Receiving direction
                     TCM unavailable seconds."
        ::= { tnOthOdukStatsTcmEntry 13 }

--------------------------------------------------------------------------------
-- Statistics FECPM Stats Scalar
--------------------------------------------------------------------------------
    tnFECPMStatsTotalMembers OBJECT-TYPE
        SYNTAX      Integer32
        MAX-ACCESS  read-only
        STATUS      current
        DESCRIPTION "."
        ::= { tnStatisticsGrouping 61 }

--------------------------------------------------------------------------------
-- Statistics FECPM Stats Table
--------------------------------------------------------------------------------
    tnFECPMStatsTable OBJECT-TYPE
        SYNTAX      SEQUENCE OF TnFECPMStatsEntry
        MAX-ACCESS  not-accessible
        STATUS      current
        DESCRIPTION "."
        ::= { tnStatisticsGrouping 62 }

    tnFECPMStatsEntry OBJECT-TYPE
        SYNTAX      TnFECPMStatsEntry
        MAX-ACCESS  not-accessible
        STATUS      current
        DESCRIPTION "."
        INDEX   { ifIndex,
                  tnStatsInterval,
                  tnFECPMStatsBin }
        ::= { tnFECPMStatsTable 1 }

    TnFECPMStatsEntry ::=
        SEQUENCE {
            tnFECPMStatsBin                 TnStatsBinType,
            tnFECPMStatsBinStatus           TnStatsBinStatus,
            tnFECPMStatsStartTime           DateAndTime,
            tnFECPMStatRxRsCorrCnt          Counter64,
            tnFECPMStatRxRsUncorrCnt        Counter64,
            tnFECPMStatRxBERPreFEC          Counter64,
            tnFECPMStatRxBERPostFEC         Counter64,
            tnFECPMStatRxSUS                Counter32
        }

    tnFECPMStatsBin OBJECT-TYPE
        SYNTAX      TnStatsBinType
        MAX-ACCESS  not-accessible
        STATUS      current
        DESCRIPTION "The bin number, starting with bin 0."
        ::= { tnFECPMStatsEntry 1 }

    tnFECPMStatsBinStatus OBJECT-TYPE
        SYNTAX      TnStatsBinStatus
        MAX-ACCESS  read-only
        STATUS      current
        DESCRIPTION "This attribute indicates the validity of the bin."
        ::= { tnFECPMStatsEntry 2 }

    tnFECPMStatsStartTime OBJECT-TYPE
        SYNTAX      DateAndTime
        MAX-ACCESS  read-only
        STATUS      current
        DESCRIPTION "This attribute is the bin collection start date
                     and time."
        ::= { tnFECPMStatsEntry 3 }

    tnFECPMStatRxRsCorrCnt OBJECT-TYPE
        SYNTAX      Counter64
        MAX-ACCESS  read-only
        STATUS      current
        DESCRIPTION "Provides a count of the number of FEC (Forward
                     Error Correction) error bits corrected at the
                     receiver."
        ::= { tnFECPMStatsEntry 4 }

    tnFECPMStatRxRsUncorrCnt OBJECT-TYPE
        SYNTAX      Counter64
        MAX-ACCESS  read-only
        STATUS      current
        DESCRIPTION "Provides a count of the number of FEC blocks
                     detected at the receiver which have uncorrectable
                     errors."
        ::= { tnFECPMStatsEntry 5 }

    tnFECPMStatRxBERPreFEC OBJECT-TYPE
        SYNTAX      Counter64
        MAX-ACCESS  read-only
        STATUS      current
        DESCRIPTION "Provides a count of the error bit rate of pre-FEC."
        ::= { tnFECPMStatsEntry 6 }

    tnFECPMStatRxBERPostFEC OBJECT-TYPE
        SYNTAX      Counter64
        MAX-ACCESS  read-only
        STATUS      current
        DESCRIPTION "Provides a count of the error bit rate of post-FEC."
        ::= { tnFECPMStatsEntry 7 }

    tnFECPMStatRxSUS OBJECT-TYPE
        SYNTAX      Counter32
        MAX-ACCESS  read-only
        STATUS      current
        DESCRIPTION "Severely Uncorrected Seconds counters on OCHOTU object."
        ::= { tnFECPMStatsEntry 8 }

--------------------------------------------------------------------------------
-- Statistics preFECBER Stats Scalar
--------------------------------------------------------------------------------
    tnpreFECBERStatsTotalMembers OBJECT-TYPE
        SYNTAX      Integer32
        MAX-ACCESS  read-only
        STATUS      current
        DESCRIPTION "."
        ::= { tnStatisticsGrouping 63 }

--------------------------------------------------------------------------------
-- Statistics preFECBER Stats Table
--------------------------------------------------------------------------------
    tnpreFECBERStatsTable OBJECT-TYPE
        SYNTAX      SEQUENCE OF TnpreFECBERStatsEntry
        MAX-ACCESS  not-accessible
        STATUS      current
        DESCRIPTION "."
        ::= { tnStatisticsGrouping 64 }

    tnpreFECBERStatsEntry OBJECT-TYPE
        SYNTAX      TnpreFECBERStatsEntry
        MAX-ACCESS  not-accessible
        STATUS      current
        DESCRIPTION "."
        INDEX   { ifIndex,
                  tnStatsInterval,
                  tnpreFECBERStatsBin }
        ::= { tnpreFECBERStatsTable 1 }

    TnpreFECBERStatsEntry ::=
        SEQUENCE {
            tnpreFECBERStatsBin                 TnStatsBinType,
            tnpreFECBERStatsBinStatus           TnStatsBinStatus,
            tnpreFECBERStatsStartTime           DateAndTime,
            tnpreFECBERStatRxBERPreFEC          Counter64
        }

    tnpreFECBERStatsBin OBJECT-TYPE
        SYNTAX      TnStatsBinType
        MAX-ACCESS  not-accessible
        STATUS      current
        DESCRIPTION "The bin number, starting with bin 0."
        ::= { tnpreFECBERStatsEntry 1 }

    tnpreFECBERStatsBinStatus OBJECT-TYPE
        SYNTAX      TnStatsBinStatus
        MAX-ACCESS  read-only
        STATUS      current
        DESCRIPTION "This attribute indicates the validity of the bin."
        ::= { tnpreFECBERStatsEntry 2 }

    tnpreFECBERStatsStartTime OBJECT-TYPE
        SYNTAX      DateAndTime
        MAX-ACCESS  read-only
        STATUS      current
        DESCRIPTION "This attribute is the bin collection start date
                     and time."
        ::= { tnpreFECBERStatsEntry 3 }

    tnpreFECBERStatRxBERPreFEC OBJECT-TYPE
        SYNTAX      Counter64
        MAX-ACCESS  read-only
        STATUS      current
        DESCRIPTION "Provides a count of the error bit rate of pre-FEC."
        ::= { tnpreFECBERStatsEntry 4 }

--------------------------------------------------------------------------------
-- Optical DC Power Out (OPOUTC) Statistics Scalar
--------------------------------------------------------------------------------
    tnOpOutCStatsTotalMembers OBJECT-TYPE
        SYNTAX      Integer32
        MAX-ACCESS  read-only
        STATUS      current
        DESCRIPTION "The total number of members in the OPOUTC stats table."
        ::= { tnStatisticsGrouping 65 }

--------------------------------------------------------------------------------
-- Optical DC Power Out (OPOUTC) Statistics Table
--------------------------------------------------------------------------------
    tnOpOutCStatsTable OBJECT-TYPE
        SYNTAX      SEQUENCE OF TnOpOutCStatsEntry
        MAX-ACCESS  not-accessible
        STATUS      current
        DESCRIPTION "."
        ::= { tnStatisticsGrouping 66 }

    tnOpOutCStatsEntry OBJECT-TYPE
        SYNTAX      TnOpOutCStatsEntry
        MAX-ACCESS  not-accessible
        STATUS      current
        DESCRIPTION "."
        INDEX   { ifIndex,
                  tnStatsInterval,
                  tnOpOutCStatsBin }
        ::= { tnOpOutCStatsTable 1 }
    TnOpOutCStatsEntry ::=
        SEQUENCE {
            tnOpOutCStatsBin         TnStatsBinType,
            tnOpOutCStatsBinStatus   TnStatsBinStatus,
            tnOpOutCStatsStartTime   DateAndTime,
            tnOpOutCStatMinPower     Integer32,
            tnOpOutCStatMaxPower     Integer32,
            tnOpOutCStatAveragePower Integer32
        }

    tnOpOutCStatsBin OBJECT-TYPE
        SYNTAX      TnStatsBinType
        MAX-ACCESS  not-accessible
        STATUS      current
        DESCRIPTION "The bin number, starting with bin 0."
        ::= { tnOpOutCStatsEntry 1 }

    tnOpOutCStatsBinStatus OBJECT-TYPE
        SYNTAX      TnStatsBinStatus
        MAX-ACCESS  read-only
        STATUS      current
        DESCRIPTION "This attribute indicates the validity of the bin."
        ::= { tnOpOutCStatsEntry 2 }

    tnOpOutCStatsStartTime OBJECT-TYPE
        SYNTAX      DateAndTime
        MAX-ACCESS  read-only
        STATUS      current
        DESCRIPTION "This attribute is the bin collection start date
                     and time."
        ::= { tnOpOutCStatsEntry 3 }

    tnOpOutCStatMinPower OBJECT-TYPE
        SYNTAX      Integer32
        UNITS       "mBm"
        MAX-ACCESS  read-only
        STATUS      current
        DESCRIPTION "Minimum optical Output power in the
                     C Band (mBm)."
        ::= { tnOpOutCStatsEntry 4 }

    tnOpOutCStatMaxPower OBJECT-TYPE
        SYNTAX      Integer32
        UNITS       "mBm"
        MAX-ACCESS  read-only
        STATUS      current
        DESCRIPTION "Maximum optical Output power in the
                     C Band (mBm)."
        ::= { tnOpOutCStatsEntry 5 }

    tnOpOutCStatAveragePower OBJECT-TYPE
        SYNTAX      Integer32
        UNITS       "mBm"
        MAX-ACCESS  read-only
        STATUS      current
        DESCRIPTION "Average optical Outputz     power in the
                     C Band (mBm)."
        ::= { tnOpOutCStatsEntry 6 }


--------------------------------------------------------------------------------
-- Optical DC Power In (OPINC) Statistics Scalar
--------------------------------------------------------------------------------
    tnOpInCStatsTotalMembers OBJECT-TYPE
        SYNTAX      Integer32
        MAX-ACCESS  read-only
        STATUS      current
        DESCRIPTION "The total number of members in the OPINC stats table."
        ::= { tnStatisticsGrouping 67 }

--------------------------------------------------------------------------------
-- Optical DC Power In (OPINC) Statistics Table
--------------------------------------------------------------------------------
    tnOpInCStatsTable OBJECT-TYPE
        SYNTAX      SEQUENCE OF TnOpInCStatsEntry
        MAX-ACCESS  not-accessible
        STATUS      current
        DESCRIPTION "."
        ::= { tnStatisticsGrouping 68 }

    tnOpInCStatsEntry OBJECT-TYPE
        SYNTAX      TnOpInCStatsEntry
        MAX-ACCESS  not-accessible
        STATUS      current
        DESCRIPTION "."
        INDEX   { ifIndex,
                  tnStatsInterval,
                  tnOpInCStatsBin }
        ::= { tnOpInCStatsTable 1 }

    TnOpInCStatsEntry ::=
        SEQUENCE {
            tnOpInCStatsBin         TnStatsBinType,
            tnOpInCStatsBinStatus   TnStatsBinStatus,
            tnOpInCStatsStartTime   DateAndTime,
            tnOpInCStatMinPower     Integer32,
            tnOpInCStatMaxPower     Integer32,
            tnOpInCStatAveragePower Integer32
        }

    tnOpInCStatsBin OBJECT-TYPE
        SYNTAX      TnStatsBinType
        MAX-ACCESS  not-accessible
        STATUS      current
        DESCRIPTION "The bin number, starting with bin 0."
        ::= { tnOpInCStatsEntry 1 }

    tnOpInCStatsBinStatus OBJECT-TYPE
        SYNTAX      TnStatsBinStatus
        MAX-ACCESS  read-only
        STATUS      current
        DESCRIPTION "This attribute indicates the validity of the bin."
        ::= { tnOpInCStatsEntry 2 }

    tnOpInCStatsStartTime OBJECT-TYPE
        SYNTAX      DateAndTime
        MAX-ACCESS  read-only
        STATUS      current
        DESCRIPTION "This attribute is the bin collection start date
                     and time."
        ::= { tnOpInCStatsEntry 3 }

    tnOpInCStatMinPower OBJECT-TYPE
        SYNTAX      Integer32
        UNITS       "mBm"
        MAX-ACCESS  read-only
        STATUS      current
        DESCRIPTION "Minimum optical Input power in the
                     C Band (mBm)."
        ::= { tnOpInCStatsEntry 4 }

    tnOpInCStatMaxPower OBJECT-TYPE
        SYNTAX      Integer32
        UNITS       "mBm"
        MAX-ACCESS  read-only
        STATUS      current
        DESCRIPTION "Maximum optical Input power in the
                     C Band (mBm)."
        ::= { tnOpInCStatsEntry 5 }

    tnOpInCStatAveragePower OBJECT-TYPE
        SYNTAX      Integer32
        UNITS       "mBm"
        MAX-ACCESS  read-only
        STATUS      current
        DESCRIPTION "Average optical Input power in the
                     C Band (mBm)."
        ::= { tnOpInCStatsEntry 6 }

--------------------------------------------------------------------------------
-- Optical DC Power Out (OPOUTL) Statistics Scalar
--------------------------------------------------------------------------------
    tnOpOutLStatsTotalMembers OBJECT-TYPE
        SYNTAX      Integer32
        MAX-ACCESS  read-only
        STATUS      current
        DESCRIPTION "The total number of members in the OPOUTL stats table."
        ::= { tnStatisticsGrouping 69 }

--------------------------------------------------------------------------------
-- Optical DC Power Out (OPOUTL) Statistics Table
--------------------------------------------------------------------------------
    tnOpOutLStatsTable OBJECT-TYPE
        SYNTAX      SEQUENCE OF TnOpOutLStatsEntry
        MAX-ACCESS  not-accessible
        STATUS      current
        DESCRIPTION "."
        ::= { tnStatisticsGrouping 70 }

    tnOpOutLStatsEntry OBJECT-TYPE
        SYNTAX      TnOpOutLStatsEntry
        MAX-ACCESS  not-accessible
        STATUS      current
        DESCRIPTION "."
        INDEX   { ifIndex,
                  tnStatsInterval,
                  tnOpOutLStatsBin }
        ::= { tnOpOutLStatsTable 1 }

    TnOpOutLStatsEntry ::=
        SEQUENCE {
            tnOpOutLStatsBin         TnStatsBinType,
            tnOpOutLStatsBinStatus   TnStatsBinStatus,
            tnOpOutLStatsStartTime   DateAndTime,
            tnOpOutLStatMinPower     Integer32,
            tnOpOutLStatMaxPower     Integer32,
            tnOpOutLStatAveragePower Integer32
        }

    tnOpOutLStatsBin OBJECT-TYPE
        SYNTAX      TnStatsBinType
        MAX-ACCESS  not-accessible
        STATUS      current
        DESCRIPTION "The bin number, starting with bin 0."
        ::= { tnOpOutLStatsEntry 1 }

    tnOpOutLStatsBinStatus OBJECT-TYPE
        SYNTAX      TnStatsBinStatus
        MAX-ACCESS  read-only
        STATUS      current
        DESCRIPTION "This attribute indicates the validity of the bin."
        ::= { tnOpOutLStatsEntry 2 }

    tnOpOutLStatsStartTime OBJECT-TYPE
        SYNTAX      DateAndTime
        MAX-ACCESS  read-only
        STATUS      current
        DESCRIPTION "This attribute is the bin collection start date
                     and time."
        ::= { tnOpOutLStatsEntry 3 }

    tnOpOutLStatMinPower OBJECT-TYPE
        SYNTAX      Integer32
        UNITS       "mBm"
        MAX-ACCESS  read-only
        STATUS      current
        DESCRIPTION "Minimum optical DC power in the
                     Out direction (mBm)."
        ::= { tnOpOutLStatsEntry 4 }

    tnOpOutLStatMaxPower OBJECT-TYPE
        SYNTAX      Integer32
        UNITS       "mBm"
        MAX-ACCESS  read-only
        STATUS      current
        DESCRIPTION "Maximum optical DC power in the
                     Out direction (mBm)."
        ::= { tnOpOutLStatsEntry 5 }

    tnOpOutLStatAveragePower OBJECT-TYPE
        SYNTAX      Integer32
        UNITS       "mBm"
        MAX-ACCESS  read-only
        STATUS      current
        DESCRIPTION "Average optical DC power in the
                     Out direction (mBm)."
        ::= { tnOpOutLStatsEntry 6 }

--------------------------------------------------------------------------------
-- Optical DC Power In (OPINL) Statistics Scalar
--------------------------------------------------------------------------------
    tnOpInLStatsTotalMembers OBJECT-TYPE
        SYNTAX      Integer32
        MAX-ACCESS  read-only
        STATUS      current
        DESCRIPTION "The total number of members in the OPINL stats table."
        ::= { tnStatisticsGrouping 71 }

--------------------------------------------------------------------------------
-- Optical DC Power In (OPINL) Statistics Table
--------------------------------------------------------------------------------
    tnOpInLStatsTable OBJECT-TYPE
        SYNTAX      SEQUENCE OF TnOpInLStatsEntry
        MAX-ACCESS  not-accessible
        STATUS      current
        DESCRIPTION "."
        ::= { tnStatisticsGrouping 72 }

    tnOpInLStatsEntry OBJECT-TYPE
        SYNTAX      TnOpInLStatsEntry
        MAX-ACCESS  not-accessible
        STATUS      current
        DESCRIPTION "."
        INDEX   { ifIndex,
                  tnStatsInterval,
                  tnOpInLStatsBin }
        ::= { tnOpInLStatsTable 1 }

    TnOpInLStatsEntry ::=
        SEQUENCE {
            tnOpInLStatsBin         TnStatsBinType,
            tnOpInLStatsBinStatus   TnStatsBinStatus,
            tnOpInLStatsStartTime   DateAndTime,
            tnOpInLStatMinPower     Integer32,
            tnOpInLStatMaxPower     Integer32,
            tnOpInLStatAveragePower Integer32
        }

    tnOpInLStatsBin OBJECT-TYPE
        SYNTAX      TnStatsBinType
        MAX-ACCESS  not-accessible
        STATUS      current
        DESCRIPTION "The bin number, starting with bin 0."
        ::= { tnOpInLStatsEntry 1 }

    tnOpInLStatsBinStatus OBJECT-TYPE
        SYNTAX      TnStatsBinStatus
        MAX-ACCESS  read-only
        STATUS      current
        DESCRIPTION "This attribute indicates the validity of the bin."
        ::= { tnOpInLStatsEntry 2 }

    tnOpInLStatsStartTime OBJECT-TYPE
        SYNTAX      DateAndTime
        MAX-ACCESS  read-only
        STATUS      current
        DESCRIPTION "This attribute is the bin collection start date
                     and time."
        ::= { tnOpInLStatsEntry 3 }

    tnOpInLStatMinPower OBJECT-TYPE
        SYNTAX      Integer32
        UNITS       "mBm"
        MAX-ACCESS  read-only
        STATUS      current
        DESCRIPTION "Minimum optical DC power in the
                     In direction (mBm)."
        ::= { tnOpInLStatsEntry 4 }

    tnOpInLStatMaxPower OBJECT-TYPE
        SYNTAX      Integer32
        UNITS       "mBm"
        MAX-ACCESS  read-only
        STATUS      current
        DESCRIPTION "Maximum optical DC power in the
                     In direction (mBm)."
        ::= { tnOpInLStatsEntry 5 }

    tnOpInLStatAveragePower OBJECT-TYPE
        SYNTAX      Integer32
        UNITS       "mBm"
        MAX-ACCESS  read-only
        STATUS      current
        DESCRIPTION "Average optical DC power in the
                     In direction (mBm)."
        ::= { tnOpInLStatsEntry 6 }

--------------------------------------------------------------------------------
-- Statistics ETHFECPM Stats Scalar
--------------------------------------------------------------------------------
    tnETHFECPMStatsTotalMembers OBJECT-TYPE
        SYNTAX      Integer32
        MAX-ACCESS  read-only
        STATUS      current
        DESCRIPTION "."
        ::= { tnStatisticsGrouping 73 }

--------------------------------------------------------------------------------
-- Statistics ETHFECPM Stats Table
--------------------------------------------------------------------------------
    tnETHFECPMStatsTable OBJECT-TYPE
        SYNTAX      SEQUENCE OF TnETHFECPMStatsEntry
        MAX-ACCESS  not-accessible
        STATUS      current
        DESCRIPTION "."
        ::= { tnStatisticsGrouping 74 }

    tnETHFECPMStatsEntry OBJECT-TYPE
        SYNTAX      TnETHFECPMStatsEntry
        MAX-ACCESS  not-accessible
        STATUS      current
        DESCRIPTION "."
        INDEX   { ifIndex,
                  tnStatsInterval,
                  tnETHFECPMStatsBin }
        ::= { tnETHFECPMStatsTable 1 }

    TnETHFECPMStatsEntry ::=
        SEQUENCE {
            tnETHFECPMStatsBin                 TnStatsBinType,
            tnETHFECPMStatsBinStatus           TnStatsBinStatus,
            tnETHFECPMStatsStartTime           DateAndTime,
--            obsolete
--            tnETHPHYFECPMStatRxRsCorrCnt       Counter64,
--            tnETHPHYFECPMStatRxRsUncorrCnt     Counter64,
            tnETHFECPMStatRxRsCorrCnt          Counter64,
            tnETHFECPMStatRxRsUncorrCnt        Counter64,
            tnETHFECPMStatRxBERpreFEC          Counter64,
            tnETHFECPMStatRxBERPostFEC         Counter64,
            tnETHFECPMStatBERpreFECCnt         Counter64
        }

    tnETHFECPMStatsBin OBJECT-TYPE
        SYNTAX      TnStatsBinType
        MAX-ACCESS  not-accessible
        STATUS      current
        DESCRIPTION "The bin number, starting with bin 0."
        ::= { tnETHFECPMStatsEntry 1 }

    tnETHFECPMStatsBinStatus OBJECT-TYPE
        SYNTAX      TnStatsBinStatus
        MAX-ACCESS  read-only
        STATUS      current
        DESCRIPTION "This attribute indicates the validity of the bin."
        ::= { tnETHFECPMStatsEntry 2 }

    tnETHFECPMStatsStartTime OBJECT-TYPE
        SYNTAX      DateAndTime
        MAX-ACCESS  read-only
        STATUS      current
        DESCRIPTION "This attribute is the bin collection start date
                     and time."
        ::= { tnETHFECPMStatsEntry 3 }

--  obsolete
--  tnETHPHYFECPMStatRxRsCorrCnt   OBJECT-TYPE ::= { tnETHFECPMStatsEntry 4 }
--  tnETHPHYFECPMStatRxRsUncorrCnt OBJECT-TYPE ::= { tnETHFECPMStatsEntry 5 }

    tnETHFECPMStatRxRsCorrCnt OBJECT-TYPE
        SYNTAX      Counter64
        MAX-ACCESS  read-only
        STATUS      current
        DESCRIPTION "A corrected FEC codeword is a codeword that
                     contains errors and was corrected."
        ::= { tnETHFECPMStatsEntry 6 }

    tnETHFECPMStatRxRsUncorrCnt OBJECT-TYPE
        SYNTAX      Counter64
        MAX-ACCESS  read-only
        STATUS      current
        DESCRIPTION "An uncorrected FEC codeword is a codeword that
                     contains errors(when the bypass correction is
                     supported and enabled)or contains errors that
                     were not corrected (when the bypass correction
                     feature is not supported and not enabled)
                     errors."
        ::= { tnETHFECPMStatsEntry 7 }

    tnETHFECPMStatRxBERpreFEC OBJECT-TYPE
        SYNTAX      Counter64
        MAX-ACCESS  read-only
        STATUS      current
        DESCRIPTION "Provides a count of the error bit rate of pre-FEC."
        ::= { tnETHFECPMStatsEntry 8 }

    tnETHFECPMStatRxBERPostFEC OBJECT-TYPE
        SYNTAX      Counter64
        MAX-ACCESS  read-only
        STATUS      current
        DESCRIPTION "Provides a count of the error bit rate of post-FEC."
        ::= { tnETHFECPMStatsEntry 9 }

    tnETHFECPMStatBERpreFECCnt OBJECT-TYPE
        SYNTAX      Counter64
        MAX-ACCESS  read-only
        STATUS      current
        DESCRIPTION "."
        ::= { tnETHFECPMStatsEntry 10 }

--------------------------------------------------------------------------------
-- Statistics SyncE Stats Scalar
--------------------------------------------------------------------------------
    tnSyncEStatsTotalMembers OBJECT-TYPE
        SYNTAX      Integer32
        MAX-ACCESS  read-only
        STATUS      current
        DESCRIPTION "."
        ::= { tnStatisticsGrouping 75 }

--------------------------------------------------------------------------------
-- Statistics SyncE Stats Table
--------------------------------------------------------------------------------
    tnSyncEStatsTable OBJECT-TYPE
        SYNTAX      SEQUENCE OF TnSyncEStatsEntry
        MAX-ACCESS  not-accessible
        STATUS      current
        DESCRIPTION "."
        ::= { tnStatisticsGrouping 76 }

    tnSyncEStatsEntry OBJECT-TYPE
        SYNTAX      TnSyncEStatsEntry
        MAX-ACCESS  not-accessible
        STATUS      current
        DESCRIPTION "."
        INDEX   { tnShelfIndex,
                  tnSlotIndex,
                  tnSyncELineRefIndex,
                  tnStatsInterval,
                  tnSyncEStatsBin }
        ::= { tnSyncEStatsTable 1 }

    TnSyncEStatsEntry ::=
        SEQUENCE {
            tnSyncEStatsBin                 TnStatsBinType,
            tnSyncEStatsBinStatus           TnStatsBinStatus,
            tnSyncEStatsStartTime           DateAndTime,
            tnSyncEStatsOffsetMin           Integer32,
            tnSyncEStatsOffsetMax           Integer32,
            tnSyncEStatsOffsetAverage       Integer32
        }

    tnSyncEStatsBin OBJECT-TYPE
        SYNTAX      TnStatsBinType
        MAX-ACCESS  not-accessible
        STATUS      current
        DESCRIPTION "The bin number, starting with bin 0."
        ::= { tnSyncEStatsEntry 1 }

    tnSyncEStatsBinStatus OBJECT-TYPE
        SYNTAX      TnStatsBinStatus
        MAX-ACCESS  read-only
        STATUS      current
        DESCRIPTION "This attribute indicates the validity of the bin."
        ::= { tnSyncEStatsEntry 2 }

    tnSyncEStatsStartTime OBJECT-TYPE
        SYNTAX      DateAndTime
        MAX-ACCESS  read-only
        STATUS      current
        DESCRIPTION "This attribute is the bin collection start date and time."
        ::= { tnSyncEStatsEntry 3 }

    tnSyncEStatsOffsetMin OBJECT-TYPE
        SYNTAX      Integer32
        UNITS       "ppb"
        MAX-ACCESS  read-only
        STATUS      current
        DESCRIPTION "Provides SyncE Line Reference offset min value.
                     When the value equal -106000, it should be shown as 'N/A'
                     (i.e. Not Available)."
        ::= { tnSyncEStatsEntry 4 }

    tnSyncEStatsOffsetMax OBJECT-TYPE
        SYNTAX      Integer32
        UNITS       "ppb"
        MAX-ACCESS  read-only
        STATUS      current
        DESCRIPTION "Provides SyncE Line Reference offset Max value.
                     When the value equal -106000, it should be shown as 'N/A'
                     (i.e. Not Available)."
        ::= { tnSyncEStatsEntry 5 }

    tnSyncEStatsOffsetAverage OBJECT-TYPE
        SYNTAX      Integer32
        UNITS       "ppb"
        MAX-ACCESS  read-only
        STATUS      current
        DESCRIPTION "Provides SyncE Line Reference offset Average value.
                     When the value equal -106000, it should be shown as 'N/A'
                     (i.e. Not Available)."
        ::= { tnSyncEStatsEntry 6 }

--------------------------------------------------------------------------------
-- Statistics Sync Stats Scalar
--------------------------------------------------------------------------------
    tnSyncStatsTotalMembers OBJECT-TYPE
        SYNTAX      Integer32
        MAX-ACCESS  read-only
        STATUS      current
        DESCRIPTION "."
        ::= { tnStatisticsGrouping 77 }

--------------------------------------------------------------------------------
-- Statistics Sync Stats Table
--------------------------------------------------------------------------------
    tnSyncStatsTable OBJECT-TYPE
        SYNTAX      SEQUENCE OF TnSyncStatsEntry
        MAX-ACCESS  not-accessible
        STATUS      current
        DESCRIPTION "."
        ::= { tnStatisticsGrouping 78 }

    tnSyncStatsEntry OBJECT-TYPE
        SYNTAX      TnSyncStatsEntry
        MAX-ACCESS  not-accessible
        STATUS      current
        DESCRIPTION "."
        INDEX   { tnShelfIndex,
                  tnSlotIndex,
                  tnStatsInterval,
                  tnSyncStatsBin }
        ::= { tnSyncStatsTable 1 }

    TnSyncStatsEntry ::=
        SEQUENCE {
            tnSyncStatsBin                 TnStatsBinType,
            tnSyncStatsBinStatus           TnStatsBinStatus,
            tnSyncStatsStartTime           DateAndTime,
            tnSyncStatsOffsetMin           Integer32,
            tnSyncStatsOffsetMax           Integer32,
            tnSyncStatsOffsetAverage       Integer32
        }

    tnSyncStatsBin OBJECT-TYPE
        SYNTAX      TnStatsBinType
        MAX-ACCESS  not-accessible
        STATUS      current
        DESCRIPTION "The bin number, starting with bin 0."
        ::= { tnSyncStatsEntry 1 }

    tnSyncStatsBinStatus OBJECT-TYPE
        SYNTAX      TnStatsBinStatus
        MAX-ACCESS  read-only
        STATUS      current
        DESCRIPTION "This attribute indicates the validity of the bin."
        ::= { tnSyncStatsEntry 2 }

    tnSyncStatsStartTime OBJECT-TYPE
        SYNTAX      DateAndTime
        MAX-ACCESS  read-only
        STATUS      current
        DESCRIPTION "This attribute is the bin collection start date and time."
        ::= { tnSyncStatsEntry 3 }

    tnSyncStatsOffsetMin OBJECT-TYPE
        SYNTAX      Integer32
        UNITS       "ppb"
        MAX-ACCESS  read-only
        STATUS      current
        DESCRIPTION "Provides Sync Line Reference offset min value.
                     When the value equal -106000, it should be shown as 'N/A'
                     (i.e. Not Available)."
        ::= { tnSyncStatsEntry 4 }

    tnSyncStatsOffsetMax OBJECT-TYPE
        SYNTAX      Integer32
        UNITS       "ppb"
        MAX-ACCESS  read-only
        STATUS      current
        DESCRIPTION "Provides Sync Line Reference offset Max value.
                     When the value equal -106000, it should be shown as 'N/A'
                     (i.e. Not Available)."
        ::= { tnSyncStatsEntry 5 }

    tnSyncStatsOffsetAverage OBJECT-TYPE
        SYNTAX      Integer32
        UNITS       "ppb"
        MAX-ACCESS  read-only
        STATUS      current
        DESCRIPTION "Provides Sync Line Reference offset Average value.
                     When the value equal -106000, it should be shown as 'N/A'
                     (i.e. Not Available)."
        ::= { tnSyncStatsEntry 6 }

--------------------------------------------------------------------------------
-- PTP Time Offset (PTOFF) Statistics Scalar
--------------------------------------------------------------------------------
    tnPTOFFTotalMembers OBJECT-TYPE
        SYNTAX      Integer32
        MAX-ACCESS  read-only
        STATUS      current
        DESCRIPTION "The total number of members in the PTOFF stats table."
        ::= { tnStatisticsGrouping 79 }

--------------------------------------------------------------------------------
-- PTP Time Offset (PTOFF) Statistics Table
--------------------------------------------------------------------------------
    tnPTOFFTable OBJECT-TYPE
        SYNTAX      SEQUENCE OF TnPTOFFEntry
        MAX-ACCESS  not-accessible
        STATUS      current
        DESCRIPTION "."
        ::= { tnStatisticsGrouping 80 }

    tnPTOFFEntry OBJECT-TYPE
        SYNTAX      TnPTOFFEntry
        MAX-ACCESS  not-accessible
        STATUS      current
        DESCRIPTION "."
        INDEX   { ifIndex,
                  tnStatsInterval,
                  tnPTOFFBin }
        ::= { tnPTOFFTable 1 }

    TnPTOFFEntry ::=
        SEQUENCE {
            tnPTOFFBin            TnStatsBinType,
            tnPTOFFBinStatus      TnStatsBinStatus,
            tnPTOFFStartTime      DateAndTime,
            tnPTOFFMin            Integer32,
            tnPTOFFMax            Integer32,
            tnPTOFFAverage        Integer32,
            tnPTOFFMin15MinTr     Integer32,
            tnPTOFFMin15MinRtr    Integer32,
            tnPTOFFMin1DayTr      Integer32,
            tnPTOFFMax15MinTr     Integer32,
            tnPTOFFMax15MinRtr    Integer32,
            tnPTOFFMax1DayTr      Integer32
        }

    tnPTOFFBin OBJECT-TYPE
        SYNTAX      TnStatsBinType
        MAX-ACCESS  not-accessible
        STATUS      current
        DESCRIPTION "The bin number, starting with bin 0."
        ::= { tnPTOFFEntry 1 }

    tnPTOFFBinStatus OBJECT-TYPE
        SYNTAX      TnStatsBinStatus
        MAX-ACCESS  read-only
        STATUS      current
        DESCRIPTION "This attribute indicates the validity of the bin."
        ::= { tnPTOFFEntry 2 }

    tnPTOFFStartTime OBJECT-TYPE
        SYNTAX      DateAndTime
        MAX-ACCESS  read-only
        STATUS      current
        DESCRIPTION "This attribute is the bin collection start date
                     and time."
        ::= { tnPTOFFEntry 3 }

    tnPTOFFMin OBJECT-TYPE
        SYNTAX      Integer32
        UNITS       "ns"
        MAX-ACCESS  read-only
        STATUS      current
        DESCRIPTION "Minimum PTP clock TimeOffset (ns).
                     When the value equal 0x80000000(-2147483648),
                     it should be shown as 'N/A'(i.e. Not Available)."
        ::= { tnPTOFFEntry 4 }

    tnPTOFFMax OBJECT-TYPE
        SYNTAX      Integer32
        UNITS       "ns"
        MAX-ACCESS  read-only
        STATUS      current
        DESCRIPTION "Maximum PTP clock TimeOffset (ns).
                     When the value equal 0x80000000(-2147483648),
                     it should be shown as 'N/A'(i.e. Not Available)."
        ::= { tnPTOFFEntry 5 }

    tnPTOFFAverage OBJECT-TYPE
        SYNTAX      Integer32
        UNITS       "ns"
        MAX-ACCESS  read-only
        STATUS      current
        DESCRIPTION "Average PTP clock TimeOffset (ns).
                     When the value equal 0x80000000(-2147483648),
                     it should be shown as 'N/A'(i.e. Not Available)."
        ::= { tnPTOFFEntry 6 }

    tnPTOFFMin15MinTr OBJECT-TYPE
        SYNTAX      Integer32
        UNITS       "ns"
        MAX-ACCESS  read-only
        STATUS      current
        DESCRIPTION "Low threshold for 15 minute PTP TimeOffset (ns)."
        ::= { tnPTOFFEntry 7 }

    tnPTOFFMin15MinRtr OBJECT-TYPE
        SYNTAX      Integer32
        UNITS       "ns"
        MAX-ACCESS  read-only
        STATUS      current
        DESCRIPTION "Low reset threshold for 15 minute PTP TimeOffset (ns)."
        ::= { tnPTOFFEntry 8 }

    tnPTOFFMin1DayTr OBJECT-TYPE
        SYNTAX      Integer32
        UNITS       "ns"
        MAX-ACCESS  read-only
        STATUS      current
        DESCRIPTION "Low threshold for 1 day PTP TimeOffset (ns)."
        ::= { tnPTOFFEntry 9 }

    tnPTOFFMax15MinTr OBJECT-TYPE
        SYNTAX      Integer32
        UNITS       "ns"
        MAX-ACCESS  read-only
        STATUS      current
        DESCRIPTION "High threshold for 15 minute PTP TimeOffset (ns)."
        ::= { tnPTOFFEntry 10 }

    tnPTOFFMax15MinRtr OBJECT-TYPE
        SYNTAX      Integer32
        UNITS       "ns"
        MAX-ACCESS  read-only
        STATUS      current
        DESCRIPTION "High reset threshold for 15 minute PTP TimeOffset (ns)."
        ::= { tnPTOFFEntry 11 }

    tnPTOFFMax1DayTr OBJECT-TYPE
        SYNTAX      Integer32
        UNITS       "ns"
        MAX-ACCESS  read-only
        STATUS      current
        DESCRIPTION "High threshold for 1 day PTP TimeOffset (ns)."
        ::= { tnPTOFFEntry 12 }

--------------------------------------------------------------------------------
-- PTP T-MS Delay (PTMSDLY) Statistics Scalar
--------------------------------------------------------------------------------
    tnPTMSDLYTotalMembers OBJECT-TYPE
        SYNTAX      Integer32
        MAX-ACCESS  read-only
        STATUS      current
        DESCRIPTION "The total number of members in the PTMSDLY stats table."
        ::= { tnStatisticsGrouping 81 }

--------------------------------------------------------------------------------
-- PTP T-MS Delay (PTMSDLY) Statistics Table
--------------------------------------------------------------------------------
    tnPTMSDLYTable OBJECT-TYPE
        SYNTAX      SEQUENCE OF TnPTMSDLYEntry
        MAX-ACCESS  not-accessible
        STATUS      current
        DESCRIPTION "."
        ::= { tnStatisticsGrouping 82 }

    tnPTMSDLYEntry OBJECT-TYPE
        SYNTAX      TnPTMSDLYEntry
        MAX-ACCESS  not-accessible
        STATUS      current
        DESCRIPTION "."
        INDEX   { ifIndex,
                  tnStatsInterval,
                  tnPTMSDLYBin }
        ::= { tnPTMSDLYTable 1 }

    TnPTMSDLYEntry ::=
        SEQUENCE {
            tnPTMSDLYBin            TnStatsBinType,
            tnPTMSDLYBinStatus      TnStatsBinStatus,
            tnPTMSDLYStartTime      DateAndTime,
            tnPTMSDLYMin            Integer32,
            tnPTMSDLYMax            Integer32,
            tnPTMSDLYAverage        Integer32,
            tnPTMSDLYMin15MinTr     Integer32,
            tnPTMSDLYMin15MinRtr    Integer32,
            tnPTMSDLYMin1DayTr      Integer32,
            tnPTMSDLYMax15MinTr     Integer32,
            tnPTMSDLYMax15MinRtr    Integer32,
            tnPTMSDLYMax1DayTr      Integer32
        }

    tnPTMSDLYBin OBJECT-TYPE
        SYNTAX      TnStatsBinType
        MAX-ACCESS  not-accessible
        STATUS      current
        DESCRIPTION "The bin number, starting with bin 0."
        ::= { tnPTMSDLYEntry 1 }

    tnPTMSDLYBinStatus OBJECT-TYPE
        SYNTAX      TnStatsBinStatus
        MAX-ACCESS  read-only
        STATUS      current
        DESCRIPTION "This attribute indicates the validity of the bin."
        ::= { tnPTMSDLYEntry 2 }

    tnPTMSDLYStartTime OBJECT-TYPE
        SYNTAX      DateAndTime
        MAX-ACCESS  read-only
        STATUS      current
        DESCRIPTION "This attribute is the bin collection start date
                     and time."
        ::= { tnPTMSDLYEntry 3 }

    tnPTMSDLYMin OBJECT-TYPE
        SYNTAX      Integer32
        UNITS       "ns"
        MAX-ACCESS  read-only
        STATUS      current
        DESCRIPTION "Minimum PTP T-MS Delay (ns).
                     When the value equal 0x80000000(-2147483648),
                     it should be shown as 'N/A'(i.e. Not Available)."
        ::= { tnPTMSDLYEntry 4 }

    tnPTMSDLYMax OBJECT-TYPE
        SYNTAX      Integer32
        UNITS       "ns"
        MAX-ACCESS  read-only
        STATUS      current
        DESCRIPTION "Maximum PTP T-MS Delay (ns).
                     When the value equal 0x80000000(-2147483648),
                     it should be shown as 'N/A'(i.e. Not Available)."
        ::= { tnPTMSDLYEntry 5 }

    tnPTMSDLYAverage OBJECT-TYPE
        SYNTAX      Integer32
        UNITS       "ns"
        MAX-ACCESS  read-only
        STATUS      current
        DESCRIPTION "Average PTP T-MS Delay (ns).
                     When the value equal 0x80000000(-2147483648),
                     it should be shown as 'N/A'(i.e. Not Available)."
        ::= { tnPTMSDLYEntry 6 }

    tnPTMSDLYMin15MinTr OBJECT-TYPE
        SYNTAX      Integer32
        UNITS       "ns"
        MAX-ACCESS  read-only
        STATUS      current
        DESCRIPTION "Low threshold for 15 minute PTP T-MS Delay (ns)."
        ::= { tnPTMSDLYEntry 7 }

    tnPTMSDLYMin15MinRtr OBJECT-TYPE
        SYNTAX      Integer32
        UNITS       "ns"
        MAX-ACCESS  read-only
        STATUS      current
        DESCRIPTION "Low reset threshold for 15 minute PTP T-MS Delay (ns)."
        ::= { tnPTMSDLYEntry 8 }

    tnPTMSDLYMin1DayTr OBJECT-TYPE
        SYNTAX      Integer32
        UNITS       "ns"
        MAX-ACCESS  read-only
        STATUS      current
        DESCRIPTION "Low threshold for 1 day PTP T-MS Delay (ns)."
        ::= { tnPTMSDLYEntry 9 }

    tnPTMSDLYMax15MinTr OBJECT-TYPE
        SYNTAX      Integer32
        UNITS       "ns"
        MAX-ACCESS  read-only
        STATUS      current
        DESCRIPTION "High threshold for 15 minute PTP T-MS Delay (ns)."
        ::= { tnPTMSDLYEntry 10 }

    tnPTMSDLYMax15MinRtr OBJECT-TYPE
        SYNTAX      Integer32
        UNITS       "ns"
        MAX-ACCESS  read-only
        STATUS      current
        DESCRIPTION "High reset threshold for 15 minute PTP T-MS Delay (ns)."
        ::= { tnPTMSDLYEntry 11 }

    tnPTMSDLYMax1DayTr OBJECT-TYPE
        SYNTAX      Integer32
        UNITS       "ns"
        MAX-ACCESS  read-only
        STATUS      current
        DESCRIPTION "High threshold for 1 day PTP T-MS Delay (ns)."
        ::= { tnPTMSDLYEntry 12 }

--------------------------------------------------------------------------------
-- PTP T-SM Delay (PTSMDLY) Statistics Scalar
--------------------------------------------------------------------------------
    tnPTSMDLYTotalMembers OBJECT-TYPE
        SYNTAX      Integer32
        MAX-ACCESS  read-only
        STATUS      current
        DESCRIPTION "The total number of members in the PTSMDLY stats table."
        ::= { tnStatisticsGrouping 83 }

--------------------------------------------------------------------------------
-- PTP T-SM Delay (PTSMDLY) Statistics Table
--------------------------------------------------------------------------------
    tnPTSMDLYTable OBJECT-TYPE
        SYNTAX      SEQUENCE OF TnPTSMDLYEntry
        MAX-ACCESS  not-accessible
        STATUS      current
        DESCRIPTION "."
        ::= { tnStatisticsGrouping 84 }

    tnPTSMDLYEntry OBJECT-TYPE
        SYNTAX      TnPTSMDLYEntry
        MAX-ACCESS  not-accessible
        STATUS      current
        DESCRIPTION "."
        INDEX   { ifIndex,
                  tnStatsInterval,
                  tnPTSMDLYBin }
        ::= { tnPTSMDLYTable 1 }

    TnPTSMDLYEntry ::=
        SEQUENCE {
            tnPTSMDLYBin            TnStatsBinType,
            tnPTSMDLYBinStatus      TnStatsBinStatus,
            tnPTSMDLYStartTime      DateAndTime,
            tnPTSMDLYMin            Integer32,
            tnPTSMDLYMax            Integer32,
            tnPTSMDLYAverage        Integer32,
            tnPTSMDLYMin15MinTr     Integer32,
            tnPTSMDLYMin15MinRtr    Integer32,
            tnPTSMDLYMin1DayTr      Integer32,
            tnPTSMDLYMax15MinTr     Integer32,
            tnPTSMDLYMax15MinRtr    Integer32,
            tnPTSMDLYMax1DayTr      Integer32
        }

    tnPTSMDLYBin OBJECT-TYPE
        SYNTAX      TnStatsBinType
        MAX-ACCESS  not-accessible
        STATUS      current
        DESCRIPTION "The bin number, starting with bin 0."
        ::= { tnPTSMDLYEntry 1 }

    tnPTSMDLYBinStatus OBJECT-TYPE
        SYNTAX      TnStatsBinStatus
        MAX-ACCESS  read-only
        STATUS      current
        DESCRIPTION "This attribute indicates the validity of the bin."
        ::= { tnPTSMDLYEntry 2 }

    tnPTSMDLYStartTime OBJECT-TYPE
        SYNTAX      DateAndTime
        MAX-ACCESS  read-only
        STATUS      current
        DESCRIPTION "This attribute is the bin collection start date
                     and time."
        ::= { tnPTSMDLYEntry 3 }

    tnPTSMDLYMin OBJECT-TYPE
        SYNTAX      Integer32
        UNITS       "ns"
        MAX-ACCESS  read-only
        STATUS      current
        DESCRIPTION "Minimum PTP T-SM Delay (ns).
                     When the value equal 0x80000000(-2147483648),
                     it should be shown as 'N/A'(i.e. Not Available)."
        ::= { tnPTSMDLYEntry 4 }

    tnPTSMDLYMax OBJECT-TYPE
        SYNTAX      Integer32
        UNITS       "ns"
        MAX-ACCESS  read-only
        STATUS      current
        DESCRIPTION "Maximum PTP T-SM Delay (ns).
                     When the value equal 0x80000000(-2147483648),
                     it should be shown as 'N/A'(i.e. Not Available)."
        ::= { tnPTSMDLYEntry 5 }

    tnPTSMDLYAverage OBJECT-TYPE
        SYNTAX      Integer32
        UNITS       "ns"
        MAX-ACCESS  read-only
        STATUS      current
        DESCRIPTION "Average PTP T-SM Delay (ns).
                     When the value equal 0x80000000(-2147483648),
                     it should be shown as 'N/A'(i.e. Not Available)."
        ::= { tnPTSMDLYEntry 6 }

    tnPTSMDLYMin15MinTr OBJECT-TYPE
        SYNTAX      Integer32
        UNITS       "ns"
        MAX-ACCESS  read-only
        STATUS      current
        DESCRIPTION "Low threshold for 15 minute PTP T-SM Delay (ns)."
        ::= { tnPTSMDLYEntry 7 }

    tnPTSMDLYMin15MinRtr OBJECT-TYPE
        SYNTAX      Integer32
        UNITS       "ns"
        MAX-ACCESS  read-only
        STATUS      current
        DESCRIPTION "Low reset threshold for 15 minute PTP T-SM Delay (ns)."
        ::= { tnPTSMDLYEntry 8 }

    tnPTSMDLYMin1DayTr OBJECT-TYPE
        SYNTAX      Integer32
        UNITS       "ns"
        MAX-ACCESS  read-only
        STATUS      current
        DESCRIPTION "Low threshold for 1 day PTP T-SM Delay (ns)."
        ::= { tnPTSMDLYEntry 9 }

    tnPTSMDLYMax15MinTr OBJECT-TYPE
        SYNTAX      Integer32
        UNITS       "ns"
        MAX-ACCESS  read-only
        STATUS      current
        DESCRIPTION "High threshold for 15 minute PTP T-SM Delay (ns)."
        ::= { tnPTSMDLYEntry 10 }

    tnPTSMDLYMax15MinRtr OBJECT-TYPE
        SYNTAX      Integer32
        UNITS       "ns"
        MAX-ACCESS  read-only
        STATUS      current
        DESCRIPTION "High reset threshold for 15 minute PTP T-SM Delay (ns)."
        ::= { tnPTSMDLYEntry 11 }

    tnPTSMDLYMax1DayTr OBJECT-TYPE
        SYNTAX      Integer32
        UNITS       "ns"
        MAX-ACCESS  read-only
        STATUS      current
        DESCRIPTION "High threshold for 1 day PTP T-SM Delay (ns)."
        ::= { tnPTSMDLYEntry 12 }

--------------------------------------------------------------------------------
-- PTP Mean Path Delay (PTMPDLY) Statistics Scalar
--------------------------------------------------------------------------------
    tnPTMPDLYTotalMembers OBJECT-TYPE
        SYNTAX      Integer32
        MAX-ACCESS  read-only
        STATUS      current
        DESCRIPTION "The total number of members in the PTMPDLY stats table."
        ::= { tnStatisticsGrouping 85 }

--------------------------------------------------------------------------------
-- PTP Mean Path Delay (PTMPDLY) Statistics Table
--------------------------------------------------------------------------------
    tnPTMPDLYTable OBJECT-TYPE
        SYNTAX      SEQUENCE OF TnPTMPDLYEntry
        MAX-ACCESS  not-accessible
        STATUS      current
        DESCRIPTION "."
        ::= { tnStatisticsGrouping 86 }

    tnPTMPDLYEntry OBJECT-TYPE
        SYNTAX      TnPTMPDLYEntry
        MAX-ACCESS  not-accessible
        STATUS      current
        DESCRIPTION "."
        INDEX   { ifIndex,
                  tnStatsInterval,
                  tnPTMPDLYBin }
        ::= { tnPTMPDLYTable 1 }

    TnPTMPDLYEntry ::=
        SEQUENCE {
            tnPTMPDLYBin            TnStatsBinType,
            tnPTMPDLYBinStatus      TnStatsBinStatus,
            tnPTMPDLYStartTime      DateAndTime,
            tnPTMPDLYMin            Integer32,
            tnPTMPDLYMax            Integer32,
            tnPTMPDLYAverage        Integer32,
            tnPTMPDLYMin15MinTr     Integer32,
            tnPTMPDLYMin15MinRtr    Integer32,
            tnPTMPDLYMin1DayTr      Integer32,
            tnPTMPDLYMax15MinTr     Integer32,
            tnPTMPDLYMax15MinRtr    Integer32,
            tnPTMPDLYMax1DayTr      Integer32
        }

    tnPTMPDLYBin OBJECT-TYPE
        SYNTAX      TnStatsBinType
        MAX-ACCESS  not-accessible
        STATUS      current
        DESCRIPTION "The bin number, starting with bin 0."
        ::= { tnPTMPDLYEntry 1 }

    tnPTMPDLYBinStatus OBJECT-TYPE
        SYNTAX      TnStatsBinStatus
        MAX-ACCESS  read-only
        STATUS      current
        DESCRIPTION "This attribute indicates the validity of the bin."
        ::= { tnPTMPDLYEntry 2 }

    tnPTMPDLYStartTime OBJECT-TYPE
        SYNTAX      DateAndTime
        MAX-ACCESS  read-only
        STATUS      current
        DESCRIPTION "This attribute is the bin collection start date
                     and time."
        ::= { tnPTMPDLYEntry 3 }

    tnPTMPDLYMin OBJECT-TYPE
        SYNTAX      Integer32
        UNITS       "ns"
        MAX-ACCESS  read-only
        STATUS      current
        DESCRIPTION "Minimum PTP Mean Path Delay (ns).
                     When the value equal 0x80000000(-2147483648),
                     it should be shown as 'N/A'(i.e. Not Available)."
        ::= { tnPTMPDLYEntry 4 }

    tnPTMPDLYMax OBJECT-TYPE
        SYNTAX      Integer32
        UNITS       "ns"
        MAX-ACCESS  read-only
        STATUS      current
        DESCRIPTION "Maximum PTP Mean Path Delay (ns).
                     When the value equal 0x80000000(-2147483648),
                     it should be shown as 'N/A'(i.e. Not Available)."
        ::= { tnPTMPDLYEntry 5 }

    tnPTMPDLYAverage OBJECT-TYPE
        SYNTAX      Integer32
        UNITS       "ns"
        MAX-ACCESS  read-only
        STATUS      current
        DESCRIPTION "Average PTP Mean Path Delay (ns).
                     When the value equal 0x80000000(-2147483648),
                     it should be shown as 'N/A'(i.e. Not Available)."
        ::= { tnPTMPDLYEntry 6 }

    tnPTMPDLYMin15MinTr OBJECT-TYPE
        SYNTAX      Integer32
        UNITS       "ns"
        MAX-ACCESS  read-only
        STATUS      current
        DESCRIPTION "Low threshold for 15 minute PTP
                     Mean Path Delay (ns)."
        ::= { tnPTMPDLYEntry 7 }

    tnPTMPDLYMin15MinRtr OBJECT-TYPE
        SYNTAX      Integer32
        UNITS       "ns"
        MAX-ACCESS  read-only
        STATUS      current
        DESCRIPTION "Low reset threshold for 15 minute
                     PTP Mean Path Delay (ns)."
        ::= { tnPTMPDLYEntry 8 }

    tnPTMPDLYMin1DayTr OBJECT-TYPE
        SYNTAX      Integer32
        UNITS       "ns"
        MAX-ACCESS  read-only
        STATUS      current
        DESCRIPTION "Low threshold for 1 day PTP Mean
                     Path Delay (ns)."
        ::= { tnPTMPDLYEntry 9 }

    tnPTMPDLYMax15MinTr OBJECT-TYPE
        SYNTAX      Integer32
        UNITS       "ns"
        MAX-ACCESS  read-only
        STATUS      current
        DESCRIPTION "High threshold for 15 minute PTP
                     Mean Path Delay (ns)."
        ::= { tnPTMPDLYEntry 10 }

    tnPTMPDLYMax15MinRtr OBJECT-TYPE
        SYNTAX      Integer32
        UNITS       "ns"
        MAX-ACCESS  read-only
        STATUS      current
        DESCRIPTION "High reset threshold for 15 minute
                     PTP Mean Path Delay (ns)."
        ::= { tnPTMPDLYEntry 11 }

    tnPTMPDLYMax1DayTr OBJECT-TYPE
        SYNTAX      Integer32
        UNITS       "ns"
        MAX-ACCESS  read-only
        STATUS      current
        DESCRIPTION "High threshold for 1 day PTP Mean
                     Path Delay (ns)."
        ::= { tnPTMPDLYEntry 12 }

--------------------------------------------------------------------------------
-- PTP Time Error by Reference comparison (PTERREF) Statistics Scalar
--------------------------------------------------------------------------------
    tnPTERREFTotalMembers OBJECT-TYPE
        SYNTAX      Integer32
        MAX-ACCESS  read-only
        STATUS      current
        DESCRIPTION "The total number of members in the PTERREF stats table."
        ::= { tnStatisticsGrouping 87 }

--------------------------------------------------------------------------------
-- PTP Time Error by Reference comparison (PTERREF) Statistics Table
--------------------------------------------------------------------------------
    tnPTERREFTable OBJECT-TYPE
        SYNTAX      SEQUENCE OF TnPTERREFEntry
        MAX-ACCESS  not-accessible
        STATUS      current
        DESCRIPTION "."
        ::= { tnStatisticsGrouping 88 }

    tnPTERREFEntry OBJECT-TYPE
        SYNTAX      TnPTERREFEntry
        MAX-ACCESS  not-accessible
        STATUS      current
        DESCRIPTION "."
        INDEX   { ifIndex,
                  tnStatsInterval,
                  tnPTERREFBin }
        ::= { tnPTERREFTable 1 }

    TnPTERREFEntry ::=
        SEQUENCE {
            tnPTERREFBin            TnStatsBinType,
            tnPTERREFBinStatus      TnStatsBinStatus,
            tnPTERREFStartTime      DateAndTime,
            tnPTERREFMin            Integer32,
            tnPTERREFMax            Integer32,
            tnPTERREFAverage        Integer32,
            tnPTERREFMin15MinTr     Integer32,
            tnPTERREFMin15MinRtr    Integer32,
            tnPTERREFMin1DayTr      Integer32,
            tnPTERREFMax15MinTr     Integer32,
            tnPTERREFMax15MinRtr    Integer32,
            tnPTERREFMax1DayTr      Integer32
        }

    tnPTERREFBin OBJECT-TYPE
        SYNTAX      TnStatsBinType
        MAX-ACCESS  not-accessible
        STATUS      current
        DESCRIPTION "The bin number, starting with bin 0."
        ::= { tnPTERREFEntry 1 }

    tnPTERREFBinStatus OBJECT-TYPE
        SYNTAX      TnStatsBinStatus
        MAX-ACCESS  read-only
        STATUS      current
        DESCRIPTION "This attribute indicates the validity of the bin."
        ::= { tnPTERREFEntry 2 }

    tnPTERREFStartTime OBJECT-TYPE
        SYNTAX      DateAndTime
        MAX-ACCESS  read-only
        STATUS      current
        DESCRIPTION "This attribute is the bin collection start date
                     and time."
        ::= { tnPTERREFEntry 3 }

    tnPTERREFMin OBJECT-TYPE
        SYNTAX      Integer32
        UNITS       "ns"
        MAX-ACCESS  read-only
        STATUS      current
        DESCRIPTION "Minimum PTP Time Error Measurement (ns).
                     When the value equal 0x80000000(-2147483648),
                     it should be shown as 'N/A'(i.e. Not Available)."
        ::= { tnPTERREFEntry 4 }

    tnPTERREFMax OBJECT-TYPE
        SYNTAX      Integer32
        UNITS       "ns"
        MAX-ACCESS  read-only
        STATUS      current
        DESCRIPTION "Maximum PTP Time Error Measurement (ns).
                     When the value equal 0x80000000(-2147483648),
                     it should be shown as 'N/A'(i.e. Not Available)."
        ::= { tnPTERREFEntry 5 }

    tnPTERREFAverage OBJECT-TYPE
        SYNTAX      Integer32
        UNITS       "ns"
        MAX-ACCESS  read-only
        STATUS      current
        DESCRIPTION "Average PTP Time Error Measurement (ns).
                     When the value equal 0x80000000(-2147483648),
                     it should be shown as 'N/A'(i.e. Not Available)."
        ::= { tnPTERREFEntry 6 }

    tnPTERREFMin15MinTr OBJECT-TYPE
        SYNTAX      Integer32
        UNITS       "ns"
        MAX-ACCESS  read-only
        STATUS      current
        DESCRIPTION "Low threshold for 15 minute PTP Time
                     Error Measurement (ns)."
        ::= { tnPTERREFEntry 7 }

    tnPTERREFMin15MinRtr OBJECT-TYPE
        SYNTAX      Integer32
        UNITS       "ns"
        MAX-ACCESS  read-only
        STATUS      current
        DESCRIPTION "Low reset threshold for 15 minute PTP
                     Time Error Measurement (ns)."
        ::= { tnPTERREFEntry 8 }

    tnPTERREFMin1DayTr OBJECT-TYPE
        SYNTAX      Integer32
        UNITS       "ns"
        MAX-ACCESS  read-only
        STATUS      current
        DESCRIPTION "Low threshold for 1 day PTP Time Error
                     Measurement (ns)."
        ::= { tnPTERREFEntry 9 }

    tnPTERREFMax15MinTr OBJECT-TYPE
        SYNTAX      Integer32
        UNITS       "ns"
        MAX-ACCESS  read-only
        STATUS      current
        DESCRIPTION "High threshold for 15 minute PTP Time
                     Error Measurement (ns)."
        ::= { tnPTERREFEntry 10 }

    tnPTERREFMax15MinRtr OBJECT-TYPE
        SYNTAX      Integer32
        UNITS       "ns"
        MAX-ACCESS  read-only
        STATUS      current
        DESCRIPTION "High reset threshold for 15 minute PTP
                     Time Error Measurement (ns)."
        ::= { tnPTERREFEntry 11 }

    tnPTERREFMax1DayTr OBJECT-TYPE
        SYNTAX      Integer32
        UNITS       "ns"
        MAX-ACCESS  read-only
        STATUS      current
        DESCRIPTION "High threshold for 1 day PTP Time Error
                     Measurement (ns)."
        ::= { tnPTERREFEntry 12 }

--------------------------------------------------------------------------------
-- PTP Time Offset Accumulation (PTOFFACUM) Statistics Scalar
--------------------------------------------------------------------------------
    tnPTOFFACUMTotalMembers OBJECT-TYPE
        SYNTAX      Integer32
        MAX-ACCESS  read-only
        STATUS      current
        DESCRIPTION "The total number of members in the PTOFFACUM stats table."
        ::= { tnStatisticsGrouping 89 }

--------------------------------------------------------------------------------
-- PTP Time Offset Accumulation (PTOFFACUM) Statistics Table
--------------------------------------------------------------------------------
    tnPTOFFACUMTable OBJECT-TYPE
        SYNTAX      SEQUENCE OF TnPTOFFACUMEntry
        MAX-ACCESS  not-accessible
        STATUS      current
        DESCRIPTION "."
        ::= { tnStatisticsGrouping 90 }

    tnPTOFFACUMEntry OBJECT-TYPE
        SYNTAX      TnPTOFFACUMEntry
        MAX-ACCESS  not-accessible
        STATUS      current
        DESCRIPTION "."
        INDEX   { ifIndex,
                  tnStatsInterval,
                  tnPTOFFACUMBin }
        ::= { tnPTOFFACUMTable 1 }

    TnPTOFFACUMEntry ::=
        SEQUENCE {
            tnPTOFFACUMBin              TnStatsBinType,
            tnPTOFFACUMBinStatus        TnStatsBinStatus,
            tnPTOFFACUMStartTime        DateAndTime,
            tnPTOFFACUMMin              Integer32,
            tnPTOFFACUMMax              Integer32,
            tnPTOFFACUMPeakToPeak       Integer32,
            tnPTOFFACUMAverage          Integer32,
            tnPTOFFACUMSum              Integer32,
            tnPTOFFACUMPeakToPeakTr     Integer32,
            tnPTOFFACUMPeakToPeakRtr    Integer32,
            tnPTOFFACUMPeakToPeak1DayTr Integer32
        }

    tnPTOFFACUMBin OBJECT-TYPE
        SYNTAX      TnStatsBinType
        MAX-ACCESS  not-accessible
        STATUS      current
        DESCRIPTION "The bin number, starting with bin 0."
        ::= { tnPTOFFACUMEntry 1 }

    tnPTOFFACUMBinStatus OBJECT-TYPE
        SYNTAX      TnStatsBinStatus
        MAX-ACCESS  read-only
        STATUS      current
        DESCRIPTION "This attribute indicates the validity of the bin."
        ::= { tnPTOFFACUMEntry 2 }

    tnPTOFFACUMStartTime OBJECT-TYPE
        SYNTAX      DateAndTime
        MAX-ACCESS  read-only
        STATUS      current
        DESCRIPTION "This attribute is the bin collection start date
                     and time."
        ::= { tnPTOFFACUMEntry 3 }

    tnPTOFFACUMMin OBJECT-TYPE
        SYNTAX      Integer32
        UNITS       "ns"
        MAX-ACCESS  read-only
        STATUS      current
        DESCRIPTION "Minimum PTP clock Time Offset Accumulation (ns).
                     When the value equal 0x80000000(-2147483648),
                     it should be shown as 'N/A'(i.e. Not Available)."
        ::= { tnPTOFFACUMEntry 4 }

    tnPTOFFACUMMax OBJECT-TYPE
        SYNTAX      Integer32
        UNITS       "ns"
        MAX-ACCESS  read-only
        STATUS      current
        DESCRIPTION "Maximum PTP clock Time Offset Accumulation (ns).
                     When the value equal 0x80000000(-2147483648),
                     it should be shown as 'N/A'(i.e. Not Available)."
        ::= { tnPTOFFACUMEntry 5 }

    tnPTOFFACUMPeakToPeak OBJECT-TYPE
        SYNTAX      Integer32
        UNITS       "ns"
        MAX-ACCESS  read-only
        STATUS      current
        DESCRIPTION "Peak to Peak PTP clock Time Offset Accumulation (ns).
                     When the value equal 0x80000000(-2147483648),
                     it should be shown as 'N/A'(i.e. Not Available)."
        ::= { tnPTOFFACUMEntry 6 }

    tnPTOFFACUMAverage OBJECT-TYPE
        SYNTAX      Integer32
        UNITS       "ns"
        MAX-ACCESS  read-only
        STATUS      current
        DESCRIPTION "Average PTP clock Time Offset Accumulation (ns).
                     When the value equal 0x80000000(-2147483648),
                     it should be shown as 'N/A'(i.e. Not Available)."
        ::= { tnPTOFFACUMEntry 7 }

    tnPTOFFACUMSum OBJECT-TYPE
        SYNTAX      Integer32
        UNITS       "ns"
        MAX-ACCESS  read-only
        STATUS      current
        DESCRIPTION "Sum PTP clock Time Offset Accumulation (ns).
                     When the value equal 0x80000000(-2147483648),
                     it should be shown as 'N/A'(i.e. Not Available)."
        ::= { tnPTOFFACUMEntry 8 }

    tnPTOFFACUMPeakToPeakTr OBJECT-TYPE
        SYNTAX      Integer32
        UNITS       "ns"
        MAX-ACCESS  read-only
        STATUS      current
        DESCRIPTION "Peak to Peak threshold for 15 minute PTP
                     clock Time Offset Accumulation (ns)."
        ::= { tnPTOFFACUMEntry 9 }

    tnPTOFFACUMPeakToPeakRtr OBJECT-TYPE
        SYNTAX      Integer32
        UNITS       "ns"
        MAX-ACCESS  read-only
        STATUS      current
        DESCRIPTION "Peak to Peak reset threshold for 15 minute
                     PTP clock Time Offset Accumulation (ns)."
        ::= { tnPTOFFACUMEntry 10 }

    tnPTOFFACUMPeakToPeak1DayTr OBJECT-TYPE
        SYNTAX      Integer32
        UNITS       "ns"
        MAX-ACCESS  read-only
        STATUS      current
        DESCRIPTION "Peak to Peak threshold for 1 day PTP clock
                     Time Offset Accumulation (ns)."
        ::= { tnPTOFFACUMEntry 11 }

--------------------------------------------------------------------------------
-- Cycle Slips Rate (CSR) Statistics Scalar
--------------------------------------------------------------------------------
    tnCsrStatsTotalMembers OBJECT-TYPE
        SYNTAX      Integer32
        MAX-ACCESS  read-only
        STATUS      current
        DESCRIPTION "The total number of members in the CSR stats table."
        ::= { tnStatisticsGrouping 91 }

--------------------------------------------------------------------------------
-- Cycle Slips Rate (CSR) Statistics Table
--------------------------------------------------------------------------------
    tnCsrStatsTable OBJECT-TYPE
        SYNTAX      SEQUENCE OF TnCsrStatsEntry
        MAX-ACCESS  not-accessible
        STATUS      current
        DESCRIPTION "."
        ::= { tnStatisticsGrouping 92 }

    tnCsrStatsEntry OBJECT-TYPE
        SYNTAX      TnCsrStatsEntry
        MAX-ACCESS  not-accessible
        STATUS      current
        DESCRIPTION "."
        INDEX   { ifIndex,
                  tnStatsInterval,
                  tnCsrStatsBin }
        ::= { tnCsrStatsTable 1 }

    TnCsrStatsEntry ::=
        SEQUENCE {
            tnCsrStatsBin         TnStatsBinType,
            tnCsrStatsBinStatus   TnStatsBinStatus,
            tnCsrStatsStartTime   DateAndTime,
            tnCsrStatMin          SnmpAdminString,
            tnCsrStatMax          SnmpAdminString,
            tnCsrStatAverage      SnmpAdminString
        }

    tnCsrStatsBin OBJECT-TYPE
        SYNTAX      TnStatsBinType
        MAX-ACCESS  not-accessible
        STATUS      current
        DESCRIPTION "The bin number, starting with bin 0."
        ::= { tnCsrStatsEntry 1 }

    tnCsrStatsBinStatus OBJECT-TYPE
        SYNTAX      TnStatsBinStatus
        MAX-ACCESS  read-only
        STATUS      current
        DESCRIPTION "This attribute indicates the validity of the bin."
        ::= { tnCsrStatsEntry 2 }

    tnCsrStatsStartTime OBJECT-TYPE
        SYNTAX      DateAndTime
        MAX-ACCESS  read-only
        STATUS      current
        DESCRIPTION "This attribute is the bin collection start date and time."
        ::= { tnCsrStatsEntry 3 }

    tnCsrStatMin OBJECT-TYPE
        SYNTAX      SnmpAdminString
        MAX-ACCESS  read-only
        STATUS      current
        DESCRIPTION "Minimum CSR received (ps)."
        ::= { tnCsrStatsEntry 4 }

    tnCsrStatMax OBJECT-TYPE
        SYNTAX      SnmpAdminString
        MAX-ACCESS  read-only
        STATUS      current
        DESCRIPTION "Maximum CSR received (ps)."
        ::= { tnCsrStatsEntry 5 }

    tnCsrStatAverage OBJECT-TYPE
        SYNTAX      SnmpAdminString
        MAX-ACCESS  read-only
        STATUS      current
        DESCRIPTION "Average CSR received (ps)."
        ::= { tnCsrStatsEntry 6 }

--------------------------------------------------------------------------------
-- Q-Margin Statistics Scalar
--------------------------------------------------------------------------------
    tnQmarginStatsTotalMembers OBJECT-TYPE
        SYNTAX      Integer32
        MAX-ACCESS  read-only
        STATUS      current
        DESCRIPTION "The total number of members in the Qmargin stats table."
        ::= { tnStatisticsGrouping 93 }

--------------------------------------------------------------------------------
-- Q-Margin Statistics Table
--------------------------------------------------------------------------------
    tnQmarginStatsTable OBJECT-TYPE
        SYNTAX      SEQUENCE OF TnQmarginStatsEntry
        MAX-ACCESS  not-accessible
        STATUS      current
        DESCRIPTION "."
        ::= { tnStatisticsGrouping 94 }

    tnQmarginStatsEntry OBJECT-TYPE
        SYNTAX      TnQmarginStatsEntry
        MAX-ACCESS  not-accessible
        STATUS      current
        DESCRIPTION "."
        INDEX   { ifIndex,
                  tnStatsInterval,
                  tnQmarginStatsBin }
        ::= { tnQmarginStatsTable 1 }

    TnQmarginStatsEntry ::=
        SEQUENCE {
            tnQmarginStatsBin         TnStatsBinType,
            tnQmarginStatsBinStatus   TnStatsBinStatus,
            tnQmarginStatsStartTime   DateAndTime,
            tnQmarginStatMin          Integer32,
            tnQmarginStatMax          Integer32,
            tnQmarginStatAverage      Integer32,
            tnQmarginStatMin15MinTr   Integer32,
            tnQmarginStatMin15MinRtr  Integer32,
            tnQmarginStatMin1DayTr    Integer32
        }

    tnQmarginStatsBin OBJECT-TYPE
        SYNTAX      TnStatsBinType
        MAX-ACCESS  not-accessible
        STATUS      current
        DESCRIPTION "The bin number, starting with bin 0."
        ::= { tnQmarginStatsEntry 1 }

    tnQmarginStatsBinStatus OBJECT-TYPE
        SYNTAX      TnStatsBinStatus
        MAX-ACCESS  read-only
        STATUS      current
        DESCRIPTION "This attribute indicates the validity of the bin."
        ::= { tnQmarginStatsEntry 2 }

    tnQmarginStatsStartTime OBJECT-TYPE
        SYNTAX      DateAndTime
        MAX-ACCESS  read-only
        STATUS      current
        DESCRIPTION "This attribute is the bin collection start date and time."
        ::= { tnQmarginStatsEntry 3 }

    tnQmarginStatMin OBJECT-TYPE
        SYNTAX      Integer32
        UNITS       "ps"
        MAX-ACCESS  read-only
        STATUS      current
        DESCRIPTION "Minimum Qmargin received (ps)."
        ::= { tnQmarginStatsEntry 4 }

    tnQmarginStatMax OBJECT-TYPE
        SYNTAX      Integer32
        UNITS       "ps"
        MAX-ACCESS  read-only
        STATUS      current
        DESCRIPTION "Maximum Qmargin received (ps)."
        ::= { tnQmarginStatsEntry 5 }

    tnQmarginStatAverage OBJECT-TYPE
        SYNTAX      Integer32
        UNITS       "ps"
        MAX-ACCESS  read-only
        STATUS      current
        DESCRIPTION "Average Qmargin received (ps)."
        ::= { tnQmarginStatsEntry 6 }

    tnQmarginStatMin15MinTr OBJECT-TYPE
        SYNTAX      Integer32
        UNITS       "ps"
        MAX-ACCESS  read-only
        STATUS      current
        DESCRIPTION "."
        ::= { tnQmarginStatsEntry 7 }

    tnQmarginStatMin15MinRtr OBJECT-TYPE
        SYNTAX      Integer32
        UNITS       "ps"
        MAX-ACCESS  read-only
        STATUS      current
        DESCRIPTION "."
        ::= { tnQmarginStatsEntry 8 }

    tnQmarginStatMin1DayTr OBJECT-TYPE
        SYNTAX      Integer32
        UNITS       "ps"
        MAX-ACCESS  read-only
        STATUS      current
        DESCRIPTION "."
        ::= { tnQmarginStatsEntry 9 }

--------------------------------------------------------------------------------
-- Polariazation Dependent Loss (PDL) Statistics Scalar
--------------------------------------------------------------------------------
    tnPdlStatsTotalMembers OBJECT-TYPE
        SYNTAX      Integer32
        MAX-ACCESS  read-only
        STATUS      current
        DESCRIPTION "The total number of members in the PDL stats table."
        ::= { tnStatisticsGrouping 95 }

--------------------------------------------------------------------------------
-- Polariazation Dependent Loss (PDL) Statistics Table
--------------------------------------------------------------------------------
    tnPdlStatsTable OBJECT-TYPE
        SYNTAX      SEQUENCE OF TnPdlStatsEntry
        MAX-ACCESS  not-accessible
        STATUS      current
        DESCRIPTION "."
        ::= { tnStatisticsGrouping 96 }

    tnPdlStatsEntry OBJECT-TYPE
        SYNTAX      TnPdlStatsEntry
        MAX-ACCESS  not-accessible
        STATUS      current
        DESCRIPTION "."
        INDEX   { ifIndex,
                  tnStatsInterval,
                  tnPdlStatsBin }
        ::= { tnPdlStatsTable 1 }

    TnPdlStatsEntry ::=
        SEQUENCE {
            tnPdlStatsBin         TnStatsBinType,
            tnPdlStatsBinStatus   TnStatsBinStatus,
            tnPdlStatsStartTime   DateAndTime,
            tnPdlStatMin          Integer32,
            tnPdlStatMax          Integer32,
            tnPdlStatAverage      Integer32
        }

    tnPdlStatsBin OBJECT-TYPE
        SYNTAX      TnStatsBinType
        MAX-ACCESS  not-accessible
        STATUS      current
        DESCRIPTION "."
        ::= { tnPdlStatsEntry 1 }

    tnPdlStatsBinStatus OBJECT-TYPE
        SYNTAX      TnStatsBinStatus
        MAX-ACCESS  read-only
        STATUS      current
        DESCRIPTION "."
        ::= { tnPdlStatsEntry 2 }

    tnPdlStatsStartTime OBJECT-TYPE
        SYNTAX      DateAndTime
        MAX-ACCESS  read-only
        STATUS      current
        DESCRIPTION "."
        ::= { tnPdlStatsEntry 3 }

    tnPdlStatMin OBJECT-TYPE
        SYNTAX      Integer32
        MAX-ACCESS  read-only
        STATUS      current
        DESCRIPTION "."
        ::= { tnPdlStatsEntry 4 }

    tnPdlStatMax OBJECT-TYPE
        SYNTAX      Integer32
        MAX-ACCESS  read-only
        STATUS      current
        DESCRIPTION "."
        ::= { tnPdlStatsEntry 5 }

    tnPdlStatAverage OBJECT-TYPE
        SYNTAX      Integer32
        MAX-ACCESS  read-only
        STATUS      current
        DESCRIPTION "."
        ::= { tnPdlStatsEntry 6 }

--------------------------------------------------------------------------------
-- State of Polariazation Change Rate (SOPR) Statistics Scalar
--------------------------------------------------------------------------------
    tnSoprStatsTotalMembers OBJECT-TYPE
        SYNTAX      Integer32
        MAX-ACCESS  read-only
        STATUS      current
        DESCRIPTION "The total number of members in the SOPR stats table."
        ::= { tnStatisticsGrouping 97 }

--------------------------------------------------------------------------------
-- State of Polariazation Change Rate (SOPR) Statistics Table
--------------------------------------------------------------------------------
    tnSoprStatsTable OBJECT-TYPE
        SYNTAX      SEQUENCE OF TnSoprStatsEntry
        MAX-ACCESS  not-accessible
        STATUS      current
        DESCRIPTION "."
        ::= { tnStatisticsGrouping 98 }

    tnSoprStatsEntry OBJECT-TYPE
        SYNTAX      TnSoprStatsEntry
        MAX-ACCESS  not-accessible
        STATUS      current
        DESCRIPTION "."
        INDEX   { ifIndex,
                  tnStatsInterval,
                  tnSoprStatsBin }
        ::= { tnSoprStatsTable 1 }

    TnSoprStatsEntry ::=
        SEQUENCE {
            tnSoprStatsBin         TnStatsBinType,
            tnSoprStatsBinStatus   TnStatsBinStatus,
            tnSoprStatsStartTime   DateAndTime,
            tnSoprStatMin          Integer32,
            tnSoprStatMax          Integer32,
            tnSoprStatAverage      Integer32
        }

    tnSoprStatsBin OBJECT-TYPE
        SYNTAX      TnStatsBinType
        MAX-ACCESS  not-accessible
        STATUS      current
        DESCRIPTION "."
        ::= { tnSoprStatsEntry 1 }

    tnSoprStatsBinStatus OBJECT-TYPE
        SYNTAX      TnStatsBinStatus
        MAX-ACCESS  read-only
        STATUS      current
        DESCRIPTION "."
        ::= { tnSoprStatsEntry 2 }

    tnSoprStatsStartTime OBJECT-TYPE
        SYNTAX      DateAndTime
        MAX-ACCESS  read-only
        STATUS      current
        DESCRIPTION "."
        ::= { tnSoprStatsEntry 3 }

    tnSoprStatMin OBJECT-TYPE
        SYNTAX      Integer32
        MAX-ACCESS  read-only
        STATUS      current
        DESCRIPTION "."
        ::= { tnSoprStatsEntry 4 }

    tnSoprStatMax OBJECT-TYPE
        SYNTAX      Integer32
        MAX-ACCESS  read-only
        STATUS      current
        DESCRIPTION "."
        ::= { tnSoprStatsEntry 5 }

    tnSoprStatAverage OBJECT-TYPE
        SYNTAX      Integer32
        MAX-ACCESS  read-only
        STATUS      current
        DESCRIPTION "."
        ::= { tnSoprStatsEntry 6 }

--------------------------------------------------------------------------------
-- Electrical Signal to Noise Ratio (ESNR) Statistics Scalar
--------------------------------------------------------------------------------
    tnEsnrStatsTotalMembers OBJECT-TYPE
        SYNTAX      Integer32
        MAX-ACCESS  read-only
        STATUS      current
        DESCRIPTION "The total number of members in the ESNR stats table."
        ::= { tnStatisticsGrouping 99 }

--------------------------------------------------------------------------------
-- Electrical Signal to Noise Ratio (ESNR) Statistics Table
--------------------------------------------------------------------------------
    tnEsnrStatsTable OBJECT-TYPE
        SYNTAX      SEQUENCE OF TnEsnrStatsEntry
        MAX-ACCESS  not-accessible
        STATUS      current
        DESCRIPTION "."
        ::= { tnStatisticsGrouping 100 }

    tnEsnrStatsEntry OBJECT-TYPE
        SYNTAX      TnEsnrStatsEntry
        MAX-ACCESS  not-accessible
        STATUS      current
        DESCRIPTION "."
        INDEX   { ifIndex,
                  tnStatsInterval,
                  tnEsnrStatsBin }
        ::= { tnEsnrStatsTable 1 }

    TnEsnrStatsEntry ::=
        SEQUENCE {
            tnEsnrStatsBin         TnStatsBinType,
            tnEsnrStatsBinStatus   TnStatsBinStatus,
            tnEsnrStatsStartTime   DateAndTime,
            tnEsnrStatMin          Integer32,
            tnEsnrStatMax          Integer32,
            tnEsnrStatAverage      Integer32
        }

    tnEsnrStatsBin OBJECT-TYPE
        SYNTAX      TnStatsBinType
        MAX-ACCESS  not-accessible
        STATUS      current
        DESCRIPTION "."
        ::= { tnEsnrStatsEntry 1 }

    tnEsnrStatsBinStatus OBJECT-TYPE
        SYNTAX      TnStatsBinStatus
        MAX-ACCESS  read-only
        STATUS      current
        DESCRIPTION "."
        ::= { tnEsnrStatsEntry 2 }

    tnEsnrStatsStartTime OBJECT-TYPE
        SYNTAX      DateAndTime
        MAX-ACCESS  read-only
        STATUS      current
        DESCRIPTION "."
        ::= { tnEsnrStatsEntry 3 }

    tnEsnrStatMin OBJECT-TYPE
        SYNTAX      Integer32
        MAX-ACCESS  read-only
        STATUS      current
        DESCRIPTION "."
        ::= { tnEsnrStatsEntry 4 }

    tnEsnrStatMax OBJECT-TYPE
        SYNTAX      Integer32
        MAX-ACCESS  read-only
        STATUS      current
        DESCRIPTION "."
        ::= { tnEsnrStatsEntry 5 }

    tnEsnrStatAverage OBJECT-TYPE
        SYNTAX      Integer32
        MAX-ACCESS  read-only
        STATUS      current
        DESCRIPTION "."
        ::= { tnEsnrStatsEntry 6 }

--------------------------------------------------------------------------------
-- Optical Super Channel In (OPSUPCHIN) Statistics Scalar
--------------------------------------------------------------------------------
    tnOpSupChInStatsTotalMembers OBJECT-TYPE
        SYNTAX      Integer32
        MAX-ACCESS  read-only
        STATUS      current
        DESCRIPTION "The total number of members in the OPSUPCHIN stats table."
        ::= { tnStatisticsGrouping 101 }

--------------------------------------------------------------------------------
-- Optical Super Channel In (OPSUPCHIN) Statistics Table
--------------------------------------------------------------------------------
    tnOpSupChInStatsTable OBJECT-TYPE
        SYNTAX      SEQUENCE OF TnOpSupChInStatsEntry
        MAX-ACCESS  not-accessible
        STATUS      current
        DESCRIPTION "."
        ::= { tnStatisticsGrouping 102 }

    tnOpSupChInStatsEntry OBJECT-TYPE
        SYNTAX      TnOpSupChInStatsEntry
        MAX-ACCESS  not-accessible
        STATUS      current
        DESCRIPTION "."
        INDEX   { ifIndex,
                  tnStatsInterval,
                  tnOpSupChInStatsBin,
                  tnOpSupChInCenterFrequency }
        ::= { tnOpSupChInStatsTable 1 }

    TnOpSupChInStatsEntry ::=
        SEQUENCE {
            tnOpSupChInStatsBin             TnStatsBinType,
            tnOpSupChInCenterFrequency      Integer32,
            tnOpSupChInStatsBinStatus       TnStatsBinStatus,
            tnOpSupChInStatsStartTime       DateAndTime,
            tnOpSupChInStatMinPower         Integer32,
            tnOpSupChInStatMaxPower         Integer32,
            tnOpSupChInStatAveragePower     Integer32,
            tnOpSupChInStatWidth            Unsigned32
        }

    tnOpSupChInStatsBin OBJECT-TYPE
        SYNTAX      TnStatsBinType
        MAX-ACCESS  not-accessible
        STATUS      current
        DESCRIPTION "The bin number, starting with bin 0."
        ::= { tnOpSupChInStatsEntry 1 }

    tnOpSupChInCenterFrequency OBJECT-TYPE
        SYNTAX      Integer32
        MAX-ACCESS  not-accessible
        STATUS      current
        DESCRIPTION "The Center Frequency."
        ::= { tnOpSupChInStatsEntry 2 }

    tnOpSupChInStatsBinStatus OBJECT-TYPE
        SYNTAX      TnStatsBinStatus
        MAX-ACCESS  read-only
        STATUS      current
        DESCRIPTION "This attribute indicates the validity of the bin."
        ::= { tnOpSupChInStatsEntry 3 }

    tnOpSupChInStatsStartTime OBJECT-TYPE
        SYNTAX      DateAndTime
        MAX-ACCESS  read-only
        STATUS      current
        DESCRIPTION "This attribute is the bin collection start date and time."
        ::= { tnOpSupChInStatsEntry 4 }

    tnOpSupChInStatMinPower OBJECT-TYPE
        SYNTAX      Integer32
        UNITS       "mBm"
        MAX-ACCESS  read-only
        STATUS      current
        DESCRIPTION "Minimum optical WT power in the In direction."
        ::= { tnOpSupChInStatsEntry 5 }

    tnOpSupChInStatMaxPower OBJECT-TYPE
        SYNTAX      Integer32
        UNITS       "mBm"
        MAX-ACCESS  read-only
        STATUS      current
        DESCRIPTION "Maximum optical WT power in the In direction."
        ::= { tnOpSupChInStatsEntry 6 }

    tnOpSupChInStatAveragePower OBJECT-TYPE
        SYNTAX      Integer32
        UNITS       "mBm"
        MAX-ACCESS  read-only
        STATUS      current
        DESCRIPTION "Average optical WT power in the In direction."
        ::= { tnOpSupChInStatsEntry 7 }

    tnOpSupChInStatWidth OBJECT-TYPE
        SYNTAX         Unsigned32
        UNITS          "MHz"
        MAX-ACCESS     read-only
        STATUS         current
        DESCRIPTION    "Channel width."
        ::= { tnOpSupChInStatsEntry 8 }

--------------------------------------------------------------------------------
-- Optical Super Channel Out (OPSUPCHOUT) Statistics Scalar
--------------------------------------------------------------------------------
    tnOpSupChOutStatsTotalMembers OBJECT-TYPE
        SYNTAX      Integer32
        MAX-ACCESS  read-only
        STATUS      current
        DESCRIPTION "The total number of members in the OPSUPCHOUT stats table."
        ::= { tnStatisticsGrouping 103 }

--------------------------------------------------------------------------------
-- Optical Super Channel Out (OPSUPCHOUT) Statistics Table
--------------------------------------------------------------------------------
    tnOpSupChOutStatsTable OBJECT-TYPE
        SYNTAX      SEQUENCE OF TnOpSupChOutStatsEntry
        MAX-ACCESS  not-accessible
        STATUS      current
        DESCRIPTION "."
        ::= { tnStatisticsGrouping 104 }

    tnOpSupChOutStatsEntry OBJECT-TYPE
        SYNTAX      TnOpSupChOutStatsEntry
        MAX-ACCESS  not-accessible
        STATUS      current
        DESCRIPTION "."
        INDEX   { ifIndex,
                  tnStatsInterval,
                  tnOpSupChOutStatsBin,
                  tnOpSupChOutCenterFrequency }
        ::= { tnOpSupChOutStatsTable 1 }

    TnOpSupChOutStatsEntry ::=
        SEQUENCE {
            tnOpSupChOutStatsBin             TnStatsBinType,
            tnOpSupChOutCenterFrequency      Integer32,
            tnOpSupChOutStatsBinStatus       TnStatsBinStatus,
            tnOpSupChOutStatsStartTime       DateAndTime,
            tnOpSupChOutStatMinPower         Integer32,
            tnOpSupChOutStatMaxPower         Integer32,
            tnOpSupChOutStatAveragePower     Integer32,
            tnOpSupChOutStatWidth            Unsigned32
        }

    tnOpSupChOutStatsBin OBJECT-TYPE
        SYNTAX      TnStatsBinType
        MAX-ACCESS  not-accessible
        STATUS      current
        DESCRIPTION "The bin number, starting with bin 0."
        ::= { tnOpSupChOutStatsEntry 1 }

    tnOpSupChOutCenterFrequency OBJECT-TYPE
        SYNTAX      Integer32
        MAX-ACCESS  not-accessible
        STATUS      current
        DESCRIPTION "The Center Frequency."
        ::= { tnOpSupChOutStatsEntry 2 }

    tnOpSupChOutStatsBinStatus OBJECT-TYPE
        SYNTAX      TnStatsBinStatus
        MAX-ACCESS  read-only
        STATUS      current
        DESCRIPTION "This attribute indicates the validity of the bin."
        ::= { tnOpSupChOutStatsEntry 3 }

    tnOpSupChOutStatsStartTime OBJECT-TYPE
        SYNTAX      DateAndTime
        MAX-ACCESS  read-only
        STATUS      current
        DESCRIPTION "This attribute is the bin collection start date and time."
        ::= { tnOpSupChOutStatsEntry 4 }

    tnOpSupChOutStatMinPower OBJECT-TYPE
        SYNTAX      Integer32
        UNITS       "mBm"
        MAX-ACCESS  read-only
        STATUS      current
        DESCRIPTION "Minimum optical WT power in the Out direction."
        ::= { tnOpSupChOutStatsEntry 5 }

    tnOpSupChOutStatMaxPower OBJECT-TYPE
        SYNTAX      Integer32
        UNITS       "mBm"
        MAX-ACCESS  read-only
        STATUS      current
        DESCRIPTION "Maximum optical WT power in the Out direction."
        ::= { tnOpSupChOutStatsEntry 6 }

    tnOpSupChOutStatAveragePower OBJECT-TYPE
        SYNTAX      Integer32
        UNITS       "mBm"
        MAX-ACCESS  read-only
        STATUS      current
        DESCRIPTION "Average optical WT power in the Out direction."
        ::= { tnOpSupChOutStatsEntry 7 }

    tnOpSupChOutStatWidth OBJECT-TYPE
        SYNTAX         Unsigned32
        UNITS          "MHz"
        MAX-ACCESS     read-only
        STATUS         current
        DESCRIPTION    "Channel width."
        ::= { tnOpSupChOutStatsEntry 8 }

--------------------------------------------------------------------------------
-- Error Vector Magnitude (EVM) Statistics Scalar
--------------------------------------------------------------------------------
    tnEvmStatsTotalMembers OBJECT-TYPE
        SYNTAX      Integer32
        MAX-ACCESS  read-only
        STATUS      current
        DESCRIPTION "The total number of members in the EVM stats table."
        ::= { tnStatisticsGrouping 105 }

--------------------------------------------------------------------------------
-- Error Vector Magnitude (EVM) Statistics Table
--------------------------------------------------------------------------------
    tnEvmStatsTable OBJECT-TYPE
        SYNTAX      SEQUENCE OF TnEvmStatsEntry
        MAX-ACCESS  not-accessible
        STATUS      current
        DESCRIPTION "."
        ::= { tnStatisticsGrouping 106 }

    tnEvmStatsEntry OBJECT-TYPE
        SYNTAX      TnEvmStatsEntry
        MAX-ACCESS  not-accessible
        STATUS      current
        DESCRIPTION "."
        INDEX   { ifIndex,
                  tnStatsInterval,
                  tnEvmStatsBin }
        ::= { tnEvmStatsTable 1 }

    TnEvmStatsEntry ::=
        SEQUENCE {
            tnEvmStatsBin         TnStatsBinType,
            tnEvmStatsBinStatus   TnStatsBinStatus,
            tnEvmStatsStartTime   DateAndTime,
            tnEvmStatMin          SnmpAdminString,
            tnEvmStatMax          SnmpAdminString,
            tnEvmStatAverage      SnmpAdminString
        }

    tnEvmStatsBin OBJECT-TYPE
        SYNTAX      TnStatsBinType
        MAX-ACCESS  not-accessible
        STATUS      current
        DESCRIPTION "The bin number, starting with bin 0."
        ::= { tnEvmStatsEntry 1 }

    tnEvmStatsBinStatus OBJECT-TYPE
        SYNTAX      TnStatsBinStatus
        MAX-ACCESS  read-only
        STATUS      current
        DESCRIPTION "This attribute indicates the validity of the bin."
        ::= { tnEvmStatsEntry 2 }

    tnEvmStatsStartTime OBJECT-TYPE
        SYNTAX      DateAndTime
        MAX-ACCESS  read-only
        STATUS      current
        DESCRIPTION "This attribute is the bin collection start date and time."
        ::= { tnEvmStatsEntry 3 }

    tnEvmStatMin OBJECT-TYPE
        SYNTAX      SnmpAdminString
        MAX-ACCESS  read-only
        STATUS      current
        DESCRIPTION "Minimum EVM received."
        ::= { tnEvmStatsEntry 4 }

    tnEvmStatMax OBJECT-TYPE
        SYNTAX      SnmpAdminString
        MAX-ACCESS  read-only
        STATUS      current
        DESCRIPTION "Maximum EVM received."
        ::= { tnEvmStatsEntry 5 }

    tnEvmStatAverage OBJECT-TYPE
        SYNTAX      SnmpAdminString
        MAX-ACCESS  read-only
        STATUS      current
        DESCRIPTION "Average EVM received."
        ::= { tnEvmStatsEntry 6 }

--------------------------------------------------------------------------------
-- Optical Signal Noise Ratio Rx (OSNRRx) Statistics Scalar
--------------------------------------------------------------------------------
    tnOsnrRxStatsTotalMembers OBJECT-TYPE
        SYNTAX      Integer32
        MAX-ACCESS  read-only
        STATUS      current
        DESCRIPTION "The total number of members in the OSNRRx stats table."
        ::= { tnStatisticsGrouping 107 }

--------------------------------------------------------------------------------
-- Optical Signal Noise Ratio Rx (OSNRRx) Statistics Table
--------------------------------------------------------------------------------
    tnOsnrRxStatsTable OBJECT-TYPE
        SYNTAX      SEQUENCE OF TnOsnrRxStatsEntry
        MAX-ACCESS  not-accessible
        STATUS      current
        DESCRIPTION "."
        ::= { tnStatisticsGrouping 108 }

    tnOsnrRxStatsEntry OBJECT-TYPE
        SYNTAX      TnOsnrRxStatsEntry
        MAX-ACCESS  not-accessible
        STATUS      current
        DESCRIPTION "."
        INDEX   { ifIndex,
                  tnStatsInterval,
                  tnOsnrRxStatsBin }
        ::= { tnOsnrRxStatsTable 1 }

    TnOsnrRxStatsEntry ::=
        SEQUENCE {
            tnOsnrRxStatsBin           TnStatsBinType,
            tnOsnrRxStatsBinStatus     TnStatsBinStatus,
            tnOsnrRxStatsStartTime     DateAndTime,
            tnOsnrRxStatMin            Integer32,
            tnOsnrRxStatMax            Integer32,
            tnOsnrRxStatAverage        Integer32
        }

    tnOsnrRxStatsBin OBJECT-TYPE
        SYNTAX      TnStatsBinType
        MAX-ACCESS  not-accessible
        STATUS      current
        DESCRIPTION "The bin number, starting with bin 0."
        ::= { tnOsnrRxStatsEntry 1 }

    tnOsnrRxStatsBinStatus OBJECT-TYPE
        SYNTAX      TnStatsBinStatus
        MAX-ACCESS  read-only
        STATUS      current
        DESCRIPTION "This attribute indicates the validity of the bin."
        ::= { tnOsnrRxStatsEntry 2 }

    tnOsnrRxStatsStartTime OBJECT-TYPE
        SYNTAX      DateAndTime
        MAX-ACCESS  read-only
        STATUS      current
        DESCRIPTION "This attribute is the bin collection start date and time."
        ::= { tnOsnrRxStatsEntry 3 }

    tnOsnrRxStatMin OBJECT-TYPE
        SYNTAX      Integer32
        UNITS       "0.01dB"
        MAX-ACCESS  read-only
        STATUS      current
        DESCRIPTION "Minimum OSNR."
        ::= { tnOsnrRxStatsEntry 4 }

    tnOsnrRxStatMax OBJECT-TYPE
        SYNTAX      Integer32
        UNITS       "0.01dB"
        MAX-ACCESS  read-only
        STATUS      current
        DESCRIPTION "Maximum OSNR."
        ::= { tnOsnrRxStatsEntry 5 }

    tnOsnrRxStatAverage OBJECT-TYPE
        SYNTAX      Integer32
        UNITS       "0.01dB"
        MAX-ACCESS  read-only
        STATUS      current
        DESCRIPTION "Average OSNR."
        ::= { tnOsnrRxStatsEntry 6 }

--------------------------------------------------------------------------------
-- Qfactor Statistics Scalar
--------------------------------------------------------------------------------
    tnQfactorStatsTotalMembers OBJECT-TYPE
        SYNTAX      Integer32
        MAX-ACCESS  read-only
        STATUS      current
        DESCRIPTION "The total number of members in the Qfactor stats table."
        ::= { tnStatisticsGrouping 109 }

--------------------------------------------------------------------------------
-- Qfactor Statistics Table
--------------------------------------------------------------------------------
    tnQfactorStatsTable OBJECT-TYPE
        SYNTAX      SEQUENCE OF TnQfactorStatsEntry
        MAX-ACCESS  not-accessible
        STATUS      current
        DESCRIPTION "."
        ::= { tnStatisticsGrouping 110 }

    tnQfactorStatsEntry OBJECT-TYPE
        SYNTAX      TnQfactorStatsEntry
        MAX-ACCESS  not-accessible
        STATUS      current
        DESCRIPTION "."
        INDEX   { ifIndex,
                  tnStatsInterval,
                  tnQfactorStatsBin }
        ::= { tnQfactorStatsTable 1 }

    TnQfactorStatsEntry ::=
        SEQUENCE {
            tnQfactorStatsBin           TnStatsBinType,
            tnQfactorStatsBinStatus     TnStatsBinStatus,
            tnQfactorStatsStartTime     DateAndTime,
            tnQfactorStatMin            Integer32,
            tnQfactorStatMax            Integer32,
            tnQfactorStatAverage        Integer32
        }

    tnQfactorStatsBin OBJECT-TYPE
        SYNTAX      TnStatsBinType
        MAX-ACCESS  not-accessible
        STATUS      current
        DESCRIPTION "The bin number, starting with bin 0."
        ::= { tnQfactorStatsEntry 1 }

    tnQfactorStatsBinStatus OBJECT-TYPE
        SYNTAX      TnStatsBinStatus
        MAX-ACCESS  read-only
        STATUS      current
        DESCRIPTION "This attribute indicates the validity of the bin."
        ::= { tnQfactorStatsEntry 2 }

    tnQfactorStatsStartTime OBJECT-TYPE
        SYNTAX      DateAndTime
        MAX-ACCESS  read-only
        STATUS      current
        DESCRIPTION "This attribute is the bin collection start date and time."
        ::= { tnQfactorStatsEntry 3 }

    tnQfactorStatMin OBJECT-TYPE
        SYNTAX      Integer32
        UNITS       "0.01dB"
        MAX-ACCESS  read-only
        STATUS      current
        DESCRIPTION "Minimum Qfactor received."
        ::= { tnQfactorStatsEntry 4 }

    tnQfactorStatMax OBJECT-TYPE
        SYNTAX      Integer32
        UNITS       "0.01dB"
        MAX-ACCESS  read-only
        STATUS      current
        DESCRIPTION "Maximum Qfactor received."
        ::= { tnQfactorStatsEntry 5 }

    tnQfactorStatAverage OBJECT-TYPE
        SYNTAX      Integer32
        UNITS       "0.01dB"
        MAX-ACCESS  read-only
        STATUS      current
        DESCRIPTION "Average Qfactor received."
        ::= { tnQfactorStatsEntry 6 }

--------------------------------------------------------------------------------
-- OCHOPR Statistics Scalar
--------------------------------------------------------------------------------
    tnOchOprStatsTotalMembers OBJECT-TYPE
        SYNTAX      Integer32
        MAX-ACCESS  read-only
        STATUS      current
        DESCRIPTION "The total number of members in the OCHOPR stats table."
        ::= { tnStatisticsGrouping 111 }

--------------------------------------------------------------------------------
-- OCHOPR Statistics Table
--------------------------------------------------------------------------------
    tnOchOprStatsTable OBJECT-TYPE
        SYNTAX      SEQUENCE OF TnOchOprStatsEntry
        MAX-ACCESS  not-accessible
        STATUS      current
        DESCRIPTION "."
        ::= { tnStatisticsGrouping 112 }

    tnOchOprStatsEntry OBJECT-TYPE
        SYNTAX      TnOchOprStatsEntry
        MAX-ACCESS  not-accessible
        STATUS      current
        DESCRIPTION "."
        INDEX   { ifIndex,
                  tnStatsInterval,
                  tnOchOprStatsBin }
        ::= { tnOchOprStatsTable 1 }

    TnOchOprStatsEntry ::=
        SEQUENCE {
            tnOchOprStatsBin              TnStatsBinType,
            tnOchOprStatsBinStatus        TnStatsBinStatus,
            tnOchOprStatsStartTime        DateAndTime,
            tnOchOprStatMinPower          Integer32,
            tnOchOprStatMaxPower          Integer32,
            tnOchOprStatAveragePower      Integer32,
            tnOchOprStatMinPowerTr        Integer32,
            tnOchOprStatMaxPowerTr        Integer32,
            tnOchOprStatMinPowerRtr       Integer32,
            tnOchOprStatMaxPowerRtr       Integer32
        }

    tnOchOprStatsBin OBJECT-TYPE
        SYNTAX      TnStatsBinType
        MAX-ACCESS  not-accessible
        STATUS      current
        DESCRIPTION "The bin number, starting with bin 0."
        ::= { tnOchOprStatsEntry 1 }

    tnOchOprStatsBinStatus OBJECT-TYPE
        SYNTAX      TnStatsBinStatus
        MAX-ACCESS  read-only
        STATUS      current
        DESCRIPTION "This attribute indicates the validity of the bin."
        ::= { tnOchOprStatsEntry 2 }

    tnOchOprStatsStartTime OBJECT-TYPE
        SYNTAX      DateAndTime
        MAX-ACCESS  read-only
        STATUS      current
        DESCRIPTION "This attribute is the bin collection start date
                     and time."
        ::= { tnOchOprStatsEntry 3 }

    tnOchOprStatMinPower OBJECT-TYPE
        SYNTAX      Integer32
        UNITS       "mBm"
        MAX-ACCESS  read-only
        STATUS      current
        DESCRIPTION "."
        ::= { tnOchOprStatsEntry 4 }

    tnOchOprStatMaxPower OBJECT-TYPE
        SYNTAX      Integer32
        UNITS       "mBm"
        MAX-ACCESS  read-only
        STATUS      current
        DESCRIPTION "."
        ::= { tnOchOprStatsEntry 5 }

    tnOchOprStatAveragePower OBJECT-TYPE
        SYNTAX      Integer32
        UNITS       "mBm"
        MAX-ACCESS  read-only
        STATUS      current
        DESCRIPTION "."
        ::= { tnOchOprStatsEntry 6 }

    tnOchOprStatMinPowerTr OBJECT-TYPE
        SYNTAX      Integer32
        UNITS       "mBm"
        MAX-ACCESS  read-only
        STATUS      current
        DESCRIPTION "."
        ::= { tnOchOprStatsEntry 7 }

    tnOchOprStatMaxPowerTr OBJECT-TYPE
        SYNTAX      Integer32
        UNITS       "mBm"
        MAX-ACCESS  read-only
        STATUS      current
        DESCRIPTION "."
        ::= { tnOchOprStatsEntry 8 }

    tnOchOprStatMinPowerRtr OBJECT-TYPE
        SYNTAX      Integer32
        UNITS       "mBm"
        MAX-ACCESS  read-only
        STATUS      current
        DESCRIPTION "."
        ::= { tnOchOprStatsEntry 9 }

    tnOchOprStatMaxPowerRtr OBJECT-TYPE
        SYNTAX      Integer32
        UNITS       "mBm"
        MAX-ACCESS  read-only
        STATUS      current
        DESCRIPTION "."
        ::= { tnOchOprStatsEntry 10 }

--------------------------------------------------------------------------------
-- FcPkt Statistics Scalar
--------------------------------------------------------------------------------
    tnFcPktStatsTotalMembers OBJECT-TYPE
        SYNTAX      Integer32
        MAX-ACCESS  read-only
        STATUS      current
        DESCRIPTION "The total number of members in the fcpkt stats table."
        ::= { tnStatisticsGrouping 113 }

--------------------------------------------------------------------------------
-- FcPkt Statistics Table
--------------------------------------------------------------------------------
    tnFcPktStatsTable OBJECT-TYPE
        SYNTAX      SEQUENCE OF TnFcPktStatsEntry
        MAX-ACCESS  not-accessible
        STATUS      current
        DESCRIPTION "."
        ::= { tnStatisticsGrouping 114 }

    tnFcPktStatsEntry OBJECT-TYPE
        SYNTAX      TnFcPktStatsEntry
        MAX-ACCESS  not-accessible
        STATUS      current
        DESCRIPTION "."
        INDEX   { ifIndex,
                  tnStatsInterval,
                  tnFcPktStatsBin }
        ::= { tnFcPktStatsTable 1 }

    TnFcPktStatsEntry ::=
        SEQUENCE {
            tnFcPktStatsBin               TnStatsBinType,
            tnFcPktStatsBinStatus         TnStatsBinStatus,
            tnFcPktStatsStartTime         DateAndTime,
            tnFcPktStatRxOctets           Counter64,
            tnFcPktStatRxPkts             Counter64,
            tnFcPktStatRxCrcAlignErrs     Counter64,
            tnFcPktStatTxOctets           Counter64,
            tnFcPktStatTxPkts             Counter64,
            tnFcPktStatTxCrcAlignErrs     Counter64
        }

    tnFcPktStatsBin OBJECT-TYPE
        SYNTAX      TnStatsBinType
        MAX-ACCESS  not-accessible
        STATUS      current
        DESCRIPTION "The bin number, starting with bin 0."
        ::= { tnFcPktStatsEntry 1 }

    tnFcPktStatsBinStatus OBJECT-TYPE
        SYNTAX      TnStatsBinStatus
        MAX-ACCESS  read-only
        STATUS      current
        DESCRIPTION "This attribute indicates the validity of the bin."
        ::= { tnFcPktStatsEntry 2 }

    tnFcPktStatsStartTime OBJECT-TYPE
        SYNTAX      DateAndTime
        MAX-ACCESS  read-only
        STATUS      current
        DESCRIPTION "This attribute is the bin collection start date and time."
        ::= { tnFcPktStatsEntry 3 }

    tnFcPktStatRxOctets OBJECT-TYPE
        SYNTAX      Counter64
        MAX-ACCESS  read-only
        STATUS      current
        DESCRIPTION "Provides a count of the total number of octets of data
                     (including the bad packets) received on the port.  Count
                     includes SOF delimiter,frame content, and an EOF
                     delimiter octets."
        ::= { tnFcPktStatsEntry 4 }

    tnFcPktStatRxPkts OBJECT-TYPE
        SYNTAX      Counter64
        MAX-ACCESS  read-only
        STATUS      current
        DESCRIPTION "Provides a count of the total number of packets (including
                     bad packet) received."
        ::= { tnFcPktStatsEntry 5 }

    tnFcPktStatRxCrcAlignErrs OBJECT-TYPE
        SYNTAX      Counter64
        MAX-ACCESS  read-only
        STATUS      current
        DESCRIPTION "Provides a count of the total number of packets received
                     that had CRC error."
        ::= { tnFcPktStatsEntry 6 }

    tnFcPktStatTxOctets OBJECT-TYPE
        SYNTAX      Counter64
        MAX-ACCESS  read-only
        STATUS      current
        DESCRIPTION "Provides a count of the total number of octets of data
                     (including the bad packets) transmited on the port.  Count
                     includes SOF delimiter,frame content,and an EOF delimiter
                     octets."
        ::= { tnFcPktStatsEntry 7 }

    tnFcPktStatTxPkts OBJECT-TYPE
        SYNTAX      Counter64
        MAX-ACCESS  read-only
        STATUS      current
        DESCRIPTION "Provides a count of the total number of packets (including
                     bad packet) transmited."
        ::= { tnFcPktStatsEntry 8 }

    tnFcPktStatTxCrcAlignErrs OBJECT-TYPE
        SYNTAX      Counter64
        MAX-ACCESS  read-only
        STATUS      current
        DESCRIPTION "Provides a count of the total number of packets transmited
                     that had CRC error."
        ::= { tnFcPktStatsEntry 9 }

--------------------------------------------------------------------------------
-- Raw Count Statistics Groups
--------------------------------------------------------------------------------

--------------------------------------------------------------------------------
-- Control Network Link Raw Count Statistics Scalar
--------------------------------------------------------------------------------
    tnControlNetworkLinkRawCountStatsTotalMembers OBJECT-TYPE
        SYNTAX      Integer32
        MAX-ACCESS  read-only
        STATUS      current
        DESCRIPTION "The total number of members in the CN link raw count stats
                     table."
        ::= { tnStatisticsRawCounts 1 }

--------------------------------------------------------------------------------
-- Control Network Link Raw Count Statistics Table
--------------------------------------------------------------------------------
    tnControlNetworkLinkRawCountStatsTable OBJECT-TYPE
        SYNTAX      SEQUENCE OF TnControlNetworkLinkRawCountStatsEntry
        MAX-ACCESS  not-accessible
        STATUS      current
        DESCRIPTION "."
        ::= { tnStatisticsRawCounts 2 }

    tnControlNetworkLinkRawCountStatsEntry OBJECT-TYPE
        SYNTAX      TnControlNetworkLinkRawCountStatsEntry
        MAX-ACCESS  not-accessible
        STATUS      current
        DESCRIPTION "."
        INDEX   { ifIndex }
        ::= { tnControlNetworkLinkRawCountStatsTable 1 }

    TnControlNetworkLinkRawCountStatsEntry ::=
        SEQUENCE {
            tnCNLinkRawCountStatIpInReceives     Counter32,
            tnCNLinkRawCountStatIpInDiscards     Counter32,
            tnCNLinkRawCountStatIpOutRequests    Counter32,
            tnCNLinkRawCountStatIpOutDiscards    Counter32,
            tnCNLinkRawCountStatIpForwDatagrams  Counter32
        }

    tnCNLinkRawCountStatIpInReceives OBJECT-TYPE
        SYNTAX      Counter32
        MAX-ACCESS  read-only
        STATUS      current
        DESCRIPTION "Count of Control Network link IP
                     packets received on the IN port of
                     the interface."
        ::= { tnControlNetworkLinkRawCountStatsEntry 1 }

    tnCNLinkRawCountStatIpInDiscards OBJECT-TYPE
        SYNTAX      Counter32
        MAX-ACCESS  read-only
        STATUS      current
        DESCRIPTION "Count of Control Network link IP
                     packets on the IN port of the interface
                     that were discarded."
        ::= { tnControlNetworkLinkRawCountStatsEntry 2 }

    tnCNLinkRawCountStatIpOutRequests OBJECT-TYPE
        SYNTAX      Counter32
        MAX-ACCESS  read-only
        STATUS      current
        DESCRIPTION "Count of Control Network link IP
                     packets transmitted on the OUT port of
                     the interface."
        ::= { tnControlNetworkLinkRawCountStatsEntry 3 }

    tnCNLinkRawCountStatIpOutDiscards OBJECT-TYPE
        SYNTAX      Counter32
        MAX-ACCESS  read-only
        STATUS      current
        DESCRIPTION "Count of Control Network link IP
                     packets on the OUT port of the interface
                     that were discarded."
        ::= { tnControlNetworkLinkRawCountStatsEntry 4 }

    tnCNLinkRawCountStatIpForwDatagrams OBJECT-TYPE
        SYNTAX      Counter32
        MAX-ACCESS  read-only
        STATUS      current
        DESCRIPTION "Count of Control Network link IP
                     forwarded datagrams."
        ::= { tnControlNetworkLinkRawCountStatsEntry 5 }

--------------------------------------------------------------------------------
-- Card Raw Count Statistics Scalar
--------------------------------------------------------------------------------
    tnCardRawCountStatsTotalMembers OBJECT-TYPE
        SYNTAX      Integer32
        MAX-ACCESS  read-only
        STATUS      current
        DESCRIPTION "The total number of members in the card raw count stats
                     table."
        ::= { tnStatisticsRawCounts 3 }

--------------------------------------------------------------------------------
-- Card Raw Count Statistics Table
--------------------------------------------------------------------------------
    tnCardRawCountStatsTable OBJECT-TYPE
        SYNTAX      SEQUENCE OF TnCardRawCountStatsEntry
        MAX-ACCESS  not-accessible
        STATUS      current
        DESCRIPTION "."
        ::= { tnStatisticsRawCounts 4 }

    tnCardRawCountStatsEntry OBJECT-TYPE
        SYNTAX      TnCardRawCountStatsEntry
        MAX-ACCESS  not-accessible
        STATUS      current
        DESCRIPTION "."
        INDEX   { tnShelfIndex,
                  tnSlotIndex,
                  tnCardStatsProcessor }
        ::= { tnCardRawCountStatsTable 1 }

    TnCardRawCountStatsEntry ::=
        SEQUENCE {
            tnCardRawCountStatsClear      TnCommand,
            tnCardRawCountStatCpuAverage  Counter32,
            tnCardRawCountStatHeapUsage   Counter32,
            tnCardRawCountStatPoolUsage   Counter32,
            tnCardRawCountStatStartTime   DateAndTime
        }

    tnCardRawCountStatsClear OBJECT-TYPE
        SYNTAX      TnCommand
        MAX-ACCESS  read-create
        STATUS      current
        DESCRIPTION "This attribute is used to clear all the
                     raw counts on a particular interface
                     and group."
        ::= { tnCardRawCountStatsEntry 1 }

    tnCardRawCountStatCpuAverage OBJECT-TYPE
        SYNTAX      Counter32
        MAX-ACCESS  read-only
        STATUS      current
        DESCRIPTION "The average CPU usage as a percentage."
        ::= { tnCardRawCountStatsEntry 2 }

    tnCardRawCountStatHeapUsage OBJECT-TYPE
        SYNTAX      Counter32
        MAX-ACCESS  read-only
        STATUS      current
        DESCRIPTION "The heap usage as a percentage."
        ::= { tnCardRawCountStatsEntry 3 }

    tnCardRawCountStatPoolUsage OBJECT-TYPE
        SYNTAX      Counter32
        MAX-ACCESS  read-only
        STATUS      current
        DESCRIPTION "The pool usage as a percentage."
        ::= { tnCardRawCountStatsEntry 4 }

    tnCardRawCountStatStartTime OBJECT-TYPE
        SYNTAX      DateAndTime
        MAX-ACCESS  read-only
        STATUS      current
        DESCRIPTION "This attribute is the bin collection start date
                     and time."
        ::= { tnCardRawCountStatsEntry 5 }

--------------------------------------------------------------------------------
-- Interface Raw Count Statistics Scalar
--------------------------------------------------------------------------------
    tnInterfaceRawCountStatsTotalMembers OBJECT-TYPE
        SYNTAX      Integer32
        MAX-ACCESS  read-only
        STATUS      current
        DESCRIPTION "The total number of members in the interface raw count stats
                     table."
        ::= { tnStatisticsRawCounts 5 }

--------------------------------------------------------------------------------
-- Interface Raw Count Statistics Table
--------------------------------------------------------------------------------
    tnInterfaceRawCountStatsTable OBJECT-TYPE
        SYNTAX      SEQUENCE OF TnInterfaceRawCountStatsEntry
        MAX-ACCESS  not-accessible
        STATUS      current
        DESCRIPTION "."
        ::= { tnStatisticsRawCounts 6 }

    tnInterfaceRawCountStatsEntry OBJECT-TYPE
        SYNTAX      TnInterfaceRawCountStatsEntry
        MAX-ACCESS  not-accessible
        STATUS      current
        DESCRIPTION "."
        INDEX   { ifIndex }
        ::= { tnInterfaceRawCountStatsTable 1 }

    TnInterfaceRawCountStatsEntry ::=
        SEQUENCE {
            tnIfRawCountStatsClear                  TnCommand,
            tnIfRawCountStatInOctets                Counter64,
            tnIfRawCountStatInUcastPkts             Counter64,
            tnIfRawCountStatInDiscards              Counter64,
            tnIfRawCountStatInErrors                Counter64,
            tnIfRawCountStatInUnknownProtos         Counter64,
            tnIfRawCountStatOutOctets               Counter64,
            tnIfRawCountStatOutUcastPkts            Counter64,
            tnIfRawCountStatOutDiscards             Counter64,
            tnIfRawCountStatOutErrors               Counter64,
            tnIfRawCountStatInMulticastPkts         Counter64,
            tnIfRawCountStatInBroadcastPkts         Counter64,
            tnIfRawCountStatOutMulticastPkts        Counter64,
            tnIfRawCountStatOutBroadcastPkts        Counter64,
            tnIfRawCountStatInPacketsNotClassified  Counter64,
            tnIfRawCountStatStartTime               DateAndTime
        }

    tnIfRawCountStatsClear OBJECT-TYPE
        SYNTAX      TnCommand
        MAX-ACCESS  read-create
        STATUS      current
        DESCRIPTION "This attribute is used to clear all the
                     raw counts on a particular interface
                     and group."
        ::= { tnInterfaceRawCountStatsEntry 1 }

    tnIfRawCountStatInOctets OBJECT-TYPE
        SYNTAX      Counter64
        MAX-ACCESS  read-only
        STATUS      current
        DESCRIPTION "Provides a count of the number of octets that
                     passed through the IN port of the interface."
        ::= { tnInterfaceRawCountStatsEntry 2 }

    tnIfRawCountStatInUcastPkts OBJECT-TYPE
        SYNTAX      Counter64
        MAX-ACCESS  read-only
        STATUS      current
        DESCRIPTION "Provides a count of the number of unicast packets
                     that passed through the IN port of the interface."
        ::= { tnInterfaceRawCountStatsEntry 3 }

    tnIfRawCountStatInDiscards OBJECT-TYPE
        SYNTAX      Counter64
        MAX-ACCESS  read-only
        STATUS      current
        DESCRIPTION "Provides a count of the number of packets
                     discarded at the IN port of the interface."
        ::= { tnInterfaceRawCountStatsEntry 4 }

    tnIfRawCountStatInErrors OBJECT-TYPE
        SYNTAX      Counter64
        MAX-ACCESS  read-only
        STATUS      current
        DESCRIPTION "Provides a count of the errored frames detected
                     at the IN port of the interface. For Ethernet
                     traffic, this value is a sum of the following
                     counts:

                     tnEtherStatRxCrcAlignErrs
                     tnEtherStatRxOversizedPkts
                     tnEtherStatRxUndersizedPkts
                     tnEtherStatRxFragments"
        ::= { tnInterfaceRawCountStatsEntry 5 }

    tnIfRawCountStatInUnknownProtos OBJECT-TYPE
        SYNTAX      Counter64
        MAX-ACCESS  read-only
        STATUS      current
        DESCRIPTION "Provides a count of the number of packets
                     received at the IN port of the interface
                     for which the protocol is unknown."
        ::= { tnInterfaceRawCountStatsEntry 6 }

    tnIfRawCountStatOutOctets OBJECT-TYPE
        SYNTAX      Counter64
        MAX-ACCESS  read-only
        STATUS      current
        DESCRIPTION "Provides a count of the number of octets
                     that passed through the OUT port
                     of the interface."
        ::= { tnInterfaceRawCountStatsEntry 7 }

    tnIfRawCountStatOutUcastPkts OBJECT-TYPE
        SYNTAX      Counter64
        MAX-ACCESS  read-only
        STATUS      current
        DESCRIPTION "Provides a count of the number of unicast
                     packets that passed through the OUT port
                     of the interface."
        ::= { tnInterfaceRawCountStatsEntry 8 }

    tnIfRawCountStatOutDiscards OBJECT-TYPE
        SYNTAX      Counter64
        MAX-ACCESS  read-only
        STATUS      current
        DESCRIPTION "Provides a count of the number of packets
                     discarded at the OUT port of the interface."
        ::= { tnInterfaceRawCountStatsEntry 9 }

    tnIfRawCountStatOutErrors OBJECT-TYPE
        SYNTAX      Counter64
        MAX-ACCESS  read-only
        STATUS      current
        DESCRIPTION "Provides a count of the errored frames detected
                     at the OUT port of the interface. For Ethernet
                     traffic, this value is a sum of the following
                     counts:

                     tnEtherStatTxCrcAlignErrs
                     tnEtherStatTxOversizedPkts
                     tnEtherStatTxUndersizedPkts
                     tnEtherStatTxFragments"
        ::= { tnInterfaceRawCountStatsEntry 10 }

    tnIfRawCountStatInMulticastPkts OBJECT-TYPE
        SYNTAX      Counter64
        MAX-ACCESS  read-only
        STATUS      current
        DESCRIPTION "Provides a count of the total number of good
                     packets detected at the IN port of the
                     interface that were directed to a multicast
                     address. Does not include packets directed to
                     the broadcast."
        ::= { tnInterfaceRawCountStatsEntry 11 }

    tnIfRawCountStatInBroadcastPkts OBJECT-TYPE
        SYNTAX      Counter64
        MAX-ACCESS  read-only
        STATUS      current
        DESCRIPTION "Provides a count of the total number of good
                     packets detected at the IN port of the
                     interface that were directed to the broadcast
                     address. Does not include multicast packets."
        ::= { tnInterfaceRawCountStatsEntry 12 }

    tnIfRawCountStatOutMulticastPkts OBJECT-TYPE
        SYNTAX      Counter64
        MAX-ACCESS  read-only
        STATUS      current
        DESCRIPTION "Provides a count of the total number of good
                     packets detected at the OUT port of the
                     interface that were directed to a multicast
                     address. Does not include packets directed to
                     the broadcast."
        ::= { tnInterfaceRawCountStatsEntry 13 }

    tnIfRawCountStatOutBroadcastPkts OBJECT-TYPE
        SYNTAX      Counter64
        MAX-ACCESS  read-only
        STATUS      current
        DESCRIPTION "Provides a count of the total number of good
                     packets detected at the OUT port of the
                     interface that were directed to the broadcast
                     address. Does not include multicast packets."
        ::= { tnInterfaceRawCountStatsEntry 14 }

    tnIfRawCountStatInPacketsNotClassified OBJECT-TYPE
        SYNTAX      Counter64
        MAX-ACCESS  read-only
        STATUS      current
        DESCRIPTION "Provides a count of the number of unclassified
                     packets received at the IN port of the
                     interface."
        ::= { tnInterfaceRawCountStatsEntry 15 }

    tnIfRawCountStatStartTime OBJECT-TYPE
        SYNTAX      DateAndTime
        MAX-ACCESS  read-only
        STATUS      current
        DESCRIPTION "This attribute is the bin collection start date
                     and time."
        ::= { tnInterfaceRawCountStatsEntry 16 }

--------------------------------------------------------------------------------
-- Ethernet Raw Count Statistics Scalar
--------------------------------------------------------------------------------
    tnEtherRawCountStatsTotalMembers OBJECT-TYPE
        SYNTAX      Integer32
        MAX-ACCESS  read-only
        STATUS      current
        DESCRIPTION "The total number of members in the ethernet raw count stats
                     table."
        ::= { tnStatisticsRawCounts 7 }

--------------------------------------------------------------------------------
-- Ethernet Raw Count Statistics Table
--------------------------------------------------------------------------------
    tnEtherRawCountStatsTable OBJECT-TYPE
        SYNTAX      SEQUENCE OF TnEtherRawCountStatsEntry
        MAX-ACCESS  not-accessible
        STATUS      current
        DESCRIPTION "."
        ::= { tnStatisticsRawCounts 8 }

    tnEtherRawCountStatsEntry OBJECT-TYPE
        SYNTAX      TnEtherRawCountStatsEntry
        MAX-ACCESS  not-accessible
        STATUS      current
        DESCRIPTION "."
        INDEX   { ifIndex }
        ::= { tnEtherRawCountStatsTable 1 }

    TnEtherRawCountStatsEntry ::=
        SEQUENCE {
            tnEtherRawCountStatsClear                TnCommand,
            tnEtherRawCountStatRxDropEvents          Counter64,
            tnEtherRawCountStatRxFragments           Counter64,
            tnEtherRawCountStatRxJabbers             Counter64,
            tnEtherRawCountStatRxMcastPkts           Counter64,
            tnEtherRawCountStatRxOctets              Counter64,
            tnEtherRawCountStatRxOversizedPkts       Counter64,
            tnEtherRawCountStatRxPkts                Counter64,
            tnEtherRawCountStatRxPktsSize1024to1518  Counter64,
            tnEtherRawCountStatRxPktsSize128to255    Counter64,
            tnEtherRawCountStatRxPktsSize256to511    Counter64,
            tnEtherRawCountStatRxPktsSize512to1023   Counter64,
--            obsolete
--            tnEtherRawCountStatRxPktsSize64orLess    Counter64,
            tnEtherRawCountStatRxPktsSize65to127     Counter64,
            tnEtherRawCountStatRxUndersizedPkts      Counter64,
            tnEtherRawCountStatTxBcastPkts           Counter64,
            tnEtherRawCountStatTxCrcAlignErrs        Counter64,
            tnEtherRawCountStatTxDropEvents          Counter64,
            tnEtherRawCountStatTxFragments           Counter64,
            tnEtherRawCountStatTxJabbers             Counter64,
            tnEtherRawCountStatTxMcastPkts           Counter64,
            tnEtherRawCountStatTxOctets              Counter64,
            tnEtherRawCountStatTxOversizedPkts       Counter64,
            tnEtherRawCountStatTxPkts                Counter64,
            tnEtherRawCountStatTxPktsSize1024to1518  Counter64,
            tnEtherRawCountStatTxPktsSize128to255    Counter64,
            tnEtherRawCountStatTxPktsSize256to511    Counter64,
            tnEtherRawCountStatTxPktsSize512to1023   Counter64,
--            obsolete
--            tnEtherRawCountStatTxPktsSize64orLess    Counter64,
            tnEtherRawCountStatTxPktsSize65to127     Counter64,
            tnEtherRawCountStatTxUndersizedPkts      Counter64,
            tnEtherRawCountStatRxBcastPkts           Counter64,
            tnEtherRawCountStatRxCrcAlignErrs        Counter64,
            tnEtherRawCountStatRxCollisions          Counter64,
            tnEtherRawCountStatRxJumboPkts           Counter64,
            tnEtherRawCountStatTxCollisions          Counter64,
            tnEtherRawCountStatTxJumboPkts           Counter64,
            tnEtherRawCountStatRmonIndex             Unsigned32,
            tnEtherRawCountStatRxPktsSize64          Counter64,
            tnEtherRawCountStatTxPktsSize64          Counter64,
            tnEtherRawCountStatRxPktErrRatio         Counter64,
            tnEtherRawCountStatTxPktErrRatio         Counter64,
            tnEtherRawCountStatStartTime             DateAndTime
        }

    tnEtherRawCountStatsClear OBJECT-TYPE
        SYNTAX      TnCommand
        MAX-ACCESS  read-create
        STATUS      current
        DESCRIPTION "This attribute is used to clear all the
                     raw counts on a particular interface
                     and group."
        ::= { tnEtherRawCountStatsEntry 1 }

    tnEtherRawCountStatRxDropEvents OBJECT-TYPE
        SYNTAX      Counter64
        MAX-ACCESS  read-only
        STATUS      current
        DESCRIPTION "Provides a count of the total number of events
                     in which packets were dropped by the monitoring
                     entity due to a lack of resources. This value is
                     not necessarily the number of packets dropped;
                     it can be the number of times this condition has
                     been detected."
        ::= { tnEtherRawCountStatsEntry 2 }

    tnEtherRawCountStatRxFragments OBJECT-TYPE
        SYNTAX      Counter64
        MAX-ACCESS  read-only
        STATUS      current
        DESCRIPTION "Provides a count of the total number of packets
                     sent or received that were less than 64 octets in
                     length (excluding framing bits but including FCS
                     octets) and had either a bad FCS with an integral
                     number of octets (FCS Error) or a bad FCS with a
                     non-integral number of octets (Alignment Error)."
        ::= { tnEtherRawCountStatsEntry 3 }

    tnEtherRawCountStatRxJabbers OBJECT-TYPE
        SYNTAX      Counter64
        MAX-ACCESS  read-only
        STATUS      current
        DESCRIPTION "Provides a count of the total number of packets sent
                     or received that were longer than 1518 octets
                     (excluding framing bits, but including FCS octets)
                     and had either a bad FCS with an integral number of
                     octets (FCS Error) or a bad FCS with a non-integral
                     number of octets (Alignment Error)."
        ::= { tnEtherRawCountStatsEntry 4 }

    tnEtherRawCountStatRxMcastPkts OBJECT-TYPE
        SYNTAX      Counter64
        MAX-ACCESS  read-only
        STATUS      current
        DESCRIPTION "Provides a count of the total number of good packets
                     received that were directed to a multicast address.
                     This does not include packets directed to the
                     broadcast."
        ::= { tnEtherRawCountStatsEntry 5 }

    tnEtherRawCountStatRxOctets OBJECT-TYPE
        SYNTAX      Counter64
        MAX-ACCESS  read-only
        STATUS      current
        DESCRIPTION "Provides a count of the total number of octets of
                     data (including the bad packets) received on the
                     port. Excludes framing bits. Includes Frame Check
                     Sequence (FCS) octets."
        ::= { tnEtherRawCountStatsEntry 6 }

    tnEtherRawCountStatRxOversizedPkts OBJECT-TYPE
        SYNTAX      Counter64
        MAX-ACCESS  read-only
        STATUS      current
        DESCRIPTION "Provides a count of the total number of packets
                     received that were longer than 1518 octets and
                     were otherwise well formed. The packet length
                     excludes framing bits and includes FCS octets."
        ::= { tnEtherRawCountStatsEntry 7 }

    tnEtherRawCountStatRxPkts OBJECT-TYPE
        SYNTAX      Counter64
        MAX-ACCESS  read-only
        STATUS      current
        DESCRIPTION "Provides a count of the total number of packets
                     (including bad packet, broadcast packets, and
                     multicast packets) received."
        ::= { tnEtherRawCountStatsEntry 8 }

    tnEtherRawCountStatRxPktsSize1024to1518 OBJECT-TYPE
        SYNTAX      Counter64
        MAX-ACCESS  read-only
        STATUS      current
        DESCRIPTION "Provides a count of the total number of packets
                     (including bad packets) received that were
                     between 1024 and 1518 octets in length inclusive.
                     The packet length excludes framing bits and
                     includes FCS octets."
        ::= { tnEtherRawCountStatsEntry 9 }

    tnEtherRawCountStatRxPktsSize128to255 OBJECT-TYPE
        SYNTAX      Counter64
        MAX-ACCESS  read-only
        STATUS      current
        DESCRIPTION "Provides a count of the total number of packets
                     (including bad packets) received that were between
                     128 and 255 octets in length inclusive. The packet
                     length excludes framing bits and includes FCS
                     octets."
        ::= { tnEtherRawCountStatsEntry 10 }

    tnEtherRawCountStatRxPktsSize256to511 OBJECT-TYPE
        SYNTAX      Counter64
        MAX-ACCESS  read-only
        STATUS      current
        DESCRIPTION "Provides a count of the total number of packets
                     (including bad packets) received that were between
                     256 and 511 octets in length inclusive. The packet
                     length excludes framing bits and includes FCS
                     octets."
        ::= { tnEtherRawCountStatsEntry 11 }

    tnEtherRawCountStatRxPktsSize512to1023 OBJECT-TYPE
        SYNTAX      Counter64
        MAX-ACCESS  read-only
        STATUS      current
        DESCRIPTION "Provides a count of the total number of packets
                     (including bad packets) received that were
                     between 512 and 1023 octets in length inclusive.
                     The packet length excludes framing bits and
                     includes FCS octets."
        ::= { tnEtherRawCountStatsEntry 12 }

--    obsolete
--    tnEtherRawCountStatRxPktsSize64orLess OBJECT-TYPE ::= { tnEtherRawCountStatsEntry 13 }

    tnEtherRawCountStatRxPktsSize65to127 OBJECT-TYPE
        SYNTAX      Counter64
        MAX-ACCESS  read-only
        STATUS      current
        DESCRIPTION "Provides a count of the total number of packets
                     (including bad packets) received that were
                     between 65 and 127 octets in length inclusive.
                     The packet length excludes framing bits and
                     includes FCS octets."
        ::= { tnEtherRawCountStatsEntry 14 }

    tnEtherRawCountStatRxUndersizedPkts OBJECT-TYPE
        SYNTAX      Counter64
        MAX-ACCESS  read-only
        STATUS      current
        DESCRIPTION "Provides a count of the total number of packets
                     received that were less than 64 octets long
                     and were otherwise well formed. The packet
                     length excludes framing bits and includes
                     FCS octets."
        ::= { tnEtherRawCountStatsEntry 15 }

    tnEtherRawCountStatTxBcastPkts OBJECT-TYPE
        SYNTAX      Counter64
        MAX-ACCESS  read-only
        STATUS      current
        DESCRIPTION "Provides a count of the total number of good
                     packets received that were directed to the
                     broadcast address. This does not include
                     multicast packets."
        ::= { tnEtherRawCountStatsEntry 16 }

    tnEtherRawCountStatTxCrcAlignErrs OBJECT-TYPE
        SYNTAX      Counter64
        MAX-ACCESS  read-only
        STATUS      current
        DESCRIPTION "Provides a count of the total number of packets
                     received that had a length of between 63 and
                     1518 octets, inclusive, but had either a FCS
                     with an integral number of octets (FCS error)
                     or a bad FCS with a non-integral number of
                     octets (Alignment Error). The packet length
                     excludes framing bits and includes FCS octets."
        ::= { tnEtherRawCountStatsEntry 17 }

    tnEtherRawCountStatTxDropEvents OBJECT-TYPE
        SYNTAX      Counter64
        MAX-ACCESS  read-only
        STATUS      current
        DESCRIPTION "Provides a count of the total number of events
                     in which packets were dropped by the monitoring
                     entity due to a lack of resources. This value
                     is not necessarily the number of packets dropped;
                     it can be the number of times this condition
                     has been detected."
        ::= { tnEtherRawCountStatsEntry 18 }

    tnEtherRawCountStatTxFragments OBJECT-TYPE
        SYNTAX      Counter64
        MAX-ACCESS  read-only
        STATUS      current
        DESCRIPTION "Provides a count of the total number of packets
                     sent or received that were less than 64 octets
                     in length (excluding framing bits but including
                     FCS octets) and had either a bad FCS with an
                     integral number of octets (FCS Error) or a bad
                     FCS with a non-integral number of octets
                     (Alignment Error)."
        ::= { tnEtherRawCountStatsEntry 19 }

    tnEtherRawCountStatTxJabbers OBJECT-TYPE
        SYNTAX      Counter64
        MAX-ACCESS  read-only
        STATUS      current
        DESCRIPTION "Provides a count of the total number of packets
                     sent or received that were longer than 1518
                     octets (excluding framing bits, but including
                     FCS octets) and had either a bad FCS with an
                     integral number of octets (FCS Error) or a bad
                     FCS with a non-integral number of octets
                     (Alignment Error)."
        ::= { tnEtherRawCountStatsEntry 20 }

    tnEtherRawCountStatTxMcastPkts OBJECT-TYPE
        SYNTAX      Counter64
        MAX-ACCESS  read-only
        STATUS      current
        DESCRIPTION "Provides a count of the total number of good
                     packets received that were directed to a
                     multicast address. This does not include packets
                     directed to the broadcast."
        ::= { tnEtherRawCountStatsEntry 21 }

    tnEtherRawCountStatTxOctets OBJECT-TYPE
        SYNTAX      Counter64
        MAX-ACCESS  read-only
        STATUS      current
        DESCRIPTION "Provides a count of the total number of octets
                     of data (including the bad packets) received
                     on the port. Excludes framing bits. Includes
                     Frame Check Sequence (FCS) octets."
        ::= { tnEtherRawCountStatsEntry 22 }

    tnEtherRawCountStatTxOversizedPkts OBJECT-TYPE
        SYNTAX      Counter64
        MAX-ACCESS  read-only
        STATUS      current
        DESCRIPTION "Provides a count of the total number of
                     packets received that were longer than 1518
                     octets and were otherwise well formed. The
                     packet length excludes framing bits and
                     includes FCS octets."
        ::= { tnEtherRawCountStatsEntry 23 }

    tnEtherRawCountStatTxPkts OBJECT-TYPE
        SYNTAX      Counter64
        MAX-ACCESS  read-only
        STATUS      current
        DESCRIPTION "Provides a count of the total number of packets
                     (including bad packet, broadcast packets, and
                     multicast packets) received."
        ::= { tnEtherRawCountStatsEntry 24 }

    tnEtherRawCountStatTxPktsSize1024to1518 OBJECT-TYPE
        SYNTAX      Counter64
        MAX-ACCESS  read-only
        STATUS      current
        DESCRIPTION "Provides a count of the total number of packets
                     (including bad packets) received that were
                     between 1024 and 1518 octets in length
                     inclusive. The packet length excludes framing
                     bits and includes FCS octets."
        ::= { tnEtherRawCountStatsEntry 25 }

    tnEtherRawCountStatTxPktsSize128to255 OBJECT-TYPE
        SYNTAX      Counter64
        MAX-ACCESS  read-only
        STATUS      current
        DESCRIPTION "Provides a count of the total number of packets
                     (including bad packets) received that were
                     between 128 and 255 octets in length inclusive.
                     The packet length excludes framing bits and
                     includes FCS octets."
        ::= { tnEtherRawCountStatsEntry 26 }

    tnEtherRawCountStatTxPktsSize256to511 OBJECT-TYPE
        SYNTAX      Counter64
        MAX-ACCESS  read-only
        STATUS      current
        DESCRIPTION "Provides a count of the total number of packets
                     (including bad packets) received that were
                     between 256 and 511octets in length inclusive.
                     The packet length excludes framing bits and
                     includes FCS octets."
        ::= { tnEtherRawCountStatsEntry 27 }

    tnEtherRawCountStatTxPktsSize512to1023 OBJECT-TYPE
        SYNTAX      Counter64
        MAX-ACCESS  read-only
        STATUS      current
        DESCRIPTION "Provides a count of the total number of packets
                     (including bad packets) received that were
                     between 512 and 1023 octets in length inclusive.
                     The packet length excludes framing bits and
                     includes FCS octets."
        ::= { tnEtherRawCountStatsEntry 28 }

--    obsolete
--    tnEtherRawCountStatTxPktsSize64orLess OBJECT-TYPE ::= { tnEtherRawCountStatsEntry 29 }

    tnEtherRawCountStatTxPktsSize65to127 OBJECT-TYPE
        SYNTAX      Counter64
        MAX-ACCESS  read-only
        STATUS      current
        DESCRIPTION "Provides a count of the total number of packets
                     (including bad packets) received that were
                     between 65 and 127 octets in length inclusive.
                     The packet length excludes framing bits and
                     includes FCS octets."
        ::= { tnEtherRawCountStatsEntry 30 }

    tnEtherRawCountStatTxUndersizedPkts OBJECT-TYPE
        SYNTAX      Counter64
        MAX-ACCESS  read-only
        STATUS      current
        DESCRIPTION "Provides a count of the total number of packets
                     received that were less than 64 octets long
                     and were otherwise well formed. The packet
                     length excludes framing bits and includes
                     FCS octets."
        ::= { tnEtherRawCountStatsEntry 31 }

    tnEtherRawCountStatRxBcastPkts OBJECT-TYPE
        SYNTAX      Counter64
        MAX-ACCESS  read-only
        STATUS      current
        DESCRIPTION "Provides a count of the total number of good
                     packets received that were directed to the
                     broadcast address. This does not include
                     multicast packets."
        ::= { tnEtherRawCountStatsEntry 32 }

    tnEtherRawCountStatRxCrcAlignErrs OBJECT-TYPE
        SYNTAX      Counter64
        MAX-ACCESS  read-only
        STATUS      current
        DESCRIPTION "Provides a count of the total number of packets
                     received that had a length of between 63 and
                     1518 octets, inclusive, but had either a FCS
                     with an integral number of octets (FCS error)
                     or a bad FCS with a non-integral number of
                     octets (Alignment Error). The packet length
                     excludes framing bits and includes FCS octets."
        ::= { tnEtherRawCountStatsEntry 33 }

    tnEtherRawCountStatRxCollisions OBJECT-TYPE
        SYNTAX      Counter64
        MAX-ACCESS  read-only
        STATUS      current
        DESCRIPTION "Provides a count of the total number of
                     collisions on the port."
        ::= { tnEtherRawCountStatsEntry 34 }

    tnEtherRawCountStatRxJumboPkts OBJECT-TYPE
        SYNTAX      Counter64
        MAX-ACCESS  read-only
        STATUS      current
        DESCRIPTION "Provides a count of the total number of Jumbo
                     frames sent or received on the port. Jumbo
                     frames are frames which have a packet size
                     greater than 1500 bytes."
        ::= { tnEtherRawCountStatsEntry 35 }

    tnEtherRawCountStatTxCollisions OBJECT-TYPE
        SYNTAX      Counter64
        MAX-ACCESS  read-only
        STATUS      current
        DESCRIPTION "Provides a count of the total number of
                     collisions on the port."
        ::= { tnEtherRawCountStatsEntry 36 }

    tnEtherRawCountStatTxJumboPkts OBJECT-TYPE
        SYNTAX      Counter64
        MAX-ACCESS  read-only
        STATUS      current
        DESCRIPTION "Provides a count of the total number of Jumbo
                     frames sent or received on the port. Jumbo
                     frames are frames which have a packet size
                     greater than 1500 bytes."
        ::= { tnEtherRawCountStatsEntry 37 }

    tnEtherRawCountStatRmonIndex OBJECT-TYPE
        SYNTAX      Unsigned32
        MAX-ACCESS  read-only
        STATUS      current
        DESCRIPTION "."
        ::= { tnEtherRawCountStatsEntry 38 }

    tnEtherRawCountStatRxPktsSize64 OBJECT-TYPE
        SYNTAX      Counter64
        MAX-ACCESS  read-only
        STATUS      current
        DESCRIPTION "Provides a count of the total number of packets
                     (including bad packets) received that were 64
                     octets in length inclusive. The packet length
                     excludes framing bits and includes FCS octets."
        ::= { tnEtherRawCountStatsEntry 39 }

    tnEtherRawCountStatTxPktsSize64 OBJECT-TYPE
        SYNTAX      Counter64
        MAX-ACCESS  read-only
        STATUS      current
        DESCRIPTION "Provides a count of the total number of packets
                     (including bad packets) received that were 64
                     octets in length inclusive. The packet length
                     excludes framing bits and includes FCS octets."
        ::= { tnEtherRawCountStatsEntry 40 }

    tnEtherRawCountStatRxPktErrRatio OBJECT-TYPE
        SYNTAX      Counter64
        MAX-ACCESS  read-only
        STATUS      current
        DESCRIPTION "Provides a ratio of the total number of errored
                     packets received to the total number of packets
                     received."
        ::= { tnEtherRawCountStatsEntry 41 }

    tnEtherRawCountStatTxPktErrRatio OBJECT-TYPE
        SYNTAX      Counter64
        MAX-ACCESS  read-only
        STATUS      current
        DESCRIPTION "Provides a ratio of the total number of errored
                     packets transmitted to the total number of packets
                     transmitted."
        ::= { tnEtherRawCountStatsEntry 42 }

    tnEtherRawCountStatStartTime OBJECT-TYPE
        SYNTAX      DateAndTime
        MAX-ACCESS  read-only
        STATUS      current
        DESCRIPTION "This attribute is the bin collection start date
                     and time."
        ::= { tnEtherRawCountStatsEntry 43 }

--------------------------------------------------------------------------------
-- SONET Raw Count Statistics Scalar
--------------------------------------------------------------------------------
    tnSonetRawCountStatsTotalMembers OBJECT-TYPE
        SYNTAX      Integer32
        MAX-ACCESS  read-only
        STATUS      current
        DESCRIPTION "The total number of members in the SONET raw count stats
                     table."
        ::= { tnStatisticsRawCounts 9 }

--------------------------------------------------------------------------------
-- SONET Raw Count Statistics Table
--------------------------------------------------------------------------------
    tnSonetRawCountStatsTable OBJECT-TYPE
        SYNTAX      SEQUENCE OF TnSonetRawCountStatsEntry
        MAX-ACCESS  not-accessible
        STATUS      current
        DESCRIPTION "."
        ::= { tnStatisticsRawCounts 10 }

    tnSonetRawCountStatsEntry OBJECT-TYPE
        SYNTAX      TnSonetRawCountStatsEntry
        MAX-ACCESS  not-accessible
        STATUS      current
        DESCRIPTION "."
        INDEX   { ifIndex }
        ::= { tnSonetRawCountStatsTable 1 }

    TnSonetRawCountStatsEntry ::=
        SEQUENCE {
            tnSonetRawCountStatsClear     TnCommand,
            tnSonetRawCountStatRxCVS      Counter32,
            tnSonetRawCountStatRxESS      Counter32,
            tnSonetRawCountStatRxSESS     Counter32,
            tnSonetRawCountStatRxSEFSS    Counter32,
            tnSonetRawCountStatRxCVL      Counter32,
            tnSonetRawCountStatRxESL      Counter32,
            tnSonetRawCountStatRxSESL     Counter32,
            tnSonetRawCountStatRxUASL     Counter32,
            tnSonetRawCountStatRxFCL      Counter32,
            tnSonetRawCountStatTxCVS      Counter32,
            tnSonetRawCountStatTxESS      Counter32,
            tnSonetRawCountStatTxSESS     Counter32,
            tnSonetRawCountStatTxSEFSS    Counter32,
            tnSonetRawCountStatTxCVL      Counter32,
            tnSonetRawCountStatTxESL      Counter32,
            tnSonetRawCountStatTxSESL     Counter32,
            tnSonetRawCountStatTxUASL     Counter32,
            tnSonetRawCountStatTxFCL      Counter32,
            tnSonetRawCountStatRxUASS     Counter32,
            tnSonetRawCountStatTxUASS     Counter32,
            tnSonetRawCountStatStartTime  DateAndTime,
            tnSonetRawCountStatRxFECVL    Counter32,
            tnSonetRawCountStatRxFEESL    Counter32,
            tnSonetRawCountStatRxFESESL   Counter32,
            tnSonetRawCountStatRxFEUASL   Counter32
        }

    tnSonetRawCountStatsClear OBJECT-TYPE
        SYNTAX      TnCommand
        MAX-ACCESS  read-create
        STATUS      current
        DESCRIPTION "This attribute is used to clear all the
                     raw counts on a particular interface
                     and group."
        ::= { tnSonetRawCountStatsEntry 1 }

    tnSonetRawCountStatRxCVS OBJECT-TYPE
        SYNTAX      Counter32
        MAX-ACCESS  read-only
        STATUS      current
        DESCRIPTION "Coding violation - section. Provides a count of
                     the number of B1 violations."
        ::= { tnSonetRawCountStatsEntry 2 }

    tnSonetRawCountStatRxESS OBJECT-TYPE
        SYNTAX      Counter32
        MAX-ACCESS  read-only
        STATUS      current
        DESCRIPTION "Errored second - section. Provides a count of
                     the number of one second intervals in which
                     any of the following conditions are true:

                     - at least one B1 BIP-8 error was detected.
                     - a loss of signal (LOS) defect was present.
                     - a severely errored frame (SEF) defect was
                       present."
        ::= { tnSonetRawCountStatsEntry 3 }

    tnSonetRawCountStatRxSESS OBJECT-TYPE
        SYNTAX      Counter32
        MAX-ACCESS  read-only
        STATUS      current
        DESCRIPTION "Severely errored second - section. Provides a
                     count of the number of one second intervals in
                     which any of the following conditions are true:

                     - the number of section layer BIP errors detected
                       exceeded the value defined in GR-253-CORE.
                     - a loss of signal (LOS) defect was present.
                     - a severely errored frame (SEF) defect was
                       present."
        ::= { tnSonetRawCountStatsEntry 4 }

    tnSonetRawCountStatRxSEFSS OBJECT-TYPE
        SYNTAX      Counter32
        MAX-ACCESS  read-only
        STATUS      current
        DESCRIPTION "Severely errored frame second - section.
                     Provides a count of the number of one second
                     intervals in which any of the following
                     conditions are true:

                     - a loss of frame (LOF) defect was present.
                     - a severely errored frame (SEF) defect was
                       present."
        ::= { tnSonetRawCountStatsEntry 5 }

    tnSonetRawCountStatRxCVL OBJECT-TYPE
        SYNTAX      Counter32
        MAX-ACCESS  read-only
        STATUS      current
        DESCRIPTION "Coding violation - line. Provides a count of
                     the number of B2 BIP violations."
        ::= { tnSonetRawCountStatsEntry 6 }

    tnSonetRawCountStatRxESL OBJECT-TYPE
        SYNTAX      Counter32
        MAX-ACCESS  read-only
        STATUS      current
        DESCRIPTION "Errored second - line. Provides a count of the
                     number of one second intervals in which any
                     of the following conditions are true:

                     - at least one B2 BIP error was detected.
                     - an alarm indicating signal (AIS-L) defect
                       was present."
        ::= { tnSonetRawCountStatsEntry 7 }

    tnSonetRawCountStatRxSESL OBJECT-TYPE
        SYNTAX      Counter32
        MAX-ACCESS  read-only
        STATUS      current
        DESCRIPTION "Severely errored second - line. Provides a
                     count of the number of one second intervals
                     in which any of the following conditions are
                     true:

                     - the number of line layer B2 errors detected
                       exceeded the value defined in GR-253-CORE.
                     - an alarm indicating signal (AIS-L) defect
                       was present."
        ::= { tnSonetRawCountStatsEntry 8 }

    tnSonetRawCountStatRxUASL OBJECT-TYPE
        SYNTAX      Counter32
        MAX-ACCESS  read-only
        STATUS      current
        DESCRIPTION "Unavailable second - line. Provides a count
                     of the number of seconds that a line is
                     unavailable. A line is deemed to be unavailable
                     when 10 consecutive severely errored seconds
                     (SESs) are detected. The period of
                     unavailability begins at the onset the 10
                     consecutive SESs (back in time). Availability
                     is declared after a period of 10 consecutive
                     non-SESs. The period of availability begins
                     at the onset of the 10 consecutive
                     non-SESs (back in time)."
        ::= { tnSonetRawCountStatsEntry 9 }

    tnSonetRawCountStatRxFCL OBJECT-TYPE
        SYNTAX      Counter32
        MAX-ACCESS  read-only
        STATUS      current
        DESCRIPTION "Failure count - line. Provides a count of the
                     number of line failures. A failure event begins
                     when a AIS-L failure is declared and ends when
                     the failure is cleared. A failure event that
                     begins in one period and ends in another period
                     is counted only in the period where it begins."
        ::= { tnSonetRawCountStatsEntry 10 }

    tnSonetRawCountStatTxCVS OBJECT-TYPE
        SYNTAX      Counter32
        MAX-ACCESS  read-only
        STATUS      current
        DESCRIPTION "Coding violation - section. Provides a count of
                     the number of B1 violations."
        ::= { tnSonetRawCountStatsEntry 11 }

    tnSonetRawCountStatTxESS OBJECT-TYPE
        SYNTAX      Counter32
        MAX-ACCESS  read-only
        STATUS      current
        DESCRIPTION "Errored second - section. Provides a count of
                     the number of one second intervals in which
                     any of the following conditions are true:

                     - at least one B1 BIP-8 error was detected.
                     - a loss of signal (LOS) defect was present.
                     - a severely errored frame (SEF) defect was
                       present."
        ::= { tnSonetRawCountStatsEntry 12 }

    tnSonetRawCountStatTxSESS OBJECT-TYPE
        SYNTAX      Counter32
        MAX-ACCESS  read-only
        STATUS      current
        DESCRIPTION "Severely errored second - section. Provides a
                     count of the number of one second intervals in
                     which any of the following conditions are true:

                     - the number of section layer BIP errors detected
                       exceeded the value defined in GR-253-CORE.
                     - a loss of signal (LOS) defect was present.
                     - a severely errored frame (SEF) defect was
                       present."
        ::= { tnSonetRawCountStatsEntry 13 }

    tnSonetRawCountStatTxSEFSS OBJECT-TYPE
        SYNTAX      Counter32
        MAX-ACCESS  read-only
        STATUS      current
        DESCRIPTION "Severely errored frame second - section.
                     Provides a count of the number of one second
                     intervals in which any of the following
                     conditions are true:

                     - a loss of frame (LOF) defect was present.
                     - a severely errored frame (SEF) defect was
                       present."
        ::= { tnSonetRawCountStatsEntry 14 }

    tnSonetRawCountStatTxCVL OBJECT-TYPE
        SYNTAX      Counter32
        MAX-ACCESS  read-only
        STATUS      current
        DESCRIPTION "Coding violation - line. Provides a count of
                     the number of B2 BIP violations."
        ::= { tnSonetRawCountStatsEntry 15 }

    tnSonetRawCountStatTxESL OBJECT-TYPE
        SYNTAX      Counter32
        MAX-ACCESS  read-only
        STATUS      current
        DESCRIPTION "Errored second - line. Provides a count of the
                     number of one second intervals in which any
                     of the following conditions are true:

                     - at least one B2 BIP error was detected.
                     - an alarm indicating signal (AIS-L) defect
                       was present."
        ::= { tnSonetRawCountStatsEntry 16 }

    tnSonetRawCountStatTxSESL OBJECT-TYPE
        SYNTAX      Counter32
        MAX-ACCESS  read-only
        STATUS      current
        DESCRIPTION "Severely errored second - line. Provides a
                     count of the number of one second intervals
                     in which any of the following conditions are
                     true:

                     - the number of line layer B2 errors detected
                       exceeded the value defined in GR-253-CORE.
                     - an alarm indicating signal (AIS-L) defect
                       was present."
        ::= { tnSonetRawCountStatsEntry 17 }

    tnSonetRawCountStatTxUASL OBJECT-TYPE
        SYNTAX      Counter32
        MAX-ACCESS  read-only
        STATUS      current
        DESCRIPTION "Unavailable second - line. Provides a count
                     of the number of seconds that a line is
                     unavailable. A line is deemed to be unavailable
                     when 10 consecutive severely errored seconds
                     (SESs) are detected. The period of
                     unavailability begins at the onset the 10
                     consecutive SESs (back in time). Availability
                     is declared after a period of 10 consecutive
                     non-SESs. The period of availability begins
                     at the onset of the 10 consecutive
                     non-SESs (back in time)."
        ::= { tnSonetRawCountStatsEntry 18 }

    tnSonetRawCountStatTxFCL OBJECT-TYPE
        SYNTAX      Counter32
        MAX-ACCESS  read-only
        STATUS      current
        DESCRIPTION "Failure count - line. Provides a count of the
                     number of line failures. A failure event begins
                     when a AIS-L failure is declared and ends when
                     the failure is cleared. A failure event that
                     begins in one period and ends in another period
                     is counted only in the period where it begins."
        ::= { tnSonetRawCountStatsEntry 19 }

    tnSonetRawCountStatRxUASS OBJECT-TYPE
        SYNTAX      Counter32
        MAX-ACCESS  read-only
        STATUS      current
        DESCRIPTION "Unavailable second - section. Provides a count
                     of the number of seconds that a section is
                     unavailable. A section is deemed to be unavailable
                     when 10 consecutive severely errored seconds
                     (SESs) are detected. The period of
                     unavailability begins at the onset the 10
                     consecutive SESs (back in time). Availability
                     is declared after a period of 10 consecutive
                     non-SESs. The period of availability begins
                     at the onset of the 10 consecutive
                     non-SESs (back in time)."
        ::= { tnSonetRawCountStatsEntry 20 }

    tnSonetRawCountStatTxUASS OBJECT-TYPE
        SYNTAX      Counter32
        MAX-ACCESS  read-only
        STATUS      current
        DESCRIPTION "Unavailable second - section.  Provides a count
                     of the number of seconds that a section is
                     unavailable.  A section is deemed to be unavailable
                     when 10 consecutive severely errored seconds (SESs)
                     are detected.  The period of unavailability begins
                     at the onset the 10 consecutive SESs (back in time).
                     Availability is declared after a period of 10
                     consecutive non-SESs.  The period of availability
                     begins at the onset of the 10 consecutive non-SESs
                     (back in time)."
        ::= { tnSonetRawCountStatsEntry 21 }

    tnSonetRawCountStatStartTime OBJECT-TYPE
        SYNTAX      DateAndTime
        MAX-ACCESS  read-only
        STATUS      current
        DESCRIPTION "This attribute is the bin collection start date
                     and time."
        ::= { tnSonetRawCountStatsEntry 22 }

    tnSonetRawCountStatRxFECVL OBJECT-TYPE
        SYNTAX      Counter32
        MAX-ACCESS  read-only
        STATUS      current
        DESCRIPTION "Coding violation - line.  Provides a count of
                     the number of B2 BIP violations."
        ::= { tnSonetRawCountStatsEntry 23 }

    tnSonetRawCountStatRxFEESL OBJECT-TYPE
        SYNTAX      Counter32
        MAX-ACCESS  read-only
        STATUS      current
        DESCRIPTION "Errored second - line."
        ::= { tnSonetRawCountStatsEntry 24 }

    tnSonetRawCountStatRxFESESL OBJECT-TYPE
        SYNTAX      Counter32
        MAX-ACCESS  read-only
        STATUS      current
        DESCRIPTION "Severely errored second - line."
        ::= { tnSonetRawCountStatsEntry 25 }

    tnSonetRawCountStatRxFEUASL OBJECT-TYPE
        SYNTAX      Counter32
        MAX-ACCESS  read-only
        STATUS      current
        DESCRIPTION "Unavailable second - line.  Provides a count of
                     the number of seconds that a line is unavailable."
        ::= { tnSonetRawCountStatsEntry 26 }

--    obsolete
--    tnDigitalWrapperRawCountStatsTotalMembers OBJECT-TYPE ::= { tnStatisticsRawCounts 11 }
--    tnDigitalWrapperRawCountStatsTable        OBJECT-TYPE ::= { tnStatisticsRawCounts 12 }
--    tnL1ProtRawCountStatsTotalMembers         OBJECT-TYPE ::= { tnStatisticsRawCounts 13 }
--    tnL1ProtRawCountStatsTable                OBJECT-TYPE ::= { tnStatisticsRawCounts 14 }

--------------------------------------------------------------------------------
-- Optical DC Power TX (OPT) Statistics Scalar
--------------------------------------------------------------------------------
    tnOptRawCountStatsTotalMembers OBJECT-TYPE
        SYNTAX      Integer32
        MAX-ACCESS  read-only
        STATUS      current
        DESCRIPTION "The total number of members in the OPT raw count stats
                     table."
        ::= { tnStatisticsRawCounts 15 }

--------------------------------------------------------------------------------
-- Optical DC Power TX (OPT) Statistics Table
--------------------------------------------------------------------------------
    tnOptRawCountStatsTable OBJECT-TYPE
        SYNTAX      SEQUENCE OF TnOptRawCountStatsEntry
        MAX-ACCESS  not-accessible
        STATUS      current
        DESCRIPTION "."
        ::= { tnStatisticsRawCounts 16 }

    tnOptRawCountStatsEntry OBJECT-TYPE
        SYNTAX      TnOptRawCountStatsEntry
        MAX-ACCESS  not-accessible
        STATUS      current
        DESCRIPTION "."
        INDEX   { ifIndex }
        ::= { tnOptRawCountStatsTable 1 }

    TnOptRawCountStatsEntry ::=
        SEQUENCE {
            tnOptRawCountStatsClear       TnCommand,
            tnOptRawCountStatMinPower     Integer32,
            tnOptRawCountStatMaxPower     Integer32,
            tnOptRawCountStatAveragePower Integer32,
            tnOptRawCountStatStartTime    DateAndTime
        }

    tnOptRawCountStatsClear OBJECT-TYPE
        SYNTAX      TnCommand
        MAX-ACCESS  read-create
        STATUS      current
        DESCRIPTION "This attribute is used to clear all the
                     raw counts on a particular interface
                     and group."
        ::= { tnOptRawCountStatsEntry 1 }

    tnOptRawCountStatMinPower OBJECT-TYPE
        SYNTAX      Integer32
        UNITS       "mBm"
        MAX-ACCESS  read-only
        STATUS      current
        DESCRIPTION "Minimum optical DC power in the
                     TX direction (mBm)."
        ::= { tnOptRawCountStatsEntry 2 }

    tnOptRawCountStatMaxPower OBJECT-TYPE
        SYNTAX      Integer32
        UNITS       "mBm"
        MAX-ACCESS  read-only
        STATUS      current
        DESCRIPTION "Maximum optical DC power in the
                     TX direction (mBm)."
        ::= { tnOptRawCountStatsEntry 3 }

    tnOptRawCountStatAveragePower OBJECT-TYPE
        SYNTAX      Integer32
        UNITS       "mBm"
        MAX-ACCESS  read-only
        STATUS      current
        DESCRIPTION "Average optical DC power in the
                     TX direction (mBm)."
        ::= { tnOptRawCountStatsEntry 4 }

    tnOptRawCountStatStartTime OBJECT-TYPE
        SYNTAX      DateAndTime
        MAX-ACCESS  read-only
        STATUS      current
        DESCRIPTION "This attribute is the bin collection start date
                     and time."
        ::= { tnOptRawCountStatsEntry 5 }

--------------------------------------------------------------------------------
-- Optical DC Power RX (OPR) Statistics Scalar
--------------------------------------------------------------------------------
    tnOprRawCountStatsTotalMembers OBJECT-TYPE
        SYNTAX      Integer32
        MAX-ACCESS  read-only
        STATUS      current
        DESCRIPTION "The total number of members in the OPR raw count stats
                     table."
        ::= { tnStatisticsRawCounts 17 }

--------------------------------------------------------------------------------
-- Optical DC Power RX (OPR) Statistics Table
--------------------------------------------------------------------------------
    tnOprRawCountStatsTable OBJECT-TYPE
        SYNTAX      SEQUENCE OF TnOprRawCountStatsEntry
        MAX-ACCESS  not-accessible
        STATUS      current
        DESCRIPTION "."
        ::= { tnStatisticsRawCounts 18 }

    tnOprRawCountStatsEntry OBJECT-TYPE
        SYNTAX      TnOprRawCountStatsEntry
        MAX-ACCESS  not-accessible
        STATUS      current
        DESCRIPTION "."
        INDEX   { ifIndex }
        ::= { tnOprRawCountStatsTable 1 }

    TnOprRawCountStatsEntry ::=
        SEQUENCE {
            tnOprRawCountStatsClear       TnCommand,
            tnOprRawCountStatMinPower     Integer32,
            tnOprRawCountStatMaxPower     Integer32,
            tnOprRawCountStatAveragePower Integer32,
            tnOprRawCountStatStartTime    DateAndTime
        }

    tnOprRawCountStatsClear OBJECT-TYPE
        SYNTAX      TnCommand
        MAX-ACCESS  read-create
        STATUS      current
        DESCRIPTION "This attribute is used to clear all the
                     raw counts on a particular interface
                     and group."
        ::= { tnOprRawCountStatsEntry 1 }

    tnOprRawCountStatMinPower OBJECT-TYPE
        SYNTAX      Integer32
        UNITS       "mBm"
        MAX-ACCESS  read-only
        STATUS      current
        DESCRIPTION "Minimum optical DC power in the
                     RX direction (mBm)."
        ::= { tnOprRawCountStatsEntry 2 }

    tnOprRawCountStatMaxPower OBJECT-TYPE
        SYNTAX      Integer32
        UNITS       "mBm"
        MAX-ACCESS  read-only
        STATUS      current
        DESCRIPTION "Maximum optical DC power in the
                     RX direction (mBm)."
        ::= { tnOprRawCountStatsEntry 3 }

    tnOprRawCountStatAveragePower OBJECT-TYPE
        SYNTAX      Integer32
        UNITS       "mBm"
        MAX-ACCESS  read-only
        STATUS      current
        DESCRIPTION "Average optical DC power in the
                     RX direction (mBm)."
        ::= { tnOprRawCountStatsEntry 4 }

    tnOprRawCountStatStartTime OBJECT-TYPE
        SYNTAX      DateAndTime
        MAX-ACCESS  read-only
        STATUS      current
        DESCRIPTION "This attribute is the bin collection start date
                     and time."
        ::= { tnOprRawCountStatsEntry 5 }

--------------------------------------------------------------------------------
-- Optical DC Power Out (OPOUT) Statistics Scalar
--------------------------------------------------------------------------------
    tnOpOutRawCountStatsTotalMembers OBJECT-TYPE
        SYNTAX      Integer32
        MAX-ACCESS  read-only
        STATUS      current
        DESCRIPTION "The total number of members in the OPOUT raw count stats
                     table."
        ::= { tnStatisticsRawCounts 19 }

--------------------------------------------------------------------------------
-- Optical DC Power Out (OPOUT) Statistics Table
--------------------------------------------------------------------------------
    tnOpOutRawCountStatsTable OBJECT-TYPE
        SYNTAX      SEQUENCE OF TnOpOutRawCountStatsEntry
        MAX-ACCESS  not-accessible
        STATUS      current
        DESCRIPTION "."
        ::= { tnStatisticsRawCounts 20 }

    tnOpOutRawCountStatsEntry OBJECT-TYPE
        SYNTAX      TnOpOutRawCountStatsEntry
        MAX-ACCESS  not-accessible
        STATUS      current
        DESCRIPTION "."
        INDEX   { ifIndex }
        ::= { tnOpOutRawCountStatsTable 1 }

    TnOpOutRawCountStatsEntry ::=
        SEQUENCE {
            tnOpOutRawCountStatsClear       TnCommand,
            tnOpOutRawCountStatMinPower     Integer32,
            tnOpOutRawCountStatMaxPower     Integer32,
            tnOpOutRawCountStatAveragePower Integer32,
            tnOpOutRawCountStatStartTime    DateAndTime
        }

    tnOpOutRawCountStatsClear OBJECT-TYPE
        SYNTAX      TnCommand
        MAX-ACCESS  read-create
        STATUS      current
        DESCRIPTION "This attribute is used to clear all the
                     raw counts on a particular interface
                     and group."
        ::= { tnOpOutRawCountStatsEntry 1 }

    tnOpOutRawCountStatMinPower OBJECT-TYPE
        SYNTAX      Integer32
        UNITS       "mBm"
        MAX-ACCESS  read-only
        STATUS      current
        DESCRIPTION "Minimum optical DC power in the
                     Out direction (mBm)."
        ::= { tnOpOutRawCountStatsEntry 2 }

    tnOpOutRawCountStatMaxPower OBJECT-TYPE
        SYNTAX      Integer32
        UNITS       "mBm"
        MAX-ACCESS  read-only
        STATUS      current
        DESCRIPTION "Maximum optical DC power in the
                     Out direction (mBm)."
        ::= { tnOpOutRawCountStatsEntry 3 }

    tnOpOutRawCountStatAveragePower OBJECT-TYPE
        SYNTAX      Integer32
        UNITS       "mBm"
        MAX-ACCESS  read-only
        STATUS      current
        DESCRIPTION "Average optical DC power in the
                     Out direction (mBm)."
        ::= { tnOpOutRawCountStatsEntry 4 }

    tnOpOutRawCountStatStartTime OBJECT-TYPE
        SYNTAX      DateAndTime
        MAX-ACCESS  read-only
        STATUS      current
        DESCRIPTION "This attribute is the bin collection start date
                     and time."
        ::= { tnOpOutRawCountStatsEntry 5 }

--------------------------------------------------------------------------------
-- Optical DC Power In (OPIN) Statistics Scalar
--------------------------------------------------------------------------------
    tnOpInRawCountStatsTotalMembers OBJECT-TYPE
        SYNTAX      Integer32
        MAX-ACCESS  read-only
        STATUS      current
        DESCRIPTION "The total number of members in the OPIN raw count stats
                     table."
        ::= { tnStatisticsRawCounts 21 }

--------------------------------------------------------------------------------
-- Optical DC Power In (OPIN) Statistics Table
--------------------------------------------------------------------------------
    tnOpInRawCountStatsTable OBJECT-TYPE
        SYNTAX      SEQUENCE OF TnOpInRawCountStatsEntry
        MAX-ACCESS  not-accessible
        STATUS      current
        DESCRIPTION "."
        ::= { tnStatisticsRawCounts 22 }

    tnOpInRawCountStatsEntry OBJECT-TYPE
        SYNTAX      TnOpInRawCountStatsEntry
        MAX-ACCESS  not-accessible
        STATUS      current
        DESCRIPTION "."
        INDEX   { ifIndex }
        ::= { tnOpInRawCountStatsTable 1 }

    TnOpInRawCountStatsEntry ::=
        SEQUENCE {
            tnOpInRawCountStatsClear       TnCommand,
            tnOpInRawCountStatMinPower     Integer32,
            tnOpInRawCountStatMaxPower     Integer32,
            tnOpInRawCountStatAveragePower Integer32,
            tnOpInRawCountStatStartTime    DateAndTime
        }

    tnOpInRawCountStatsClear OBJECT-TYPE
        SYNTAX      TnCommand
        MAX-ACCESS  read-create
        STATUS      current
        DESCRIPTION "This attribute is used to clear all the
                     raw counts on a particular interface
                     and group."
        ::= { tnOpInRawCountStatsEntry 1 }

    tnOpInRawCountStatMinPower OBJECT-TYPE
        SYNTAX      Integer32
        UNITS       "mBm"
        MAX-ACCESS  read-only
        STATUS      current
        DESCRIPTION "Minimum optical DC power in the
                     In direction (mBm)."
        ::= { tnOpInRawCountStatsEntry 2 }

    tnOpInRawCountStatMaxPower OBJECT-TYPE
        SYNTAX      Integer32
        UNITS       "mBm"
        MAX-ACCESS  read-only
        STATUS      current
        DESCRIPTION "Maximum optical DC power in the
                     In direction (mBm)."
        ::= { tnOpInRawCountStatsEntry 3 }

    tnOpInRawCountStatAveragePower OBJECT-TYPE
        SYNTAX      Integer32
        UNITS       "mBm"
        MAX-ACCESS  read-only
        STATUS      current
        DESCRIPTION "Average optical DC power in the
                     In direction (mBm)."
        ::= { tnOpInRawCountStatsEntry 4 }

    tnOpInRawCountStatStartTime OBJECT-TYPE
        SYNTAX      DateAndTime
        MAX-ACCESS  read-only
        STATUS      current
        DESCRIPTION "This attribute is the bin collection start date
                     and time."
        ::= { tnOpInRawCountStatsEntry 5 }

--------------------------------------------------------------------------------
-- Optical WT Power Out (OPOCHOUT) Statistics Scalar
--------------------------------------------------------------------------------
    tnOpOchOutRawCountStatsTotalMembers OBJECT-TYPE
        SYNTAX      Integer32
        MAX-ACCESS  read-only
        STATUS      current
        DESCRIPTION "The total number of members in the OPOCHOUT raw count stats
                     table."
        ::= { tnStatisticsRawCounts 23 }

--------------------------------------------------------------------------------
-- Optical WT Power Out (OPOCHOUT) Statistics Table
--------------------------------------------------------------------------------
    tnOpOchOutRawCountStatsTable OBJECT-TYPE
        SYNTAX      SEQUENCE OF TnOpOchOutRawCountStatsEntry
        MAX-ACCESS  not-accessible
        STATUS      current
        DESCRIPTION "."
        ::= { tnStatisticsRawCounts 24 }

    tnOpOchOutRawCountStatsEntry OBJECT-TYPE
        SYNTAX      TnOpOchOutRawCountStatsEntry
        MAX-ACCESS  not-accessible
        STATUS      current
        DESCRIPTION "."
        INDEX   { ifIndex,
                  tnOpticalStatsITUChannel }
        ::= { tnOpOchOutRawCountStatsTable 1 }

    TnOpOchOutRawCountStatsEntry ::=
        SEQUENCE {
            tnOpOchOutRawCountStatsClear       TnCommand,
            tnOpOchOutRawCountStatMinPower     Integer32,
            tnOpOchOutRawCountStatMaxPower     Integer32,
            tnOpOchOutRawCountStatAveragePower Integer32,
            tnOpOchOutRawCountStatStartTime    DateAndTime,
            tnOpOchOutRawCountStatWidth        Unsigned32
        }

    tnOpOchOutRawCountStatsClear OBJECT-TYPE
        SYNTAX      TnCommand
        MAX-ACCESS  read-create
        STATUS      current
        DESCRIPTION "This attribute is used to clear all the
                     raw counts for all frequencies on a particular
                     interface and group, regardless of the
                     frequency index."
        ::= { tnOpOchOutRawCountStatsEntry 1 }

    tnOpOchOutRawCountStatMinPower OBJECT-TYPE
        SYNTAX      Integer32
        UNITS       "mBm"
        MAX-ACCESS  read-only
        STATUS      current
        DESCRIPTION "Minimum optical WT power in the
                     Out direction (mBm)."
        ::= { tnOpOchOutRawCountStatsEntry 2 }

    tnOpOchOutRawCountStatMaxPower OBJECT-TYPE
        SYNTAX      Integer32
        UNITS       "mBm"
        MAX-ACCESS  read-only
        STATUS      current
        DESCRIPTION "Maximum optical WT power in the
                     Out direction (mBm)."
        ::= { tnOpOchOutRawCountStatsEntry 3 }

    tnOpOchOutRawCountStatAveragePower OBJECT-TYPE
        SYNTAX      Integer32
        UNITS       "mBm"
        MAX-ACCESS  read-only
        STATUS      current
        DESCRIPTION "Average optical WT power in the
                     Out direction (mBm)."
        ::= { tnOpOchOutRawCountStatsEntry 4 }

    tnOpOchOutRawCountStatStartTime OBJECT-TYPE
        SYNTAX      DateAndTime
        MAX-ACCESS  read-only
        STATUS      current
        DESCRIPTION "This attribute is the bin collection start date
                     and time."
        ::= { tnOpOchOutRawCountStatsEntry 5 }

    tnOpOchOutRawCountStatWidth OBJECT-TYPE
        SYNTAX      Unsigned32
        UNITS       "MHz"
        MAX-ACCESS  read-only
        STATUS      current
        DESCRIPTION "Channel width."
        ::= { tnOpOchOutRawCountStatsEntry 6 }

--------------------------------------------------------------------------------
-- Optical WT Power In (OPOCHIN) Statistics Scalar
--------------------------------------------------------------------------------
    tnOpOchInRawCountStatsTotalMembers OBJECT-TYPE
        SYNTAX      Integer32
        MAX-ACCESS  read-only
        STATUS      current
        DESCRIPTION "The total number of members in the OPOCHIN raw count stats
                     table."
        ::= { tnStatisticsRawCounts 25 }

--------------------------------------------------------------------------------
-- Optical WT Power In (OPOCHIN) Statistics Table
--------------------------------------------------------------------------------
    tnOpOchInRawCountStatsTable OBJECT-TYPE
        SYNTAX      SEQUENCE OF TnOpOchInRawCountStatsEntry
        MAX-ACCESS  not-accessible
        STATUS      current
        DESCRIPTION "."
        ::= { tnStatisticsRawCounts 26 }

    tnOpOchInRawCountStatsEntry OBJECT-TYPE
        SYNTAX      TnOpOchInRawCountStatsEntry
        MAX-ACCESS  not-accessible
        STATUS      current
        DESCRIPTION "."
        INDEX   { ifIndex,
                  tnOpticalStatsITUChannel }
        ::= { tnOpOchInRawCountStatsTable 1 }

    TnOpOchInRawCountStatsEntry ::=
        SEQUENCE {
            tnOpOchInRawCountStatsClear       TnCommand,
            tnOpOchInRawCountStatMinPower     Integer32,
            tnOpOchInRawCountStatMaxPower     Integer32,
            tnOpOchInRawCountStatAveragePower Integer32,
            tnOpOchInRawCountStatStartTime    DateAndTime,
            tnOpOchInRawCountStatWidth        Unsigned32
        }

    tnOpOchInRawCountStatsClear OBJECT-TYPE
        SYNTAX      TnCommand
        MAX-ACCESS  read-create
        STATUS      current
        DESCRIPTION "This attribute is used to clear all the
                     raw counts for all frequencies on a particular
                     interface and group, regardless of the
                     frequency index."
        ::= { tnOpOchInRawCountStatsEntry 1 }

    tnOpOchInRawCountStatMinPower OBJECT-TYPE
        SYNTAX      Integer32
        UNITS       "mBm"
        MAX-ACCESS  read-only
        STATUS      current
        DESCRIPTION "Minimum optical WT power in the
                     In direction (mBm)."
        ::= { tnOpOchInRawCountStatsEntry 2 }

    tnOpOchInRawCountStatMaxPower OBJECT-TYPE
        SYNTAX      Integer32
        UNITS       "mBm"
        MAX-ACCESS  read-only
        STATUS      current
        DESCRIPTION "Maximum optical WT power in the
                     In direction (mBm)."
        ::= { tnOpOchInRawCountStatsEntry 3 }

    tnOpOchInRawCountStatAveragePower OBJECT-TYPE
        SYNTAX      Integer32
        UNITS       "mBm"
        MAX-ACCESS  read-only
        STATUS      current
        DESCRIPTION "Average optical WT power in the
                     In direction (mBm)."
        ::= { tnOpOchInRawCountStatsEntry 4 }

    tnOpOchInRawCountStatStartTime OBJECT-TYPE
        SYNTAX      DateAndTime
        MAX-ACCESS  read-only
        STATUS      current
        DESCRIPTION "This attribute is the bin collection start date
                     and time."
        ::= { tnOpOchInRawCountStatsEntry 5 }

    tnOpOchInRawCountStatWidth OBJECT-TYPE
        SYNTAX      Unsigned32
        UNITS       "MHz"
        MAX-ACCESS  read-only
        STATUS      current
        DESCRIPTION "Channel width."
        ::= { tnOpOchInRawCountStatsEntry 6 }

--------------------------------------------------------------------------------
-- SDH Raw Count Statistics Scalar
--------------------------------------------------------------------------------
    tnSdhRawCountStatsTotalMembers OBJECT-TYPE
        SYNTAX      Integer32
        MAX-ACCESS  read-only
        STATUS      current
        DESCRIPTION "The total number of members in the SDH raw count stats
                     table."
        ::= { tnStatisticsRawCounts 27 }

--------------------------------------------------------------------------------
-- SONET Raw Count Statistics Table
--------------------------------------------------------------------------------
    tnSdhRawCountStatsTable OBJECT-TYPE
        SYNTAX      SEQUENCE OF TnSdhRawCountStatsEntry
        MAX-ACCESS  not-accessible
        STATUS      current
        DESCRIPTION "."
        ::= { tnStatisticsRawCounts 28 }

    tnSdhRawCountStatsEntry OBJECT-TYPE
        SYNTAX      TnSdhRawCountStatsEntry
        MAX-ACCESS  not-accessible
        STATUS      current
        DESCRIPTION "."
        INDEX   { ifIndex }
        ::= { tnSdhRawCountStatsTable 1 }

    TnSdhRawCountStatsEntry ::=
        SEQUENCE {
            tnSdhRawCountStatsClear     TnCommand,
            tnSdhRawCountStatRxRSEB     Counter32,
            tnSdhRawCountStatRxRSES     Counter32,
            tnSdhRawCountStatRxRSSES    Counter32,
            tnSdhRawCountStatRxMSEB     Counter32,
            tnSdhRawCountStatRxMSES     Counter32,
            tnSdhRawCountStatRxMSSES    Counter32,
            tnSdhRawCountStatRxMSUAS    Counter32,
            tnSdhRawCountStatTxRSEB     Counter32,
            tnSdhRawCountStatTxRSES     Counter32,
            tnSdhRawCountStatTxRSSES    Counter32,
            tnSdhRawCountStatTxMSEB     Counter32,
            tnSdhRawCountStatTxMSES     Counter32,
            tnSdhRawCountStatTxMSSES    Counter32,
            tnSdhRawCountStatTxMSUAS    Counter32,
            tnSdhRawCountStatRxRSUAS    Counter32,
            tnSdhRawCountStatTxRSUAS    Counter32,
            tnSdhRawCountStatStartTime  DateAndTime,
            tnSdhRawCountStatRxMSFEEB   Counter32,
            tnSdhRawCountStatRxMSFEES   Counter32,
            tnSdhRawCountStatRxMSFESES  Counter32,
            tnSdhRawCountStatRxMSFEUAS  Counter32
        }

    tnSdhRawCountStatsClear OBJECT-TYPE
        SYNTAX      TnCommand
        MAX-ACCESS  read-create
        STATUS      current
        DESCRIPTION "This attribute is used to clear all the
                     raw counts on a particular interface
                     and group."
        ::= { tnSdhRawCountStatsEntry 1 }

    tnSdhRawCountStatRxRSEB OBJECT-TYPE
        SYNTAX      Counter32
        MAX-ACCESS  read-only
        STATUS      current
        DESCRIPTION "Regenerator section - errored block. Provides
                     a count of the number of B1 violations."
        ::= { tnSdhRawCountStatsEntry 2 }

    tnSdhRawCountStatRxRSES OBJECT-TYPE
        SYNTAX      Counter32
        MAX-ACCESS  read-only
        STATUS      current
        DESCRIPTION "Regenerator section - errored second. Provides
                     a count of the number of one second intervals in
                     which any of the following conditions are true:

                     - at least one B1 BIP-8 error was detected.
                     - a loss of signal (LOS) defect was present.
                     - a severely errored frame (SEF) defect was
                       present."
        ::= { tnSdhRawCountStatsEntry 3 }

    tnSdhRawCountStatRxRSSES OBJECT-TYPE
        SYNTAX      Counter32
        MAX-ACCESS  read-only
        STATUS      current
        DESCRIPTION "Regenerator section - severely errored second.
                     Provides a count of the number of one second
                     intervals in which any of the following conditions
                     are true:

                     - the number of regenerator section layer BIP
                       errors detected exceeded the value defined in
                       GR-253-CORE.
                     - a loss of signal (LOS) defect was present.
                     - a severely errored frame (SEF) defect was
                       present."
        ::= { tnSdhRawCountStatsEntry 4 }

    tnSdhRawCountStatRxMSEB OBJECT-TYPE
        SYNTAX      Counter32
        MAX-ACCESS  read-only
        STATUS      current
        DESCRIPTION "Multiplex section - errored block. Provides a
                     count of the number of B2 BIP violations."
        ::= { tnSdhRawCountStatsEntry 5 }

    tnSdhRawCountStatRxMSES OBJECT-TYPE
        SYNTAX      Counter32
        MAX-ACCESS  read-only
        STATUS      current
        DESCRIPTION "Multiplex section - errored second. Provides
                     a count of the number of one second intervals
                     in which any of the following conditions are true:

                     - at least one B2 BIP error was detected.
                     - an alarm indicating signal (MS-AIS) defect
                       was present."
        ::= { tnSdhRawCountStatsEntry 6 }

    tnSdhRawCountStatRxMSSES OBJECT-TYPE
        SYNTAX      Counter32
        MAX-ACCESS  read-only
        STATUS      current
        DESCRIPTION "Multiplex section - severely errored second.
                     Provides a count of the number of one second
                     intervals in which any of the following
                     conditions are true:

                     - the number of multiplex section layer B2 errors
                       detected exceeded the value defined in
                       GR-253-CORE.
                     - an alarm indicating signal (MS-AIS) defect
                       was present."
        ::= { tnSdhRawCountStatsEntry 7 }

    tnSdhRawCountStatRxMSUAS OBJECT-TYPE
        SYNTAX      Counter32
        MAX-ACCESS  read-only
        STATUS      current
        DESCRIPTION "Multiplex section - unavailable second. Provides
                     a count of the number of seconds that a line is
                     unavailable. A multiplex section is deemed to be
                     unavailable when 10 consecutive severely errored
                     seconds (SESs) are detected. The period of
                     unavailability begins at the onset the 10
                     consecutive SESs (back in time). Availability
                     is declared after a period of 10 consecutive
                     non-SESs. The period of availability begins
                     at the onset of the 10 consecutive
                     non-SESs (back in time)."
        ::= { tnSdhRawCountStatsEntry 8 }

    tnSdhRawCountStatTxRSEB OBJECT-TYPE
        SYNTAX      Counter32
        MAX-ACCESS  read-only
        STATUS      current
        DESCRIPTION "Regenerator section - errored block. Provides a
                     count of the number of B1 violations."
        ::= { tnSdhRawCountStatsEntry 9 }

    tnSdhRawCountStatTxRSES OBJECT-TYPE
        SYNTAX      Counter32
        MAX-ACCESS  read-only
        STATUS      current
        DESCRIPTION "Regenerator section - errored second. Provides
                     a count of the number of one second intervals in
                     which any of the following conditions are true:

                     - at least one B1 BIP-8 error was detected.
                     - a loss of signal (LOS) defect was present.
                     - a severely errored frame (SEF) defect was
                       present."
        ::= { tnSdhRawCountStatsEntry 10 }

    tnSdhRawCountStatTxRSSES OBJECT-TYPE
        SYNTAX      Counter32
        MAX-ACCESS  read-only
        STATUS      current
        DESCRIPTION "Regenerator section - severely errored second.
                     Provides a count of the number of one second
                     intervals in which any of the following conditions
                     are true:

                     - the number of regenerator section layer BIP
                       errors detected exceeded the value defined in
                       GR-253-CORE.
                     - a loss of signal (LOS) defect was present.
                     - a severely errored frame (SEF) defect was
                       present."
        ::= { tnSdhRawCountStatsEntry 11 }

    tnSdhRawCountStatTxMSEB OBJECT-TYPE
        SYNTAX      Counter32
        MAX-ACCESS  read-only
        STATUS      current
        DESCRIPTION "Multiplex section - errored block. Provides a
                     count of the number of B2 BIP violations."
        ::= { tnSdhRawCountStatsEntry 12 }

    tnSdhRawCountStatTxMSES OBJECT-TYPE
        SYNTAX      Counter32
        MAX-ACCESS  read-only
        STATUS      current
        DESCRIPTION "Multiplex section - errored second. Provides
                     a count of the number of one second intervals
                     in which any of the following conditions are true:

                     - at least one B2 BIP error was detected.
                     - an alarm indicating signal (MS-AIS) defect
                       was present."
        ::= { tnSdhRawCountStatsEntry 13 }

    tnSdhRawCountStatTxMSSES OBJECT-TYPE
        SYNTAX      Counter32
        MAX-ACCESS  read-only
        STATUS      current
        DESCRIPTION "Multiplex section - severely errored second.
                     Provides a count of the number of one second
                     intervals in which any of the following
                     conditions are true:

                     - the number of multiplex section layer B2 errors
                       detected exceeded the value defined in
                       GR-253-CORE.
                     - an alarm indicating signal (MS-AIS) defect
                       was present."
        ::= { tnSdhRawCountStatsEntry 14 }

    tnSdhRawCountStatTxMSUAS OBJECT-TYPE
        SYNTAX      Counter32
        MAX-ACCESS  read-only
        STATUS      current
        DESCRIPTION "Multiplex section - unavailable second. Provides
                     a count of the number of seconds that a line is
                     unavailable. A multiplex section is deemed to be
                     unavailable when 10 consecutive severely errored
                     seconds (SESs) are detected. The period of
                     unavailability begins at the onset the 10
                     consecutive SESs (back in time). Availability
                     is declared after a period of 10 consecutive
                     non-SESs. The period of availability begins
                     at the onset of the 10 consecutive
                     non-SESs (back in time)."
        ::= { tnSdhRawCountStatsEntry 15 }

    tnSdhRawCountStatRxRSUAS OBJECT-TYPE
        SYNTAX      Counter32
        MAX-ACCESS  read-only
        STATUS      current
        DESCRIPTION "Regenerator section - unavailable second. Provides
                     a count of the number of seconds that a line is
                     unavailable. A regenerator section is deemed to be
                     unavailable when 10 consecutive severely errored
                     seconds (SESs) are detected. The period of
                     unavailability begins at the onset the 10
                     consecutive SESs (back in time). Availability
                     is declared after a period of 10 consecutive
                     non-SESs. The period of availability begins
                     at the onset of the 10 consecutive
                     non-SESs (back in time)."
        ::= { tnSdhRawCountStatsEntry 16 }

    tnSdhRawCountStatTxRSUAS OBJECT-TYPE
        SYNTAX      Counter32
        MAX-ACCESS  read-only
        STATUS      current
        DESCRIPTION "Regenerator section - unavailable second. Provides
                     a count of the number of seconds that a line is
                     unavailable. A regenerator section is deemed to be
                     unavailable when 10 consecutive severely errored
                     seconds (SESs) are detected. The period of
                     unavailability begins at the onset the 10
                     consecutive SESs (back in time). Availability is
                     declared after a period of 10 consecutive non-SESs.
                     The period of availability begins at the onset of
                     the 10 consecutive non-SESs (back in time)."
        ::= { tnSdhRawCountStatsEntry 17 }

    tnSdhRawCountStatStartTime OBJECT-TYPE
        SYNTAX      DateAndTime
        MAX-ACCESS  read-only
        STATUS      current
        DESCRIPTION "This attribute is the bin collection start date
                     and time."
        ::= { tnSdhRawCountStatsEntry 18 }

    tnSdhRawCountStatRxMSFEEB OBJECT-TYPE
        SYNTAX      Counter32
        MAX-ACCESS  read-only
        STATUS      current
        DESCRIPTION "Multiplex section - errored block. Provides a
                     count of the number of B2 BIP violations."
        ::= { tnSdhRawCountStatsEntry 19 }

    tnSdhRawCountStatRxMSFEES OBJECT-TYPE
        SYNTAX      Counter32
        MAX-ACCESS  read-only
        STATUS      current
        DESCRIPTION "Multiplex section - errored second."
        ::= { tnSdhRawCountStatsEntry 20 }

    tnSdhRawCountStatRxMSFESES OBJECT-TYPE
        SYNTAX      Counter32
        MAX-ACCESS  read-only
        STATUS      current
        DESCRIPTION "Multiplex section - severely errored second."
        ::= { tnSdhRawCountStatsEntry 21 }

    tnSdhRawCountStatRxMSFEUAS OBJECT-TYPE
        SYNTAX      Counter32
        MAX-ACCESS  read-only
        STATUS      current
        DESCRIPTION "Multiplex section - unavailable second. Provides
                     a count of the number of seconds that a line is
                     unavailable."
        ::= { tnSdhRawCountStatsEntry 22 }

--    obsolete
--    tnPathSummaryRawCountStatsTotalMembers  OBJECT-TYPE ::= { tnStatisticsRawCounts 29 }
--    tnPathSummaryRawCountStatsTable         OBJECT-TYPE ::= { tnStatisticsRawCounts 30 }
--    tnFibreChannelRawCountStatsTotalMembers OBJECT-TYPE ::= { tnStatisticsRawCounts 31 }
--    tnFibreChannelRawCountStatsTable        OBJECT-TYPE ::= { tnStatisticsRawCounts 32 }

--------------------------------------------------------------------------------
-- Physical Coding Sublayer (PCS) Raw Count Statistics Scalar
--------------------------------------------------------------------------------
    tnPhyCodeSublayerRawCountStatsTotalMembers OBJECT-TYPE
        SYNTAX      Integer32
        MAX-ACCESS  read-only
        STATUS      current
        DESCRIPTION "The total number of members in the PCS raw count stats
                     table."
        ::= { tnStatisticsRawCounts 33 }

--------------------------------------------------------------------------------
-- Physical Coding Sublayer (PCS) Raw Count Statistics Table
--------------------------------------------------------------------------------
    tnPhyCodeSublayerRawCountStatsTable OBJECT-TYPE
        SYNTAX      SEQUENCE OF TnPhyCodeSublayerRawCountStatsEntry
        MAX-ACCESS  not-accessible
        STATUS      current
        DESCRIPTION "."
        ::= { tnStatisticsRawCounts 34 }

    tnPhyCodeSublayerRawCountStatsEntry OBJECT-TYPE
        SYNTAX      TnPhyCodeSublayerRawCountStatsEntry
        MAX-ACCESS  not-accessible
        STATUS      current
        DESCRIPTION "."
        INDEX   { ifIndex }
        ::= { tnPhyCodeSublayerRawCountStatsTable 1 }

    TnPhyCodeSublayerRawCountStatsEntry ::=
        SEQUENCE {
            tnPhyCodeSublayerRawCountStatsClear     TnCommand,
            tnPhyCodeSublayerRawCountStatRxCV       Counter32,
            tnPhyCodeSublayerRawCountStatRxES       Counter32,
            tnPhyCodeSublayerRawCountStatRxSES      Counter32,
            tnPhyCodeSublayerRawCountStatRxSEFS     Counter32,
            tnPhyCodeSublayerRawCountStatTxCV       Counter32,
            tnPhyCodeSublayerRawCountStatTxES       Counter32,
            tnPhyCodeSublayerRawCountStatTxSES      Counter32,
            tnPhyCodeSublayerRawCountStatTxSEFS     Counter32,
            tnPhyCodeSublayerRawCountStatStartTime  DateAndTime
        }

    tnPhyCodeSublayerRawCountStatsClear OBJECT-TYPE
        SYNTAX      TnCommand
        MAX-ACCESS  read-create
        STATUS      current
        DESCRIPTION "This attribute is used to clear all the
                     raw counts on a particular interface
                     and group."
        ::= { tnPhyCodeSublayerRawCountStatsEntry 1 }

    tnPhyCodeSublayerRawCountStatRxCV OBJECT-TYPE
        SYNTAX      Counter32
        MAX-ACCESS  read-only
        STATUS      current
        DESCRIPTION "Coding violation."
        ::= { tnPhyCodeSublayerRawCountStatsEntry 2 }

    tnPhyCodeSublayerRawCountStatRxES OBJECT-TYPE
        SYNTAX      Counter32
        MAX-ACCESS  read-only
        STATUS      current
        DESCRIPTION "Errored second."
        ::= { tnPhyCodeSublayerRawCountStatsEntry 3 }

    tnPhyCodeSublayerRawCountStatRxSES OBJECT-TYPE
        SYNTAX      Counter32
        MAX-ACCESS  read-only
        STATUS      current
        DESCRIPTION "Severely errored second."
        ::= { tnPhyCodeSublayerRawCountStatsEntry 4 }

    tnPhyCodeSublayerRawCountStatRxSEFS OBJECT-TYPE
        SYNTAX      Counter32
        MAX-ACCESS  read-only
        STATUS      current
        DESCRIPTION "Severely errored frame second."
        ::= { tnPhyCodeSublayerRawCountStatsEntry 5 }

    tnPhyCodeSublayerRawCountStatTxCV OBJECT-TYPE
        SYNTAX      Counter32
        MAX-ACCESS  read-only
        STATUS      current
        DESCRIPTION "Coding violation."
        ::= { tnPhyCodeSublayerRawCountStatsEntry 6 }

    tnPhyCodeSublayerRawCountStatTxES OBJECT-TYPE
        SYNTAX      Counter32
        MAX-ACCESS  read-only
        STATUS      current
        DESCRIPTION "Errored second."
        ::= { tnPhyCodeSublayerRawCountStatsEntry 7 }

    tnPhyCodeSublayerRawCountStatTxSES OBJECT-TYPE
        SYNTAX      Counter32
        MAX-ACCESS  read-only
        STATUS      current
        DESCRIPTION "Severely errored second."
        ::= { tnPhyCodeSublayerRawCountStatsEntry 8 }

    tnPhyCodeSublayerRawCountStatTxSEFS OBJECT-TYPE
        SYNTAX      Counter32
        MAX-ACCESS  read-only
        STATUS      current
        DESCRIPTION "Severely errored frame second."
        ::= { tnPhyCodeSublayerRawCountStatsEntry 9 }

    tnPhyCodeSublayerRawCountStatStartTime OBJECT-TYPE
        SYNTAX      DateAndTime
        MAX-ACCESS  read-only
        STATUS      current
        DESCRIPTION "This attribute is the bin collection start date
                     and time."
        ::= { tnPhyCodeSublayerRawCountStatsEntry 10 }

--------------------------------------------------------------------------------
-- Digital Wrapper 64 Bit Raw Count Statistics Scalar
--------------------------------------------------------------------------------
    tnDigitalWrapper64BitRawCountStatsTotalMembers OBJECT-TYPE
        SYNTAX      Integer32
        MAX-ACCESS  read-only
        STATUS      current
        DESCRIPTION "The total number of members in the digital wrapper raw count
                     stats table."
        ::= { tnStatisticsRawCounts 35 }

--------------------------------------------------------------------------------
-- Digital Wrapper 64 Bit Raw Count Statistics Table
--------------------------------------------------------------------------------
    tnDigitalWrapper64BitRawCountStatsTable OBJECT-TYPE
        SYNTAX      SEQUENCE OF TnDigitalWrapper64BitRawCountStatsEntry
        MAX-ACCESS  not-accessible
        STATUS      current
        DESCRIPTION "."
        ::= { tnStatisticsRawCounts 36 }

    tnDigitalWrapper64BitRawCountStatsEntry OBJECT-TYPE
        SYNTAX      TnDigitalWrapper64BitRawCountStatsEntry
        MAX-ACCESS  not-accessible
        STATUS      current
        DESCRIPTION "."
        INDEX   { ifIndex }
        ::= { tnDigitalWrapper64BitRawCountStatsTable 1 }

    TnDigitalWrapper64BitRawCountStatsEntry ::=
        SEQUENCE {
            tnDw64BitRawCountStatsClear            TnCommand,
            tnDw64BitRawCountStatRxRSCorrCnt       Counter64,
            tnDw64BitRawCountStatRxRSUncorrCnt     Counter64,
            tnDw64BitRawCountStatRxSMBIP8ErrCnt    Counter64,
            tnDw64BitRawCountStatRxPMBIP8ErrCnt    Counter64,
            tnDw64BitRawCountStatRxSMBEIErrCnt     Counter64,
            tnDw64BitRawCountStatRxPMBEIErrCnt     Counter64,
            tnDw64BitRawCountStatRxRSSES           Counter64,
            tnDw64BitRawCountStatRxSMES            Counter64,
            tnDw64BitRawCountStatRxPMES            Counter64,
            tnDw64BitRawCountStatRxSMSES           Counter64,
            tnDw64BitRawCountStatRxPMSES           Counter64,
            tnDw64BitRawCountStatRxSMUAS           Counter64,
            tnDw64BitRawCountStatRxPMUAS           Counter64,
            tnDw64BitRawCountStatStartTime         DateAndTime,
            tnDw64BitRawCountStatRxBERPreFEC       Counter64,
            tnDw64BitRawCountStatRxBERPostFEC      Counter64,
            tnDw64BitRawCountStatRxSMFEBIP8ErrCnt  Counter64,
            tnDw64BitRawCountStatRxPMFEBIP8ErrCnt  Counter64,
            tnDw64BitRawCountStatRxSMBIAESErrCnt   Counter64,
            tnDw64BitRawCountStatRxSMIAESErrCnt    Counter64,
            tnDw64BitRawCountStatRxSMFEES          Counter64,
            tnDw64BitRawCountStatRxPMFEES          Counter64,
            tnDw64BitRawCountStatRxSMFESES         Counter64,
            tnDw64BitRawCountStatRxPMFESES         Counter64,
            tnDw64BitRawCountStatRxSMFEUAS         Counter64,
            tnDw64BitRawCountStatRxPMFEUAS         Counter64
        }

    tnDw64BitRawCountStatsClear OBJECT-TYPE
        SYNTAX      TnCommand
        MAX-ACCESS  read-create
        STATUS      current
        DESCRIPTION "This attribute is used to clear all the
                     raw counts on a particular interface
                     and group."
        ::= { tnDigitalWrapper64BitRawCountStatsEntry 1 }

    tnDw64BitRawCountStatRxRSCorrCnt OBJECT-TYPE
        SYNTAX      Counter64
        MAX-ACCESS  read-only
        STATUS      current
        DESCRIPTION "Provides a count of the number of bits
                     corrected at the receiver."
        ::= { tnDigitalWrapper64BitRawCountStatsEntry 2 }

    tnDw64BitRawCountStatRxRSUncorrCnt OBJECT-TYPE
        SYNTAX      Counter64
        MAX-ACCESS  read-only
        STATUS      current
        DESCRIPTION "Provides a count of the number of blocks
                     detected at the receiver which have
                     uncorrectable errors."
        ::= { tnDigitalWrapper64BitRawCountStatsEntry 3 }

    tnDw64BitRawCountStatRxSMBIP8ErrCnt OBJECT-TYPE
        SYNTAX      Counter64
        MAX-ACCESS  read-only
        STATUS      current
        DESCRIPTION "Provides a count of the section monitor
                     bit interleaved parity (BIP-8) errors
                     detected at the receiver."
        ::= { tnDigitalWrapper64BitRawCountStatsEntry 4 }

    tnDw64BitRawCountStatRxPMBIP8ErrCnt OBJECT-TYPE
        SYNTAX      Counter64
        MAX-ACCESS  read-only
        STATUS      current
        DESCRIPTION "Provides a count of the path monitor bit
                     interleaved parity (BIP-8) errors detected
                     at the receiver."
        ::= { tnDigitalWrapper64BitRawCountStatsEntry 5 }

    tnDw64BitRawCountStatRxSMBEIErrCnt OBJECT-TYPE
        SYNTAX      Counter64
        MAX-ACCESS  read-only
        STATUS      current
        DESCRIPTION "Provides a count of the section monitor
                     backward error indication (BEI) errors
                     detected at the receiver."
        ::= { tnDigitalWrapper64BitRawCountStatsEntry 6 }

    tnDw64BitRawCountStatRxPMBEIErrCnt OBJECT-TYPE
        SYNTAX      Counter64
        MAX-ACCESS  read-only
        STATUS      current
        DESCRIPTION "Provides a count of the path monitor
                     backward error indication (BEI) errors
                     detected at the receiver."
        ::= { tnDigitalWrapper64BitRawCountStatsEntry 7 }

    tnDw64BitRawCountStatRxRSSES OBJECT-TYPE
        SYNTAX      Counter64
        MAX-ACCESS  read-only
        STATUS      current
        DESCRIPTION "RX RS Severely Errored Second (SES): A one-second
                     period which contains 15% errored blocks or at
                     least one defect."
        ::= { tnDigitalWrapper64BitRawCountStatsEntry 8 }

    tnDw64BitRawCountStatRxSMES OBJECT-TYPE
        SYNTAX      Counter64
        MAX-ACCESS  read-only
        STATUS      current
        DESCRIPTION "Provides a count of the section monitor
                     errored seconds."
        ::= { tnDigitalWrapper64BitRawCountStatsEntry 9 }

    tnDw64BitRawCountStatRxPMES OBJECT-TYPE
        SYNTAX      Counter64
        MAX-ACCESS  read-only
        STATUS      current
        DESCRIPTION "Provides a count of the path monitor
                     errored seconds."
        ::= { tnDigitalWrapper64BitRawCountStatsEntry 10 }

    tnDw64BitRawCountStatRxSMSES OBJECT-TYPE
        SYNTAX      Counter64
        MAX-ACCESS  read-only
        STATUS      current
        DESCRIPTION "Provides a count of the section monitor
                     severely errored seconds."
        ::= { tnDigitalWrapper64BitRawCountStatsEntry 11 }

    tnDw64BitRawCountStatRxPMSES OBJECT-TYPE
        SYNTAX      Counter64
        MAX-ACCESS  read-only
        STATUS      current
        DESCRIPTION "Provides a count of the path monitor
                     severely errored seconds."
        ::= { tnDigitalWrapper64BitRawCountStatsEntry 12 }

    tnDw64BitRawCountStatRxSMUAS OBJECT-TYPE
        SYNTAX      Counter64
        MAX-ACCESS  read-only
        STATUS      current
        DESCRIPTION "Provides a count of the section monitor
                     unavailable seconds."
        ::= { tnDigitalWrapper64BitRawCountStatsEntry 13 }

    tnDw64BitRawCountStatRxPMUAS OBJECT-TYPE
        SYNTAX      Counter64
        MAX-ACCESS  read-only
        STATUS      current
        DESCRIPTION "Provides a count of the path monitor
                     unavailable seconds."
        ::= { tnDigitalWrapper64BitRawCountStatsEntry 14 }

    tnDw64BitRawCountStatStartTime OBJECT-TYPE
        SYNTAX      DateAndTime
        MAX-ACCESS  read-only
        STATUS      current
        DESCRIPTION "This attribute is the bin collection start date
                     and time."
        ::= { tnDigitalWrapper64BitRawCountStatsEntry 15 }

    tnDw64BitRawCountStatRxBERPreFEC OBJECT-TYPE
        SYNTAX      Counter64
        MAX-ACCESS  read-only
        STATUS      current
        DESCRIPTION "Provides the error bit rate of pre-FEC
                     (Forward Error Correction)."
        ::= { tnDigitalWrapper64BitRawCountStatsEntry 16 }

    tnDw64BitRawCountStatRxBERPostFEC OBJECT-TYPE
        SYNTAX      Counter64
        MAX-ACCESS  read-only
        STATUS      current
        DESCRIPTION "Provides the error bit rate of post-FEC
                     (Forward Error Correction)."
        ::= { tnDigitalWrapper64BitRawCountStatsEntry 17 }

    tnDw64BitRawCountStatRxSMFEBIP8ErrCnt OBJECT-TYPE
        SYNTAX      Counter64
        MAX-ACCESS  read-only
        STATUS      current
        DESCRIPTION "Provides a count of the far end section monitor
                     bit interleaved parity (BIP-8) errors detected
                     at the receiver."
        ::= { tnDigitalWrapper64BitRawCountStatsEntry 18 }

    tnDw64BitRawCountStatRxPMFEBIP8ErrCnt OBJECT-TYPE
        SYNTAX      Counter64
        MAX-ACCESS  read-only
        STATUS      current
        DESCRIPTION "Provides a count of the far end bit interleaved
                     parity (BIP-8) errors detected at the receiver."
        ::= { tnDigitalWrapper64BitRawCountStatsEntry 19 }

    tnDw64BitRawCountStatRxSMBIAESErrCnt OBJECT-TYPE
        SYNTAX      Counter64
        MAX-ACCESS  read-only
        STATUS      current
        DESCRIPTION "Provides a count of the section monitor backward
                     error indication (BEI) errors."
        ::= { tnDigitalWrapper64BitRawCountStatsEntry 20 }

    tnDw64BitRawCountStatRxSMIAESErrCnt OBJECT-TYPE
        SYNTAX      Counter64
        MAX-ACCESS  read-only
        STATUS      current
        DESCRIPTION "Provides a count of the backward error indication
                     (BEI) errors."
        ::= { tnDigitalWrapper64BitRawCountStatsEntry 21 }

    tnDw64BitRawCountStatRxSMFEES OBJECT-TYPE
        SYNTAX      Counter64
        MAX-ACCESS  read-only
        STATUS      current
        DESCRIPTION "Provides a count of section monitoring far end
                     errored seconds."
        ::= { tnDigitalWrapper64BitRawCountStatsEntry 22 }

    tnDw64BitRawCountStatRxPMFEES OBJECT-TYPE
        SYNTAX      Counter64
        MAX-ACCESS  read-only
        STATUS      current
        DESCRIPTION "Provides a count of far end errored seconds."
        ::= { tnDigitalWrapper64BitRawCountStatsEntry 23 }

    tnDw64BitRawCountStatRxSMFESES OBJECT-TYPE
        SYNTAX      Counter64
        MAX-ACCESS  read-only
        STATUS      current
        DESCRIPTION "Provides a count of section monitoring far end
                     severely errored seconds."
        ::= { tnDigitalWrapper64BitRawCountStatsEntry 24 }

    tnDw64BitRawCountStatRxPMFESES OBJECT-TYPE
        SYNTAX      Counter64
        MAX-ACCESS  read-only
        STATUS      current
        DESCRIPTION "Provides a count of far end severely errored
                     seconds."
        ::= { tnDigitalWrapper64BitRawCountStatsEntry 25 }

    tnDw64BitRawCountStatRxSMFEUAS OBJECT-TYPE
        SYNTAX      Counter64
        MAX-ACCESS  read-only
        STATUS      current
        DESCRIPTION "Provides a count of section monitoring far end
                     unavailable seconds."
        ::= { tnDigitalWrapper64BitRawCountStatsEntry 26 }

    tnDw64BitRawCountStatRxPMFEUAS OBJECT-TYPE
        SYNTAX      Counter64
        MAX-ACCESS  read-only
        STATUS      current
        DESCRIPTION "Provides a count of far end unavailable seconds."
        ::= { tnDigitalWrapper64BitRawCountStatsEntry 27 }

--------------------------------------------------------------------------------
-- Chromatic Dispersion received (CDR) Raw Count Statistics Scalar
--------------------------------------------------------------------------------
    tnCdrRawCountStatsTotalMembers OBJECT-TYPE
        SYNTAX      Integer32
        MAX-ACCESS  read-only
        STATUS      current
        DESCRIPTION "The total number of members in the CDR raw count stats
                     table."
        ::= { tnStatisticsRawCounts 37 }

--------------------------------------------------------------------------------
-- Chromatic Dispersion received (CDR) Raw Count Statistics Table
--------------------------------------------------------------------------------
    tnCdrRawCountStatsTable OBJECT-TYPE
        SYNTAX      SEQUENCE OF TnCdrRawCountStatsEntry
        MAX-ACCESS  not-accessible
        STATUS      current
        DESCRIPTION "."
        ::= { tnStatisticsRawCounts 38 }

    tnCdrRawCountStatsEntry OBJECT-TYPE
        SYNTAX      TnCdrRawCountStatsEntry
        MAX-ACCESS  not-accessible
        STATUS      current
        DESCRIPTION "."
        INDEX   { ifIndex }
        ::= { tnCdrRawCountStatsTable 1 }

    TnCdrRawCountStatsEntry ::=
        SEQUENCE {
            tnCdrRawCountStatsClear       TnCommand,
            tnCdrRawCountStatMin          Integer32,
            tnCdrRawCountStatMax          Integer32,
            tnCdrRawCountStatAverage      Integer32,
            tnCdrRawCountStatStartTime    DateAndTime
        }

    tnCdrRawCountStatsClear OBJECT-TYPE
        SYNTAX      TnCommand
        MAX-ACCESS  read-create
        STATUS      current
        DESCRIPTION "This attribute is used to clear all the
                     raw counts on a particular interface
                     and group."
        ::= { tnCdrRawCountStatsEntry 1 }

    tnCdrRawCountStatMin OBJECT-TYPE
        SYNTAX      Integer32
        UNITS       "ps/nm"
        MAX-ACCESS  read-only
        STATUS      current
        DESCRIPTION "Minimum chromatic dispersion received (ps/nm)."
        ::= { tnCdrRawCountStatsEntry 2 }

    tnCdrRawCountStatMax OBJECT-TYPE
        SYNTAX      Integer32
        UNITS       "ps/nm"
        MAX-ACCESS  read-only
        STATUS      current
        DESCRIPTION "Maximum chromatic dispersion received (ps/nm)."
        ::= { tnCdrRawCountStatsEntry 3 }

    tnCdrRawCountStatAverage OBJECT-TYPE
        SYNTAX      Integer32
        UNITS       "ps/nm"
        MAX-ACCESS  read-only
        STATUS      current
        DESCRIPTION "Average chromatic dispersion received (ps/nm)."
        ::= { tnCdrRawCountStatsEntry 4 }

    tnCdrRawCountStatStartTime OBJECT-TYPE
        SYNTAX      DateAndTime
        MAX-ACCESS  read-only
        STATUS      current
        DESCRIPTION "This attribute is the bin collection start date
                     and time."
        ::= { tnCdrRawCountStatsEntry 5 }

--------------------------------------------------------------------------------
-- Differential Group Delay received (DGDR) Raw Count Statistics Scalar
--------------------------------------------------------------------------------
    tnDgdrRawCountStatsTotalMembers OBJECT-TYPE
        SYNTAX      Integer32
        MAX-ACCESS  read-only
        STATUS      current
        DESCRIPTION "The total number of members in the DGDR raw count stats
                     table."
        ::= { tnStatisticsRawCounts 39 }

--------------------------------------------------------------------------------
-- Differential Group Delay received (DGDR) Raw Count Statistics Table
--------------------------------------------------------------------------------
    tnDgdrRawCountStatsTable OBJECT-TYPE
        SYNTAX      SEQUENCE OF TnDgdrRawCountStatsEntry
        MAX-ACCESS  not-accessible
        STATUS      current
        DESCRIPTION "."
        ::= { tnStatisticsRawCounts 40 }

    tnDgdrRawCountStatsEntry OBJECT-TYPE
        SYNTAX      TnDgdrRawCountStatsEntry
        MAX-ACCESS  not-accessible
        STATUS      current
        DESCRIPTION "."
        INDEX   { ifIndex }
        ::= { tnDgdrRawCountStatsTable 1 }

    TnDgdrRawCountStatsEntry ::=
        SEQUENCE {
            tnDgdrRawCountStatsClear       TnCommand,
            tnDgdrRawCountStatMin          Integer32,
            tnDgdrRawCountStatMax          Integer32,
            tnDgdrRawCountStatAverage      Integer32,
            tnDgdrRawCountStatStartTime    DateAndTime
        }

    tnDgdrRawCountStatsClear OBJECT-TYPE
        SYNTAX      TnCommand
        MAX-ACCESS  read-create
        STATUS      current
        DESCRIPTION "This attribute is used to clear all the
                     raw counts on a particular interface
                     and group."
        ::= { tnDgdrRawCountStatsEntry 1 }

    tnDgdrRawCountStatMin OBJECT-TYPE
        SYNTAX      Integer32
        UNITS       "ps"
        MAX-ACCESS  read-only
        STATUS      current
        DESCRIPTION "Minimum differential group delay received (ps)."
        ::= { tnDgdrRawCountStatsEntry 2 }

    tnDgdrRawCountStatMax OBJECT-TYPE
        SYNTAX      Integer32
        UNITS       "ps"
        MAX-ACCESS  read-only
        STATUS      current
        DESCRIPTION "Maximum differential group delay received (ps)."
        ::= { tnDgdrRawCountStatsEntry 3 }

    tnDgdrRawCountStatAverage OBJECT-TYPE
        SYNTAX      Integer32
        UNITS       "ps"
        MAX-ACCESS  read-only
        STATUS      current
        DESCRIPTION "Average differential group delay received (ps)."
        ::= { tnDgdrRawCountStatsEntry 4 }

    tnDgdrRawCountStatStartTime OBJECT-TYPE
        SYNTAX      DateAndTime
        MAX-ACCESS  read-only
        STATUS      current
        DESCRIPTION "This attribute is the bin collection start date
                     and time."
        ::= { tnDgdrRawCountStatsEntry 5 }

--------------------------------------------------------------------------------
-- Frequency Offset received (FOFFR) Raw Count Statistics Scalar
--------------------------------------------------------------------------------
    tnFoffrRawCountStatsTotalMembers OBJECT-TYPE
        SYNTAX      Integer32
        MAX-ACCESS  read-only
        STATUS      current
        DESCRIPTION "The total number of members in the FOFFR raw count stats
                     table."
        ::= { tnStatisticsRawCounts 41 }

--------------------------------------------------------------------------------
-- Frequency Offset received (FOFFR) Raw Count Statistics Table
--------------------------------------------------------------------------------
    tnFoffrRawCountStatsTable OBJECT-TYPE
        SYNTAX      SEQUENCE OF TnFoffrRawCountStatsEntry
        MAX-ACCESS  not-accessible
        STATUS      current
        DESCRIPTION "."
        ::= { tnStatisticsRawCounts 42 }

    tnFoffrRawCountStatsEntry OBJECT-TYPE
        SYNTAX      TnFoffrRawCountStatsEntry
        MAX-ACCESS  not-accessible
        STATUS      current
        DESCRIPTION "."
        INDEX   { ifIndex }
        ::= { tnFoffrRawCountStatsTable 1 }

    TnFoffrRawCountStatsEntry ::=
        SEQUENCE {
            tnFoffrRawCountStatsClear       TnCommand,
            tnFoffrRawCountStatMin          Integer32,
            tnFoffrRawCountStatMax          Integer32,
            tnFoffrRawCountStatAverage      Integer32,
            tnFoffrRawCountStatStartTime    DateAndTime
        }

    tnFoffrRawCountStatsClear OBJECT-TYPE
        SYNTAX      TnCommand
        MAX-ACCESS  read-create
        STATUS      current
        DESCRIPTION "This attribute is used to clear all the
                     raw counts on a particular interface
                     and group."
        ::= { tnFoffrRawCountStatsEntry 1 }

    tnFoffrRawCountStatMin OBJECT-TYPE
        SYNTAX      Integer32
        UNITS       "GHz"
        MAX-ACCESS  read-only
        STATUS      current
        DESCRIPTION "Minimum frequency offset received (GHz)."
        ::= { tnFoffrRawCountStatsEntry 2 }

    tnFoffrRawCountStatMax OBJECT-TYPE
        SYNTAX      Integer32
        UNITS       "GHz"
        MAX-ACCESS  read-only
        STATUS      current
        DESCRIPTION "Maximum frequency offset received (GHz)."
        ::= { tnFoffrRawCountStatsEntry 3 }

    tnFoffrRawCountStatAverage OBJECT-TYPE
        SYNTAX      Integer32
        UNITS       "GHz"
        MAX-ACCESS  read-only
        STATUS      current
        DESCRIPTION "Average frequency offset received (GHz)."
        ::= { tnFoffrRawCountStatsEntry 4 }

    tnFoffrRawCountStatStartTime OBJECT-TYPE
        SYNTAX      DateAndTime
        MAX-ACCESS  read-only
        STATUS      current
        DESCRIPTION "This attribute is the bin collection start date
                     and time."
        ::= { tnFoffrRawCountStatsEntry 5 }

--------------------------------------------------------------------------------
-- E1 Raw Count Statistics Scalar
--------------------------------------------------------------------------------
    tnE1RawCountStatsTotalMembers OBJECT-TYPE
        SYNTAX      Integer32
        MAX-ACCESS  read-only
        STATUS      current
        DESCRIPTION "The total number of members in the E1 raw count stats table."
        ::= { tnStatisticsRawCounts 43 }

--------------------------------------------------------------------------------
-- E1 Raw Count Statistics Table
--------------------------------------------------------------------------------
    tnE1RawCountStatsTable OBJECT-TYPE
        SYNTAX      SEQUENCE OF TnE1RawCountStatsEntry
        MAX-ACCESS  not-accessible
        STATUS      current
        DESCRIPTION "."
        ::= { tnStatisticsRawCounts 44 }

    tnE1RawCountStatsEntry OBJECT-TYPE
        SYNTAX      TnE1RawCountStatsEntry
        MAX-ACCESS  not-accessible
        STATUS      current
        DESCRIPTION "."
        INDEX   { ifIndex }
        ::= { tnE1RawCountStatsTable 1 }

    TnE1RawCountStatsEntry ::=
        SEQUENCE {
            tnE1RawCountStatsClear     TnCommand,
            tnE1RawCountStatRxBBEP     Counter32,
            tnE1RawCountStatRxESP      Counter32,
            tnE1RawCountStatRxSESP     Counter32,
            tnE1RawCountStatRxUASP     Counter32,
            tnE1RawCountStatRxESL      Counter32,
            tnE1RawCountStatRxSESL     Counter32,
            tnE1RawCountStatTxBBEP     Counter32,
            tnE1RawCountStatTxESP      Counter32,
            tnE1RawCountStatTxSESP     Counter32,
            tnE1RawCountStatTxUASP     Counter32,
            tnE1RawCountStatStartTime  DateAndTime
        }

    tnE1RawCountStatsClear OBJECT-TYPE
        SYNTAX      TnCommand
        MAX-ACCESS  read-create
        STATUS      current
        DESCRIPTION "This attribute is used to clear all the
                     raw counts on a particular interface
                     and group."
        ::= { tnE1RawCountStatsEntry 1 }

    tnE1RawCountStatRxBBEP OBJECT-TYPE
        SYNTAX      Counter32
        MAX-ACCESS  read-only
        STATUS      current
        DESCRIPTION "Background Block Errors - Path."
        ::= { tnE1RawCountStatsEntry 2 }

    tnE1RawCountStatRxESP OBJECT-TYPE
        SYNTAX      Counter32
        MAX-ACCESS  read-only
        STATUS      current
        DESCRIPTION "Errored second - Path."
        ::= { tnE1RawCountStatsEntry 3 }

    tnE1RawCountStatRxSESP OBJECT-TYPE
        SYNTAX      Counter32
        MAX-ACCESS  read-only
        STATUS      current
        DESCRIPTION "Severely errored second - Path."
        ::= { tnE1RawCountStatsEntry 4 }

    tnE1RawCountStatRxUASP OBJECT-TYPE
        SYNTAX      Counter32
        MAX-ACCESS  read-only
        STATUS      current
        DESCRIPTION "Unavailable Seconds - Path."
        ::= { tnE1RawCountStatsEntry 5 }

    tnE1RawCountStatRxESL OBJECT-TYPE
        SYNTAX      Counter32
        MAX-ACCESS  read-only
        STATUS      current
        DESCRIPTION "Errored second - line."
        ::= { tnE1RawCountStatsEntry 6 }

    tnE1RawCountStatRxSESL OBJECT-TYPE
        SYNTAX      Counter32
        MAX-ACCESS  read-only
        STATUS      current
        DESCRIPTION "Severely errored second - line."
        ::= { tnE1RawCountStatsEntry 7 }

    tnE1RawCountStatTxBBEP OBJECT-TYPE
        SYNTAX      Counter32
        MAX-ACCESS  read-only
        STATUS      current
        DESCRIPTION "Background Block Errors - Path."
        ::= { tnE1RawCountStatsEntry 8 }

    tnE1RawCountStatTxESP OBJECT-TYPE
        SYNTAX      Counter32
        MAX-ACCESS  read-only
        STATUS      current
        DESCRIPTION "Errored second."
        ::= { tnE1RawCountStatsEntry 9 }

    tnE1RawCountStatTxSESP OBJECT-TYPE
        SYNTAX      Counter32
        MAX-ACCESS  read-only
        STATUS      current
        DESCRIPTION "Severely errored second."
        ::= { tnE1RawCountStatsEntry 10 }

    tnE1RawCountStatTxUASP OBJECT-TYPE
        SYNTAX      Counter32
        MAX-ACCESS  read-only
        STATUS      current
        DESCRIPTION "Unavailable second."
        ::= { tnE1RawCountStatsEntry 11 }

    tnE1RawCountStatStartTime OBJECT-TYPE
        SYNTAX      DateAndTime
        MAX-ACCESS  read-only
        STATUS      current
        DESCRIPTION "This attribute is the bin collection start date
                     and time."
        ::= { tnE1RawCountStatsEntry 12 }

--------------------------------------------------------------------------------
-- PreFECBitsBER Raw Count Statistics Scalar
--------------------------------------------------------------------------------
    tnPreFECBitsRawCountStatsTotalMembers OBJECT-TYPE
        SYNTAX      Integer32
        MAX-ACCESS  read-only
        STATUS      current
        DESCRIPTION "The total number of members in the PreFECBits raw count
                     stats table."
        ::= { tnStatisticsRawCounts 45 }

--------------------------------------------------------------------------------
-- PreFECBitsBER Raw Count Statistics Table
--------------------------------------------------------------------------------
    tnPreFECBitsRawCountStatsTable OBJECT-TYPE
        SYNTAX      SEQUENCE OF TnPreFECBitsRawCountStatsEntry
        MAX-ACCESS  not-accessible
        STATUS      current
        DESCRIPTION "."
        ::= { tnStatisticsRawCounts 46 }

    tnPreFECBitsRawCountStatsEntry OBJECT-TYPE
        SYNTAX      TnPreFECBitsRawCountStatsEntry
        MAX-ACCESS  not-accessible
        STATUS      current
        DESCRIPTION "."
        INDEX   { ifIndex }
        ::= { tnPreFECBitsRawCountStatsTable 1 }

    TnPreFECBitsRawCountStatsEntry ::=
        SEQUENCE {
            tnPreFECBitsRawCountStatsClear        TnCommand,
            tnPreFECBitsRawCountStatMin           Counter64,
            tnPreFECBitsRawCountStatMax           Counter64,
            tnPreFECBitsRawCountStatAverage       Counter64,
            tnPreFECBitsRawCountStatStartTime     DateAndTime
        }

    tnPreFECBitsRawCountStatsClear OBJECT-TYPE
        SYNTAX      TnCommand
        MAX-ACCESS  read-create
        STATUS      current
        DESCRIPTION "This attribute is used to clear all the raw counts
                     on a particular interface and group."
        ::= { tnPreFECBitsRawCountStatsEntry 1 }

    tnPreFECBitsRawCountStatMin OBJECT-TYPE
        SYNTAX      Counter64
        UNITS       "Bits in 1-second"
        MAX-ACCESS  read-only
        STATUS      current
        DESCRIPTION "Bits in 1-second."
        ::= { tnPreFECBitsRawCountStatsEntry 2 }

    tnPreFECBitsRawCountStatMax OBJECT-TYPE
        SYNTAX      Counter64
        UNITS       "Bits in 1-second."
        MAX-ACCESS  read-only
        STATUS      current
        DESCRIPTION "Minimum PreFECBits bits received (Bits in 1-second)."
        ::= { tnPreFECBitsRawCountStatsEntry 3 }

    tnPreFECBitsRawCountStatAverage OBJECT-TYPE
        SYNTAX      Counter64
        UNITS       "Bits in 1-second"
        MAX-ACCESS  read-only
        STATUS      current
        DESCRIPTION "Minimum PreFECBits bits received (Bits in 1-second)."
        ::= { tnPreFECBitsRawCountStatsEntry 4 }

    tnPreFECBitsRawCountStatStartTime OBJECT-TYPE
        SYNTAX      DateAndTime
        MAX-ACCESS  read-only
        STATUS      current
        DESCRIPTION "This attribute is the bin collection start date
                     and time."
        ::= { tnPreFECBitsRawCountStatsEntry 5 }

--    obsolete
--    tnTcm64BitRawCountStatsTotalMembers OBJECT-TYPE ::= { tnStatisticsRawCounts 47 }
--    tnTcm64BitRawCountStatsTable        OBJECT-TYPE ::= { tnStatisticsRawCounts 48 }

--------------------------------------------------------------------------------
-- Encryption 64 Bit Raw Count Statistics Scalar
--------------------------------------------------------------------------------
    tnEncrypt64BitRawCountStatsTotalMembers OBJECT-TYPE
        SYNTAX      Integer32
        MAX-ACCESS  read-only
        STATUS      current
        DESCRIPTION "The total number of members in the encryption raw count
                     stats table."
        ::= { tnStatisticsRawCounts 49 }

--------------------------------------------------------------------------------
-- Encryption 64 Bit Raw Count Statistics Table
--------------------------------------------------------------------------------
    tnEncrypt64BitRawCountStatsTable OBJECT-TYPE
        SYNTAX      SEQUENCE OF TnEncrypt64BitRawCountStatsEntry
        MAX-ACCESS  not-accessible
        STATUS      current
        DESCRIPTION "."
        ::= { tnStatisticsRawCounts 50 }

    tnEncrypt64BitRawCountStatsEntry OBJECT-TYPE
        SYNTAX      TnEncrypt64BitRawCountStatsEntry
        MAX-ACCESS  not-accessible
        STATUS      current
        DESCRIPTION "."
        INDEX   { ifIndex }
        ::= { tnEncrypt64BitRawCountStatsTable 1 }

    TnEncrypt64BitRawCountStatsEntry ::=
        SEQUENCE {
            tnEncrypt64BitRawCountStatsClear              TnCommand,
            tnEncrypt64BitRawCountStatStartTime           DateAndTime,
            tnEncrypt64BitRawCountStatTx128BitBlkCnt      Counter64,
            tnEncrypt64BitRawCountStatRxFailToDecryptCnt  Counter64
        }

    tnEncrypt64BitRawCountStatsClear OBJECT-TYPE
        SYNTAX      TnCommand
        MAX-ACCESS  read-create
        STATUS      current
        DESCRIPTION "This attribute is used to clear all the raw counts
                     on a particular interface and group."
        ::= { tnEncrypt64BitRawCountStatsEntry 1 }

    tnEncrypt64BitRawCountStatStartTime OBJECT-TYPE
        SYNTAX      DateAndTime
        MAX-ACCESS  read-only
        STATUS      current
        DESCRIPTION "This attribute is the bin collection start date
                     and time."
        ::= { tnEncrypt64BitRawCountStatsEntry 2 }

    tnEncrypt64BitRawCountStatTx128BitBlkCnt OBJECT-TYPE
        SYNTAX      Counter64
        MAX-ACCESS  read-only
        STATUS      current
        DESCRIPTION "Provides a count of each 128 bit block of data
                     that is encrypted."
        ::= { tnEncrypt64BitRawCountStatsEntry 3 }

    tnEncrypt64BitRawCountStatRxFailToDecryptCnt OBJECT-TYPE
        SYNTAX      Counter64
        MAX-ACCESS  read-only
        STATUS      current
        DESCRIPTION "Provides a count of each 128 bit block of data
                     failure to decrypt."
        ::= { tnEncrypt64BitRawCountStatsEntry 4 }

--------------------------------------------------------------------------------
-- RX Statistics ODUk Raw Count Scalar
--------------------------------------------------------------------------------
    tnOthOdukRawCountStatsRxTotalMembers OBJECT-TYPE
        SYNTAX      Integer32
        MAX-ACCESS  read-only
        STATUS      current
        DESCRIPTION "."
        ::= { tnStatisticsRawCounts 51 }

--------------------------------------------------------------------------------
-- RX Statistics ODUk Raw Count Table
--------------------------------------------------------------------------------
    tnOthOdukRawCountStatsRxTable OBJECT-TYPE
        SYNTAX      SEQUENCE OF TnOthOdukRawCountStatsRxEntry
        MAX-ACCESS  not-accessible
        STATUS      current
        DESCRIPTION "."
        ::= { tnStatisticsRawCounts 52 }

    tnOthOdukRawCountStatsRxEntry OBJECT-TYPE
        SYNTAX      TnOthOdukRawCountStatsRxEntry
        MAX-ACCESS  not-accessible
        STATUS      current
        DESCRIPTION "."
        INDEX   { tnOthIfIndex,
                  tnOthIfIndexLo }
        ::= { tnOthOdukRawCountStatsRxTable 1 }

    TnOthOdukRawCountStatsRxEntry ::=
        SEQUENCE {
            tnOthOdukRawCountStatsRxClear           TnCommand,
            tnOthOdukRawCountStatsRxStartTime       DateAndTime,
            tnOthOdukRawCountStatRxNeBIP8ErrCnt     Counter64,
            tnOthOdukRawCountStatRxNeES             Counter64,
            tnOthOdukRawCountStatRxNeSES            Counter64,
            tnOthOdukRawCountStatRxNeUAS            Counter64,
            tnOthOdukRawCountStatRxFeBIP8ErrCnt     Counter64,
            tnOthOdukRawCountStatRxFeES             Counter64,
            tnOthOdukRawCountStatRxFeSES            Counter64,
            tnOthOdukRawCountStatRxFeUAS            Counter64
        }

    tnOthOdukRawCountStatsRxClear OBJECT-TYPE
        SYNTAX      TnCommand
        MAX-ACCESS  read-create
        STATUS      current
        DESCRIPTION "This attribute is used to clear all the raw counts
                     on a particular ODU entity."
        ::= { tnOthOdukRawCountStatsRxEntry 1 }

    tnOthOdukRawCountStatsRxStartTime OBJECT-TYPE
        SYNTAX      DateAndTime
        MAX-ACCESS  read-only
        STATUS      current
        DESCRIPTION "This attribute is the bin collection start date
                     and time."
        ::= { tnOthOdukRawCountStatsRxEntry 2 }

    tnOthOdukRawCountStatRxNeBIP8ErrCnt OBJECT-TYPE
        SYNTAX      Counter64
        MAX-ACCESS  read-only
        STATUS      current
        DESCRIPTION "Provides a count of near-end Receiving direction
                     ODU BIP8 error blocks."
        ::= { tnOthOdukRawCountStatsRxEntry 3 }

    tnOthOdukRawCountStatRxNeES OBJECT-TYPE
        SYNTAX      Counter64
        MAX-ACCESS  read-only
        STATUS      current
        DESCRIPTION "Provides a count of near-end Receiving direction
                     ODU errored seconds."
        ::= { tnOthOdukRawCountStatsRxEntry 4 }

    tnOthOdukRawCountStatRxNeSES OBJECT-TYPE
        SYNTAX      Counter64
        MAX-ACCESS  read-only
        STATUS      current
        DESCRIPTION "Provides a count of near-end Receiving direction
                     ODU severely errored seconds."
        ::= { tnOthOdukRawCountStatsRxEntry 5 }

    tnOthOdukRawCountStatRxNeUAS OBJECT-TYPE
        SYNTAX      Counter64
        MAX-ACCESS  read-only
        STATUS      current
        DESCRIPTION "Provides a count of near-end Receiving direction
                     ODU unavailable seconds."
        ::= { tnOthOdukRawCountStatsRxEntry 6 }

    tnOthOdukRawCountStatRxFeBIP8ErrCnt OBJECT-TYPE
        SYNTAX      Counter64
        MAX-ACCESS  read-only
        STATUS      current
        DESCRIPTION "Provides a count of receiving direction ODU BEI
                     counts, i.e., Far-End receiving direction error
                     blocks."
        ::= { tnOthOdukRawCountStatsRxEntry 7 }

    tnOthOdukRawCountStatRxFeES OBJECT-TYPE
        SYNTAX      Counter64
        MAX-ACCESS  read-only
        STATUS      current
        DESCRIPTION "Provides a count of far-End Receiving direction ODU
                     errored seconds."
        ::= { tnOthOdukRawCountStatsRxEntry 8 }

    tnOthOdukRawCountStatRxFeSES OBJECT-TYPE
        SYNTAX      Counter64
        MAX-ACCESS  read-only
        STATUS      current
        DESCRIPTION "Provides a count of far-End Receiving direction ODU
                     severely errored seconds."
        ::= { tnOthOdukRawCountStatsRxEntry 9 }

    tnOthOdukRawCountStatRxFeUAS OBJECT-TYPE
        SYNTAX      Counter64
        MAX-ACCESS  read-only
        STATUS      current
        DESCRIPTION "Provides a count of far-End Receiving direction ODU
                     unavailable seconds."
        ::= { tnOthOdukRawCountStatsRxEntry 10 }

--------------------------------------------------------------------------------
-- TX Statistics ODUk Raw Count Scalar
--------------------------------------------------------------------------------
    tnOthOdukRawCountStatsTxTotalMembers OBJECT-TYPE
        SYNTAX      Integer32
        MAX-ACCESS  read-only
        STATUS      current
        DESCRIPTION "."
        ::= { tnStatisticsRawCounts 53 }

--------------------------------------------------------------------------------
-- TX Statistics ODUk Raw Count Table
--------------------------------------------------------------------------------
    tnOthOdukRawCountStatsTxTable OBJECT-TYPE
        SYNTAX      SEQUENCE OF TnOthOdukRawCountStatsTxEntry
        MAX-ACCESS  not-accessible
        STATUS      current
        DESCRIPTION "."
        ::= { tnStatisticsRawCounts 54 }

    tnOthOdukRawCountStatsTxEntry OBJECT-TYPE
        SYNTAX      TnOthOdukRawCountStatsTxEntry
        MAX-ACCESS  not-accessible
        STATUS      current
        DESCRIPTION "."
        INDEX   { tnOthIfIndex,
                  tnOthIfIndexLo }
        ::= { tnOthOdukRawCountStatsTxTable 1 }

    TnOthOdukRawCountStatsTxEntry ::=
        SEQUENCE {
            tnOthOdukRawCountStatsTxClear           TnCommand,
            tnOthOdukRawCountStatsTxStartTime       DateAndTime,
            tnOthOdukRawCountStatTxNeBIP8ErrCnt     Counter64,
            tnOthOdukRawCountStatTxNeES             Counter64,
            tnOthOdukRawCountStatTxNeSES            Counter64,
            tnOthOdukRawCountStatTxNeUAS            Counter64,
            tnOthOdukRawCountStatTxFeBIP8ErrCnt     Counter64,
            tnOthOdukRawCountStatTxFeES             Counter64,
            tnOthOdukRawCountStatTxFeSES            Counter64,
            tnOthOdukRawCountStatTxFeUAS            Counter64
        }

    tnOthOdukRawCountStatsTxClear OBJECT-TYPE
        SYNTAX      TnCommand
        MAX-ACCESS  read-create
        STATUS      current
        DESCRIPTION "This attribute is used to clear all the raw counts
                     on a particular ODU entity."
        ::= { tnOthOdukRawCountStatsTxEntry 1 }

    tnOthOdukRawCountStatsTxStartTime OBJECT-TYPE
        SYNTAX      DateAndTime
        MAX-ACCESS  read-only
        STATUS      current
        DESCRIPTION "This attribute is the bin collection start date
                     and time."
        ::= { tnOthOdukRawCountStatsTxEntry 2 }

    tnOthOdukRawCountStatTxNeBIP8ErrCnt OBJECT-TYPE
        SYNTAX      Counter64
        MAX-ACCESS  read-only
        STATUS      current
        DESCRIPTION "Provides a count of near-end transmitting direction
                     ODU BIP8 error blocks."
        ::= { tnOthOdukRawCountStatsTxEntry 3 }

    tnOthOdukRawCountStatTxNeES OBJECT-TYPE
        SYNTAX      Counter64
        MAX-ACCESS  read-only
        STATUS      current
        DESCRIPTION "Provides a count of near-end transmitting direction
                     ODU errored seconds."
        ::= { tnOthOdukRawCountStatsTxEntry 4 }

    tnOthOdukRawCountStatTxNeSES OBJECT-TYPE
        SYNTAX      Counter64
        MAX-ACCESS  read-only
        STATUS      current
        DESCRIPTION "Provides a count of near-end transmitting direction
                     ODU severely errored seconds."
        ::= { tnOthOdukRawCountStatsTxEntry 5 }

    tnOthOdukRawCountStatTxNeUAS OBJECT-TYPE
        SYNTAX      Counter64
        MAX-ACCESS  read-only
        STATUS      current
        DESCRIPTION "Provides a count of near-end transmitting direction
                     ODU unavailable seconds."
        ::= { tnOthOdukRawCountStatsTxEntry 6 }

    tnOthOdukRawCountStatTxFeBIP8ErrCnt OBJECT-TYPE
        SYNTAX      Counter64
        MAX-ACCESS  read-only
        STATUS      current
        DESCRIPTION "Provides a count of transmitting direction ODU BEI
                     counts, i.e., Far-End transmitting direction error
                     blocks."
        ::= { tnOthOdukRawCountStatsTxEntry 7 }

    tnOthOdukRawCountStatTxFeES OBJECT-TYPE
        SYNTAX      Counter64
        MAX-ACCESS  read-only
        STATUS      current
        DESCRIPTION "Provides a count of Far-End transmitting direction
                     ODU errored seconds."
        ::= { tnOthOdukRawCountStatsTxEntry 8 }

    tnOthOdukRawCountStatTxFeSES OBJECT-TYPE
        SYNTAX      Counter64
        MAX-ACCESS  read-only
        STATUS      current
        DESCRIPTION "Provides a count of Far-End transmitting direction
                     ODU severely errored seconds."
        ::= { tnOthOdukRawCountStatsTxEntry 9 }

    tnOthOdukRawCountStatTxFeUAS OBJECT-TYPE
        SYNTAX      Counter64
        MAX-ACCESS  read-only
        STATUS      current
        DESCRIPTION "Provides a count of Far-End transmitting direction
                     ODU unavailable seconds."
        ::= { tnOthOdukRawCountStatsTxEntry 10 }

--------------------------------------------------------------------------------
-- Statistics OTUk Raw Count Scalar
--------------------------------------------------------------------------------
    tnOthOtukRawCountStatsTotalMembers OBJECT-TYPE
        SYNTAX      Integer32
        MAX-ACCESS  read-only
        STATUS      current
        DESCRIPTION "."
        ::= { tnStatisticsRawCounts 55 }

--------------------------------------------------------------------------------
-- Statistics OTUk Raw Count Table
--------------------------------------------------------------------------------
    tnOthOtukRawCountStatsTable OBJECT-TYPE
        SYNTAX      SEQUENCE OF TnOthOtukRawCountStatsEntry
        MAX-ACCESS  not-accessible
        STATUS      current
        DESCRIPTION "."
        ::= { tnStatisticsRawCounts 56 }

    tnOthOtukRawCountStatsEntry OBJECT-TYPE
        SYNTAX      TnOthOtukRawCountStatsEntry
        MAX-ACCESS  not-accessible
        STATUS      current
        DESCRIPTION "."
        INDEX   { ifIndex }
        ::= { tnOthOtukRawCountStatsTable 1 }

    TnOthOtukRawCountStatsEntry ::=
        SEQUENCE {
            tnOthOtukRawCountStatsClear               TnCommand,
            tnOthOtukRawCountStatsStartTime           DateAndTime,
            tnOthOtukRawCountStatRxRsCorrCnt          Counter64,
            tnOthOtukRawCountStatRxRsUncorrCnt        Counter64,
            tnOthOtukRawCountStatRxBERPreFEC          Counter64,
            tnOthOtukRawCountStatRxBERPostFEC         Counter64,
            tnOthOtukRawCountStatRxNeSMBIP8ErrCnt     Counter64,
            tnOthOtukRawCountStatRxNeSMES             Counter64,
            tnOthOtukRawCountStatRxNeSMSES            Counter64,
            tnOthOtukRawCountStatRxNeSMUAS            Counter64,
            tnOthOtukRawCountStatRxNeIAES             Counter64,
            tnOthOtukRawCountStatRxFeSMBIP8ErrCnt     Counter64,
            tnOthOtukRawCountStatRxFeSMES             Counter64,
            tnOthOtukRawCountStatRxFeSMSES            Counter64,
            tnOthOtukRawCountStatRxFeSMUAS            Counter64,
            tnOthOtukRawCountStatRxFeIAES             Counter64,
            tnOthOtukRawCountStatRxNeBIAES            Counter64
        }

    tnOthOtukRawCountStatsClear OBJECT-TYPE
        SYNTAX      TnCommand
        MAX-ACCESS  read-create
        STATUS      current
        DESCRIPTION "This attribute is used to clear all the raw OTU PM
                     counts on a particular OTU entity."
        ::= { tnOthOtukRawCountStatsEntry 1 }

    tnOthOtukRawCountStatsStartTime OBJECT-TYPE
        SYNTAX      DateAndTime
        MAX-ACCESS  read-only
        STATUS      current
        DESCRIPTION "This attribute is the raw bin collection start date
                     and time."
        ::= { tnOthOtukRawCountStatsEntry 2 }

    tnOthOtukRawCountStatRxRsCorrCnt OBJECT-TYPE
        SYNTAX      Counter64
        MAX-ACCESS  read-only
        STATUS      current
        DESCRIPTION "Provides the raw count of the number of FEC error
                     bits corrected at the receiver."
        ::= { tnOthOtukRawCountStatsEntry 3 }

    tnOthOtukRawCountStatRxRsUncorrCnt OBJECT-TYPE
        SYNTAX      Counter64
        MAX-ACCESS  read-only
        STATUS      current
        DESCRIPTION "Provides the raw count of the number of FEC blocks
                     detected at the receiver which have uncorrectable
                     errors."
        ::= { tnOthOtukRawCountStatsEntry 4 }

    tnOthOtukRawCountStatRxBERPreFEC OBJECT-TYPE
        SYNTAX      Counter64
        MAX-ACCESS  read-only
        STATUS      current
        DESCRIPTION "Provides the raw count of the error bit rate of pre-FEC."
        ::= { tnOthOtukRawCountStatsEntry 5 }

    tnOthOtukRawCountStatRxBERPostFEC OBJECT-TYPE
        SYNTAX      Counter64
        MAX-ACCESS  read-only
        STATUS      current
        DESCRIPTION "Provides the raw count of the error bit rate of post-FEC."
        ::= { tnOthOtukRawCountStatsEntry 6 }

    tnOthOtukRawCountStatRxNeSMBIP8ErrCnt OBJECT-TYPE
        SYNTAX      Counter64
        MAX-ACCESS  read-only
        STATUS      current
        DESCRIPTION "Provides the raw count of near-end section monitor
                     bit interleaved parity (BIP-8) errors detected at
                     the receiver."
        ::= { tnOthOtukRawCountStatsEntry 7 }

    tnOthOtukRawCountStatRxNeSMES OBJECT-TYPE
        SYNTAX      Counter64
        MAX-ACCESS  read-only
        STATUS      current
        DESCRIPTION "Provides the raw count of near-end section monitor
                     errored seconds detected at the receiver."
        ::= { tnOthOtukRawCountStatsEntry 8 }

    tnOthOtukRawCountStatRxNeSMSES OBJECT-TYPE
        SYNTAX      Counter64
        MAX-ACCESS  read-only
        STATUS      current
        DESCRIPTION "Provides the raw count of near-end section monitor
                     severely errored seconds detected at the receiver."
        ::= { tnOthOtukRawCountStatsEntry 9 }

    tnOthOtukRawCountStatRxNeSMUAS OBJECT-TYPE
        SYNTAX      Counter64
        MAX-ACCESS  read-only
        STATUS      current
        DESCRIPTION "Provides the raw count of near-end section monitor
                     severely errored seconds detected at the receiver."
        ::= { tnOthOtukRawCountStatsEntry 10 }

    tnOthOtukRawCountStatRxNeIAES OBJECT-TYPE
        SYNTAX      Counter64
        MAX-ACCESS  read-only
        STATUS      current
        DESCRIPTION "Provides the raw count of near-end IAE defect seconds
                     detected at the receiver."
        ::= { tnOthOtukRawCountStatsEntry 11 }

    tnOthOtukRawCountStatRxFeSMBIP8ErrCnt OBJECT-TYPE
        SYNTAX      Counter64
        MAX-ACCESS  read-only
        STATUS      current
        DESCRIPTION "Provides the raw count of the backward error
                     indication (BEI) errors, i.e., the far-end section
                     monitor bit."
        ::= { tnOthOtukRawCountStatsEntry 12 }

    tnOthOtukRawCountStatRxFeSMES OBJECT-TYPE
        SYNTAX      Counter64
        MAX-ACCESS  read-only
        STATUS      current
        DESCRIPTION "Provides the raw count of far-end  section monitor
                     errored seconds  detected at the receiver."
        ::= { tnOthOtukRawCountStatsEntry 13 }

    tnOthOtukRawCountStatRxFeSMSES OBJECT-TYPE
        SYNTAX      Counter64
        MAX-ACCESS  read-only
        STATUS      current
        DESCRIPTION "Provides the raw count of near-end  section monitor
                     severely errored seconds  detected at the receiver."
        ::= { tnOthOtukRawCountStatsEntry 14 }

    tnOthOtukRawCountStatRxFeSMUAS OBJECT-TYPE
        SYNTAX      Counter64
        MAX-ACCESS  read-only
        STATUS      current
        DESCRIPTION "Provides the raw count of near-end section monitor
                     unavailable seconds detected at the receiver."
        ::= { tnOthOtukRawCountStatsEntry 15 }

    tnOthOtukRawCountStatRxFeIAES OBJECT-TYPE
        SYNTAX      Counter64
        MAX-ACCESS  read-only
        STATUS      current
        DESCRIPTION "Provides the raw count of the backward IAE defect
                     seconds, i.e., the far-end IAE defect seconds at
                     the receiver."
        ::= { tnOthOtukRawCountStatsEntry 16 }

    tnOthOtukRawCountStatRxNeBIAES OBJECT-TYPE
        SYNTAX      Counter64
        MAX-ACCESS  read-only
        STATUS      current
        DESCRIPTION "Provides a count of the section monitor backward
                     error indication (BEI) errors."
        ::= { tnOthOtukRawCountStatsEntry 17 }

--------------------------------------------------------------------------------
 -- Statistics Baseline Table
--------------------------------------------------------------------------------
    tnStatsBaselineTable OBJECT-TYPE
        SYNTAX      SEQUENCE OF TnStatsBaselineEntry
        MAX-ACCESS  not-accessible
        STATUS      current
        DESCRIPTION "."
        ::= { tnStatisticsBaseline 1 }

    tnStatsBaselineEntry OBJECT-TYPE
        SYNTAX      TnStatsBaselineEntry
        MAX-ACCESS  not-accessible
        STATUS      current
        DESCRIPTION "."
        INDEX   { ifIndex,
                  tnStatsGroupId }
        ::= { tnStatsBaselineTable 1 }

    TnStatsBaselineEntry ::=
        SEQUENCE {
            tnStatsBaselineReason INTEGER,
            tnStatsBaselineValue  Integer32,
            tnStatsBaselineTime   DateAndTime
        }

    tnStatsBaselineReason OBJECT-TYPE
        SYNTAX      INTEGER {
                      zero(1),
                      one(2),
                      two(3),
                      three(4),
                      four(5),
                      five(6),
                      six(7),
                      seven(8),
                      eight(9),
                      nine(10),
                      losClrd(11),
                      laserOn(12),
                      newSystem(13),
                      otReplaced(14)
                    }
        MAX-ACCESS  read-create
        STATUS      current
        DESCRIPTION "Baseline reason."
        ::= { tnStatsBaselineEntry 1 }

    tnStatsBaselineValue OBJECT-TYPE
        SYNTAX      Integer32
        UNITS       "mBm"
        MAX-ACCESS  read-only
        STATUS      current
        DESCRIPTION "Baselined Value (an optical power value)."
        ::= { tnStatsBaselineEntry 2 }

    tnStatsBaselineTime OBJECT-TYPE
        SYNTAX      DateAndTime
        MAX-ACCESS  read-only
        STATUS      current
        DESCRIPTION "Time of baseline."
        ::= { tnStatsBaselineEntry 3 }

--------------------------------------------------------------------------------
-- Optical Signal Noise Ratio (OSNR) Statistics OTUk Raw Count Scalar
--------------------------------------------------------------------------------
    tnOsnrRawCountStatsTotalMembers OBJECT-TYPE
        SYNTAX      Integer32
        MAX-ACCESS  read-only
        STATUS      current
        DESCRIPTION "The total number of members in the OSNR raw count
                     stats table."
        ::= { tnStatisticsRawCounts 57 }

--------------------------------------------------------------------------------
-- Optical Signal Noise Ratio (OSNR) Statistics OTUk Raw Count Table
--------------------------------------------------------------------------------
    tnOsnrRawCountStatsTable OBJECT-TYPE
        SYNTAX      SEQUENCE OF TnOsnrRawCountStatsEntry
        MAX-ACCESS  not-accessible
        STATUS      current
        DESCRIPTION "."
        ::= { tnStatisticsRawCounts 58 }

    tnOsnrRawCountStatsEntry OBJECT-TYPE
        SYNTAX      TnOsnrRawCountStatsEntry
        MAX-ACCESS  not-accessible
        STATUS      current
        DESCRIPTION "."
        INDEX   { ifIndex,
                  tnOpticalStatsITUChannel }
        ::= { tnOsnrRawCountStatsTable 1 }

    TnOsnrRawCountStatsEntry ::=
        SEQUENCE {
            tnOsnrRawCountStatsClear          TnCommand,
            tnOsnrRawCountStatStartTime       DateAndTime,
            tnOsnrRawCountStatMinOSNR         Integer32,
            tnOsnrRawCountStatMaxOSNR         Integer32,
            tnOsnrRawCountStatAverageOSNR     Integer32
        }

    tnOsnrRawCountStatsClear OBJECT-TYPE
        SYNTAX      TnCommand
        MAX-ACCESS  read-create
        STATUS      current
        DESCRIPTION "This attribute is used to clear all the raw counts
                     for all frequencies on a particular interface and
                     group, regardless of the frequency index."
        ::= { tnOsnrRawCountStatsEntry 1 }

    tnOsnrRawCountStatStartTime OBJECT-TYPE
        SYNTAX      DateAndTime
        MAX-ACCESS  read-only
        STATUS      current
        DESCRIPTION "This attribute is the bin collection start date
                     and time."
        ::= { tnOsnrRawCountStatsEntry 2 }

    tnOsnrRawCountStatMinOSNR OBJECT-TYPE
        SYNTAX      Integer32
        UNITS       "mB"
        MAX-ACCESS  read-only
        STATUS      current
        DESCRIPTION "Minimum OSNR (mB)."
        ::= { tnOsnrRawCountStatsEntry 3 }

    tnOsnrRawCountStatMaxOSNR OBJECT-TYPE
        SYNTAX      Integer32
        UNITS       "mB"
        MAX-ACCESS  read-only
        STATUS      current
        DESCRIPTION "Maximum OSNR (mB)."
        ::= { tnOsnrRawCountStatsEntry 4 }

    tnOsnrRawCountStatAverageOSNR OBJECT-TYPE
        SYNTAX      Integer32
        UNITS       "mB"
        MAX-ACCESS  read-only
        STATUS      current
        DESCRIPTION "Average optical WT power in the In direction (mB)."
        ::= { tnOsnrRawCountStatsEntry 5 }

--------------------------------------------------------------------------------
-- Delay Measurement (DM) Statistics ODUk Raw Count Scalar
--------------------------------------------------------------------------------
    tnOthOdukRawCountStatsDMTotalMembers OBJECT-TYPE
        SYNTAX      Integer32
        MAX-ACCESS  read-only
        STATUS      current
        DESCRIPTION "."
        ::= { tnStatisticsRawCounts 59 }

--------------------------------------------------------------------------------
-- Delay Measurement (DM) Statistics ODUk Raw Count Table
--------------------------------------------------------------------------------
    tnOthOdukRawCountStatsDMTable OBJECT-TYPE
        SYNTAX      SEQUENCE OF TnOthOdukRawCountStatsDMEntry
        MAX-ACCESS  not-accessible
        STATUS      current
        DESCRIPTION "."
        ::= { tnStatisticsRawCounts 60 }

    tnOthOdukRawCountStatsDMEntry OBJECT-TYPE
        SYNTAX      TnOthOdukRawCountStatsDMEntry
        MAX-ACCESS  not-accessible
        STATUS      current
        DESCRIPTION "."
        INDEX   { tnOthIfIndex,
                  tnOthIfIndexLo }
        ::= { tnOthOdukRawCountStatsDMTable 1 }

    TnOthOdukRawCountStatsDMEntry ::=
        SEQUENCE {
            tnOthOdukRawCountStatsDMClear         TnCommand,
            tnOthOdukRawCountStatsDMStartTime     DateAndTime,
            tnOthOdukRawCountStatsDMMinDm         Integer32,
            tnOthOdukRawCountStatsDMMaxDm         Integer32,
            tnOthOdukRawCountStatsDMAverageDm     Integer32
        }

    tnOthOdukRawCountStatsDMClear OBJECT-TYPE
        SYNTAX      TnCommand
        MAX-ACCESS  read-create
        STATUS      current
        DESCRIPTION "This attribute is used to clear all the raw counts
                     for all frequencies on a particular interface and
                     group, regardless of the frequency index."
        ::= { tnOthOdukRawCountStatsDMEntry 1 }

    tnOthOdukRawCountStatsDMStartTime OBJECT-TYPE
        SYNTAX      DateAndTime
        MAX-ACCESS  read-only
        STATUS      current
        DESCRIPTION "This attribute is the bin collection start date
                     and time."
        ::= { tnOthOdukRawCountStatsDMEntry 2 }

    tnOthOdukRawCountStatsDMMinDm OBJECT-TYPE
        SYNTAX      Integer32
        UNITS       "us"
        MAX-ACCESS  read-only
        STATUS      current
        DESCRIPTION "Minimum Dm (micro-seconds)."
        ::= { tnOthOdukRawCountStatsDMEntry 3 }

    tnOthOdukRawCountStatsDMMaxDm OBJECT-TYPE
        SYNTAX      Integer32
        UNITS       "us"
        MAX-ACCESS  read-only
        STATUS      current
        DESCRIPTION "Maximum Dm (micro-seconds)."
        ::= { tnOthOdukRawCountStatsDMEntry 4 }

    tnOthOdukRawCountStatsDMAverageDm OBJECT-TYPE
        SYNTAX      Integer32
        UNITS       "us"
        MAX-ACCESS  read-only
        STATUS      current
        DESCRIPTION "Average optical WT power in the In direction
                     (micro-seconds)."
        ::= { tnOthOdukRawCountStatsDMEntry 5 }

--------------------------------------------------------------------------------
-- Statistics Tandem Connection Monitoring (TCM) Raw Count Scalar
--------------------------------------------------------------------------------
    tnOthOdukTcmRawCountStatsTotalMembers OBJECT-TYPE
        SYNTAX      Integer32
        MAX-ACCESS  read-only
        STATUS      current
        DESCRIPTION "."
        ::= { tnStatisticsRawCounts 61 }

--------------------------------------------------------------------------------
-- Statistics Tandem Connection Monitoring (TCM) Raw Count Table
--------------------------------------------------------------------------------
    tnOthOdukTcmRawCountStatsTable OBJECT-TYPE
        SYNTAX      SEQUENCE OF TnOthOdukTcmRawCountStatsEntry
        MAX-ACCESS  not-accessible
        STATUS      current
        DESCRIPTION "."
        ::= { tnStatisticsRawCounts 62 }

    tnOthOdukTcmRawCountStatsEntry OBJECT-TYPE
        SYNTAX      TnOthOdukTcmRawCountStatsEntry
        MAX-ACCESS  not-accessible
        STATUS      current
        DESCRIPTION "."
        INDEX   { tnOthOdukTcmIfIndex,
                  tnOthOdukTcmIfIndexLo }
        ::= { tnOthOdukTcmRawCountStatsTable 1 }

    TnOthOdukTcmRawCountStatsEntry ::=
        SEQUENCE {
            tnOthOdukTcmRawCountStatsClear            TnCommand,
            tnOthOdukTcmRawCountStatsNeRxBIP8ErrCnt   Counter64,
            tnOthOdukTcmRawCountStatsNeRxIAESErrCnt   Counter64,
            tnOthOdukTcmRawCountStatsNeRxES           Counter64,
            tnOthOdukTcmRawCountStatsNeRxSES          Counter64,
            tnOthOdukTcmRawCountStatsNeRxUAS          Counter64,
            tnOthOdukTcmRawCountStatsFeRxBIP8ErrCnt   Counter64,
            tnOthOdukTcmRawCountStatsFeRxBIAESErrCnt  Counter64,
            tnOthOdukTcmRawCountStatsFeRxES           Counter64,
            tnOthOdukTcmRawCountStatsFeRxSES          Counter64,
            tnOthOdukTcmRawCountStatsFeRxUAS          Counter64,
            tnOthOdukTcmRawCountStatsStartTime        DateAndTime
        }

    tnOthOdukTcmRawCountStatsClear OBJECT-TYPE
        SYNTAX      TnCommand
        MAX-ACCESS  read-create
        STATUS      current
        DESCRIPTION "This attribute is used to clear all the raw counts
                     on a particular TCM entity."
        ::= { tnOthOdukTcmRawCountStatsEntry 1 }

    tnOthOdukTcmRawCountStatsNeRxBIP8ErrCnt OBJECT-TYPE
        SYNTAX      Counter64
        MAX-ACCESS  read-only
        STATUS      current
        DESCRIPTION "Provides a count of near-end Receiving direction
                     TCM BIP8 error blocks."
        ::= { tnOthOdukTcmRawCountStatsEntry 2 }

    tnOthOdukTcmRawCountStatsNeRxIAESErrCnt OBJECT-TYPE
        SYNTAX      Counter64
        MAX-ACCESS  read-only
        STATUS      current
        DESCRIPTION "Provides a count of near-end IAE defect seconds
                     detected at the receiver."
        ::= { tnOthOdukTcmRawCountStatsEntry 3 }

    tnOthOdukTcmRawCountStatsNeRxES OBJECT-TYPE
        SYNTAX      Counter64
        MAX-ACCESS  read-only
        STATUS      current
        DESCRIPTION "Provides a count of near-end Receiving direction
                     TCM errored seconds."
        ::= { tnOthOdukTcmRawCountStatsEntry 4 }

    tnOthOdukTcmRawCountStatsNeRxSES OBJECT-TYPE
        SYNTAX      Counter64
        MAX-ACCESS  read-only
        STATUS      current
        DESCRIPTION "Provides a count of near-end Receiving direction
                     TCM severely errored seconds."
        ::= { tnOthOdukTcmRawCountStatsEntry 5 }

    tnOthOdukTcmRawCountStatsNeRxUAS OBJECT-TYPE
        SYNTAX      Counter64
        MAX-ACCESS  read-only
        STATUS      current
        DESCRIPTION "Provides a count of near-end Receiving direction
                     TCM unavailable seconds."
        ::= { tnOthOdukTcmRawCountStatsEntry 6 }

    tnOthOdukTcmRawCountStatsFeRxBIP8ErrCnt OBJECT-TYPE
        SYNTAX      Counter64
        MAX-ACCESS  read-only
        STATUS      current
        DESCRIPTION "Provides a count of receiving direction TCM BEI
                     counts; i.e., far-end receiving direction error
                     blocks "
        ::= { tnOthOdukTcmRawCountStatsEntry 7 }

    tnOthOdukTcmRawCountStatsFeRxBIAESErrCnt OBJECT-TYPE
        SYNTAX      Counter64
        MAX-ACCESS  read-only
        STATUS      current
        DESCRIPTION "Provides a count of the backward IAE defect seconds,
                     i.e., the far-end IAE defect seconds at the receiver."
        ::= { tnOthOdukTcmRawCountStatsEntry 8 }

    tnOthOdukTcmRawCountStatsFeRxES OBJECT-TYPE
        SYNTAX      Counter64
        MAX-ACCESS  read-only
        STATUS      current
        DESCRIPTION "Provides a count of far-end Receiving direction
                     TCM errored seconds."
        ::= { tnOthOdukTcmRawCountStatsEntry 9 }

    tnOthOdukTcmRawCountStatsFeRxSES OBJECT-TYPE
        SYNTAX      Counter64
        MAX-ACCESS  read-only
        STATUS      current
        DESCRIPTION "Provides a count of far-end Receiving direction
                     TCM severely errored seconds."
        ::= { tnOthOdukTcmRawCountStatsEntry 10 }

    tnOthOdukTcmRawCountStatsFeRxUAS OBJECT-TYPE
        SYNTAX      Counter64
        MAX-ACCESS  read-only
        STATUS      current
        DESCRIPTION "Provides a count of far-end Receiving direction TCM
                     unavailable seconds."
        ::= { tnOthOdukTcmRawCountStatsEntry 11 }

    tnOthOdukTcmRawCountStatsStartTime OBJECT-TYPE
        SYNTAX      DateAndTime
        MAX-ACCESS  read-only
        STATUS      current
        DESCRIPTION "This attribute is the bin collection start date
                     and time."
        ::= { tnOthOdukTcmRawCountStatsEntry 12 }

--------------------------------------------------------------------------------
-- Statistics FECPM Raw Count Scalar
--------------------------------------------------------------------------------
    tnFECPMRawCountStatsTotalMembers OBJECT-TYPE
        SYNTAX      Integer32
        MAX-ACCESS  read-only
        STATUS      current
        DESCRIPTION "."
        ::= { tnStatisticsRawCounts 63 }

--------------------------------------------------------------------------------
-- Statistics FECPM Raw Count Table
--------------------------------------------------------------------------------
    tnFECPMRawCountStatsTable OBJECT-TYPE
        SYNTAX      SEQUENCE OF TnFECPMRawCountStatsEntry
        MAX-ACCESS  not-accessible
        STATUS      current
        DESCRIPTION "."
        ::= { tnStatisticsRawCounts 64 }

    tnFECPMRawCountStatsEntry OBJECT-TYPE
        SYNTAX      TnFECPMRawCountStatsEntry
        MAX-ACCESS  not-accessible
        STATUS      current
        DESCRIPTION "."
        INDEX   { ifIndex }
        ::= { tnFECPMRawCountStatsTable 1 }

    TnFECPMRawCountStatsEntry ::=
        SEQUENCE {
            tnFECPMRawCountStatsClear               TnCommand,
            tnFECPMRawCountStatsStartTime           DateAndTime,
            tnFECPMRawCountStatRxRsCorrCnt          Counter64,
            tnFECPMRawCountStatRxRsUncorrCnt        Counter64,
            tnFECPMRawCountStatRxBERPreFEC          Counter64,
            tnFECPMRawCountStatRxBERPostFEC         Counter64
        }

    tnFECPMRawCountStatsClear OBJECT-TYPE
        SYNTAX      TnCommand
        MAX-ACCESS  read-create
        STATUS      current
        DESCRIPTION "This attribute is used to clear all the raw OTU PM
                     counts on a particular OTU entity."
        ::= { tnFECPMRawCountStatsEntry 1 }

    tnFECPMRawCountStatsStartTime OBJECT-TYPE
        SYNTAX      DateAndTime
        MAX-ACCESS  read-only
        STATUS      current
        DESCRIPTION "This attribute is the raw bin collection start date
                     and time."
        ::= { tnFECPMRawCountStatsEntry 2 }

    tnFECPMRawCountStatRxRsCorrCnt OBJECT-TYPE
        SYNTAX      Counter64
        MAX-ACCESS  read-only
        STATUS      current
        DESCRIPTION "Provides the raw count of the number of FEC error
                     bits corrected at the receiver."
        ::= { tnFECPMRawCountStatsEntry 3 }

    tnFECPMRawCountStatRxRsUncorrCnt OBJECT-TYPE
        SYNTAX      Counter64
        MAX-ACCESS  read-only
        STATUS      current
        DESCRIPTION "Provides the raw count of the number of FEC blocks
                     detected at the receiver which have uncorrectable
                     errors."
        ::= { tnFECPMRawCountStatsEntry 4 }

    tnFECPMRawCountStatRxBERPreFEC OBJECT-TYPE
        SYNTAX      Counter64
        MAX-ACCESS  read-only
        STATUS      current
        DESCRIPTION "Provides the raw count of the error bit rate of pre-FEC."
        ::= { tnFECPMRawCountStatsEntry 5 }

    tnFECPMRawCountStatRxBERPostFEC OBJECT-TYPE
        SYNTAX      Counter64
        MAX-ACCESS  read-only
        STATUS      current
        DESCRIPTION "Provides the raw count of the error bit rate of post-FEC."
        ::= { tnFECPMRawCountStatsEntry 6 }

--------------------------------------------------------------------------------
-- Statistics preFECBER Raw Count Scalar
--------------------------------------------------------------------------------
    tnpreFECBERRawCountStatsTotalMembers OBJECT-TYPE
        SYNTAX      Integer32
        MAX-ACCESS  read-only
        STATUS      current
        DESCRIPTION "."
        ::= { tnStatisticsRawCounts 65 }

--------------------------------------------------------------------------------
-- Statistics preFECBER Raw Count Table
--------------------------------------------------------------------------------
    tnpreFECBERRawCountStatsTable OBJECT-TYPE
        SYNTAX      SEQUENCE OF TnpreFECBERRawCountStatsEntry
        MAX-ACCESS  not-accessible
        STATUS      current
        DESCRIPTION "."
        ::= { tnStatisticsRawCounts 66 }

    tnpreFECBERRawCountStatsEntry OBJECT-TYPE
        SYNTAX      TnpreFECBERRawCountStatsEntry
        MAX-ACCESS  not-accessible
        STATUS      current
        DESCRIPTION "."
        INDEX   { ifIndex }
        ::= { tnpreFECBERRawCountStatsTable 1 }

    TnpreFECBERRawCountStatsEntry ::=
        SEQUENCE {
            tnpreFECBERRawCountStatsClear               TnCommand,
            tnpreFECBERRawCountStatsStartTime           DateAndTime,
            tnpreFECBERRawCountStatRxBERPreFEC          Counter64
        }

    tnpreFECBERRawCountStatsClear OBJECT-TYPE
        SYNTAX      TnCommand
        MAX-ACCESS  read-create
        STATUS      current
        DESCRIPTION "This attribute is used to clear all the raw OTU PM
                     counts on a particular OTU entity."
        ::= { tnpreFECBERRawCountStatsEntry 1 }

    tnpreFECBERRawCountStatsStartTime OBJECT-TYPE
        SYNTAX      DateAndTime
        MAX-ACCESS  read-only
        STATUS      current
        DESCRIPTION "This attribute is the raw bin collection start date
                     and time."
        ::= { tnpreFECBERRawCountStatsEntry 2 }

    tnpreFECBERRawCountStatRxBERPreFEC OBJECT-TYPE
        SYNTAX      Counter64
        MAX-ACCESS  read-only
        STATUS      current
        DESCRIPTION "Provides the raw count of the error bit rate of pre-FECBER."
        ::= { tnpreFECBERRawCountStatsEntry 3 }

--------------------------------------------------------------------------------
-- Optical Input C Band (OPINC) Statistics Scalar
--------------------------------------------------------------------------------
    tnOpInCRawCountStatsTotalMembers OBJECT-TYPE
        SYNTAX      Integer32
        MAX-ACCESS  read-only
        STATUS      current
        DESCRIPTION "The total number of members in the OPINC raw count stats
                     table."
        ::= { tnStatisticsRawCounts 67 }

--------------------------------------------------------------------------------
-- Optical Input C (OPINC) Statistics Table
--------------------------------------------------------------------------------
    tnOpInCRawCountStatsTable OBJECT-TYPE
        SYNTAX      SEQUENCE OF TnOpincRawCountStatsEntry
        MAX-ACCESS  not-accessible
        STATUS      current
        DESCRIPTION "."
        ::= { tnStatisticsRawCounts 68 }

    tnOpInCRawCountStatsEntry OBJECT-TYPE
        SYNTAX      TnOpincRawCountStatsEntry
        MAX-ACCESS  not-accessible
        STATUS      current
        DESCRIPTION "."
        INDEX   { ifIndex }
        ::= { tnOpInCRawCountStatsTable 1 }

    TnOpincRawCountStatsEntry ::=
        SEQUENCE {
            tnOpInCRawCountStatsClear       TnCommand,
            tnOpInCRawCountStatMinPower     Integer32,
            tnOpInCRawCountStatMaxPower     Integer32,
            tnOpInCRawCountStatAveragePower Integer32,
            tnOpInCRawCountStatStartTime    DateAndTime
        }

    tnOpInCRawCountStatsClear OBJECT-TYPE
        SYNTAX      TnCommand
        MAX-ACCESS  read-create
        STATUS      current
        DESCRIPTION "This attribute is used to clear all the
                     raw counts on a particular interface
                     and group."
        ::= { tnOpInCRawCountStatsEntry 1 }

    tnOpInCRawCountStatMinPower OBJECT-TYPE
        SYNTAX      Integer32
        UNITS       "mBm"
        MAX-ACCESS  read-only
        STATUS      current
        DESCRIPTION "Minimum optical Input power in the
                     C Band (mBm)."
        ::= { tnOpInCRawCountStatsEntry 2 }

    tnOpInCRawCountStatMaxPower OBJECT-TYPE
        SYNTAX      Integer32
        UNITS       "mBm"
        MAX-ACCESS  read-only
        STATUS      current
        DESCRIPTION "Maximum optical Input power in the
                     C Band (mBm)."
        ::= { tnOpInCRawCountStatsEntry 3 }

    tnOpInCRawCountStatAveragePower OBJECT-TYPE
        SYNTAX      Integer32
        UNITS       "mBm"
        MAX-ACCESS  read-only
        STATUS      current
        DESCRIPTION "Average optical Input power in the
                     C Band (mBm)."
        ::= { tnOpInCRawCountStatsEntry 4 }

    tnOpInCRawCountStatStartTime OBJECT-TYPE
        SYNTAX      DateAndTime
        MAX-ACCESS  read-only
        STATUS      current
        DESCRIPTION "This attribute is the bin collection start date
                     and time."
        ::= { tnOpInCRawCountStatsEntry 5 }

--------------------------------------------------------------------------------
-- Optical Output C Band (OPOUTC) Statistics Scalar
--------------------------------------------------------------------------------
    tnOpOutCRawCountStatsTotalMembers OBJECT-TYPE
        SYNTAX      Integer32
        MAX-ACCESS  read-only
        STATUS      current
        DESCRIPTION "The total number of members in the OPOUTC raw count stats
                     table."
        ::= { tnStatisticsRawCounts 69 }

--------------------------------------------------------------------------------
-- Optical Input C (OPOUTC) Statistics Table
--------------------------------------------------------------------------------
    tnOpOutCRawCountStatsTable OBJECT-TYPE
        SYNTAX      SEQUENCE OF TnOpoutcRawCountStatsEntry
        MAX-ACCESS  not-accessible
        STATUS      current
        DESCRIPTION "."
        ::= { tnStatisticsRawCounts 70 }

    tnOpOutCRawCountStatsEntry OBJECT-TYPE
        SYNTAX      TnOpoutcRawCountStatsEntry
        MAX-ACCESS  not-accessible
        STATUS      current
        DESCRIPTION "."
        INDEX   { ifIndex }
        ::= { tnOpOutCRawCountStatsTable 1 }

    TnOpoutcRawCountStatsEntry ::=
        SEQUENCE {
            tnOpOutCRawCountStatsClear       TnCommand,
            tnOpOutCRawCountStatMinPower     Integer32,
            tnOpOutCRawCountStatMaxPower     Integer32,
            tnOpOutCRawCountStatAveragePower Integer32,
            tnOpOutCRawCountStatStartTime    DateAndTime
        }

    tnOpOutCRawCountStatsClear OBJECT-TYPE
        SYNTAX      TnCommand
        MAX-ACCESS  read-create
        STATUS      current
        DESCRIPTION "This attribute is used to clear all the
                     raw counts on a particular interface
                     and group."
        ::= { tnOpOutCRawCountStatsEntry 1 }

    tnOpOutCRawCountStatMinPower OBJECT-TYPE
        SYNTAX      Integer32
        UNITS       "mBm"
        MAX-ACCESS  read-only
        STATUS      current
        DESCRIPTION "Minimum optical Output power in the
                     C Band (mBm)."
        ::= { tnOpOutCRawCountStatsEntry 2 }

    tnOpOutCRawCountStatMaxPower OBJECT-TYPE
        SYNTAX      Integer32
        UNITS       "mBm"
        MAX-ACCESS  read-only
        STATUS      current
        DESCRIPTION "Maximum optical Output power in the
                     C Band (mBm)."
        ::= { tnOpOutCRawCountStatsEntry 3 }

    tnOpOutCRawCountStatAveragePower OBJECT-TYPE
        SYNTAX      Integer32
        UNITS       "mBm"
        MAX-ACCESS  read-only
        STATUS      current
        DESCRIPTION "Average optical Output power in the
                     C Band (mBm)."
        ::= { tnOpOutCRawCountStatsEntry 4 }

    tnOpOutCRawCountStatStartTime OBJECT-TYPE
        SYNTAX      DateAndTime
        MAX-ACCESS  read-only
        STATUS      current
        DESCRIPTION "This attribute is the bin collection start date
                     and time."
        ::= { tnOpOutCRawCountStatsEntry 5 }

--------------------------------------------------------------------------------
-- Optical Input L Band (OPINL) Statistics Scalar
--------------------------------------------------------------------------------
    tnOpInLRawCountStatsTotalMembers OBJECT-TYPE
        SYNTAX      Integer32
        MAX-ACCESS  read-only
        STATUS      current
        DESCRIPTION "The total number of members in the OPINL raw count stats
                     table."
        ::= { tnStatisticsRawCounts 71 }

--------------------------------------------------------------------------------
-- Optical DC Power In (OPINL) Statistics Table
--------------------------------------------------------------------------------
    tnOpInLRawCountStatsTable OBJECT-TYPE
        SYNTAX      SEQUENCE OF TnOpInLRawCountStatsEntry
        MAX-ACCESS  not-accessible
        STATUS      current
        DESCRIPTION "."
        ::= { tnStatisticsRawCounts 72 }

    tnOpInLRawCountStatsEntry OBJECT-TYPE
        SYNTAX      TnOpInLRawCountStatsEntry
        MAX-ACCESS  not-accessible
        STATUS      current
        DESCRIPTION "."
        INDEX   { ifIndex }
        ::= { tnOpInLRawCountStatsTable 1 }

    TnOpInLRawCountStatsEntry ::=
        SEQUENCE {
            tnOpInLRawCountStatsClear       TnCommand,
            tnOpInLRawCountStatMinPower     Integer32,
            tnOpInLRawCountStatMaxPower     Integer32,
            tnOpInLRawCountStatAveragePower Integer32,
            tnOpInLRawCountStatStartTime    DateAndTime
        }

    tnOpInLRawCountStatsClear OBJECT-TYPE
        SYNTAX      TnCommand
        MAX-ACCESS  read-create
        STATUS      current
        DESCRIPTION "This attribute is used to clear all the
                     raw counts on a particular interface
                     and group."
        ::= { tnOpInLRawCountStatsEntry 1 }

    tnOpInLRawCountStatMinPower OBJECT-TYPE
        SYNTAX      Integer32
        UNITS       "mBm"
        MAX-ACCESS  read-only
        STATUS      current
        DESCRIPTION "Minimum optical DC power in the
                     In direction (mBm)."
        ::= { tnOpInLRawCountStatsEntry 2 }

    tnOpInLRawCountStatMaxPower OBJECT-TYPE
        SYNTAX      Integer32
        UNITS       "mBm"
        MAX-ACCESS  read-only
        STATUS      current
        DESCRIPTION "Maximum optical DC power in the
                     In direction (mBm)."
        ::= { tnOpInLRawCountStatsEntry 3 }

    tnOpInLRawCountStatAveragePower OBJECT-TYPE
        SYNTAX      Integer32
        UNITS       "mBm"
        MAX-ACCESS  read-only
        STATUS      current
        DESCRIPTION "Average optical DC power in the
                     In direction (mBm)."
        ::= { tnOpInLRawCountStatsEntry 4 }

    tnOpInLRawCountStatStartTime OBJECT-TYPE
        SYNTAX      DateAndTime
        MAX-ACCESS  read-only
        STATUS      current
        DESCRIPTION "This attribute is the bin collection start date
                     and time."
        ::= { tnOpInLRawCountStatsEntry 5 }

--------------------------------------------------------------------------------
-- Optical Output L Band (OPOUTL) Statistics Scalar
--------------------------------------------------------------------------------
    tnOpOutLRawCountStatsTotalMembers OBJECT-TYPE
        SYNTAX      Integer32
        MAX-ACCESS  read-only
        STATUS      current
        DESCRIPTION "The total number of members in the OPOUTL raw count stats
                     table."
        ::= { tnStatisticsRawCounts 73 }

--------------------------------------------------------------------------------
-- Optical DC Power Out (OPOUTL) Statistics Table
--------------------------------------------------------------------------------
    tnOpOutLRawCountStatsTable OBJECT-TYPE
        SYNTAX      SEQUENCE OF TnOpOutLRawCountStatsEntry
        MAX-ACCESS  not-accessible
        STATUS      current
        DESCRIPTION "."
        ::= { tnStatisticsRawCounts 74 }

    tnOpOutLRawCountStatsEntry OBJECT-TYPE
        SYNTAX      TnOpOutLRawCountStatsEntry
        MAX-ACCESS  not-accessible
        STATUS      current
        DESCRIPTION "."
        INDEX   { ifIndex }
        ::= { tnOpOutLRawCountStatsTable 1 }

    TnOpOutLRawCountStatsEntry ::=
        SEQUENCE {
            tnOpOutLRawCountStatsClear       TnCommand,
            tnOpOutLRawCountStatMinPower     Integer32,
            tnOpOutLRawCountStatMaxPower     Integer32,
            tnOpOutLRawCountStatAveragePower Integer32,
            tnOpOutLRawCountStatStartTime    DateAndTime
        }

    tnOpOutLRawCountStatsClear OBJECT-TYPE
        SYNTAX      TnCommand
        MAX-ACCESS  read-create
        STATUS      current
        DESCRIPTION "This attribute is used to clear all the
                     raw counts on a particular interface
                     and group."
        ::= { tnOpOutLRawCountStatsEntry 1 }

    tnOpOutLRawCountStatMinPower OBJECT-TYPE
        SYNTAX      Integer32
        UNITS       "mBm"
        MAX-ACCESS  read-only
        STATUS      current
        DESCRIPTION "Minimum optical DC power in the
                     Out direction (mBm)."
        ::= { tnOpOutLRawCountStatsEntry 2 }

    tnOpOutLRawCountStatMaxPower OBJECT-TYPE
        SYNTAX      Integer32
        UNITS       "mBm"
        MAX-ACCESS  read-only
        STATUS      current
        DESCRIPTION "Maximum optical DC power in the
                     Out direction (mBm)."
        ::= { tnOpOutLRawCountStatsEntry 3 }

    tnOpOutLRawCountStatAveragePower OBJECT-TYPE
        SYNTAX      Integer32
        UNITS       "mBm"
        MAX-ACCESS  read-only
        STATUS      current
        DESCRIPTION "Average optical DC power in the
                     Out direction (mBm)."
        ::= { tnOpOutLRawCountStatsEntry 4 }

    tnOpOutLRawCountStatStartTime OBJECT-TYPE
        SYNTAX      DateAndTime
        MAX-ACCESS  read-only
        STATUS      current
        DESCRIPTION "This attribute is the bin collection start date
                     and time."
        ::= { tnOpOutLRawCountStatsEntry 5 }

--------------------------------------------------------------------------------
-- Statistics ETHFECPM Raw Count Scalar
--------------------------------------------------------------------------------
    tnETHFECPMRawCountStatsTotalMembers OBJECT-TYPE
        SYNTAX      Integer32
        MAX-ACCESS  read-only
        STATUS      current
        DESCRIPTION "."
        ::= { tnStatisticsRawCounts 75 }

--------------------------------------------------------------------------------
-- Statistics ETHFECPM Raw Count Table
--------------------------------------------------------------------------------
    tnETHFECPMRawCountStatsTable OBJECT-TYPE
        SYNTAX      SEQUENCE OF TnETHFECPMRawCountStatsEntry
        MAX-ACCESS  not-accessible
        STATUS      current
        DESCRIPTION "."
        ::= { tnStatisticsRawCounts 76 }

    tnETHFECPMRawCountStatsEntry OBJECT-TYPE
        SYNTAX      TnETHFECPMRawCountStatsEntry
        MAX-ACCESS  not-accessible
        STATUS      current
        DESCRIPTION "."
        INDEX   { ifIndex }
        ::= { tnETHFECPMRawCountStatsTable 1 }

    TnETHFECPMRawCountStatsEntry ::=
        SEQUENCE {
            tnETHFECPMRawCountStatsClear               TnCommand,
            tnETHFECPMRawCountStatsStartTime           DateAndTime,
            tnETHFECPMRawCountStatRxRsCorrCnt          Counter64,
            tnETHFECPMRawCountStatRxRsUncorrCnt        Counter64,
            tnETHFECPMRawCountStatRxBERpreFEC          Counter64,
            tnETHFECPMRawCountStatRxBERPostFEC         Counter64
        }

    tnETHFECPMRawCountStatsClear OBJECT-TYPE
        SYNTAX      TnCommand
        MAX-ACCESS  read-create
        STATUS      current
        DESCRIPTION "This attribute is used to clear all the raw OTU PM
                     counts on a particular OTU entity."
        ::= { tnETHFECPMRawCountStatsEntry 1 }

    tnETHFECPMRawCountStatsStartTime OBJECT-TYPE
        SYNTAX      DateAndTime
        MAX-ACCESS  read-only
        STATUS      current
        DESCRIPTION "This attribute is the raw bin collection start date
                     and time."
        ::= { tnETHFECPMRawCountStatsEntry 2 }

    tnETHFECPMRawCountStatRxRsCorrCnt OBJECT-TYPE
        SYNTAX      Counter64
        MAX-ACCESS  read-only
        STATUS      current
        DESCRIPTION "Provides the raw count of the number of FEC error
                     bits corrected at the receiver."
        ::= { tnETHFECPMRawCountStatsEntry 3 }

    tnETHFECPMRawCountStatRxRsUncorrCnt OBJECT-TYPE
        SYNTAX      Counter64
        MAX-ACCESS  read-only
        STATUS      current
        DESCRIPTION "Provides the raw count of the number of FEC blocks
                     detected at the receiver which have uncorrectable
                     errors."
        ::= { tnETHFECPMRawCountStatsEntry 4 }

    tnETHFECPMRawCountStatRxBERpreFEC OBJECT-TYPE
        SYNTAX      Counter64
        MAX-ACCESS  read-only
        STATUS      current
        DESCRIPTION "Provides the raw count of the error bit rate of pre-FEC."
        ::= { tnETHFECPMRawCountStatsEntry 5 }

    tnETHFECPMRawCountStatRxBERPostFEC OBJECT-TYPE
        SYNTAX      Counter64
        MAX-ACCESS  read-only
        STATUS      current
        DESCRIPTION "Provides the raw count of the error bit rate of post-FEC."
        ::= { tnETHFECPMRawCountStatsEntry 6 }

--------------------------------------------------------------------------------
-- Statistics SyncE Raw Count Scalar
--------------------------------------------------------------------------------
    tnSyncERawCountStatsTotalMembers OBJECT-TYPE
        SYNTAX      Integer32
        MAX-ACCESS  read-only
        STATUS      current
        DESCRIPTION "."
        ::= { tnStatisticsRawCounts 77 }

--------------------------------------------------------------------------------
-- Statistics SyncE Raw Count Table
--------------------------------------------------------------------------------
    tnSyncERawCountStatsTable OBJECT-TYPE
        SYNTAX      SEQUENCE OF TnSyncERawCountStatsEntry
        MAX-ACCESS  not-accessible
        STATUS      current
        DESCRIPTION "."
        ::= { tnStatisticsRawCounts 78 }

    tnSyncERawCountStatsEntry OBJECT-TYPE
        SYNTAX      TnSyncERawCountStatsEntry
        MAX-ACCESS  not-accessible
        STATUS      current
        DESCRIPTION "."
        INDEX   { tnShelfIndex,
                  tnSlotIndex,
                  tnSyncELineRefIndex}
        ::= { tnSyncERawCountStatsTable 1 }

    TnSyncERawCountStatsEntry ::=
        SEQUENCE {
            tnSyncERawCountStatsClear               TnCommand,
            tnSyncERawCountStatsStartTime           DateAndTime,
            tnSyncERawCountStatsOffsetMin           Integer32,
            tnSyncERawCountStatsOffsetMax           Integer32,
            tnSyncERawCountStatsOffsetAverage       Integer32
        }

    tnSyncERawCountStatsClear OBJECT-TYPE
        SYNTAX      TnCommand
        MAX-ACCESS  read-create
        STATUS      current
        DESCRIPTION "This attribute is used to clear all the raw SyncE PM counts."
        ::= { tnSyncERawCountStatsEntry 1 }

    tnSyncERawCountStatsStartTime OBJECT-TYPE
        SYNTAX      DateAndTime
        MAX-ACCESS  read-only
        STATUS      current
        DESCRIPTION "This attribute is the raw bin collection start date and time."
        ::= { tnSyncERawCountStatsEntry 2 }

    tnSyncERawCountStatsOffsetMin OBJECT-TYPE
        SYNTAX      Integer32
        UNITS       "ppb"
        MAX-ACCESS  read-only
        STATUS      current
        DESCRIPTION "Provides the raw count of the number of SyncE Line Refference
                     offset Min value.
                     When the value equal -106000, it should be shown as 'N/A'
                     (i.e. Not Available)."
        ::= { tnSyncERawCountStatsEntry 3 }

    tnSyncERawCountStatsOffsetMax OBJECT-TYPE
        SYNTAX      Integer32
        UNITS       "ppb"
        MAX-ACCESS  read-only
        STATUS      current
        DESCRIPTION "Provides the raw count of the number of SyncE Line Refference
                     offset Max value.
                     When the value equal -106000, it should be shown as 'N/A'
                     (i.e. Not Available)."
        ::= { tnSyncERawCountStatsEntry 4 }

    tnSyncERawCountStatsOffsetAverage OBJECT-TYPE
        SYNTAX      Integer32
        UNITS       "ppb"
        MAX-ACCESS  read-only
        STATUS      current
        DESCRIPTION "Provides the raw count of the number of SyncE Line Refference
                     offset Average value.
                     When the value equal -106000, it should be shown as 'N/A'
                     (i.e. Not Available)."
        ::= { tnSyncERawCountStatsEntry 5 }

--------------------------------------------------------------------------------
-- Statistics Sync Raw Count Scalar
--------------------------------------------------------------------------------
    tnSyncRawCountStatsTotalMembers OBJECT-TYPE
        SYNTAX      Integer32
        MAX-ACCESS  read-only
        STATUS      current
        DESCRIPTION "."
        ::= { tnStatisticsRawCounts 79 }

--------------------------------------------------------------------------------
-- Statistics Sync Raw Count Table
--------------------------------------------------------------------------------
    tnSyncRawCountStatsTable OBJECT-TYPE
        SYNTAX      SEQUENCE OF TnSyncRawCountStatsEntry
        MAX-ACCESS  not-accessible
        STATUS      current
        DESCRIPTION "."
        ::= { tnStatisticsRawCounts 80 }

    tnSyncRawCountStatsEntry OBJECT-TYPE
        SYNTAX      TnSyncRawCountStatsEntry
        MAX-ACCESS  not-accessible
        STATUS      current
        DESCRIPTION "."
        INDEX   { tnShelfIndex,
                  tnSlotIndex}
        ::= { tnSyncRawCountStatsTable 1 }

    TnSyncRawCountStatsEntry ::=
        SEQUENCE {
            tnSyncRawCountStatsClear               TnCommand,
            tnSyncRawCountStatsStartTime           DateAndTime,
            tnSyncRawCountStatsOffsetMin           Integer32,
            tnSyncRawCountStatsOffsetMax           Integer32,
            tnSyncRawCountStatsOffsetAverage       Integer32
        }

    tnSyncRawCountStatsClear OBJECT-TYPE
        SYNTAX      TnCommand
        MAX-ACCESS  read-create
        STATUS      current
        DESCRIPTION "This attribute is used to clear all the raw Sync PM counts."
        ::= { tnSyncRawCountStatsEntry 1 }

    tnSyncRawCountStatsStartTime OBJECT-TYPE
        SYNTAX      DateAndTime
        MAX-ACCESS  read-only
        STATUS      current
        DESCRIPTION "This attribute is the raw bin collection start date and time."
        ::= { tnSyncRawCountStatsEntry 2 }

    tnSyncRawCountStatsOffsetMin OBJECT-TYPE
        SYNTAX      Integer32
        UNITS       "ppb"
        MAX-ACCESS  read-only
        STATUS      current
        DESCRIPTION "Provides the raw count of the number of Sync Line Reference
                     offset Min value."
        ::= { tnSyncRawCountStatsEntry 3 }

    tnSyncRawCountStatsOffsetMax OBJECT-TYPE
        SYNTAX      Integer32
        UNITS       "ppb"
        MAX-ACCESS  read-only
        STATUS      current
        DESCRIPTION "Provides the raw count of the number of Sync Line Reference
                     offset Max value."
        ::= { tnSyncRawCountStatsEntry 4 }

    tnSyncRawCountStatsOffsetAverage OBJECT-TYPE
        SYNTAX      Integer32
        UNITS       "ppb"
        MAX-ACCESS  read-only
        STATUS      current
        DESCRIPTION "Provides the raw count of the number of Sync Line Reference
                     offset Average value."
        ::= { tnSyncRawCountStatsEntry 5 }

--------------------------------------------------------------------------------
-- PTP Time Offset (PTOFF) Raw Count Scalar
--------------------------------------------------------------------------------
    tnPTOFFRawCountTotalMembers OBJECT-TYPE
        SYNTAX      Integer32
        MAX-ACCESS  read-only
        STATUS      current
        DESCRIPTION "The total number of members
                     in the PTP Time Offset raw count
                     stats table."
        ::= { tnStatisticsRawCounts 81 }

--------------------------------------------------------------------------------
-- PTP Time Offset (PTOFF) Raw Count Scalar
--------------------------------------------------------------------------------
    tnPTOFFRawCountTable OBJECT-TYPE
        SYNTAX      SEQUENCE OF TnPTOFFRawCountEntry
        MAX-ACCESS  not-accessible
        STATUS      current
        DESCRIPTION "."
        ::= { tnStatisticsRawCounts 82 }

    tnPTOFFRawCountEntry OBJECT-TYPE
        SYNTAX      TnPTOFFRawCountEntry
        MAX-ACCESS  not-accessible
        STATUS      current
        DESCRIPTION "."
        INDEX   { ifIndex }
        ::= { tnPTOFFRawCountTable 1 }

    TnPTOFFRawCountEntry ::=
        SEQUENCE {
            tnPTOFFRawCountClear        TnCommand,
            tnPTOFFRawCountMin          Integer32,
            tnPTOFFRawCountMax          Integer32,
            tnPTOFFRawCountAverage      Integer32,
            tnPTOFFRawCountStartTime    DateAndTime
        }

    tnPTOFFRawCountClear OBJECT-TYPE
        SYNTAX      TnCommand
        MAX-ACCESS  read-create
        STATUS      current
        DESCRIPTION "This attribute is used to clear all the
                     raw counts on a particular interface
                     and group."
        ::= { tnPTOFFRawCountEntry 1 }

    tnPTOFFRawCountMin OBJECT-TYPE
        SYNTAX      Integer32
        UNITS       "ns"
        MAX-ACCESS  read-only
        STATUS      current
        DESCRIPTION "Minimum PTP clock TimeOffset (ns).
                     When the value equal 0x80000000(-2147483648),
                     it should be shown as 'N/A'(i.e. Not Available)."
        ::= { tnPTOFFRawCountEntry 2 }

    tnPTOFFRawCountMax OBJECT-TYPE
        SYNTAX      Integer32
        UNITS       "ns"
        MAX-ACCESS  read-only
        STATUS      current
        DESCRIPTION "Maximum PTP clock TimeOffset (ns).
                     When the value equal 0x80000000(-2147483648),
                     it should be shown as 'N/A'(i.e. Not Available)."
        ::= { tnPTOFFRawCountEntry 3 }

    tnPTOFFRawCountAverage OBJECT-TYPE
        SYNTAX      Integer32
        UNITS       "ns"
        MAX-ACCESS  read-only
        STATUS      current
        DESCRIPTION "Average PTP clock TimeOffset (ns).
                     When the value equal 0x80000000(-2147483648),
                     it should be shown as 'N/A'(i.e. Not Available)."
        ::= { tnPTOFFRawCountEntry 4 }

    tnPTOFFRawCountStartTime OBJECT-TYPE
        SYNTAX      DateAndTime
        MAX-ACCESS  read-only
        STATUS      current
        DESCRIPTION "This attribute is the bin collection start
                     date and time."
        ::= { tnPTOFFRawCountEntry 5 }

--------------------------------------------------------------------------------
-- PTP T-MS Delay (PTMSDLY) Raw Count Scalar
--------------------------------------------------------------------------------
    tnPTMSDLYRawCountTotalMembers OBJECT-TYPE
        SYNTAX      Integer32
        MAX-ACCESS  read-only
        STATUS      current
        DESCRIPTION "The total number of members
                     in the PTP T-MS Delay raw count
                     stats table."
        ::= { tnStatisticsRawCounts 83 }

--------------------------------------------------------------------------------
-- PTP T-MS Delay (PTMSDLY) Raw Count Scalar
--------------------------------------------------------------------------------
    tnPTMSDLYRawCountTable OBJECT-TYPE
        SYNTAX      SEQUENCE OF TnPTMSDLYRawCountEntry
        MAX-ACCESS  not-accessible
        STATUS      current
        DESCRIPTION "."
        ::= { tnStatisticsRawCounts 84 }

    tnPTMSDLYRawCountEntry OBJECT-TYPE
        SYNTAX      TnPTMSDLYRawCountEntry
        MAX-ACCESS  not-accessible
        STATUS      current
        DESCRIPTION "."
        INDEX   { ifIndex }
        ::= { tnPTMSDLYRawCountTable 1 }

    TnPTMSDLYRawCountEntry ::=
        SEQUENCE {
            tnPTMSDLYRawCountClear        TnCommand,
            tnPTMSDLYRawCountMin          Integer32,
            tnPTMSDLYRawCountMax          Integer32,
            tnPTMSDLYRawCountAverage      Integer32,
            tnPTMSDLYRawCountStartTime    DateAndTime
        }

    tnPTMSDLYRawCountClear OBJECT-TYPE
        SYNTAX      TnCommand
        MAX-ACCESS  read-create
        STATUS      current
        DESCRIPTION "This attribute is used to clear all the
                     raw counts on a particular interface
                     and group."
        ::= { tnPTMSDLYRawCountEntry 1 }

    tnPTMSDLYRawCountMin OBJECT-TYPE
        SYNTAX      Integer32
        UNITS       "ns"
        MAX-ACCESS  read-only
        STATUS      current
        DESCRIPTION "Minimum PTP T-MS Delay (ns).
                     When the value equal 0x80000000(-2147483648),
                     it should be shown as 'N/A'(i.e. Not Available)."
        ::= { tnPTMSDLYRawCountEntry 2 }

    tnPTMSDLYRawCountMax OBJECT-TYPE
        SYNTAX      Integer32
        UNITS       "ns"
        MAX-ACCESS  read-only
        STATUS      current
        DESCRIPTION "Maximum PTP T-MS Delay (ns).
                     When the value equal 0x80000000(-2147483648),
                     it should be shown as 'N/A'(i.e. Not Available)."
        ::= { tnPTMSDLYRawCountEntry 3 }

    tnPTMSDLYRawCountAverage OBJECT-TYPE
        SYNTAX      Integer32
        UNITS       "ns"
        MAX-ACCESS  read-only
        STATUS      current
        DESCRIPTION "Average PTP T-MS Delay (ns).
                     When the value equal 0x80000000(-2147483648),
                     it should be shown as 'N/A'(i.e. Not Available)."
        ::= { tnPTMSDLYRawCountEntry 4 }

    tnPTMSDLYRawCountStartTime OBJECT-TYPE
        SYNTAX      DateAndTime
        MAX-ACCESS  read-only
        STATUS      current
        DESCRIPTION "This attribute is the bin collection start date
                     and time."
        ::= { tnPTMSDLYRawCountEntry 5 }

--------------------------------------------------------------------------------
-- PTP T-SM Delay (PTSMDLY) Raw Count Scalar
--------------------------------------------------------------------------------
    tnPTSMDLYRawCountTotalMembers OBJECT-TYPE
        SYNTAX      Integer32
        MAX-ACCESS  read-only
        STATUS      current
        DESCRIPTION "The total number of members
                     in the PTP T-SM Delay raw count
                     stats table."
        ::= { tnStatisticsRawCounts 85 }

--------------------------------------------------------------------------------
-- PTP T-SM Delay (PTSMDLY) Raw Count Scalar
--------------------------------------------------------------------------------
    tnPTSMDLYRawCountTable OBJECT-TYPE
        SYNTAX      SEQUENCE OF TnPTSMDLYRawCountEntry
        MAX-ACCESS  not-accessible
        STATUS      current
        DESCRIPTION "."
        ::= { tnStatisticsRawCounts 86 }

    tnPTSMDLYRawCountEntry OBJECT-TYPE
        SYNTAX      TnPTSMDLYRawCountEntry
        MAX-ACCESS  not-accessible
        STATUS      current
        DESCRIPTION "."
        INDEX   { ifIndex }
        ::= { tnPTSMDLYRawCountTable 1 }

    TnPTSMDLYRawCountEntry ::=
        SEQUENCE {
            tnPTSMDLYRawCountClear        TnCommand,
            tnPTSMDLYRawCountMin          Integer32,
            tnPTSMDLYRawCountMax          Integer32,
            tnPTSMDLYRawCountAverage      Integer32,
            tnPTSMDLYRawCountStartTime    DateAndTime
        }

    tnPTSMDLYRawCountClear OBJECT-TYPE
        SYNTAX      TnCommand
        MAX-ACCESS  read-create
        STATUS      current
        DESCRIPTION "This attribute is used to clear all the
                     raw counts on a particular interface
                     and group."
        ::= { tnPTSMDLYRawCountEntry 1 }

    tnPTSMDLYRawCountMin OBJECT-TYPE
        SYNTAX      Integer32
        UNITS       "ns"
        MAX-ACCESS  read-only
        STATUS      current
        DESCRIPTION "Minimum PTP T-SM Delay (ns).
                     When the value equal 0x80000000(-2147483648),
                     it should be shown as 'N/A'(i.e. Not Available)."
        ::= { tnPTSMDLYRawCountEntry 2 }

    tnPTSMDLYRawCountMax OBJECT-TYPE
        SYNTAX      Integer32
        UNITS       "ns"
        MAX-ACCESS  read-only
        STATUS      current
        DESCRIPTION "Maximum PTP T-SM Delay (ns).
                     When the value equal 0x80000000(-2147483648),
                     it should be shown as 'N/A'(i.e. Not Available)."
        ::= { tnPTSMDLYRawCountEntry 3 }

    tnPTSMDLYRawCountAverage OBJECT-TYPE
        SYNTAX      Integer32
        UNITS       "ns"
        MAX-ACCESS  read-only
        STATUS      current
        DESCRIPTION "Average PTP T-SM Delay (ns).
                     When the value equal 0x80000000(-2147483648),
                     it should be shown as 'N/A'(i.e. Not Available)."
        ::= { tnPTSMDLYRawCountEntry 4 }

    tnPTSMDLYRawCountStartTime OBJECT-TYPE
        SYNTAX      DateAndTime
        MAX-ACCESS  read-only
        STATUS      current
        DESCRIPTION "This attribute is the bin collection start date
                     and time."
        ::= { tnPTSMDLYRawCountEntry 5 }

--------------------------------------------------------------------------------
-- PTP Mean Path Delay (PTMPDLY) Raw Count Scalar
--------------------------------------------------------------------------------
    tnPTMPDLYRawCountTotalMembers OBJECT-TYPE
        SYNTAX      Integer32
        MAX-ACCESS  read-only
        STATUS      current
        DESCRIPTION "The total number of members
                     in the PTP Mean Path Delay
                     raw count stats table."
        ::= { tnStatisticsRawCounts 87 }

--------------------------------------------------------------------------------
-- PTP Mean Path Delay (PTMPDLY) Raw Count Scalar
--------------------------------------------------------------------------------
    tnPTMPDLYRawCountTable OBJECT-TYPE
        SYNTAX      SEQUENCE OF TnPTMPDLYRawCountEntry
        MAX-ACCESS  not-accessible
        STATUS      current
        DESCRIPTION "."
        ::= { tnStatisticsRawCounts 88 }

    tnPTMPDLYRawCountEntry OBJECT-TYPE
        SYNTAX      TnPTMPDLYRawCountEntry
        MAX-ACCESS  not-accessible
        STATUS      current
        DESCRIPTION "."
        INDEX   { ifIndex }
        ::= { tnPTMPDLYRawCountTable 1 }

    TnPTMPDLYRawCountEntry ::=
        SEQUENCE {
            tnPTMPDLYRawCountClear        TnCommand,
            tnPTMPDLYRawCountMin          Integer32,
            tnPTMPDLYRawCountMax          Integer32,
            tnPTMPDLYRawCountAverage      Integer32,
            tnPTMPDLYRawCountStartTime    DateAndTime
        }

    tnPTMPDLYRawCountClear OBJECT-TYPE
        SYNTAX      TnCommand
        MAX-ACCESS  read-create
        STATUS      current
        DESCRIPTION "This attribute is used to clear all the
                     raw counts on a particular interface
                     and group."
        ::= { tnPTMPDLYRawCountEntry 1 }

    tnPTMPDLYRawCountMin OBJECT-TYPE
        SYNTAX      Integer32
        UNITS       "ns"
        MAX-ACCESS  read-only
        STATUS      current
        DESCRIPTION "Minimum PTP Mean Path Delay (ns).
                     When the value equal 0x80000000(-2147483648),
                     it should be shown as 'N/A'(i.e. Not Available)."
        ::= { tnPTMPDLYRawCountEntry 2 }

    tnPTMPDLYRawCountMax OBJECT-TYPE
        SYNTAX      Integer32
        UNITS       "ns"
        MAX-ACCESS  read-only
        STATUS      current
        DESCRIPTION "Maximum PTP Mean Path Delay (ns).
                     When the value equal 0x80000000(-2147483648),
                     it should be shown as 'N/A'(i.e. Not Available)."
        ::= { tnPTMPDLYRawCountEntry 3 }

    tnPTMPDLYRawCountAverage OBJECT-TYPE
        SYNTAX      Integer32
        UNITS       "ns"
        MAX-ACCESS  read-only
        STATUS      current
        DESCRIPTION "Average PTP Mean Path Delay (ns).
                     When the value equal 0x80000000(-2147483648),
                     it should be shown as 'N/A'(i.e. Not Available)."
        ::= { tnPTMPDLYRawCountEntry 4 }

    tnPTMPDLYRawCountStartTime OBJECT-TYPE
        SYNTAX      DateAndTime
        MAX-ACCESS  read-only
        STATUS      current
        DESCRIPTION "This attribute is the bin collection start date
                     and time."
        ::= { tnPTMPDLYRawCountEntry 5 }

--------------------------------------------------------------------------------
-- PTP Time Error by Reference comparison (PTERREF) Raw Count Scalar
--------------------------------------------------------------------------------
    tnPTERREFRawCountTotalMembers OBJECT-TYPE
        SYNTAX      Integer32
        MAX-ACCESS  read-only
        STATUS      current
        DESCRIPTION "The total number of members
                     in the PTP Time Error by Reference
                     comparison raw count stats table."
        ::= { tnStatisticsRawCounts 89 }

--------------------------------------------------------------------------------
-- PTP Time Error by Reference comparison (PTERREF) Raw Count Scalar
--------------------------------------------------------------------------------
    tnPTERREFRawCountTable OBJECT-TYPE
        SYNTAX      SEQUENCE OF TnPTERREFRawCountEntry
        MAX-ACCESS  not-accessible
        STATUS      current
        DESCRIPTION "."
        ::= { tnStatisticsRawCounts 90 }

    tnPTERREFRawCountEntry OBJECT-TYPE
        SYNTAX      TnPTERREFRawCountEntry
        MAX-ACCESS  not-accessible
        STATUS      current
        DESCRIPTION "."
        INDEX   { ifIndex }
        ::= { tnPTERREFRawCountTable 1 }

    TnPTERREFRawCountEntry ::=
        SEQUENCE {
            tnPTERREFRawCountClear        TnCommand,
            tnPTERREFRawCountMin          Integer32,
            tnPTERREFRawCountMax          Integer32,
            tnPTERREFRawCountAverage      Integer32,
            tnPTERREFRawCountStartTime    DateAndTime
        }

    tnPTERREFRawCountClear OBJECT-TYPE
        SYNTAX      TnCommand
        MAX-ACCESS  read-create
        STATUS      current
        DESCRIPTION "This attribute is used to clear all the
                     raw counts on a particular interface
                     and group."
        ::= { tnPTERREFRawCountEntry 1 }

    tnPTERREFRawCountMin OBJECT-TYPE
        SYNTAX      Integer32
        UNITS       "ns"
        MAX-ACCESS  read-only
        STATUS      current
        DESCRIPTION "Minimum PTP Time Error by Reference comparison (ns).
                     When the value equal 0x80000000(-2147483648),
                     it should be shown as 'N/A'(i.e. Not Available)."
        ::= { tnPTERREFRawCountEntry 2 }

    tnPTERREFRawCountMax OBJECT-TYPE
        SYNTAX      Integer32
        UNITS       "ns"
        MAX-ACCESS  read-only
        STATUS      current
        DESCRIPTION "Maximum PTP Time Error by Reference comparison (ns).
                     When the value equal 0x80000000(-2147483648),
                     it should be shown as 'N/A'(i.e. Not Available)."
        ::= { tnPTERREFRawCountEntry 3 }

    tnPTERREFRawCountAverage OBJECT-TYPE
        SYNTAX      Integer32
        UNITS       "ns"
        MAX-ACCESS  read-only
        STATUS      current
        DESCRIPTION "Average PTP Time Error by Reference comparison (ns).
                     When the value equal 0x80000000(-2147483648),
                     it should be shown as 'N/A'(i.e. Not Available)."
        ::= { tnPTERREFRawCountEntry 4 }

    tnPTERREFRawCountStartTime OBJECT-TYPE
        SYNTAX      DateAndTime
        MAX-ACCESS  read-only
        STATUS      current
        DESCRIPTION "This attribute is the bin collection start date
                     and time."
        ::= { tnPTERREFRawCountEntry 5 }

--------------------------------------------------------------------------------
-- PTP Time Offset Accumulation (PTOFFACUM) Raw Count Scalar
--------------------------------------------------------------------------------
    tnPTOFFACUMRawCountTotalMembers OBJECT-TYPE
        SYNTAX      Integer32
        MAX-ACCESS  read-only
        STATUS      current
        DESCRIPTION "The total number of members
                     in the PTP Time Offset Accumulation
                     raw count stats table."
        ::= { tnStatisticsRawCounts 91 }

--------------------------------------------------------------------------------
-- PTP Time Offset Accumulation (PTOFFACUM) Raw Count Scalar
--------------------------------------------------------------------------------
    tnPTOFFACUMRawCountTable OBJECT-TYPE
        SYNTAX      SEQUENCE OF TnPTOFFACUMRawCountEntry
        MAX-ACCESS  not-accessible
        STATUS      current
        DESCRIPTION "."
        ::= { tnStatisticsRawCounts 92 }

    tnPTOFFACUMRawCountEntry OBJECT-TYPE
        SYNTAX      TnPTOFFACUMRawCountEntry
        MAX-ACCESS  not-accessible
        STATUS      current
        DESCRIPTION "."
        INDEX   { ifIndex }
        ::= { tnPTOFFACUMRawCountTable 1 }

    TnPTOFFACUMRawCountEntry ::=
        SEQUENCE {
            tnPTOFFACUMRawCountClear        TnCommand,
            tnPTOFFACUMRawCountPeakToPeak   Integer32,
            tnPTOFFACUMRawCountAverage      Integer32,
            tnPTOFFACUMRawCountSum          Integer32,
            tnPTOFFACUMRawCountStartTime    DateAndTime
        }

    tnPTOFFACUMRawCountClear OBJECT-TYPE
        SYNTAX      TnCommand
        MAX-ACCESS  read-create
        STATUS      current
        DESCRIPTION "This attribute is used to clear all the
                     raw counts on a particular interface
                     and group."
        ::= { tnPTOFFACUMRawCountEntry 1 }

    tnPTOFFACUMRawCountPeakToPeak OBJECT-TYPE
        SYNTAX      Integer32
        UNITS       "ns"
        MAX-ACCESS  read-only
        STATUS      current
        DESCRIPTION "Peak to Peak PTP Time Offset Accumulation (ns).
                     When the value equal 0x80000000(-2147483648),
                     it should be shown as 'N/A'(i.e. Not Available)."
        ::= { tnPTOFFACUMRawCountEntry 2 }

    tnPTOFFACUMRawCountAverage OBJECT-TYPE
        SYNTAX      Integer32
        UNITS       "ns"
        MAX-ACCESS  read-only
        STATUS      current
        DESCRIPTION "Average PTP Time Offset Accumulation (ns).
                     When the value equal 0x80000000(-2147483648),
                     it should be shown as 'N/A'(i.e. Not Available)."
        ::= { tnPTOFFACUMRawCountEntry 3 }

    tnPTOFFACUMRawCountSum OBJECT-TYPE
        SYNTAX      Integer32
        UNITS       "ns"
        MAX-ACCESS  read-only
        STATUS      current
        DESCRIPTION "Sum PTP PTP Time Offset Accumulation (ns).
                     When the value equal 0x80000000(-2147483648),
                     it should be shown as 'N/A'(i.e. Not Available)."
        ::= { tnPTOFFACUMRawCountEntry 4 }

    tnPTOFFACUMRawCountStartTime OBJECT-TYPE
        SYNTAX      DateAndTime
        MAX-ACCESS  read-only
        STATUS      current
        DESCRIPTION "This attribute is the bin collection start date
                     and time."
        ::= { tnPTOFFACUMRawCountEntry 5 }

--------------------------------------------------------------------------------
-- Cycle Slips Rate (CSR) Raw Count Statistics Scalar
--------------------------------------------------------------------------------
    tnCsrRawCountStatsTotalMembers OBJECT-TYPE
        SYNTAX      Integer32
        MAX-ACCESS  read-only
        STATUS      current
        DESCRIPTION "The total number of members in the CSR raw count stats
                     table."
        ::= { tnStatisticsRawCounts 93 }

--------------------------------------------------------------------------------
-- Cycle Slips Rate (CSR) Raw Count Statistics Table
--------------------------------------------------------------------------------
    tnCsrRawCountStatsTable OBJECT-TYPE
        SYNTAX      SEQUENCE OF TnCsrRawCountStatsEntry
        MAX-ACCESS  not-accessible
        STATUS      current
        DESCRIPTION "."
        ::= { tnStatisticsRawCounts 94 }

    tnCsrRawCountStatsEntry OBJECT-TYPE
        SYNTAX      TnCsrRawCountStatsEntry
        MAX-ACCESS  not-accessible
        STATUS      current
        DESCRIPTION "."
        INDEX   { ifIndex }
        ::= { tnCsrRawCountStatsTable 1 }

    TnCsrRawCountStatsEntry ::=
        SEQUENCE {
            tnCsrRawCountStatsClear       TnCommand,
            tnCsrRawCountStatMin          SnmpAdminString,
            tnCsrRawCountStatMax          SnmpAdminString,
            tnCsrRawCountStatAverage      SnmpAdminString,
            tnCsrRawCountStatStartTime    DateAndTime
        }

    tnCsrRawCountStatsClear OBJECT-TYPE
        SYNTAX      TnCommand
        MAX-ACCESS  read-create
        STATUS      current
        DESCRIPTION "This attribute is used to clear all the raw counts on a
                     particular interface and group."
        ::= { tnCsrRawCountStatsEntry 1 }

    tnCsrRawCountStatMin OBJECT-TYPE
        SYNTAX      SnmpAdminString
        MAX-ACCESS  read-only
        STATUS      current
        DESCRIPTION "Minimum CSR received (ps)."
        ::= { tnCsrRawCountStatsEntry 2 }

    tnCsrRawCountStatMax OBJECT-TYPE
        SYNTAX      SnmpAdminString
        MAX-ACCESS  read-only
        STATUS      current
        DESCRIPTION "Maximum CSR received (ps)."
        ::= { tnCsrRawCountStatsEntry 3 }

    tnCsrRawCountStatAverage OBJECT-TYPE
        SYNTAX      SnmpAdminString
        MAX-ACCESS  read-only
        STATUS      current
        DESCRIPTION "Average CSR received (ps)."
        ::= { tnCsrRawCountStatsEntry 4 }

    tnCsrRawCountStatStartTime OBJECT-TYPE
        SYNTAX      DateAndTime
        MAX-ACCESS  read-only
        STATUS      current
        DESCRIPTION "This attribute is the bin collection start date and time."
        ::= { tnCsrRawCountStatsEntry 5 }

--------------------------------------------------------------------------------
-- Q-Margin Raw Count Statistics Scalar
--------------------------------------------------------------------------------
    tnQmarginRawCountStatsTotalMembers OBJECT-TYPE
        SYNTAX      Integer32
        MAX-ACCESS  read-only
        STATUS      current
        DESCRIPTION "The total number of members in the Qmargin raw count stats
                     table."
        ::= { tnStatisticsRawCounts 95 }

--------------------------------------------------------------------------------
-- Q-Margin Raw Count Statistics Table
--------------------------------------------------------------------------------
    tnQmarginRawCountStatsTable OBJECT-TYPE
        SYNTAX      SEQUENCE OF TnQmarginRawCountStatsEntry
        MAX-ACCESS  not-accessible
        STATUS      current
        DESCRIPTION "."
        ::= { tnStatisticsRawCounts 96 }

    tnQmarginRawCountStatsEntry OBJECT-TYPE
        SYNTAX      TnQmarginRawCountStatsEntry
        MAX-ACCESS  not-accessible
        STATUS      current
        DESCRIPTION "."
        INDEX   { ifIndex }
        ::= { tnQmarginRawCountStatsTable 1 }

    TnQmarginRawCountStatsEntry ::=
        SEQUENCE {
            tnQmarginRawCountStatsClear       TnCommand,
            tnQmarginRawCountStatMin          Integer32,
            tnQmarginRawCountStatMax          Integer32,
            tnQmarginRawCountStatAverage      Integer32,
            tnQmarginRawCountStatStartTime    DateAndTime
        }

    tnQmarginRawCountStatsClear OBJECT-TYPE
        SYNTAX      TnCommand
        MAX-ACCESS  read-create
        STATUS      current
        DESCRIPTION "This attribute is used to clear all the raw counts on a
                     particular interface and group."
        ::= { tnQmarginRawCountStatsEntry 1 }

    tnQmarginRawCountStatMin OBJECT-TYPE
        SYNTAX      Integer32
        UNITS       "ps"
        MAX-ACCESS  read-only
        STATUS      current
        DESCRIPTION "Minimum Qmargin received (ps)."
        ::= { tnQmarginRawCountStatsEntry 2 }

    tnQmarginRawCountStatMax OBJECT-TYPE
        SYNTAX      Integer32
        UNITS       "ps"
        MAX-ACCESS  read-only
        STATUS      current
        DESCRIPTION "Maximum Qmargin received (ps)."
        ::= { tnQmarginRawCountStatsEntry 3 }

    tnQmarginRawCountStatAverage OBJECT-TYPE
        SYNTAX      Integer32
        UNITS       "ps"
        MAX-ACCESS  read-only
        STATUS      current
        DESCRIPTION "Average Qmargin received (ps)."
        ::= { tnQmarginRawCountStatsEntry 4 }

    tnQmarginRawCountStatStartTime OBJECT-TYPE
        SYNTAX      DateAndTime
        MAX-ACCESS  read-only
        STATUS      current
        DESCRIPTION "This attribute is the bin collection start date and time."
        ::= { tnQmarginRawCountStatsEntry 5 }

--------------------------------------------------------------------------------
-- Polariazation Dependent Loss (PDL) Raw Count Statistics Scalar
--------------------------------------------------------------------------------
    tnPdlRawCountStatsTotalMembers OBJECT-TYPE
        SYNTAX      Integer32
        MAX-ACCESS  read-only
        STATUS      current
        DESCRIPTION "The total number of members in the PDL raw count stats
                     table."
        ::= { tnStatisticsRawCounts 97 }

--------------------------------------------------------------------------------
-- Polariazation Dependent Loss (PDL) Raw Count Statistics Table
--------------------------------------------------------------------------------
    tnPdlRawCountStatsTable OBJECT-TYPE
        SYNTAX      SEQUENCE OF TnPdlRawCountStatsEntry
        MAX-ACCESS  not-accessible
        STATUS      current
        DESCRIPTION "."
        ::= { tnStatisticsRawCounts 98 }

    tnPdlRawCountStatsEntry OBJECT-TYPE
        SYNTAX      TnPdlRawCountStatsEntry
        MAX-ACCESS  not-accessible
        STATUS      current
        DESCRIPTION "."
        INDEX   { ifIndex }
        ::= { tnPdlRawCountStatsTable 1 }

    TnPdlRawCountStatsEntry ::=
        SEQUENCE {
            tnPdlRawCountStatsClear       TnCommand,
            tnPdlRawCountStatMin          Integer32,
            tnPdlRawCountStatMax          Integer32,
            tnPdlRawCountStatAverage      Integer32,
            tnPdlRawCountStatStartTime    DateAndTime
        }

    tnPdlRawCountStatsClear OBJECT-TYPE
        SYNTAX      TnCommand
        MAX-ACCESS  read-create
        STATUS      current
        DESCRIPTION "This attribute is used to clear all the raw counts on a
                     particular interface and group."
        ::= { tnPdlRawCountStatsEntry 1 }

    tnPdlRawCountStatMin OBJECT-TYPE
        SYNTAX      Integer32
        MAX-ACCESS  read-only
        STATUS      current
        DESCRIPTION "Minimum Pdl received (dB)."
        ::= { tnPdlRawCountStatsEntry 2 }

    tnPdlRawCountStatMax OBJECT-TYPE
        SYNTAX      Integer32
        MAX-ACCESS  read-only
        STATUS      current
        DESCRIPTION "Maximum Pdl received (dB)."
        ::= { tnPdlRawCountStatsEntry 3 }

    tnPdlRawCountStatAverage OBJECT-TYPE
        SYNTAX      Integer32
        MAX-ACCESS  read-only
        STATUS      current
        DESCRIPTION "Average Pdl received (dB)."
        ::= { tnPdlRawCountStatsEntry 4 }

    tnPdlRawCountStatStartTime OBJECT-TYPE
        SYNTAX      DateAndTime
        MAX-ACCESS  read-only
        STATUS      current
        DESCRIPTION "This attribute is the bin collection start date and time."
        ::= { tnPdlRawCountStatsEntry 5 }

--------------------------------------------------------------------------------
-- State of Polariazation Change Rate (SOPR) Raw Count Statistics Scalar
--------------------------------------------------------------------------------
    tnSoprRawCountStatsTotalMembers OBJECT-TYPE
        SYNTAX      Integer32
        MAX-ACCESS  read-only
        STATUS      current
        DESCRIPTION "The total number of members in the SOPR raw count stats
                     table."
        ::= { tnStatisticsRawCounts 99 }

--------------------------------------------------------------------------------
-- State of Polariazation Change Rate (SOPR) Raw Count Statistics Table
--------------------------------------------------------------------------------
    tnSoprRawCountStatsTable OBJECT-TYPE
        SYNTAX      SEQUENCE OF TnSoprRawCountStatsEntry
        MAX-ACCESS  not-accessible
        STATUS      current
        DESCRIPTION "."
        ::= { tnStatisticsRawCounts 100 }

    tnSoprRawCountStatsEntry OBJECT-TYPE
        SYNTAX      TnSoprRawCountStatsEntry
        MAX-ACCESS  not-accessible
        STATUS      current
        DESCRIPTION "."
        INDEX   { ifIndex }
        ::= { tnSoprRawCountStatsTable 1 }

    TnSoprRawCountStatsEntry ::=
        SEQUENCE {
            tnSoprRawCountStatsClear       TnCommand,
            tnSoprRawCountStatMin          Integer32,
            tnSoprRawCountStatMax          Integer32,
            tnSoprRawCountStatAverage      Integer32,
            tnSoprRawCountStatStartTime    DateAndTime
        }

    tnSoprRawCountStatsClear OBJECT-TYPE
        SYNTAX      TnCommand
        MAX-ACCESS  read-create
        STATUS      current
        DESCRIPTION "This attribute is used to clear all the raw counts on a
                     particular interface and group."
        ::= { tnSoprRawCountStatsEntry 1 }

    tnSoprRawCountStatMin OBJECT-TYPE
        SYNTAX      Integer32
        MAX-ACCESS  read-only
        STATUS      current
        DESCRIPTION "."
        ::= { tnSoprRawCountStatsEntry 2 }

    tnSoprRawCountStatMax OBJECT-TYPE
        SYNTAX      Integer32
        MAX-ACCESS  read-only
        STATUS      current
        DESCRIPTION "."
        ::= { tnSoprRawCountStatsEntry 3 }

    tnSoprRawCountStatAverage OBJECT-TYPE
        SYNTAX      Integer32
        MAX-ACCESS  read-only
        STATUS      current
        DESCRIPTION "."
        ::= { tnSoprRawCountStatsEntry 4 }

    tnSoprRawCountStatStartTime OBJECT-TYPE
        SYNTAX      DateAndTime
        MAX-ACCESS  read-only
        STATUS      current
        DESCRIPTION "This attribute is the bin collection start date and time."
        ::= { tnSoprRawCountStatsEntry 5 }

--------------------------------------------------------------------------------
-- Electrical Signal to Noise Ratio (ESNR) Raw Count Statistics Scalar
--------------------------------------------------------------------------------
    tnEsnrRawCountStatsTotalMembers OBJECT-TYPE
        SYNTAX      Integer32
        MAX-ACCESS  read-only
        STATUS      current
        DESCRIPTION "The total number of members in the ESNR raw count stats
                     table."
        ::= { tnStatisticsRawCounts 101 }

--------------------------------------------------------------------------------
-- Electrical Signal to Noise Ratio (ESNR) Raw Count Statistics Table
--------------------------------------------------------------------------------
    tnEsnrRawCountStatsTable OBJECT-TYPE
        SYNTAX      SEQUENCE OF TnEsnrRawCountStatsEntry
        MAX-ACCESS  not-accessible
        STATUS      current
        DESCRIPTION "."
        ::= { tnStatisticsRawCounts 102 }

    tnEsnrRawCountStatsEntry OBJECT-TYPE
        SYNTAX      TnEsnrRawCountStatsEntry
        MAX-ACCESS  not-accessible
        STATUS      current
        DESCRIPTION "."
        INDEX   { ifIndex }
        ::= { tnEsnrRawCountStatsTable 1 }

    TnEsnrRawCountStatsEntry ::=
        SEQUENCE {
            tnEsnrRawCountStatsClear       TnCommand,
            tnEsnrRawCountStatMin          Integer32,
            tnEsnrRawCountStatMax          Integer32,
            tnEsnrRawCountStatAverage      Integer32,
            tnEsnrRawCountStatStartTime    DateAndTime
        }

    tnEsnrRawCountStatsClear OBJECT-TYPE
        SYNTAX      TnCommand
        MAX-ACCESS  read-create
        STATUS      current
        DESCRIPTION "This attribute is used to clear all the raw counts on a
                     particular interface and group."
        ::= { tnEsnrRawCountStatsEntry 1 }

    tnEsnrRawCountStatMin OBJECT-TYPE
        SYNTAX      Integer32
        MAX-ACCESS  read-only
        STATUS      current
        DESCRIPTION "."
        ::= { tnEsnrRawCountStatsEntry 2 }

    tnEsnrRawCountStatMax OBJECT-TYPE
        SYNTAX      Integer32
        MAX-ACCESS  read-only
        STATUS      current
        DESCRIPTION "."
        ::= { tnEsnrRawCountStatsEntry 3 }

    tnEsnrRawCountStatAverage OBJECT-TYPE
        SYNTAX      Integer32
        MAX-ACCESS  read-only
        STATUS      current
        DESCRIPTION "."
        ::= { tnEsnrRawCountStatsEntry 4 }

    tnEsnrRawCountStatStartTime OBJECT-TYPE
        SYNTAX      DateAndTime
        MAX-ACCESS  read-only
        STATUS      current
        DESCRIPTION "This attribute is the bin collection start date and time."
        ::= { tnEsnrRawCountStatsEntry 5 }

--------------------------------------------------------------------------------
-- Optical Super Channel Power In (OPSUPCHIN) Raw CountStatistics Scalar
--------------------------------------------------------------------------------
    tnOpSupChInRawCountStatsTotalMembers OBJECT-TYPE
        SYNTAX      Integer32
        MAX-ACCESS  read-only
        STATUS      current
        DESCRIPTION "The total number of members in the OPSUPCHIN raw count
                     stats table."
        ::= { tnStatisticsRawCounts 103 }

--------------------------------------------------------------------------------
-- Optical Super Channel Power In (OPSUPCHIN) Raw Count Statistics Table
--------------------------------------------------------------------------------
    tnOpSupChInRawCountStatsTable OBJECT-TYPE
        SYNTAX      SEQUENCE OF TnOpSupChInRawCountStatsEntry
        MAX-ACCESS  not-accessible
        STATUS      current
        DESCRIPTION "."
        ::= { tnStatisticsRawCounts 104 }

    tnOpSupChInRawCountStatsEntry OBJECT-TYPE
        SYNTAX      TnOpSupChInRawCountStatsEntry
        MAX-ACCESS  not-accessible
        STATUS      current
        DESCRIPTION "."
        INDEX   { ifIndex,
                  tnOpSupChInCenterFrequency }
        ::= { tnOpSupChInRawCountStatsTable 1 }

    TnOpSupChInRawCountStatsEntry ::=
        SEQUENCE {
            tnOpSupChInRawCountStatsClear           TnCommand,
            tnOpSupChInRawCountStatMinPower         Integer32,
            tnOpSupChInRawCountStatMaxPower         Integer32,
            tnOpSupChInRawCountStatAveragePower     Integer32,
            tnOpSupChInRawCountStatStartTime        DateAndTime,
            tnOpSupChInRawCountStatWidth            Unsigned32
        }

    tnOpSupChInRawCountStatsClear OBJECT-TYPE
        SYNTAX      TnCommand
        MAX-ACCESS  read-create
        STATUS      current
        DESCRIPTION "This attribute is used to clear all the raw counts for
                     all frequencies on a particular interface and group,
                     regardless of the frequency index."
        ::= { tnOpSupChInRawCountStatsEntry 1 }

    tnOpSupChInRawCountStatMinPower OBJECT-TYPE
        SYNTAX      Integer32
        UNITS       "mBm"
        MAX-ACCESS  read-only
        STATUS      current
        DESCRIPTION "Minimum optical WT power in the In direction."
        ::= { tnOpSupChInRawCountStatsEntry 2 }

    tnOpSupChInRawCountStatMaxPower OBJECT-TYPE
        SYNTAX      Integer32
        UNITS       "mBm"
        MAX-ACCESS  read-only
        STATUS      current
        DESCRIPTION "Maximum optical WT power in the In direction."
        ::= { tnOpSupChInRawCountStatsEntry 3 }

    tnOpSupChInRawCountStatAveragePower OBJECT-TYPE
        SYNTAX      Integer32
        UNITS       "mBm"
        MAX-ACCESS  read-only
        STATUS      current
        DESCRIPTION "Average optical WT power in the In direction."
        ::= { tnOpSupChInRawCountStatsEntry 4 }

    tnOpSupChInRawCountStatStartTime OBJECT-TYPE
        SYNTAX      DateAndTime
        MAX-ACCESS  read-only
        STATUS      current
        DESCRIPTION "This attribute is the bin collection start date and time."
        ::= { tnOpSupChInRawCountStatsEntry 5 }

    tnOpSupChInRawCountStatWidth OBJECT-TYPE
        SYNTAX      Unsigned32
        UNITS       "MHz"
        MAX-ACCESS  read-only
        STATUS      current
        DESCRIPTION "Channel width."
        ::= { tnOpSupChInRawCountStatsEntry 6 }

--------------------------------------------------------------------------------
-- Optical Super Channel Power Out (OPSUPCHOUT) Raw Count Statistics Scalar
--------------------------------------------------------------------------------
    tnOpSupChOutRawCountStatsTotalMembers OBJECT-TYPE
        SYNTAX      Integer32
        MAX-ACCESS  read-only
        STATUS      current
        DESCRIPTION "The total number of members in the OPSUPCHOUT raw count
                     stats table."
        ::= { tnStatisticsRawCounts 105 }

--------------------------------------------------------------------------------
-- Optical Super Channel Power Out (OPSUPCHOUT) Raw Count Statistics Table
--------------------------------------------------------------------------------
    tnOpSupChOutRawCountStatsTable OBJECT-TYPE
        SYNTAX      SEQUENCE OF TnOpSupChOutRawCountStatsEntry
        MAX-ACCESS  not-accessible
        STATUS      current
        DESCRIPTION "."
        ::= { tnStatisticsRawCounts 106 }

    tnOpSupChOutRawCountStatsEntry OBJECT-TYPE
        SYNTAX      TnOpSupChOutRawCountStatsEntry
        MAX-ACCESS  not-accessible
        STATUS      current
        DESCRIPTION "."
        INDEX   { ifIndex,
                  tnOpSupChOutCenterFrequency }
        ::= { tnOpSupChOutRawCountStatsTable 1 }

    TnOpSupChOutRawCountStatsEntry ::=
        SEQUENCE {
            tnOpSupChOutRawCountStatsClear           TnCommand,
            tnOpSupChOutRawCountStatMinPower         Integer32,
            tnOpSupChOutRawCountStatMaxPower         Integer32,
            tnOpSupChOutRawCountStatAveragePower     Integer32,
            tnOpSupChOutRawCountStatStartTime        DateAndTime,
            tnOpSupChOutRawCountStatWidth            Unsigned32
        }

    tnOpSupChOutRawCountStatsClear OBJECT-TYPE
        SYNTAX      TnCommand
        MAX-ACCESS  read-create
        STATUS      current
        DESCRIPTION "This attribute is used to clear all the raw counts for
                     all frequencies on a particular interface and group,
                     regardless of the frequency index."
        ::= { tnOpSupChOutRawCountStatsEntry 1 }

    tnOpSupChOutRawCountStatMinPower OBJECT-TYPE
        SYNTAX      Integer32
        UNITS       "mBm"
        MAX-ACCESS  read-only
        STATUS      current
        DESCRIPTION "Minimum optical WT power in the Out direction."
        ::= { tnOpSupChOutRawCountStatsEntry 2 }

    tnOpSupChOutRawCountStatMaxPower OBJECT-TYPE
        SYNTAX      Integer32
        UNITS       "mBm"
        MAX-ACCESS  read-only
        STATUS      current
        DESCRIPTION "Maximum optical WT power in the Out direction."
        ::= { tnOpSupChOutRawCountStatsEntry 3 }

    tnOpSupChOutRawCountStatAveragePower OBJECT-TYPE
        SYNTAX      Integer32
        UNITS       "mBm"
        MAX-ACCESS  read-only
        STATUS      current
        DESCRIPTION "Average optical WT power in the Out direction."
        ::= { tnOpSupChOutRawCountStatsEntry 4 }

    tnOpSupChOutRawCountStatStartTime OBJECT-TYPE
        SYNTAX      DateAndTime
        MAX-ACCESS  read-only
        STATUS      current
        DESCRIPTION "This attribute is the bin collection start date and time."
        ::= { tnOpSupChOutRawCountStatsEntry 5 }

    tnOpSupChOutRawCountStatWidth OBJECT-TYPE
        SYNTAX      Unsigned32
        UNITS       "MHz"
        MAX-ACCESS  read-only
        STATUS      current
        DESCRIPTION "Channel width."
        ::= { tnOpSupChOutRawCountStatsEntry 6 }

--------------------------------------------------------------------------------
-- Error Vector Magnitude (EVM) Raw Count Statistics Scalar
--------------------------------------------------------------------------------
    tnEvmRawCountStatsTotalMembers OBJECT-TYPE
        SYNTAX      Integer32
        MAX-ACCESS  read-only
        STATUS      current
        DESCRIPTION "The total number of members in the CSR raw count stats
                     table."
        ::= { tnStatisticsRawCounts 107 }

--------------------------------------------------------------------------------
-- Error Vector Magnitude (EVM) Raw Count Statistics Table
--------------------------------------------------------------------------------
    tnEvmRawCountStatsTable OBJECT-TYPE
        SYNTAX      SEQUENCE OF TnEvmRawCountStatsEntry
        MAX-ACCESS  not-accessible
        STATUS      current
        DESCRIPTION "."
        ::= { tnStatisticsRawCounts 108 }

    tnEvmRawCountStatsEntry OBJECT-TYPE
        SYNTAX      TnEvmRawCountStatsEntry
        MAX-ACCESS  not-accessible
        STATUS      current
        DESCRIPTION "."
        INDEX   { ifIndex }
        ::= { tnEvmRawCountStatsTable 1 }

    TnEvmRawCountStatsEntry ::=
        SEQUENCE {
            tnEvmRawCountStatsClear       TnCommand,
            tnEvmRawCountStatMin          SnmpAdminString,
            tnEvmRawCountStatMax          SnmpAdminString,
            tnEvmRawCountStatAverage      SnmpAdminString,
            tnEvmRawCountStatStartTime    DateAndTime
        }

    tnEvmRawCountStatsClear OBJECT-TYPE
        SYNTAX      TnCommand
        MAX-ACCESS  read-create
        STATUS      current
        DESCRIPTION "This attribute is used to clear all the raw counts on a
                     particular interface and group."
        ::= { tnEvmRawCountStatsEntry 1 }

    tnEvmRawCountStatMin OBJECT-TYPE
        SYNTAX      SnmpAdminString
        MAX-ACCESS  read-only
        STATUS      current
        DESCRIPTION "Minimum EVM received."
        ::= { tnEvmRawCountStatsEntry 2 }

    tnEvmRawCountStatMax OBJECT-TYPE
        SYNTAX      SnmpAdminString
        MAX-ACCESS  read-only
        STATUS      current
        DESCRIPTION "Maximum EVM received."
        ::= { tnEvmRawCountStatsEntry 3 }

    tnEvmRawCountStatAverage OBJECT-TYPE
        SYNTAX      SnmpAdminString
        MAX-ACCESS  read-only
        STATUS      current
        DESCRIPTION "Average EVM received."
        ::= { tnEvmRawCountStatsEntry 4 }

    tnEvmRawCountStatStartTime OBJECT-TYPE
        SYNTAX      DateAndTime
        MAX-ACCESS  read-only
        STATUS      current
        DESCRIPTION "This attribute is the bin collection start date and time."
        ::= { tnEvmRawCountStatsEntry 5 }

--------------------------------------------------------------------------------
-- Optical Signal Noise Ratio Rx (OSNRRx) Statistics Raw Count Scalar
--------------------------------------------------------------------------------
    tnOsnrRxRawCountStatsTotalMembers OBJECT-TYPE
        SYNTAX      Integer32
        MAX-ACCESS  read-only
        STATUS      current
        DESCRIPTION "The total number of members in the OSNRRx raw count
                     stats table."
        ::= { tnStatisticsRawCounts 109 }

--------------------------------------------------------------------------------
-- Optical Signal Noise Ratio Rx (OSNRRx) Statistics Raw Count Table
--------------------------------------------------------------------------------
    tnOsnrRxRawCountStatsTable OBJECT-TYPE
        SYNTAX      SEQUENCE OF TnOsnrRxRawCountStatsEntry
        MAX-ACCESS  not-accessible
        STATUS      current
        DESCRIPTION "."
        ::= { tnStatisticsRawCounts 110 }

    tnOsnrRxRawCountStatsEntry OBJECT-TYPE
        SYNTAX      TnOsnrRxRawCountStatsEntry
        MAX-ACCESS  not-accessible
        STATUS      current
        DESCRIPTION "."
        INDEX   { ifIndex }
        ::= { tnOsnrRxRawCountStatsTable 1 }

    TnOsnrRxRawCountStatsEntry ::=
        SEQUENCE {
            tnOsnrRxRawCountStatsClear        TnCommand,
            tnOsnrRxRawCountStatMin           Integer32,
            tnOsnrRxRawCountStatMax           Integer32,
            tnOsnrRxRawCountStatAverage       Integer32,
            tnOsnrRxRawCountStatStartTime     DateAndTime
        }

    tnOsnrRxRawCountStatsClear OBJECT-TYPE
        SYNTAX      TnCommand
        MAX-ACCESS  read-create
        STATUS      current
        DESCRIPTION "This attribute is used to clear all the raw counts for
                     all frequencies on a particular interface and group,
                     regardless of the frequency index."
        ::= { tnOsnrRxRawCountStatsEntry 1 }

    tnOsnrRxRawCountStatMin OBJECT-TYPE
        SYNTAX      Integer32
        UNITS       "0.01dB"
        MAX-ACCESS  read-only
        STATUS      current
        DESCRIPTION "Minimum OSNR."
        ::= { tnOsnrRxRawCountStatsEntry 2 }

    tnOsnrRxRawCountStatMax OBJECT-TYPE
        SYNTAX      Integer32
        UNITS       "0.01dB"
        MAX-ACCESS  read-only
        STATUS      current
        DESCRIPTION "Maximum OSNR."
        ::= { tnOsnrRxRawCountStatsEntry 3 }

    tnOsnrRxRawCountStatAverage OBJECT-TYPE
        SYNTAX      Integer32
        UNITS       "0.01dB"
        MAX-ACCESS  read-only
        STATUS      current
        DESCRIPTION "Average OSNR."
        ::= { tnOsnrRxRawCountStatsEntry 4 }

    tnOsnrRxRawCountStatStartTime OBJECT-TYPE
        SYNTAX      DateAndTime
        MAX-ACCESS  read-only
        STATUS      current
        DESCRIPTION "This attribute is the bin collection start date and time."
        ::= { tnOsnrRxRawCountStatsEntry 5 }

--------------------------------------------------------------------------------
-- Qfactor Raw Count Statistics Scalar
--------------------------------------------------------------------------------
    tnQfactorRawCountStatsTotalMembers OBJECT-TYPE
        SYNTAX      Integer32
        MAX-ACCESS  read-only
        STATUS      current
        DESCRIPTION "The total number of members in the Qfactor raw count stats
                     table."
        ::= { tnStatisticsRawCounts 111 }

--------------------------------------------------------------------------------
-- Qfactor Raw Count Statistics Table
--------------------------------------------------------------------------------
    tnQfactorRawCountStatsTable OBJECT-TYPE
        SYNTAX      SEQUENCE OF TnQfactorRawCountStatsEntry
        MAX-ACCESS  not-accessible
        STATUS      current
        DESCRIPTION "."
        ::= { tnStatisticsRawCounts 112 }

    tnQfactorRawCountStatsEntry OBJECT-TYPE
        SYNTAX      TnQfactorRawCountStatsEntry
        MAX-ACCESS  not-accessible
        STATUS      current
        DESCRIPTION "."
        INDEX   { ifIndex }
        ::= { tnQfactorRawCountStatsTable 1 }

    TnQfactorRawCountStatsEntry ::=
        SEQUENCE {
            tnQfactorRawCountStatsClear        TnCommand,
            tnQfactorRawCountStatMin           Integer32,
            tnQfactorRawCountStatMax           Integer32,
            tnQfactorRawCountStatAverage       Integer32,
            tnQfactorRawCountStatStartTime     DateAndTime
        }

    tnQfactorRawCountStatsClear OBJECT-TYPE
        SYNTAX      TnCommand
        MAX-ACCESS  read-create
        STATUS      current
        DESCRIPTION "This attribute is used to clear all the raw counts on a
                     particular interface and group."
        ::= { tnQfactorRawCountStatsEntry 1 }

    tnQfactorRawCountStatMin OBJECT-TYPE
        SYNTAX      Integer32
        UNITS       "0.01dB"
        MAX-ACCESS  read-only
        STATUS      current
        DESCRIPTION "Minimum Qfactor received."
        ::= { tnQfactorRawCountStatsEntry 2 }

    tnQfactorRawCountStatMax OBJECT-TYPE
        SYNTAX      Integer32
        UNITS       "0.01dB"
        MAX-ACCESS  read-only
        STATUS      current
        DESCRIPTION "Maximum Qfactor received."
        ::= { tnQfactorRawCountStatsEntry 3 }

    tnQfactorRawCountStatAverage OBJECT-TYPE
        SYNTAX      Integer32
        UNITS       "0.01dB"
        MAX-ACCESS  read-only
        STATUS      current
        DESCRIPTION "Average Qfactor received."
        ::= { tnQfactorRawCountStatsEntry 4 }

    tnQfactorRawCountStatStartTime OBJECT-TYPE
        SYNTAX      DateAndTime
        MAX-ACCESS  read-only
        STATUS      current
        DESCRIPTION "This attribute is the bin collection start date and time."
        ::= { tnQfactorRawCountStatsEntry 5 }

--------------------------------------------------------------------------------
-- OCHOPR Statistics Scalar
--------------------------------------------------------------------------------
    tnOchOprRawCountStatsTotalMembers OBJECT-TYPE
        SYNTAX      Integer32
        MAX-ACCESS  read-only
        STATUS      current
        DESCRIPTION "The total number of members in the OCHOPR raw count stats
                     table."
        ::= { tnStatisticsRawCounts 113 }

--------------------------------------------------------------------------------
-- OCHOPR Statistics Table
--------------------------------------------------------------------------------
    tnOchOprRawCountStatsTable OBJECT-TYPE
        SYNTAX      SEQUENCE OF TnOchOprRawCountStatsEntry
        MAX-ACCESS  not-accessible
        STATUS      current
        DESCRIPTION "."
        ::= { tnStatisticsRawCounts 114 }

    tnOchOprRawCountStatsEntry OBJECT-TYPE
        SYNTAX      TnOchOprRawCountStatsEntry
        MAX-ACCESS  not-accessible
        STATUS      current
        DESCRIPTION "."
        INDEX   { ifIndex }
        ::= { tnOchOprRawCountStatsTable 1 }

    TnOchOprRawCountStatsEntry ::=
        SEQUENCE {
            tnOchOprRawCountStatsClear           TnCommand,
            tnOchOprRawCountStatMinPower         Integer32,
            tnOchOprRawCountStatMaxPower         Integer32,
            tnOchOprRawCountStatAveragePower     Integer32,
            tnOchOprRawCountStatStartTime        DateAndTime
        }

    tnOchOprRawCountStatsClear OBJECT-TYPE
        SYNTAX      TnCommand
        MAX-ACCESS  read-create
        STATUS      current
        DESCRIPTION "This attribute is used to clear all the raw counts on a
                     particular interface and group."
        ::= { tnOchOprRawCountStatsEntry 1 }

    tnOchOprRawCountStatMinPower OBJECT-TYPE
        SYNTAX      Integer32
        UNITS       "mBm"
        MAX-ACCESS  read-only
        STATUS      current
        DESCRIPTION "."
        ::= { tnOchOprRawCountStatsEntry 2 }

    tnOchOprRawCountStatMaxPower OBJECT-TYPE
        SYNTAX      Integer32
        UNITS       "mBm"
        MAX-ACCESS  read-only
        STATUS      current
        DESCRIPTION "."
        ::= { tnOchOprRawCountStatsEntry 3 }

    tnOchOprRawCountStatAveragePower OBJECT-TYPE
        SYNTAX      Integer32
        UNITS       "mBm"
        MAX-ACCESS  read-only
        STATUS      current
        DESCRIPTION "."
        ::= { tnOchOprRawCountStatsEntry 4 }

    tnOchOprRawCountStatStartTime OBJECT-TYPE
        SYNTAX      DateAndTime
        MAX-ACCESS  read-only
        STATUS      current
        DESCRIPTION "This attribute is the bin collection start date and time."
        ::= { tnOchOprRawCountStatsEntry 5 }

--------------------------------------------------------------------------------
-- FcPkt Raw Count Statistics Scalar
--------------------------------------------------------------------------------
    tnFcPktRawCountStatsTotalMembers OBJECT-TYPE
        SYNTAX      Integer32
        MAX-ACCESS  read-only
        STATUS      current
        DESCRIPTION "The total number of members in the fcpkt raw count stats
                     table."
        ::= { tnStatisticsRawCounts 115 }

--------------------------------------------------------------------------------
-- FcPkt Raw Count Statistics Table
--------------------------------------------------------------------------------
    tnFcPktRawCountStatsTable OBJECT-TYPE
        SYNTAX      SEQUENCE OF TnFcPktRawCountStatsEntry
        MAX-ACCESS  not-accessible
        STATUS      current
        DESCRIPTION "."
        ::= { tnStatisticsRawCounts 116 }

    tnFcPktRawCountStatsEntry OBJECT-TYPE
        SYNTAX      TnFcPktRawCountStatsEntry
        MAX-ACCESS  not-accessible
        STATUS      current
        DESCRIPTION "."
        INDEX   { ifIndex }
        ::= { tnFcPktRawCountStatsTable 1 }

    TnFcPktRawCountStatsEntry ::=
        SEQUENCE {
            tnFcPktRawCountStatsClear             TnCommand,
            tnFcPktRawCountStatRxOctets           Counter64,
            tnFcPktRawCountStatRxPkts             Counter64,
            tnFcPktRawCountStatRxCrcAlignErrs     Counter64,
            tnFcPktRawCountStatTxOctets           Counter64,
            tnFcPktRawCountStatTxPkts             Counter64,
            tnFcPktRawCountStatTxCrcAlignErrs     Counter64,
            tnFcPktRawCountStatStartTime          DateAndTime
        }

    tnFcPktRawCountStatsClear OBJECT-TYPE
        SYNTAX      TnCommand
        MAX-ACCESS  read-create
        STATUS      current
        DESCRIPTION "This attribute is used to clear all the raw counts on a
                     particular interface and group."
        ::= { tnFcPktRawCountStatsEntry 1 }

    tnFcPktRawCountStatRxOctets OBJECT-TYPE
        SYNTAX      Counter64
        MAX-ACCESS  read-only
        STATUS      current
        DESCRIPTION "Provides a count of the total number of octets of data
                     (including the bad packets) received on the port.  Count
                     includes SOF delimiter,frame content, and an EOF delimiter
                     octets."
        ::= { tnFcPktRawCountStatsEntry 2 }

    tnFcPktRawCountStatRxPkts OBJECT-TYPE
        SYNTAX      Counter64
        MAX-ACCESS  read-only
        STATUS      current
        DESCRIPTION "Provides a count of the total number of packets (including
                     bad packet) received."
        ::= { tnFcPktRawCountStatsEntry 3 }

    tnFcPktRawCountStatRxCrcAlignErrs OBJECT-TYPE
        SYNTAX      Counter64
        MAX-ACCESS  read-only
        STATUS      current
        DESCRIPTION "Provides a count of the total number of packets received
                     that had CRC error."
        ::= { tnFcPktRawCountStatsEntry 4 }

    tnFcPktRawCountStatTxOctets OBJECT-TYPE
        SYNTAX      Counter64
        MAX-ACCESS  read-only
        STATUS      current
        DESCRIPTION "Provides a count of the total number of octets of data
                     (including the bad packets) transmited on the port.  Count
                     includes SOF delimiter,frame content, and an EOF delimiter
                     octets."
        ::= { tnFcPktRawCountStatsEntry 5 }

    tnFcPktRawCountStatTxPkts OBJECT-TYPE
        SYNTAX      Counter64
        MAX-ACCESS  read-only
        STATUS      current
        DESCRIPTION "Provides a count of the total number of packets (including
                     bad packet) transmited."
        ::= { tnFcPktRawCountStatsEntry 6 }

    tnFcPktRawCountStatTxCrcAlignErrs OBJECT-TYPE
        SYNTAX      Counter64
        MAX-ACCESS  read-only
        STATUS      current
        DESCRIPTION "Provides a count of the total number of packets transmited
                     that had CRC error."
        ::= { tnFcPktRawCountStatsEntry 7 }

    tnFcPktRawCountStatStartTime OBJECT-TYPE
        SYNTAX      DateAndTime
        MAX-ACCESS  read-only
        STATUS      current
        DESCRIPTION "This attribute is the bin collection start date and time."
        ::= { tnFcPktRawCountStatsEntry 8 }

--------------------------------------------------------------------------------
-- RX Statistics ODUk Threshold Scalars
--------------------------------------------------------------------------------
    tnOthOdu0StatRxNeBIP8ErrCnt15MinTr OBJECT-TYPE
        SYNTAX      Counter64
        MAX-ACCESS  read-only
        STATUS      current
        DESCRIPTION "15 minute threshold value for the number of ODU0
                     layer error blocks detected at near-end receiving
                     direction."
        ::= { tnStatisticsOdukRxScalars 1 }

    tnOthOdu0StatRxNeBIP8ErrCnt15MinRtr OBJECT-TYPE
        SYNTAX      Counter64
        MAX-ACCESS  read-only
        STATUS      current
        DESCRIPTION "15 minute reset threshold value for the number of
                     ODU0 layer error blocks detected at near-end
                     receiving direction."
        ::= { tnStatisticsOdukRxScalars 2 }

    tnOthOdu0StatRxNeBIP8ErrCnt1DayTr OBJECT-TYPE
        SYNTAX      Counter64
        MAX-ACCESS  read-only
        STATUS      current
        DESCRIPTION "1 day threshold value for the number of ODU0 layer
                     error blocks detected at near-end receiving direction."
        ::= { tnStatisticsOdukRxScalars 3 }

    tnOthOdu0StatRxFeBIP8ErrCnt15MinTr OBJECT-TYPE
        SYNTAX      Counter64
        MAX-ACCESS  read-only
        STATUS      current
        DESCRIPTION "15 minute threshold value for the number of ODU0
                     layer error blocks detected at far-end receiving
                     direction."
        ::= { tnStatisticsOdukRxScalars 4 }

    tnOthOdu0StatRxFeBIP8ErrCnt15MinRtr OBJECT-TYPE
        SYNTAX      Counter64
        MAX-ACCESS  read-only
        STATUS      current
        DESCRIPTION "15 minute reset threshold value for the number of
                     ODU0 layer error blocks detected at far-end receiving
                     direction."
        ::= { tnStatisticsOdukRxScalars 5 }

    tnOthOdu0StatRxFeBIP8ErrCnt1DayTr OBJECT-TYPE
        SYNTAX      Counter64
        MAX-ACCESS  read-only
        STATUS      current
        DESCRIPTION "1 day threshold value for the number of ODU0 layer
                     error blocks detected at far-end receiving direction."
        ::= { tnStatisticsOdukRxScalars 6 }

    tnOthOdu1StatRxNeBIP8ErrCnt15MinTr OBJECT-TYPE
        SYNTAX      Counter64
        MAX-ACCESS  read-only
        STATUS      current
        DESCRIPTION "15 minute threshold value for the number of ODU1
                     layer error blocks detected at near-end receiving
                     direction."
        ::= { tnStatisticsOdukRxScalars 7 }

    tnOthOdu1StatRxNeBIP8ErrCnt15MinRtr OBJECT-TYPE
        SYNTAX      Counter64
        MAX-ACCESS  read-only
        STATUS      current
        DESCRIPTION "15 minute reset threshold value for the number of
                     ODU1 layer error blocks detected at near-end
                     receiving direction."
        ::= { tnStatisticsOdukRxScalars 8 }

    tnOthOdu1StatRxNeBIP8ErrCnt1DayTr OBJECT-TYPE
        SYNTAX      Counter64
        MAX-ACCESS  read-only
        STATUS      current
        DESCRIPTION "1 day threshold value for the number of ODU1 layer
                     error blocks detected at near-end receiving direction."
        ::= { tnStatisticsOdukRxScalars 9 }

    tnOthOdu1StatRxFeBIP8ErrCnt15MinTr OBJECT-TYPE
        SYNTAX      Counter64
        MAX-ACCESS  read-only
        STATUS      current
        DESCRIPTION "15 minute threshold value for the number of ODU1
                     layer error blocks detected at far-end receiving
                     direction."
        ::= { tnStatisticsOdukRxScalars 10 }

    tnOthOdu1StatRxFeBIP8ErrCnt15MinRtr OBJECT-TYPE
        SYNTAX      Counter64
        MAX-ACCESS  read-only
        STATUS      current
        DESCRIPTION "15 minute reset threshold value for the number of
                     ODU1 layer error blocks detected at far-end receiving
                     direction."
        ::= { tnStatisticsOdukRxScalars 11 }

    tnOthOdu1StatRxFeBIP8ErrCnt1DayTr OBJECT-TYPE
        SYNTAX      Counter64
        MAX-ACCESS  read-only
        STATUS      current
        DESCRIPTION "1 day threshold value for the number of ODU1 layer
                     error blocks detected at far-end receiving direction."
        ::= { tnStatisticsOdukRxScalars 12 }

    tnOthOdu2StatRxNeBIP8ErrCnt15MinTr OBJECT-TYPE
        SYNTAX      Counter64
        MAX-ACCESS  read-only
        STATUS      current
        DESCRIPTION "15 minute threshold value for the number of ODU2
                     layer error blocks detected at near-end receiving
                     direction."
        ::= { tnStatisticsOdukRxScalars 13 }

    tnOthOdu2StatRxNeBIP8ErrCnt15MinRtr OBJECT-TYPE
        SYNTAX      Counter64
        MAX-ACCESS  read-only
        STATUS      current
        DESCRIPTION "15 minute reset threshold value for the number of
                     ODU2 layer error blocks detected at near-end
                     receiving direction."
        ::= { tnStatisticsOdukRxScalars 14 }

    tnOthOdu2StatRxNeBIP8ErrCnt1DayTr OBJECT-TYPE
        SYNTAX      Counter64
        MAX-ACCESS  read-only
        STATUS      current
        DESCRIPTION "1 day threshold value for the number of ODU2 layer
                     error blocks detected at near-end receiving direction."
        ::= { tnStatisticsOdukRxScalars 15 }

    tnOthOdu2StatRxFeBIP8ErrCnt15MinTr OBJECT-TYPE
        SYNTAX      Counter64
        MAX-ACCESS  read-only
        STATUS      current
        DESCRIPTION "15 minute threshold value for the number of ODU2
                     layer error blocks detected at far-end receiving
                     direction."
        ::= { tnStatisticsOdukRxScalars 16 }

    tnOthOdu2StatRxFeBIP8ErrCnt15MinRtr OBJECT-TYPE
        SYNTAX      Counter64
        MAX-ACCESS  read-only
        STATUS      current
        DESCRIPTION "15 minute reset threshold value for the number of
                     ODU2 layer error blocks detected at far-end receiving
                     direction."
        ::= { tnStatisticsOdukRxScalars 17 }

    tnOthOdu2StatRxFeBIP8ErrCnt1DayTr OBJECT-TYPE
        SYNTAX      Counter64
        MAX-ACCESS  read-only
        STATUS      current
        DESCRIPTION "1 day threshold value for the number of ODU2 layer
                     error blocks detected at far-end receiving direction."
        ::= { tnStatisticsOdukRxScalars 18 }

    tnOthOdu3StatRxNeBIP8ErrCnt15MinTr OBJECT-TYPE
        SYNTAX      Counter64
        MAX-ACCESS  read-only
        STATUS      current
        DESCRIPTION "15 minute threshold value for the number of ODU3
                     layer error blocks detected at near-end receiving
                     direction."
        ::= { tnStatisticsOdukRxScalars 19 }

    tnOthOdu3StatRxNeBIP8ErrCnt15MinRtr OBJECT-TYPE
        SYNTAX      Counter64
        MAX-ACCESS  read-only
        STATUS      current
        DESCRIPTION "15 minute reset threshold value for the number of
                     ODU3 layer error blocks detected at near-end
                     receiving direction."
        ::= { tnStatisticsOdukRxScalars 20 }

    tnOthOdu3StatRxNeBIP8ErrCnt1DayTr OBJECT-TYPE
        SYNTAX      Counter64
        MAX-ACCESS  read-only
        STATUS      current
        DESCRIPTION "1 day threshold value for the number of ODU3 layer
                     error blocks detected at near-end receiving direction."
        ::= { tnStatisticsOdukRxScalars 21 }

    tnOthOdu3StatRxFeBIP8ErrCnt15MinTr OBJECT-TYPE
        SYNTAX      Counter64
        MAX-ACCESS  read-only
        STATUS      current
        DESCRIPTION "15 minute threshold value for the number of ODU3
                     layer error blocks detected at far-end receiving
                     direction."
        ::= { tnStatisticsOdukRxScalars 22 }

    tnOthOdu3StatRxFeBIP8ErrCnt15MinRtr OBJECT-TYPE
        SYNTAX      Counter64
        MAX-ACCESS  read-only
        STATUS      current
        DESCRIPTION "15 minute reset threshold value for the number of
                     ODU3 layer error blocks detected at far-end receiving
                     direction."
        ::= { tnStatisticsOdukRxScalars 23 }

    tnOthOdu3StatRxFeBIP8ErrCnt1DayTr OBJECT-TYPE
        SYNTAX      Counter64
        MAX-ACCESS  read-only
        STATUS      current
        DESCRIPTION "1 day threshold value for the number of ODU3 layer
                     error blocks detected at far-end receiving direction."
        ::= { tnStatisticsOdukRxScalars 24 }

    tnOthOdu4StatRxNeBIP8ErrCnt15MinTr OBJECT-TYPE
        SYNTAX      Counter64
        MAX-ACCESS  read-only
        STATUS      current
        DESCRIPTION "15 minute threshold value for the number of ODU4
                     layer error blocks detected at near-end receiving
                     direction."
        ::= { tnStatisticsOdukRxScalars 25 }

    tnOthOdu4StatRxNeBIP8ErrCnt15MinRtr OBJECT-TYPE
        SYNTAX      Counter64
        MAX-ACCESS  read-only
        STATUS      current
        DESCRIPTION "15 minute reset threshold value for the number of
                     ODU4 layer error blocks detected at near-end
                     receiving direction."
        ::= { tnStatisticsOdukRxScalars 26 }

    tnOthOdu4StatRxNeBIP8ErrCnt1DayTr OBJECT-TYPE
        SYNTAX      Counter64
        MAX-ACCESS  read-only
        STATUS      current
        DESCRIPTION "1 day threshold value for the number of ODU4 layer
                     error blocks detected at near-end receiving direction."
        ::= { tnStatisticsOdukRxScalars 27 }

    tnOthOdu4StatRxFeBIP8ErrCnt15MinTr OBJECT-TYPE
        SYNTAX      Counter64
        MAX-ACCESS  read-only
        STATUS      current
        DESCRIPTION "15 minute threshold value for the number of ODU4
                     layer error blocks detected at far-end receiving
                     direction."
        ::= { tnStatisticsOdukRxScalars 28 }

    tnOthOdu4StatRxFeBIP8ErrCnt15MinRtr OBJECT-TYPE
        SYNTAX      Counter64
        MAX-ACCESS  read-only
        STATUS      current
        DESCRIPTION "15 minute reset threshold value for the number of
                     ODU4 layer error blocks detected at far-end receiving
                     direction."
        ::= { tnStatisticsOdukRxScalars 29 }

    tnOthOdu4StatRxFeBIP8ErrCnt1DayTr OBJECT-TYPE
        SYNTAX      Counter64
        MAX-ACCESS  read-only
        STATUS      current
        DESCRIPTION "1 day threshold value for the number of ODU4 layer
                     error blocks detected at far-end receiving direction."
        ::= { tnStatisticsOdukRxScalars 30 }

    tnOthOdukStatRxNeES15MinTr OBJECT-TYPE
        SYNTAX      Counter64
        MAX-ACCESS  read-only
        STATUS      current
        DESCRIPTION "15 minute threshold value for errored seconds
                     detected at near-end receiving direction."
        ::= { tnStatisticsOdukRxScalars 31 }

    tnOthOdukStatRxNeES15MinRtr OBJECT-TYPE
        SYNTAX      Counter64
        MAX-ACCESS  read-only
        STATUS      current
        DESCRIPTION "15 minute reset threshold value for errored seconds
                     detected at near-end receiving direction."
        ::= { tnStatisticsOdukRxScalars 32 }

    tnOthOdukStatRxNeES1DayTr OBJECT-TYPE
        SYNTAX      Counter64
        MAX-ACCESS  read-only
        STATUS      current
        DESCRIPTION "1 day threshold value for errored seconds detected
                     at near-end receiving direction."
        ::= { tnStatisticsOdukRxScalars 33 }

    tnOthOdukStatRxFeES15MinTr OBJECT-TYPE
        SYNTAX      Counter64
        MAX-ACCESS  read-only
        STATUS      current
        DESCRIPTION "15 minute threshold value for errored seconds
                     detected at far-end receiving direction."
        ::= { tnStatisticsOdukRxScalars 34 }

    tnOthOdukStatRxFeES15MinRtr OBJECT-TYPE
        SYNTAX      Counter64
        MAX-ACCESS  read-only
        STATUS      current
        DESCRIPTION "15 minute reset threshold value for errored seconds
                     detected at far-end receiving direction."
        ::= { tnStatisticsOdukRxScalars 35 }

    tnOthOdukStatRxFeES1DayTr OBJECT-TYPE
        SYNTAX      Counter64
        MAX-ACCESS  read-only
        STATUS      current
        DESCRIPTION "1 day threshold value for errored seconds detected
                     at far-end receiving direction."
        ::= { tnStatisticsOdukRxScalars 36 }

    tnOthOdukStatRxNeSES15MinTr OBJECT-TYPE
        SYNTAX      Counter64
        MAX-ACCESS  read-only
        STATUS      current
        DESCRIPTION "15 minute threshold value for severely errored
                     seconds detected at near-end receiving direction."
        ::= { tnStatisticsOdukRxScalars 37 }

    tnOthOdukStatRxNeSES15MinRtr OBJECT-TYPE
        SYNTAX      Counter64
        MAX-ACCESS  read-only
        STATUS      current
        DESCRIPTION "15 minute reset threshold value for severely errored
                     seconds detected at near-end receiving direction."
        ::= { tnStatisticsOdukRxScalars 38 }

    tnOthOdukStatRxNeSES1DayTr OBJECT-TYPE
        SYNTAX      Counter64
        MAX-ACCESS  read-only
        STATUS      current
        DESCRIPTION "1 day threshold value for severely errored seconds
                     detected at near-end receiving direction."
        ::= { tnStatisticsOdukRxScalars 39 }

    tnOthOdukStatRxFeSES15MinTr OBJECT-TYPE
        SYNTAX      Counter64
        MAX-ACCESS  read-only
        STATUS      current
        DESCRIPTION "15 minute threshold value for severely errored
                     seconds detected at far-end receiving direction."
        ::= { tnStatisticsOdukRxScalars 40 }

    tnOthOdukStatRxFeSES15MinRtr OBJECT-TYPE
        SYNTAX      Counter64
        MAX-ACCESS  read-only
        STATUS      current
        DESCRIPTION "15 minute reset threshold value for severely errored
                     seconds detected at far-end receiving direction."
        ::= { tnStatisticsOdukRxScalars 41 }

    tnOthOdukStatRxFeSES1DayTr OBJECT-TYPE
        SYNTAX      Counter64
        MAX-ACCESS  read-only
        STATUS      current
        DESCRIPTION "1 day threshold value for severely errored seconds
                     detected at far-end receiving direction."
        ::= { tnStatisticsOdukRxScalars 42 }

    tnOthOdukStatRxNeUAS15MinTr OBJECT-TYPE
        SYNTAX      Counter64
        MAX-ACCESS  read-only
        STATUS      current
        DESCRIPTION "15 minute threshold value for unavailable errored
                     seconds detected at near-end receiving direction."
        ::= { tnStatisticsOdukRxScalars 43 }

    tnOthOdukStatRxNeUAS15MinRtr OBJECT-TYPE
        SYNTAX      Counter64
        MAX-ACCESS  read-only
        STATUS      current
        DESCRIPTION "15 minute reset threshold value for unavailable
                     errored seconds detected at near-end receiving
                     direction."
        ::= { tnStatisticsOdukRxScalars 44 }

    tnOthOdukStatRxNeUAS1DayTr OBJECT-TYPE
        SYNTAX      Counter64
        MAX-ACCESS  read-only
        STATUS      current
        DESCRIPTION "1 day threshold value for unavailable errored
                     seconds detected at near-end receiving direction."
        ::= { tnStatisticsOdukRxScalars 45 }

    tnOthOdukStatRxFeUAS15MinTr OBJECT-TYPE
        SYNTAX      Counter64
        MAX-ACCESS  read-only
        STATUS      current
        DESCRIPTION "15 minute threshold value for unavailable errored
                     seconds detected at far-end receiving direction."
        ::= { tnStatisticsOdukRxScalars 46 }

    tnOthOdukStatRxFeUAS15MinRtr OBJECT-TYPE
        SYNTAX      Counter64
        MAX-ACCESS  read-only
        STATUS      current
        DESCRIPTION "15 minute reset threshold value for unavailable
                     errored seconds detected at far-end receiving direction."
        ::= { tnStatisticsOdukRxScalars 47 }

    tnOthOdukStatRxFeUAS1DayTr OBJECT-TYPE
        SYNTAX      Counter64
        MAX-ACCESS  read-only
        STATUS      current
        DESCRIPTION "1 day threshold value for unavailable errored
                     seconds detected at far-end receiving direction."
        ::= { tnStatisticsOdukRxScalars 48 }

    tnOthOduflexGFPRxNeBIP8ErrCnt15MinTr OBJECT-TYPE
        SYNTAX      Counter64
        MAX-ACCESS  read-only
        STATUS      current
        DESCRIPTION "15 minute threshold value for the number of OduflexGFP
                     layer error blocks detected at near-end receiving
                     direction."
        ::= { tnStatisticsOdukRxScalars 49 }

    tnOthOduflexGFPRxNeBIP8ErrCnt15MinRtr OBJECT-TYPE
        SYNTAX      Counter64
        MAX-ACCESS  read-only
        STATUS      current
        DESCRIPTION "15 minute reset threshold value for the number of
                     OduflexGFP layer error blocks detected at near-end
                     receiving direction."
        ::= { tnStatisticsOdukRxScalars 50 }

    tnOthOduflexGFPRxNeBIP8ErrCnt1DayTr OBJECT-TYPE
        SYNTAX      Counter64
        MAX-ACCESS  read-only
        STATUS      current
        DESCRIPTION "1 day threshold value for the number of OduflexGFP layer
                     error blocks detected at near-end receiving
                     direction."
        ::= { tnStatisticsOdukRxScalars 51 }

    tnOthOduflexGFPRxFeBIP8ErrCnt15MinTr OBJECT-TYPE
        SYNTAX      Counter64
        MAX-ACCESS  read-only
        STATUS      current
        DESCRIPTION "15 minute threshold value for the number of OduflexGFP
                     layer error blocks detected at far-end receiving
                     direction."
        ::= { tnStatisticsOdukRxScalars 52 }

    tnOthOduflexGFPRxFeBIP8ErrCnt15MinRtr OBJECT-TYPE
        SYNTAX      Counter64
        MAX-ACCESS  read-only
        STATUS      current
        DESCRIPTION "15 minute reset threshold value for the number of
                     OduflexGFP layer error blocks detected at far-end
                     receiving direction."
        ::= { tnStatisticsOdukRxScalars 53 }

    tnOthOduflexGFPRxFeBIP8ErrCnt1DayTr OBJECT-TYPE
        SYNTAX      Counter64
        MAX-ACCESS  read-only
        STATUS      current
        DESCRIPTION "1 day threshold value for the number of OduflexGFP layer
                     error blocks detected at far-end receiving
                     direction."
        ::= { tnStatisticsOdukRxScalars 54 }

    tnOthOduflexFC400RxNeBIP8ErrCnt15MinTr OBJECT-TYPE
        SYNTAX      Counter64
        MAX-ACCESS  read-only
        STATUS      current
        DESCRIPTION "15 minute threshold value for the number of OduflexFC400
                     layer error blocks detected at near-end receiving
                     direction."
        ::= { tnStatisticsOdukRxScalars 55 }

    tnOthOduflexFC400RxNeBIP8ErrCnt15MinRtr OBJECT-TYPE
        SYNTAX      Counter64
        MAX-ACCESS  read-only
        STATUS      current
        DESCRIPTION "15 minute reset threshold value for the number of
                     OduflexFC400 layer error blocks detected at near-end
                     receiving direction."
        ::= { tnStatisticsOdukRxScalars 56 }

    tnOthOduflexFC400RxNeBIP8ErrCnt1DayTr OBJECT-TYPE
        SYNTAX      Counter64
        MAX-ACCESS  read-only
        STATUS      current
        DESCRIPTION "1 day threshold value for the number of OduflexFC400 layer
                     error blocks detected at near-end receiving
                     direction."
        ::= { tnStatisticsOdukRxScalars 57 }

    tnOthOduflexFC400RxFeBIP8ErrCnt15MinTr OBJECT-TYPE
        SYNTAX      Counter64
        MAX-ACCESS  read-only
        STATUS      current
        DESCRIPTION "15 minute threshold value for the number of OduflexFC400
                     layer error blocks detected at far-end receiving
                     direction."
        ::= { tnStatisticsOdukRxScalars 58 }

    tnOthOduflexFC400RxFeBIP8ErrCnt15MinRtr OBJECT-TYPE
        SYNTAX      Counter64
        MAX-ACCESS  read-only
        STATUS      current
        DESCRIPTION "15 minute reset threshold value for the number of
                     OduflexFC400 layer error blocks detected at far-end
                     receiving direction."
        ::= { tnStatisticsOdukRxScalars 59 }

    tnOthOduflexFC400RxFeBIP8ErrCnt1DayTr OBJECT-TYPE
        SYNTAX      Counter64
        MAX-ACCESS  read-only
        STATUS      current
        DESCRIPTION "1 day threshold value for the number of OduflexFC400 layer
                     error blocks detected at far-end receiving
                     direction."
        ::= { tnStatisticsOdukRxScalars 60 }

    tnOthOduflexFC800RxNeBIP8ErrCnt15MinTr OBJECT-TYPE
        SYNTAX      Counter64
        MAX-ACCESS  read-only
        STATUS      current
        DESCRIPTION "15 minute threshold value for the number of OduflexFC800
                     layer error blocks detected at near-end receiving
                     direction."
        ::= { tnStatisticsOdukRxScalars 61 }

    tnOthOduflexFC800RxNeBIP8ErrCnt15MinRtr OBJECT-TYPE
        SYNTAX      Counter64
        MAX-ACCESS  read-only
        STATUS      current
        DESCRIPTION "15 minute reset threshold value for the number of
                     OduflexFC800 layer error blocks detected at near-end
                     receiving direction."
        ::= { tnStatisticsOdukRxScalars 62 }

    tnOthOduflexFC800RxNeBIP8ErrCnt1DayTr OBJECT-TYPE
        SYNTAX      Counter64
        MAX-ACCESS  read-only
        STATUS      current
        DESCRIPTION "1 day threshold value for the number of OduflexFC800 layer
                     error blocks detected at near-end receiving
                     direction."
        ::= { tnStatisticsOdukRxScalars 63 }

    tnOthOduflexFC800RxFeBIP8ErrCnt15MinTr OBJECT-TYPE
        SYNTAX      Counter64
        MAX-ACCESS  read-only
        STATUS      current
        DESCRIPTION "15 minute threshold value for the number of OduflexFC800
                     layer error blocks detected at far-end receiving
                     direction."
        ::= { tnStatisticsOdukRxScalars 64 }

    tnOthOduflexFC800RxFeBIP8ErrCnt15MinRtr OBJECT-TYPE
        SYNTAX      Counter64
        MAX-ACCESS  read-only
        STATUS      current
        DESCRIPTION "15 minute reset threshold value for the number of
                     OduflexFC800 layer error blocks detected at far-end
                     receiving direction."
        ::= { tnStatisticsOdukRxScalars 65 }

    tnOthOduflexFC800RxFeBIP8ErrCnt1DayTr OBJECT-TYPE
        SYNTAX      Counter64
        MAX-ACCESS  read-only
        STATUS      current
        DESCRIPTION "1 day threshold value for the number of OduflexFC800 layer
                     error blocks detected at far-end receiving
                     direction."
        ::= { tnStatisticsOdukRxScalars 66 }

    tnOthOduflexFC1600RxNeBIP8ErrCnt15MinTr OBJECT-TYPE
        SYNTAX      Counter64
        MAX-ACCESS  read-only
        STATUS      current
        DESCRIPTION "15 minute threshold value for the number of OduflexFC1600
                     layer error blocks detected at near-end receiving
                     direction."
        ::= { tnStatisticsOdukRxScalars 67 }

    tnOthOduflexFC1600RxNeBIP8ErrCnt15MinRtr OBJECT-TYPE
        SYNTAX      Counter64
        MAX-ACCESS  read-only
        STATUS      current
        DESCRIPTION "15 minute reset threshold value for the number of
                     OduflexFC1600 layer error blocks detected at near-end
                     receiving direction."
        ::= { tnStatisticsOdukRxScalars 68 }

    tnOthOduflexFC1600RxNeBIP8ErrCnt1DayTr OBJECT-TYPE
        SYNTAX      Counter64
        MAX-ACCESS  read-only
        STATUS      current
        DESCRIPTION "1 day threshold value for the number of OduflexFC1600 layer
                     error blocks detected at near-end receiving
                     direction."
        ::= { tnStatisticsOdukRxScalars 69 }

    tnOthOduflexFC1600RxFeBIP8ErrCnt15MinTr OBJECT-TYPE
        SYNTAX      Counter64
        MAX-ACCESS  read-only
        STATUS      current
        DESCRIPTION "15 minute threshold value for the number of OduflexFC1600
                     layer error blocks detected at far-end receiving
                     direction."
        ::= { tnStatisticsOdukRxScalars 70 }

    tnOthOduflexFC1600RxFeBIP8ErrCnt15MinRtr OBJECT-TYPE
        SYNTAX      Counter64
        MAX-ACCESS  read-only
        STATUS      current
        DESCRIPTION "15 minute reset threshold value for the number of
                     OduflexFC1600 layer error blocks detected at far-end
                     receiving direction."
        ::= { tnStatisticsOdukRxScalars 71 }

    tnOthOduflexFC1600RxFeBIP8ErrCnt1DayTr OBJECT-TYPE
        SYNTAX      Counter64
        MAX-ACCESS  read-only
        STATUS      current
        DESCRIPTION "1 day threshold value for the number of OduflexFC1600 layer
                     error blocks detected at far-end receiving
                     direction."
        ::= { tnStatisticsOdukRxScalars 72 }

    tnOthOduflexIBSDRRxNeBIP8ErrCnt15MinTr OBJECT-TYPE
        SYNTAX      Counter64
        MAX-ACCESS  read-only
        STATUS      current
        DESCRIPTION "15 minute threshold value for the number of OduflexIBSDR
                     layer error blocks detected at near-end receiving
                     direction."
        ::= { tnStatisticsOdukRxScalars 73 }

    tnOthOduflexIBSDRRxNeBIP8ErrCnt15MinRtr OBJECT-TYPE
        SYNTAX      Counter64
        MAX-ACCESS  read-only
        STATUS      current
        DESCRIPTION "15 minute reset threshold value for the number of
                     OduflexIBSDR layer error blocks detected at near-end
                     receiving direction."
        ::= { tnStatisticsOdukRxScalars 74 }

    tnOthOduflexIBSDRRxNeBIP8ErrCnt1DayTr OBJECT-TYPE
        SYNTAX      Counter64
        MAX-ACCESS  read-only
        STATUS      current
        DESCRIPTION "1 day threshold value for the number of OduflexIBSDR layer
                     error blocks detected at near-end receiving
                     direction."
        ::= { tnStatisticsOdukRxScalars 75 }

    tnOthOduflexIBSDRRxFeBIP8ErrCnt15MinTr OBJECT-TYPE
        SYNTAX      Counter64
        MAX-ACCESS  read-only
        STATUS      current
        DESCRIPTION "15 minute threshold value for the number of OduflexIBSDR
                     layer error blocks detected at far-end receiving
                     direction."
        ::= { tnStatisticsOdukRxScalars 76 }

    tnOthOduflexIBSDRRxFeBIP8ErrCnt15MinRtr OBJECT-TYPE
        SYNTAX      Counter64
        MAX-ACCESS  read-only
        STATUS      current
        DESCRIPTION "15 minute reset threshold value for the number of
                     OduflexIBSDR layer error blocks detected at far-end
                     receiving direction."
        ::= { tnStatisticsOdukRxScalars 77 }

    tnOthOduflexIBSDRRxFeBIP8ErrCnt1DayTr OBJECT-TYPE
        SYNTAX      Counter64
        MAX-ACCESS  read-only
        STATUS      current
        DESCRIPTION "1 day threshold value for the number of OduflexIBSDR layer
                     error blocks detected at far-end receiving
                     direction."
        ::= { tnStatisticsOdukRxScalars 78 }

    tnOthOduflexIBDDRRxNeBIP8ErrCnt15MinTr OBJECT-TYPE
        SYNTAX      Counter64
        MAX-ACCESS  read-only
        STATUS      current
        DESCRIPTION "15 minute threshold value for the number of OduflexIBDDR
                     layer error blocks detected at near-end receiving
                     direction."
        ::= { tnStatisticsOdukRxScalars 79 }

    tnOthOduflexIBDDRRxNeBIP8ErrCnt15MinRtr OBJECT-TYPE
        SYNTAX      Counter64
        MAX-ACCESS  read-only
        STATUS      current
        DESCRIPTION "15 minute reset threshold value for the number of
                     OduflexIBDDR layer error blocks detected at near-end
                     receiving direction."
        ::= { tnStatisticsOdukRxScalars 80 }

    tnOthOduflexIBDDRRxNeBIP8ErrCnt1DayTr OBJECT-TYPE
        SYNTAX      Counter64
        MAX-ACCESS  read-only
        STATUS      current
        DESCRIPTION "1 day threshold value for the number of OduflexIBDDR layer
                     error blocks detected at near-end receiving
                     direction."
        ::= { tnStatisticsOdukRxScalars 81 }

    tnOthOduflexIBDDRRxFeBIP8ErrCnt15MinTr OBJECT-TYPE
        SYNTAX      Counter64
        MAX-ACCESS  read-only
        STATUS      current
        DESCRIPTION "15 minute threshold value for the number of OduflexIBDDR
                     layer error blocks detected at far-end receiving
                     direction."
        ::= { tnStatisticsOdukRxScalars 82 }

    tnOthOduflexIBDDRRxFeBIP8ErrCnt15MinRtr OBJECT-TYPE
        SYNTAX      Counter64
        MAX-ACCESS  read-only
        STATUS      current
        DESCRIPTION "15 minute reset threshold value for the number of
                     OduflexIBDDR layer error blocks detected at far-end
                     receiving direction."
        ::= { tnStatisticsOdukRxScalars 83 }

    tnOthOduflexIBDDRRxFeBIP8ErrCnt1DayTr OBJECT-TYPE
        SYNTAX      Counter64
        MAX-ACCESS  read-only
        STATUS      current
        DESCRIPTION "1 day threshold value for the number of OduflexIBDDR layer
                     error blocks detected at far-end receiving
                     direction."
        ::= { tnStatisticsOdukRxScalars 84 }

    tnOthOduflexIBQDRRxNeBIP8ErrCnt15MinTr OBJECT-TYPE
        SYNTAX      Counter64
        MAX-ACCESS  read-only
        STATUS      current
        DESCRIPTION "15 minute threshold value for the number of OduflexIBQDR
                     layer error blocks detected at near-end receiving
                     direction."
        ::= { tnStatisticsOdukRxScalars 85 }

    tnOthOduflexIBQDRRxNeBIP8ErrCnt15MinRtr OBJECT-TYPE
        SYNTAX      Counter64
        MAX-ACCESS  read-only
        STATUS      current
        DESCRIPTION "15 minute reset threshold value for the number of
                     OduflexIBQDR layer error blocks detected at near-end
                     receiving direction."
        ::= { tnStatisticsOdukRxScalars 86 }

    tnOthOduflexIBQDRRxNeBIP8ErrCnt1DayTr OBJECT-TYPE
        SYNTAX      Counter64
        MAX-ACCESS  read-only
        STATUS      current
        DESCRIPTION "1 day threshold value for the number of OduflexIBQDR layer
                     error blocks detected at near-end receiving
                     direction."
        ::= { tnStatisticsOdukRxScalars 87 }

    tnOthOduflexIBQDRRxFeBIP8ErrCnt15MinTr OBJECT-TYPE
        SYNTAX      Counter64
        MAX-ACCESS  read-only
        STATUS      current
        DESCRIPTION "15 minute threshold value for the number of OduflexIBQDR
                     layer error blocks detected at far-end receiving
                     direction."
        ::= { tnStatisticsOdukRxScalars 88 }

    tnOthOduflexIBQDRRxFeBIP8ErrCnt15MinRtr OBJECT-TYPE
        SYNTAX      Counter64
        MAX-ACCESS  read-only
        STATUS      current
        DESCRIPTION "15 minute reset threshold value for the number of
                     OduflexIBQDR layer error blocks detected at far-end
                     receiving direction."
        ::= { tnStatisticsOdukRxScalars 89 }

    tnOthOduflexIBQDRRxFeBIP8ErrCnt1DayTr OBJECT-TYPE
        SYNTAX      Counter64
        MAX-ACCESS  read-only
        STATUS      current
        DESCRIPTION "1 day threshold value for the number of OduflexIBQDR layer
                     error blocks detected at far-end receiving
                     direction."
        ::= { tnStatisticsOdukRxScalars 90 }

    tnOthOduflex3GSDI18RxNeBIP8ErrCnt15MinTr OBJECT-TYPE
        SYNTAX      Counter64
        MAX-ACCESS  read-only
        STATUS      current
        DESCRIPTION "15 minute threshold value for the number of Oduflex3GSDI18
                     layer error blocks detected at near-end receiving
                     direction."
        ::= { tnStatisticsOdukRxScalars 91 }

    tnOthOduflex3GSDI18RxNeBIP8ErrCnt15MinRtr OBJECT-TYPE
        SYNTAX      Counter64
        MAX-ACCESS  read-only
        STATUS      current
        DESCRIPTION "15 minute reset threshold value for the number of
                     Oduflex3GSDI18 layer error blocks detected at near-end
                     receiving direction."
        ::= { tnStatisticsOdukRxScalars 92 }

    tnOthOduflex3GSDI18RxNeBIP8ErrCnt1DayTr OBJECT-TYPE
        SYNTAX      Counter64
        MAX-ACCESS  read-only
        STATUS      current
        DESCRIPTION "1 day threshold value for the number of Oduflex3GSDI18 layer
                     error blocks detected at near-end receiving
                     direction."
        ::= { tnStatisticsOdukRxScalars 93 }

    tnOthOduflex3GSDI18RxFeBIP8ErrCnt15MinTr OBJECT-TYPE
        SYNTAX      Counter64
        MAX-ACCESS  read-only
        STATUS      current
        DESCRIPTION "15 minute threshold value for the number of Oduflex3GSDI18
                     layer error blocks detected at far-end receiving
                     direction."
        ::= { tnStatisticsOdukRxScalars 94 }

    tnOthOduflex3GSDI18RxFeBIP8ErrCnt15MinRtr OBJECT-TYPE
        SYNTAX      Counter64
        MAX-ACCESS  read-only
        STATUS      current
        DESCRIPTION "15 minute reset threshold value for the number of
                     Oduflex3GSDI18 layer error blocks detected at far-end
                     receiving direction."
        ::= { tnStatisticsOdukRxScalars 95 }

    tnOthOduflex3GSDI18RxFeBIP8ErrCnt1DayTr OBJECT-TYPE
        SYNTAX      Counter64
        MAX-ACCESS  read-only
        STATUS      current
        DESCRIPTION "1 day threshold value for the number of Oduflex3GSDI18 layer
                     error blocks detected at far-end receiving
                     direction."
        ::= { tnStatisticsOdukRxScalars 96 }

    tnOthOduflex3GSDI19RxNeBIP8ErrCnt15MinTr OBJECT-TYPE
        SYNTAX      Counter64
        MAX-ACCESS  read-only
        STATUS      current
        DESCRIPTION "15 minute threshold value for the number of Oduflex3GSDI19
                     layer error blocks detected at near-end receiving
                     direction."
        ::= { tnStatisticsOdukRxScalars 97 }

    tnOthOduflex3GSDI19RxNeBIP8ErrCnt15MinRtr OBJECT-TYPE
        SYNTAX      Counter64
        MAX-ACCESS  read-only
        STATUS      current
        DESCRIPTION "15 minute reset threshold value for the number of
                     Oduflex3GSDI19 layer error blocks detected at near-end
                     receiving direction."
        ::= { tnStatisticsOdukRxScalars 98 }

    tnOthOduflex3GSDI19RxNeBIP8ErrCnt1DayTr OBJECT-TYPE
        SYNTAX      Counter64
        MAX-ACCESS  read-only
        STATUS      current
        DESCRIPTION "1 day threshold value for the number of Oduflex3GSDI19 layer
                     error blocks detected at near-end receiving
                     direction."
        ::= { tnStatisticsOdukRxScalars 99 }

    tnOthOduflex3GSDI19RxFeBIP8ErrCnt15MinTr OBJECT-TYPE
        SYNTAX      Counter64
        MAX-ACCESS  read-only
        STATUS      current
        DESCRIPTION "15 minute threshold value for the number of Oduflex3GSDI19
                     layer error blocks detected at far-end receiving
                     direction."
        ::= { tnStatisticsOdukRxScalars 100 }

    tnOthOduflex3GSDI19RxFeBIP8ErrCnt15MinRtr OBJECT-TYPE
        SYNTAX      Counter64
        MAX-ACCESS  read-only
        STATUS      current
        DESCRIPTION "15 minute reset threshold value for the number of
                     Oduflex3GSDI19 layer error blocks detected at far-end
                     receiving direction."
        ::= { tnStatisticsOdukRxScalars 101 }

    tnOthOduflex3GSDI19RxFeBIP8ErrCnt1DayTr OBJECT-TYPE
        SYNTAX      Counter64
        MAX-ACCESS  read-only
        STATUS      current
        DESCRIPTION "1 day threshold value for the number of Oduflex3GSDI19 layer
                     error blocks detected at far-end receiving
                     direction."
        ::= { tnStatisticsOdukRxScalars 102 }

    tnOthOducStatRxNeBIP8ErrCnt15MinTr OBJECT-TYPE
        SYNTAX      Counter64
        MAX-ACCESS  read-only
        STATUS      current
        DESCRIPTION "."
        ::= { tnStatisticsOdukRxScalars 103 }

    tnOthOducStatRxNeBIP8ErrCnt15MinRtr OBJECT-TYPE
        SYNTAX      Counter64
        MAX-ACCESS  read-only
        STATUS      current
        DESCRIPTION "."
        ::= { tnStatisticsOdukRxScalars 104 }

    tnOthOducStatRxNeBIP8ErrCnt1DayTr OBJECT-TYPE
        SYNTAX      Counter64
        MAX-ACCESS  read-only
        STATUS      current
        DESCRIPTION "."
        ::= { tnStatisticsOdukRxScalars 105 }

    tnOthOducStatRxFeBIP8ErrCnt15MinTr OBJECT-TYPE
        SYNTAX      Counter64
        MAX-ACCESS  read-only
        STATUS      current
        DESCRIPTION "."
        ::= { tnStatisticsOdukRxScalars 106 }

    tnOthOducStatRxFeBIP8ErrCnt15MinRtr OBJECT-TYPE
        SYNTAX      Counter64
        MAX-ACCESS  read-only
        STATUS      current
        DESCRIPTION "."
        ::= { tnStatisticsOdukRxScalars 107 }

    tnOthOducStatRxFeBIP8ErrCnt1DayTr OBJECT-TYPE
        SYNTAX      Counter64
        MAX-ACCESS  read-only
        STATUS      current
        DESCRIPTION "."
        ::= { tnStatisticsOdukRxScalars 108 }

    tnOthOduflex400GBERxNeBIP8ErrCnt15MinTr OBJECT-TYPE
        SYNTAX      Counter64
        MAX-ACCESS  read-only
        STATUS      current
        DESCRIPTION "."
        ::= { tnStatisticsOdukRxScalars 109 }

    tnOthOduflex400GBERxNeBIP8ErrCnt15MinRtr OBJECT-TYPE
        SYNTAX      Counter64
        MAX-ACCESS  read-only
        STATUS      current
        DESCRIPTION "."
        ::= { tnStatisticsOdukRxScalars 110 }

    tnOthOduflex400GBERxNeBIP8ErrCnt1DayTr OBJECT-TYPE
        SYNTAX      Counter64
        MAX-ACCESS  read-only
        STATUS      current
        DESCRIPTION "."
        ::= { tnStatisticsOdukRxScalars 111 }

    tnOthOduflex400GBERxFeBIP8ErrCnt15MinTr OBJECT-TYPE
        SYNTAX      Counter64
        MAX-ACCESS  read-only
        STATUS      current
        DESCRIPTION "."
        ::= { tnStatisticsOdukRxScalars 112 }

    tnOthOduflex400GBERxFeBIP8ErrCnt15MinRtr OBJECT-TYPE
        SYNTAX      Counter64
        MAX-ACCESS  read-only
        STATUS      current
        DESCRIPTION "."
        ::= { tnStatisticsOdukRxScalars 113 }

    tnOthOduflex400GBERxFeBIP8ErrCnt1DayTr OBJECT-TYPE
        SYNTAX      Counter64
        MAX-ACCESS  read-only
        STATUS      current
        DESCRIPTION "."
        ::= { tnStatisticsOdukRxScalars 114 }

    tnOthOduflexFC3200RxNeBIP8ErrCnt15MinTr OBJECT-TYPE
        SYNTAX      Counter64
        MAX-ACCESS  read-only
        STATUS      current
        DESCRIPTION "15 min threshold value for the number of OduflexFC3200 layer
                     error blocks detected at near-end receiving direction."
        ::= { tnStatisticsOdukRxScalars 115 }

    tnOthOduflexFC3200RxNeBIP8ErrCnt15MinRtr OBJECT-TYPE
        SYNTAX      Counter64
        MAX-ACCESS  read-only
        STATUS      current
        DESCRIPTION "15 minute reset threshold value for the number of
                     OduflexFC3200 layer error blocks detected at near-end
                     receiving direction."
        ::= { tnStatisticsOdukRxScalars 116 }

    tnOthOduflexFC3200RxNeBIP8ErrCnt1DayTr OBJECT-TYPE
        SYNTAX      Counter64
        MAX-ACCESS  read-only
        STATUS      current
        DESCRIPTION "1 day threshold value for the number of OduflexFC3200 layer
                     error blocks detected at near-end receiving direction."
        ::= { tnStatisticsOdukRxScalars 117 }

    tnOthOduflexFC3200RxFeBIP8ErrCnt15MinTr OBJECT-TYPE
        SYNTAX      Counter64
        MAX-ACCESS  read-only
        STATUS      current
        DESCRIPTION "15 min threshold value for the number of OduflexFC3200 layer
                     error blocks detected at far-end receiving direction."
        ::= { tnStatisticsOdukRxScalars 118 }

    tnOthOduflexFC3200RxFeBIP8ErrCnt15MinRtr OBJECT-TYPE
        SYNTAX      Counter64
        MAX-ACCESS  read-only
        STATUS      current
        DESCRIPTION "15 minute reset threshold value for the number of
                     OduflexFC3200 layer error blocks detected at far-end
                     receiving direction."
        ::= { tnStatisticsOdukRxScalars 119 }

    tnOthOduflexFC3200RxFeBIP8ErrCnt1DayTr OBJECT-TYPE
        SYNTAX      Counter64
        MAX-ACCESS  read-only
        STATUS      current
        DESCRIPTION "1 day threshold value for the number of OduflexFC3200 layer
                     error blocks detected at far-end receiving direction."
        ::= { tnStatisticsOdukRxScalars 120 }

    tnOthOdutc1StatRxNeBIP8ErrCnt15MinTr OBJECT-TYPE
        SYNTAX      Counter64
        MAX-ACCESS  read-only
        STATUS      current
        DESCRIPTION "15 minute threshold value for the number of ODUTC1 layer
                     error blocks detected at near-end receiving direction."
        ::= { tnStatisticsOdukRxScalars 121 }

    tnOthOdutc1StatRxNeBIP8ErrCnt15MinRtr OBJECT-TYPE
        SYNTAX      Counter64
        MAX-ACCESS  read-only
        STATUS      current
        DESCRIPTION "15 minute reset threshold value for the number of ODUTC1
                     layer error blocks detected at near-end receiving direction."
        ::= { tnStatisticsOdukRxScalars 122 }

    tnOthOdutc1StatRxNeBIP8ErrCnt1DayTr OBJECT-TYPE
        SYNTAX      Counter64
        MAX-ACCESS  read-only
        STATUS      current
        DESCRIPTION "1 day threshold value for the number of ODUTC1 layer error
                     blocks detected at near-end receiving direction."
        ::= { tnStatisticsOdukRxScalars 123 }

    tnOthOdutc1StatRxFeBIP8ErrCnt15MinTr OBJECT-TYPE
        SYNTAX      Counter64
        MAX-ACCESS  read-only
        STATUS      current
        DESCRIPTION "15 minute threshold value for the number of ODUTC1 layer
                     error blocks detected at far-end receiving direction."
        ::= { tnStatisticsOdukRxScalars 124 }

    tnOthOdutc1StatRxFeBIP8ErrCnt15MinRtr OBJECT-TYPE
        SYNTAX      Counter64
        MAX-ACCESS  read-only
        STATUS      current
        DESCRIPTION "15 minute reset threshold value for the number of ODUTC1
                     layer error blocks detected at far-end receiving direction."
        ::= { tnStatisticsOdukRxScalars 125 }

    tnOthOdutc1StatRxFeBIP8ErrCnt1DayTr OBJECT-TYPE
        SYNTAX      Counter64
        MAX-ACCESS  read-only
        STATUS      current
        DESCRIPTION "1 day threshold value for the number of ODUTC1 layer error
                     blocks detected at far-end receiving direction."
        ::= { tnStatisticsOdukRxScalars 126 }

    tnOthOdutc4StatRxNeBIP8ErrCnt15MinTr OBJECT-TYPE
        SYNTAX      Counter64
        MAX-ACCESS  read-only
        STATUS      current
        DESCRIPTION "15 minute threshold value for the number of ODUTC4 layer
                     error blocks detected at near-end receiving direction."
        ::= { tnStatisticsOdukRxScalars 127 }

    tnOthOdutc4StatRxNeBIP8ErrCnt15MinRtr OBJECT-TYPE
        SYNTAX      Counter64
        MAX-ACCESS  read-only
        STATUS      current
        DESCRIPTION "15 minute reset threshold value for the number of ODUTC4
                     layer error blocks detected at near-end receiving direction."
        ::= { tnStatisticsOdukRxScalars 128 }

    tnOthOdutc4StatRxNeBIP8ErrCnt1DayTr OBJECT-TYPE
        SYNTAX      Counter64
        MAX-ACCESS  read-only
        STATUS      current
        DESCRIPTION "1 day threshold value for the number of ODUTC4 layer error
                     blocks detected at near-end receiving direction."
        ::= { tnStatisticsOdukRxScalars 129 }

    tnOthOdutc4StatRxFeBIP8ErrCnt15MinTr OBJECT-TYPE
        SYNTAX      Counter64
        MAX-ACCESS  read-only
        STATUS      current
        DESCRIPTION "15 minute threshold value for the number of ODUTC4 layer
                     error blocks detected at far-end receiving direction."
        ::= { tnStatisticsOdukRxScalars 130 }

    tnOthOdutc4StatRxFeBIP8ErrCnt15MinRtr OBJECT-TYPE
        SYNTAX      Counter64
        MAX-ACCESS  read-only
        STATUS      current
        DESCRIPTION "15 minute reset threshold value for the number of ODUTC4
                     layer error blocks detected at far-end receiving direction."
        ::= { tnStatisticsOdukRxScalars 131 }

    tnOthOdutc4StatRxFeBIP8ErrCnt1DayTr OBJECT-TYPE
        SYNTAX      Counter64
        MAX-ACCESS  read-only
        STATUS      current
        DESCRIPTION "1 day threshold value for the number of ODUTC4 layer error
                     blocks detected at far-end receiving direction."
        ::= { tnStatisticsOdukRxScalars 132 }

--------------------------------------------------------------------------------
-- TX Statistics ODUk Threshold Scalars
--------------------------------------------------------------------------------
    tnOthOdu0StatTxNeBIP8ErrCnt15MinTr OBJECT-TYPE
        SYNTAX      Counter64
        MAX-ACCESS  read-only
        STATUS      current
        DESCRIPTION "15 minute threshold value for the number of ODU0
                     layer error blocks detected at near-end transmitting
                     direction."
        ::= { tnStatisticsOdukTxScalars 1 }

    tnOthOdu0StatTxNeBIP8ErrCnt15MinRtr OBJECT-TYPE
        SYNTAX      Counter64
        MAX-ACCESS  read-only
        STATUS      current
        DESCRIPTION "15 minute reset threshold value for the number of
                     ODU0 layer error blocks detected at near-end
                     transmitting direction."
        ::= { tnStatisticsOdukTxScalars 2 }

    tnOthOdu0StatTxNeBIP8ErrCnt1DayTr OBJECT-TYPE
        SYNTAX      Counter64
        MAX-ACCESS  read-only
        STATUS      current
        DESCRIPTION "1 day threshold value for the number of ODU0 layer
                     error blocks detected at near-end transmitting
                     direction."
        ::= { tnStatisticsOdukTxScalars 3 }

    tnOthOdu0StatTxFeBIP8ErrCnt15MinTr OBJECT-TYPE
        SYNTAX      Counter64
        MAX-ACCESS  read-only
        STATUS      current
        DESCRIPTION "15 minute threshold value for the number of ODU0
                     layer error blocks detected at far-end transmitting
                     direction."
        ::= { tnStatisticsOdukTxScalars 4 }

    tnOthOdu0StatTxFeBIP8ErrCnt15MinRtr OBJECT-TYPE
        SYNTAX      Counter64
        MAX-ACCESS  read-only
        STATUS      current
        DESCRIPTION "15 minute reset threshold value for the number of
                     ODU0 layer error blocks detected at far-end
                     transmitting direction."
        ::= { tnStatisticsOdukTxScalars 5 }

    tnOthOdu0StatTxFeBIP8ErrCnt1DayTr OBJECT-TYPE
        SYNTAX      Counter64
        MAX-ACCESS  read-only
        STATUS      current
        DESCRIPTION "1 day threshold value for the number of ODU0 layer
                     error blocks detected at far-end transmitting
                     direction."
        ::= { tnStatisticsOdukTxScalars 6 }

    tnOthOdu1StatTxNeBIP8ErrCnt15MinTr OBJECT-TYPE
        SYNTAX      Counter64
        MAX-ACCESS  read-only
        STATUS      current
        DESCRIPTION "15 minute threshold value for the number of ODU1
                     layer error blocks detected at near-end transmitting
                     direction."
        ::= { tnStatisticsOdukTxScalars 7 }

    tnOthOdu1StatTxNeBIP8ErrCnt15MinRtr OBJECT-TYPE
        SYNTAX      Counter64
        MAX-ACCESS  read-only
        STATUS      current
        DESCRIPTION "15 minute reset threshold value for the number of
                     ODU1 layer error blocks detected at near-end
                     transmitting direction."
        ::= { tnStatisticsOdukTxScalars 8 }

    tnOthOdu1StatTxNeBIP8ErrCnt1DayTr OBJECT-TYPE
        SYNTAX      Counter64
        MAX-ACCESS  read-only
        STATUS      current
        DESCRIPTION "1 day threshold value for the number of ODU1 layer
                     error blocks detected at near-end transmitting
                     direction."
        ::= { tnStatisticsOdukTxScalars 9 }

    tnOthOdu1StatTxFeBIP8ErrCnt15MinTr OBJECT-TYPE
        SYNTAX      Counter64
        MAX-ACCESS  read-only
        STATUS      current
        DESCRIPTION "15 minute threshold value for the number of ODU1
                     layer error blocks detected at far-end transmitting
                     direction."
        ::= { tnStatisticsOdukTxScalars 10 }

    tnOthOdu1StatTxFeBIP8ErrCnt15MinRtr OBJECT-TYPE
        SYNTAX      Counter64
        MAX-ACCESS  read-only
        STATUS      current
        DESCRIPTION "15 minute reset threshold value for the number of
                     ODU1 layer error blocks detected at far-end
                     transmitting direction."
        ::= { tnStatisticsOdukTxScalars 11 }

    tnOthOdu1StatTxFeBIP8ErrCnt1DayTr OBJECT-TYPE
        SYNTAX      Counter64
        MAX-ACCESS  read-only
        STATUS      current
        DESCRIPTION "1 day threshold value for the number of ODU1 layer
                     error blocks detected at far-end transmitting
                     direction."
        ::= { tnStatisticsOdukTxScalars 12 }

    tnOthOdu2StatTxNeBIP8ErrCnt15MinTr OBJECT-TYPE
        SYNTAX      Counter64
        MAX-ACCESS  read-only
        STATUS      current
        DESCRIPTION "15 minute threshold value for the number of ODU2
                     layer error blocks detected at near-end transmitting
                     direction."
        ::= { tnStatisticsOdukTxScalars 13 }

    tnOthOdu2StatTxNeBIP8ErrCnt15MinRtr OBJECT-TYPE
        SYNTAX      Counter64
        MAX-ACCESS  read-only
        STATUS      current
        DESCRIPTION "15 minute reset threshold value for the number of
                     ODU2 layer error blocks detected at near-end
                     transmitting direction."
        ::= { tnStatisticsOdukTxScalars 14 }

    tnOthOdu2StatTxNeBIP8ErrCnt1DayTr OBJECT-TYPE
        SYNTAX      Counter64
        MAX-ACCESS  read-only
        STATUS      current
        DESCRIPTION "1 day threshold value for the number of ODU2 layer
                     error blocks detected at near-end transmitting
                     direction."
        ::= { tnStatisticsOdukTxScalars 15 }

    tnOthOdu2StatTxFeBIP8ErrCnt15MinTr OBJECT-TYPE
        SYNTAX      Counter64
        MAX-ACCESS  read-only
        STATUS      current
        DESCRIPTION "15 minute threshold value for the number of ODU2
                     layer error blocks detected at far-end transmitting
                     direction."
        ::= { tnStatisticsOdukTxScalars 16 }

    tnOthOdu2StatTxFeBIP8ErrCnt15MinRtr OBJECT-TYPE
        SYNTAX      Counter64
        MAX-ACCESS  read-only
        STATUS      current
        DESCRIPTION "15 minute reset threshold value for the number of
                     ODU2 layer error blocks detected at far-end
                     transmitting direction."
        ::= { tnStatisticsOdukTxScalars 17 }

    tnOthOdu2StatTxFeBIP8ErrCnt1DayTr OBJECT-TYPE
        SYNTAX      Counter64
        MAX-ACCESS  read-only
        STATUS      current
        DESCRIPTION "1 day threshold value for the number of ODU2 layer
                     error blocks detected at far-end transmitting
                     direction."
        ::= { tnStatisticsOdukTxScalars 18 }

    tnOthOdu3StatTxNeBIP8ErrCnt15MinTr OBJECT-TYPE
        SYNTAX      Counter64
        MAX-ACCESS  read-only
        STATUS      current
        DESCRIPTION "15 minute threshold value for the number of ODU3
                     layer error blocks detected at near-end transmitting
                     direction."
        ::= { tnStatisticsOdukTxScalars 19 }

    tnOthOdu3StatTxNeBIP8ErrCnt15MinRtr OBJECT-TYPE
        SYNTAX      Counter64
        MAX-ACCESS  read-only
        STATUS      current
        DESCRIPTION "15 minute reset threshold value for the number of
                     ODU3 layer error blocks detected at near-end
                     transmitting direction."
        ::= { tnStatisticsOdukTxScalars 20 }

    tnOthOdu3StatTxNeBIP8ErrCnt1DayTr OBJECT-TYPE
        SYNTAX      Counter64
        MAX-ACCESS  read-only
        STATUS      current
        DESCRIPTION "1 day threshold value for the number of ODU3 layer
                     error blocks detected at near-end transmitting
                     direction."
        ::= { tnStatisticsOdukTxScalars 21 }

    tnOthOdu3StatTxFeBIP8ErrCnt15MinTr OBJECT-TYPE
        SYNTAX      Counter64
        MAX-ACCESS  read-only
        STATUS      current
        DESCRIPTION "15 minute threshold value for the number of ODU3
                     layer error blocks detected at far-end transmitting
                     direction."
        ::= { tnStatisticsOdukTxScalars 22 }

    tnOthOdu3StatTxFeBIP8ErrCnt15MinRtr OBJECT-TYPE
        SYNTAX      Counter64
        MAX-ACCESS  read-only
        STATUS      current
        DESCRIPTION "15 minute reset threshold value for the number of
                     ODU3 layer error blocks detected at far-end
                     transmitting direction."
        ::= { tnStatisticsOdukTxScalars 23 }

    tnOthOdu3StatTxFeBIP8ErrCnt1DayTr OBJECT-TYPE
        SYNTAX      Counter64
        MAX-ACCESS  read-only
        STATUS      current
        DESCRIPTION "1 day threshold value for the number of ODU3 layer
                     error blocks detected at far-end transmitting
                     direction."
        ::= { tnStatisticsOdukTxScalars 24 }

    tnOthOdu4StatTxNeBIP8ErrCnt15MinTr OBJECT-TYPE
        SYNTAX      Counter64
        MAX-ACCESS  read-only
        STATUS      current
        DESCRIPTION "15 minute threshold value for the number of ODU4
                     layer error blocks detected at near-end transmitting
                     direction."
        ::= { tnStatisticsOdukTxScalars 25 }

    tnOthOdu4StatTxNeBIP8ErrCnt15MinRtr OBJECT-TYPE
        SYNTAX      Counter64
        MAX-ACCESS  read-only
        STATUS      current
        DESCRIPTION "15 minute reset threshold value for the number of
                     ODU4 layer error blocks detected at near-end
                     transmitting direction."
        ::= { tnStatisticsOdukTxScalars 26 }

    tnOthOdu4StatTxNeBIP8ErrCnt1DayTr OBJECT-TYPE
        SYNTAX      Counter64
        MAX-ACCESS  read-only
        STATUS      current
        DESCRIPTION "1 day threshold value for the number of ODU4 layer
                     error blocks detected at near-end transmitting
                     direction."
        ::= { tnStatisticsOdukTxScalars 27 }

    tnOthOdu4StatTxFeBIP8ErrCnt15MinTr OBJECT-TYPE
        SYNTAX      Counter64
        MAX-ACCESS  read-only
        STATUS      current
        DESCRIPTION "15 minute threshold value for the number of ODU4
                     layer error blocks detected at far-end transmitting
                     direction."
        ::= { tnStatisticsOdukTxScalars 28 }

    tnOthOdu4StatTxFeBIP8ErrCnt15MinRtr OBJECT-TYPE
        SYNTAX      Counter64
        MAX-ACCESS  read-only
        STATUS      current
        DESCRIPTION "15 minute reset threshold value for the number of
                     ODU4 layer error blocks detected at far-end
                     transmitting direction."
        ::= { tnStatisticsOdukTxScalars 29 }

    tnOthOdu4StatTxFeBIP8ErrCnt1DayTr OBJECT-TYPE
        SYNTAX      Counter64
        MAX-ACCESS  read-only
        STATUS      current
        DESCRIPTION "1 day threshold value for the number of ODU4 layer
                     error blocks detected at far-end transmitting
                     direction."
        ::= { tnStatisticsOdukTxScalars 30 }

    tnOthOdukStatTxNeES15MinTr OBJECT-TYPE
        SYNTAX      Counter64
        MAX-ACCESS  read-only
        STATUS      current
        DESCRIPTION "15 minute threshold value for errored seconds
                     detected at near-end transmitting direction."
        ::= { tnStatisticsOdukTxScalars 31 }

    tnOthOdukStatTxNeES15MinRtr OBJECT-TYPE
        SYNTAX      Counter64
        MAX-ACCESS  read-only
        STATUS      current
        DESCRIPTION "15 minute reset threshold value for errored seconds
                     detected at near-end transmitting direction."
        ::= { tnStatisticsOdukTxScalars 32 }

    tnOthOdukStatTxNeES1DayTr OBJECT-TYPE
        SYNTAX      Counter64
        MAX-ACCESS  read-only
        STATUS      current
        DESCRIPTION "1 day threshold value for errored seconds detected
                     at near-end transmitting direction."
        ::= { tnStatisticsOdukTxScalars 33 }

    tnOthOdukStatTxFeES15MinTr OBJECT-TYPE
        SYNTAX      Counter64
        MAX-ACCESS  read-only
        STATUS      current
        DESCRIPTION "15 minute threshold value for errored seconds
                     detected at far-end transmitting direction."
        ::= { tnStatisticsOdukTxScalars 34 }

    tnOthOdukStatTxFeES15MinRtr OBJECT-TYPE
        SYNTAX      Counter64
        MAX-ACCESS  read-only
        STATUS      current
        DESCRIPTION "15 minute reset threshold value for errored seconds
                     detected at far-end transmitting direction."
        ::= { tnStatisticsOdukTxScalars 35 }

    tnOthOdukStatTxFeES1DayTr OBJECT-TYPE
        SYNTAX      Counter64
        MAX-ACCESS  read-only
        STATUS      current
        DESCRIPTION "1 day threshold value for errored seconds detected
                     at far-end transmitting direction."
        ::= { tnStatisticsOdukTxScalars 36 }

    tnOthOdukStatTxNeSES15MinTr OBJECT-TYPE
        SYNTAX      Counter64
        MAX-ACCESS  read-only
        STATUS      current
        DESCRIPTION "15 minute threshold value for severely errored
                     seconds detected at near-end transmitting direction."
        ::= { tnStatisticsOdukTxScalars 37 }

    tnOthOdukStatTxNeSES15MinRtr OBJECT-TYPE
        SYNTAX      Counter64
        MAX-ACCESS  read-only
        STATUS      current
        DESCRIPTION "15 minute reset threshold value for severely errored
                     seconds detected at near-end transmitting direction."
        ::= { tnStatisticsOdukTxScalars 38 }

    tnOthOdukStatTxNeSES1DayTr OBJECT-TYPE
        SYNTAX      Counter64
        MAX-ACCESS  read-only
        STATUS      current
        DESCRIPTION "1 day threshold value for severely errored seconds
                     detected at near-end transmitting direction."
        ::= { tnStatisticsOdukTxScalars 39 }

    tnOthOdukStatTxFeSES15MinTr OBJECT-TYPE
        SYNTAX      Counter64
        MAX-ACCESS  read-only
        STATUS      current
        DESCRIPTION "15 minute threshold value for severely errored
                     seconds detected at far-end transmitting direction."
        ::= { tnStatisticsOdukTxScalars 40 }

    tnOthOdukStatTxFeSES15MinRtr OBJECT-TYPE
        SYNTAX      Counter64
        MAX-ACCESS  read-only
        STATUS      current
        DESCRIPTION "15 minute reset threshold value for severely errored
                     seconds detected at far-end transmitting direction."
        ::= { tnStatisticsOdukTxScalars 41 }

    tnOthOdukStatTxFeSES1DayTr OBJECT-TYPE
        SYNTAX      Counter64
        MAX-ACCESS  read-only
        STATUS      current
        DESCRIPTION "1 day threshold value for severely errored seconds
                     detected at far-end transmitting direction."
        ::= { tnStatisticsOdukTxScalars 42 }

    tnOthOdukStatTxNeUAS15MinTr OBJECT-TYPE
        SYNTAX      Counter64
        MAX-ACCESS  read-only
        STATUS      current
        DESCRIPTION "15 minute threshold value for unavailable errored
                     seconds detected at near-end transmitting direction."
        ::= { tnStatisticsOdukTxScalars 43 }

    tnOthOdukStatTxNeUAS15MinRtr OBJECT-TYPE
        SYNTAX      Counter64
        MAX-ACCESS  read-only
        STATUS      current
        DESCRIPTION "15 minute reset threshold value for unavailable
                     errored seconds detected at near-end transmitting
                     direction."
        ::= { tnStatisticsOdukTxScalars 44 }

    tnOthOdukStatTxNeUAS1DayTr OBJECT-TYPE
        SYNTAX      Counter64
        MAX-ACCESS  read-only
        STATUS      current
        DESCRIPTION "1 day threshold value for unavailable errored
                     seconds detected at near-end transmitting direction."
        ::= { tnStatisticsOdukTxScalars 45 }

    tnOthOdukStatTxFeUAS15MinTr OBJECT-TYPE
        SYNTAX      Counter64
        MAX-ACCESS  read-only
        STATUS      current
        DESCRIPTION "15 minute threshold value for unavailable errored
                     seconds detected at far-end transmitting direction."
        ::= { tnStatisticsOdukTxScalars 46 }

    tnOthOdukStatTxFeUAS15MinRtr OBJECT-TYPE
        SYNTAX      Counter64
        MAX-ACCESS  read-only
        STATUS      current
        DESCRIPTION "15 minute reset threshold value for unavailable
                     errored seconds detected at far-end transmitting
                     direction."
        ::= { tnStatisticsOdukTxScalars 47 }

    tnOthOdukStatTxFeUAS1DayTr OBJECT-TYPE
        SYNTAX      Counter64
        MAX-ACCESS  read-only
        STATUS      current
        DESCRIPTION "1 day threshold value for unavailable errored
                     seconds detected at far-end transmitting direction."
        ::= { tnStatisticsOdukTxScalars 48 }

    tnOthOduflexGFPTxNeBIP8ErrCnt15MinTr OBJECT-TYPE
        SYNTAX      Counter64
        MAX-ACCESS  read-only
        STATUS      current
        DESCRIPTION "15 minute threshold value for the number of OduflexGFP
                     layer error blocks detected at near-end transmitting
                     direction."
        ::= { tnStatisticsOdukTxScalars 49 }

    tnOthOduflexGFPTxNeBIP8ErrCnt15MinRtr OBJECT-TYPE
        SYNTAX      Counter64
        MAX-ACCESS  read-only
        STATUS      current
        DESCRIPTION "15 minute reset threshold value for the number of
                     OduflexGFP layer error blocks detected at near-end
                     transmitting direction."
        ::= { tnStatisticsOdukTxScalars 50 }

    tnOthOduflexGFPTxNeBIP8ErrCnt1DayTr OBJECT-TYPE
        SYNTAX      Counter64
        MAX-ACCESS  read-only
        STATUS      current
        DESCRIPTION "1 day threshold value for the number of OduflexGFP layer
                     error blocks detected at near-end transmitting
                     direction."
        ::= { tnStatisticsOdukTxScalars 51 }

    tnOthOduflexGFPTxFeBIP8ErrCnt15MinTr OBJECT-TYPE
        SYNTAX      Counter64
        MAX-ACCESS  read-only
        STATUS      current
        DESCRIPTION "15 minute threshold value for the number of OduflexGFP
                     layer error blocks detected at far-end transmitting
                     direction."
        ::= { tnStatisticsOdukTxScalars 52 }

    tnOthOduflexGFPTxFeBIP8ErrCnt15MinRtr OBJECT-TYPE
        SYNTAX      Counter64
        MAX-ACCESS  read-only
        STATUS      current
        DESCRIPTION "15 minute reset threshold value for the number of
                     OduflexGFP layer error blocks detected at far-end
                     transmitting direction."
        ::= { tnStatisticsOdukTxScalars 53 }

    tnOthOduflexGFPTxFeBIP8ErrCnt1DayTr OBJECT-TYPE
        SYNTAX      Counter64
        MAX-ACCESS  read-only
        STATUS      current
        DESCRIPTION "1 day threshold value for the number of OduflexGFP layer
                     error blocks detected at far-end transmitting
                     direction."
        ::= { tnStatisticsOdukTxScalars 54 }

    tnOthOduflexFC400TxNeBIP8ErrCnt15MinTr OBJECT-TYPE
        SYNTAX      Counter64
        MAX-ACCESS  read-only
        STATUS      current
        DESCRIPTION "15 minute threshold value for the number of OduflexFC400
                     layer error blocks detected at near-end transmitting
                     direction."
        ::= { tnStatisticsOdukTxScalars 55 }

    tnOthOduflexFC400TxNeBIP8ErrCnt15MinRtr OBJECT-TYPE
        SYNTAX      Counter64
        MAX-ACCESS  read-only
        STATUS      current
        DESCRIPTION "15 minute reset threshold value for the number of
                     OduflexFC400 layer error blocks detected at near-end
                     transmitting direction."
        ::= { tnStatisticsOdukTxScalars 56 }

    tnOthOduflexFC400TxNeBIP8ErrCnt1DayTr OBJECT-TYPE
        SYNTAX      Counter64
        MAX-ACCESS  read-only
        STATUS      current
        DESCRIPTION "1 day threshold value for the number of OduflexFC400 layer
                     error blocks detected at near-end transmitting
                     direction."
        ::= { tnStatisticsOdukTxScalars 57 }

    tnOthOduflexFC400TxFeBIP8ErrCnt15MinTr OBJECT-TYPE
        SYNTAX      Counter64
        MAX-ACCESS  read-only
        STATUS      current
        DESCRIPTION "15 minute threshold value for the number of OduflexFC400
                     layer error blocks detected at far-end transmitting
                     direction."
        ::= { tnStatisticsOdukTxScalars 58 }

    tnOthOduflexFC400TxFeBIP8ErrCnt15MinRtr OBJECT-TYPE
        SYNTAX      Counter64
        MAX-ACCESS  read-only
        STATUS      current
        DESCRIPTION "15 minute reset threshold value for the number of
                     OduflexFC400 layer error blocks detected at far-end
                     transmitting direction."
        ::= { tnStatisticsOdukTxScalars 59 }

    tnOthOduflexFC400TxFeBIP8ErrCnt1DayTr OBJECT-TYPE
        SYNTAX      Counter64
        MAX-ACCESS  read-only
        STATUS      current
        DESCRIPTION "1 day threshold value for the number of OduflexFC400 layer
                     error blocks detected at far-end transmitting
                     direction."
        ::= { tnStatisticsOdukTxScalars 60 }

    tnOthOduflexFC800TxNeBIP8ErrCnt15MinTr OBJECT-TYPE
        SYNTAX      Counter64
        MAX-ACCESS  read-only
        STATUS      current
        DESCRIPTION "15 minute threshold value for the number of OduflexFC800
                     layer error blocks detected at near-end transmitting
                     direction."
        ::= { tnStatisticsOdukTxScalars 61 }

    tnOthOduflexFC800TxNeBIP8ErrCnt15MinRtr OBJECT-TYPE
        SYNTAX      Counter64
        MAX-ACCESS  read-only
        STATUS      current
        DESCRIPTION "15 minute reset threshold value for the number of
                     OduflexFC800 layer error blocks detected at near-end
                     transmitting direction."
        ::= { tnStatisticsOdukTxScalars 62 }

    tnOthOduflexFC800TxNeBIP8ErrCnt1DayTr OBJECT-TYPE
        SYNTAX      Counter64
        MAX-ACCESS  read-only
        STATUS      current
        DESCRIPTION "1 day threshold value for the number of OduflexFC800 layer
                     error blocks detected at near-end transmitting
                     direction."
        ::= { tnStatisticsOdukTxScalars 63 }

    tnOthOduflexFC800TxFeBIP8ErrCnt15MinTr OBJECT-TYPE
        SYNTAX      Counter64
        MAX-ACCESS  read-only
        STATUS      current
        DESCRIPTION "15 minute threshold value for the number of OduflexFC800
                     layer error blocks detected at far-end transmitting
                     direction."
        ::= { tnStatisticsOdukTxScalars 64 }

    tnOthOduflexFC800TxFeBIP8ErrCnt15MinRtr OBJECT-TYPE
        SYNTAX      Counter64
        MAX-ACCESS  read-only
        STATUS      current
        DESCRIPTION "15 minute reset threshold value for the number of
                     OduflexFC800 layer error blocks detected at far-end
                     transmitting direction."
        ::= { tnStatisticsOdukTxScalars 65 }

    tnOthOduflexFC800TxFeBIP8ErrCnt1DayTr OBJECT-TYPE
        SYNTAX      Counter64
        MAX-ACCESS  read-only
        STATUS      current
        DESCRIPTION "1 day threshold value for the number of OduflexFC800 layer
                     error blocks detected at far-end transmitting
                     direction."
        ::= { tnStatisticsOdukTxScalars 66 }

    tnOthOduflexFC1600TxNeBIP8ErrCnt15MinTr OBJECT-TYPE
        SYNTAX      Counter64
        MAX-ACCESS  read-only
        STATUS      current
        DESCRIPTION "15 minute threshold value for the number of OduflexFC1600
                     layer error blocks detected at near-end transmitting
                     direction."
        ::= { tnStatisticsOdukTxScalars 67 }

    tnOthOduflexFC1600TxNeBIP8ErrCnt15MinRtr OBJECT-TYPE
        SYNTAX      Counter64
        MAX-ACCESS  read-only
        STATUS      current
        DESCRIPTION "15 minute reset threshold value for the number of
                     OduflexFC1600 layer error blocks detected at near-end
                     transmitting direction."
        ::= { tnStatisticsOdukTxScalars 68 }

    tnOthOduflexFC1600TxNeBIP8ErrCnt1DayTr OBJECT-TYPE
        SYNTAX      Counter64
        MAX-ACCESS  read-only
        STATUS      current
        DESCRIPTION "1 day threshold value for the number of OduflexFC1600 layer
                     error blocks detected at near-end transmitting
                     direction."
        ::= { tnStatisticsOdukTxScalars 69 }

    tnOthOduflexFC1600TxFeBIP8ErrCnt15MinTr OBJECT-TYPE
        SYNTAX      Counter64
        MAX-ACCESS  read-only
        STATUS      current
        DESCRIPTION "15 minute threshold value for the number of OduflexFC1600
                     layer error blocks detected at far-end transmitting
                     direction."
        ::= { tnStatisticsOdukTxScalars 70 }

    tnOthOduflexFC1600TxFeBIP8ErrCnt15MinRtr OBJECT-TYPE
        SYNTAX      Counter64
        MAX-ACCESS  read-only
        STATUS      current
        DESCRIPTION "15 minute reset threshold value for the number of
                     OduflexFC1600 layer error blocks detected at far-end
                     transmitting direction."
        ::= { tnStatisticsOdukTxScalars 71 }

    tnOthOduflexFC1600TxFeBIP8ErrCnt1DayTr OBJECT-TYPE
        SYNTAX      Counter64
        MAX-ACCESS  read-only
        STATUS      current
        DESCRIPTION "1 day threshold value for the number of OduflexFC1600 layer
                     error blocks detected at far-end transmitting
                     direction."
        ::= { tnStatisticsOdukTxScalars 72 }

    tnOthOduflexIBSDRTxNeBIP8ErrCnt15MinTr OBJECT-TYPE
        SYNTAX      Counter64
        MAX-ACCESS  read-only
        STATUS      current
        DESCRIPTION "15 minute threshold value for the number of OduflexIBSDR
                     layer error blocks detected at near-end transmitting
                     direction."
        ::= { tnStatisticsOdukTxScalars 73 }

    tnOthOduflexIBSDRTxNeBIP8ErrCnt15MinRtr OBJECT-TYPE
        SYNTAX      Counter64
        MAX-ACCESS  read-only
        STATUS      current
        DESCRIPTION "15 minute reset threshold value for the number of
                     OduflexIBSDR layer error blocks detected at near-end
                     transmitting direction."
        ::= { tnStatisticsOdukTxScalars 74 }

    tnOthOduflexIBSDRTxNeBIP8ErrCnt1DayTr OBJECT-TYPE
        SYNTAX      Counter64
        MAX-ACCESS  read-only
        STATUS      current
        DESCRIPTION "1 day threshold value for the number of OduflexIBSDR layer
                     error blocks detected at near-end transmitting
                     direction."
        ::= { tnStatisticsOdukTxScalars 75 }

    tnOthOduflexIBSDRTxFeBIP8ErrCnt15MinTr OBJECT-TYPE
        SYNTAX      Counter64
        MAX-ACCESS  read-only
        STATUS      current
        DESCRIPTION "15 minute threshold value for the number of OduflexIBSDR
                     layer error blocks detected at far-end transmitting
                     direction."
        ::= { tnStatisticsOdukTxScalars 76 }

    tnOthOduflexIBSDRTxFeBIP8ErrCnt15MinRtr OBJECT-TYPE
        SYNTAX      Counter64
        MAX-ACCESS  read-only
        STATUS      current
        DESCRIPTION "15 minute reset threshold value for the number of
                     OduflexIBSDR layer error blocks detected at far-end
                     transmitting direction."
        ::= { tnStatisticsOdukTxScalars 77 }

    tnOthOduflexIBSDRTxFeBIP8ErrCnt1DayTr OBJECT-TYPE
        SYNTAX      Counter64
        MAX-ACCESS  read-only
        STATUS      current
        DESCRIPTION "1 day threshold value for the number of OduflexIBSDR layer
                     error blocks detected at far-end transmitting
                     direction."
        ::= { tnStatisticsOdukTxScalars 78 }

    tnOthOduflexIBDDRTxNeBIP8ErrCnt15MinTr OBJECT-TYPE
        SYNTAX      Counter64
        MAX-ACCESS  read-only
        STATUS      current
        DESCRIPTION "15 minute threshold value for the number of OduflexIBDDR
                     layer error blocks detected at near-end transmitting
                     direction."
        ::= { tnStatisticsOdukTxScalars 79 }

    tnOthOduflexIBDDRTxNeBIP8ErrCnt15MinRtr OBJECT-TYPE
        SYNTAX      Counter64
        MAX-ACCESS  read-only
        STATUS      current
        DESCRIPTION "15 minute reset threshold value for the number of
                     OduflexIBDDR layer error blocks detected at near-end
                     transmitting direction."
        ::= { tnStatisticsOdukTxScalars 80 }

    tnOthOduflexIBDDRTxNeBIP8ErrCnt1DayTr OBJECT-TYPE
        SYNTAX      Counter64
        MAX-ACCESS  read-only
        STATUS      current
        DESCRIPTION "1 day threshold value for the number of OduflexIBDDR layer
                     error blocks detected at near-end transmitting
                     direction."
        ::= { tnStatisticsOdukTxScalars 81 }

    tnOthOduflexIBDDRTxFeBIP8ErrCnt15MinTr OBJECT-TYPE
        SYNTAX      Counter64
        MAX-ACCESS  read-only
        STATUS      current
        DESCRIPTION "15 minute threshold value for the number of OduflexIBDDR
                     layer error blocks detected at far-end transmitting
                     direction."
        ::= { tnStatisticsOdukTxScalars 82 }

    tnOthOduflexIBDDRTxFeBIP8ErrCnt15MinRtr OBJECT-TYPE
        SYNTAX      Counter64
        MAX-ACCESS  read-only
        STATUS      current
        DESCRIPTION "15 minute reset threshold value for the number of
                     OduflexIBDDR layer error blocks detected at far-end
                     transmitting direction."
        ::= { tnStatisticsOdukTxScalars 83 }

    tnOthOduflexIBDDRTxFeBIP8ErrCnt1DayTr OBJECT-TYPE
        SYNTAX      Counter64
        MAX-ACCESS  read-only
        STATUS      current
        DESCRIPTION "1 day threshold value for the number of OduflexIBDDR layer
                     error blocks detected at far-end transmitting
                     direction."
        ::= { tnStatisticsOdukTxScalars 84 }

    tnOthOduflexIBQDRTxNeBIP8ErrCnt15MinTr OBJECT-TYPE
        SYNTAX      Counter64
        MAX-ACCESS  read-only
        STATUS      current
        DESCRIPTION "15 minute threshold value for the number of OduflexIBQDR
                     layer error blocks detected at near-end transmitting
                     direction."
        ::= { tnStatisticsOdukTxScalars 85 }

    tnOthOduflexIBQDRTxNeBIP8ErrCnt15MinRtr OBJECT-TYPE
        SYNTAX      Counter64
        MAX-ACCESS  read-only
        STATUS      current
        DESCRIPTION "15 minute reset threshold value for the number of
                     OduflexIBQDR layer error blocks detected at near-end
                     transmitting direction."
        ::= { tnStatisticsOdukTxScalars 86 }

    tnOthOduflexIBQDRTxNeBIP8ErrCnt1DayTr OBJECT-TYPE
        SYNTAX      Counter64
        MAX-ACCESS  read-only
        STATUS      current
        DESCRIPTION "1 day threshold value for the number of OduflexIBQDR layer
                     error blocks detected at near-end transmitting
                     direction."
        ::= { tnStatisticsOdukTxScalars 87 }

    tnOthOduflexIBQDRTxFeBIP8ErrCnt15MinTr OBJECT-TYPE
        SYNTAX      Counter64
        MAX-ACCESS  read-only
        STATUS      current
        DESCRIPTION "15 minute threshold value for the number of OduflexIBQDR
                     layer error blocks detected at far-end transmitting
                     direction."
        ::= { tnStatisticsOdukTxScalars 88 }

    tnOthOduflexIBQDRTxFeBIP8ErrCnt15MinRtr OBJECT-TYPE
        SYNTAX      Counter64
        MAX-ACCESS  read-only
        STATUS      current
        DESCRIPTION "15 minute reset threshold value for the number of
                     OduflexIBQDR layer error blocks detected at far-end
                     transmitting direction."
        ::= { tnStatisticsOdukTxScalars 89 }

    tnOthOduflexIBQDRTxFeBIP8ErrCnt1DayTr OBJECT-TYPE
        SYNTAX      Counter64
        MAX-ACCESS  read-only
        STATUS      current
        DESCRIPTION "1 day threshold value for the number of OduflexIBQDR layer
                     error blocks detected at far-end transmitting
                     direction."
        ::= { tnStatisticsOdukTxScalars 90 }

    tnOthOduflex3GSDI18TxNeBIP8ErrCnt15MinTr OBJECT-TYPE
        SYNTAX      Counter64
        MAX-ACCESS  read-only
        STATUS      current
        DESCRIPTION "15 minute threshold value for the number of Oduflex3GSDI18
                     layer error blocks detected at near-end transmitting
                     direction."
        ::= { tnStatisticsOdukTxScalars 91 }

    tnOthOduflex3GSDI18TxNeBIP8ErrCnt15MinRtr OBJECT-TYPE
        SYNTAX      Counter64
        MAX-ACCESS  read-only
        STATUS      current
        DESCRIPTION "15 minute reset threshold value for the number of
                     Oduflex3GSDI18 layer error blocks detected at near-end
                     transmitting direction."
        ::= { tnStatisticsOdukTxScalars 92 }

    tnOthOduflex3GSDI18TxNeBIP8ErrCnt1DayTr OBJECT-TYPE
        SYNTAX      Counter64
        MAX-ACCESS  read-only
        STATUS      current
        DESCRIPTION "1 day threshold value for the number of Oduflex3GSDI18 layer
                     error blocks detected at near-end transmitting
                     direction."
        ::= { tnStatisticsOdukTxScalars 93 }

    tnOthOduflex3GSDI18TxFeBIP8ErrCnt15MinTr OBJECT-TYPE
        SYNTAX      Counter64
        MAX-ACCESS  read-only
        STATUS      current
        DESCRIPTION "15 minute threshold value for the number of Oduflex3GSDI18
                     layer error blocks detected at far-end transmitting
                     direction."
        ::= { tnStatisticsOdukTxScalars 94 }

    tnOthOduflex3GSDI18TxFeBIP8ErrCnt15MinRtr OBJECT-TYPE
        SYNTAX      Counter64
        MAX-ACCESS  read-only
        STATUS      current
        DESCRIPTION "15 minute reset threshold value for the number of
                     Oduflex3GSDI18 layer error blocks detected at far-end
                     transmitting direction."
        ::= { tnStatisticsOdukTxScalars 95 }

    tnOthOduflex3GSDI18TxFeBIP8ErrCnt1DayTr OBJECT-TYPE
        SYNTAX      Counter64
        MAX-ACCESS  read-only
        STATUS      current
        DESCRIPTION "1 day threshold value for the number of Oduflex3GSDI18 layer
                     error blocks detected at far-end transmitting
                     direction."
        ::= { tnStatisticsOdukTxScalars 96 }

    tnOthOduflex3GSDI19TxNeBIP8ErrCnt15MinTr OBJECT-TYPE
        SYNTAX      Counter64
        MAX-ACCESS  read-only
        STATUS      current
        DESCRIPTION "15 minute threshold value for the number of Oduflex3GSDI19
                     layer error blocks detected at near-end transmitting
                     direction."
        ::= { tnStatisticsOdukTxScalars 97 }

    tnOthOduflex3GSDI19TxNeBIP8ErrCnt15MinRtr OBJECT-TYPE
        SYNTAX      Counter64
        MAX-ACCESS  read-only
        STATUS      current
        DESCRIPTION "15 minute reset threshold value for the number of
                     Oduflex3GSDI19 layer error blocks detected at near-end
                     transmitting direction."
        ::= { tnStatisticsOdukTxScalars 98 }

    tnOthOduflex3GSDI19TxNeBIP8ErrCnt1DayTr OBJECT-TYPE
        SYNTAX      Counter64
        MAX-ACCESS  read-only
        STATUS      current
        DESCRIPTION "1 day threshold value for the number of Oduflex3GSDI19 layer
                     error blocks detected at near-end transmitting
                     direction."
        ::= { tnStatisticsOdukTxScalars 99 }

    tnOthOduflex3GSDI19TxFeBIP8ErrCnt15MinTr OBJECT-TYPE
        SYNTAX      Counter64
        MAX-ACCESS  read-only
        STATUS      current
        DESCRIPTION "15 minute threshold value for the number of Oduflex3GSDI19
                     layer error blocks detected at far-end transmitting
                     direction."
        ::= { tnStatisticsOdukTxScalars 100 }

    tnOthOduflex3GSDI19TxFeBIP8ErrCnt15MinRtr OBJECT-TYPE
        SYNTAX      Counter64
        MAX-ACCESS  read-only
        STATUS      current
        DESCRIPTION "15 minute reset threshold value for the number of
                     Oduflex3GSDI19 layer error blocks detected at far-end
                     transmitting direction."
        ::= { tnStatisticsOdukTxScalars 101 }

    tnOthOduflex3GSDI19TxFeBIP8ErrCnt1DayTr OBJECT-TYPE
        SYNTAX      Counter64
        MAX-ACCESS  read-only
        STATUS      current
        DESCRIPTION "1 day threshold value for the number of Oduflex3GSDI19 layer
                     error blocks detected at far-end transmitting
                     direction."
        ::= { tnStatisticsOdukTxScalars 102 }

    tnOthOducStatTxNeBIP8ErrCnt15MinTr OBJECT-TYPE
        SYNTAX      Counter64
        MAX-ACCESS  read-only
        STATUS      current
        DESCRIPTION "."
        ::= { tnStatisticsOdukTxScalars 103 }

    tnOthOducStatTxNeBIP8ErrCnt15MinRtr OBJECT-TYPE
        SYNTAX      Counter64
        MAX-ACCESS  read-only
        STATUS      current
        DESCRIPTION "."
        ::= { tnStatisticsOdukTxScalars 104 }

    tnOthOducStatTxNeBIP8ErrCnt1DayTr OBJECT-TYPE
        SYNTAX      Counter64
        MAX-ACCESS  read-only
        STATUS      current
        DESCRIPTION "."
        ::= { tnStatisticsOdukTxScalars 105 }

    tnOthOducStatTxFeBIP8ErrCnt15MinTr OBJECT-TYPE
        SYNTAX      Counter64
        MAX-ACCESS  read-only
        STATUS      current
        DESCRIPTION "."
        ::= { tnStatisticsOdukTxScalars 106 }

    tnOthOducStatTxFeBIP8ErrCnt15MinRtr OBJECT-TYPE
        SYNTAX      Counter64
        MAX-ACCESS  read-only
        STATUS      current
        DESCRIPTION "."
        ::= { tnStatisticsOdukTxScalars 107 }

    tnOthOducStatTxFeBIP8ErrCnt1DayTr OBJECT-TYPE
        SYNTAX      Counter64
        MAX-ACCESS  read-only
        STATUS      current
        DESCRIPTION "."
        ::= { tnStatisticsOdukTxScalars 108 }

    tnOthOduflex400GBETxNeBIP8ErrCnt15MinTr OBJECT-TYPE
        SYNTAX      Counter64
        MAX-ACCESS  read-only
        STATUS      current
        DESCRIPTION "."
        ::= { tnStatisticsOdukTxScalars 109 }

    tnOthOduflex400GBETxNeBIP8ErrCnt15MinRtr OBJECT-TYPE
        SYNTAX      Counter64
        MAX-ACCESS  read-only
        STATUS      current
        DESCRIPTION "."
        ::= { tnStatisticsOdukTxScalars 110 }

    tnOthOduflex400GBETxNeBIP8ErrCnt1DayTr OBJECT-TYPE
        SYNTAX      Counter64
        MAX-ACCESS  read-only
        STATUS      current
        DESCRIPTION "."
        ::= { tnStatisticsOdukTxScalars 111 }

    tnOthOduflex400GBETxFeBIP8ErrCnt15MinTr OBJECT-TYPE
        SYNTAX      Counter64
        MAX-ACCESS  read-only
        STATUS      current
        DESCRIPTION "."
        ::= { tnStatisticsOdukTxScalars 112 }

    tnOthOduflex400GBETxFeBIP8ErrCnt15MinRtr OBJECT-TYPE
        SYNTAX      Counter64
        MAX-ACCESS  read-only
        STATUS      current
        DESCRIPTION "."
        ::= { tnStatisticsOdukTxScalars 113 }

    tnOthOduflex400GBETxFeBIP8ErrCnt1DayTr OBJECT-TYPE
        SYNTAX      Counter64
        MAX-ACCESS  read-only
        STATUS      current
        DESCRIPTION "."
        ::= { tnStatisticsOdukTxScalars 114 }

    tnOthOduflexFC3200TxNeBIP8ErrCnt15MinTr OBJECT-TYPE
        SYNTAX      Counter64
        MAX-ACCESS  read-only
        STATUS      current
        DESCRIPTION "15 min threshold value for the number of OduflexFC3200 layer
                     error blocks detected at near-end transmitting direction."
        ::= { tnStatisticsOdukTxScalars 115 }

    tnOthOduflexFC3200TxNeBIP8ErrCnt15MinRtr OBJECT-TYPE
        SYNTAX      Counter64
        MAX-ACCESS  read-only
        STATUS      current
        DESCRIPTION "15 minute reset threshold value for the number of
                     OduflexFC3200 layer error blocks detected at near-end
                     transmitting direction."
        ::= { tnStatisticsOdukTxScalars 116 }

    tnOthOduflexFC3200TxNeBIP8ErrCnt1DayTr OBJECT-TYPE
        SYNTAX      Counter64
        MAX-ACCESS  read-only
        STATUS      current
        DESCRIPTION "1 day threshold value for the number of OduflexFC3200 layer
                     error blocks detected at near-end transmitting direction."
        ::= { tnStatisticsOdukTxScalars 117 }

    tnOthOduflexFC3200TxFeBIP8ErrCnt15MinTr OBJECT-TYPE
        SYNTAX      Counter64
        MAX-ACCESS  read-only
        STATUS      current
        DESCRIPTION "15 min threshold value for the number of OduflexFC3200 layer
                     error blocks detected at far-end transmitting direction."
        ::= { tnStatisticsOdukTxScalars 118 }

    tnOthOduflexFC3200TxFeBIP8ErrCnt15MinRtr OBJECT-TYPE
        SYNTAX      Counter64
        MAX-ACCESS  read-only
        STATUS      current
        DESCRIPTION "15 minute reset threshold value for the number of
                     OduflexFC3200 layer error blocks detected at far-end
                     transmitting direction."
        ::= { tnStatisticsOdukTxScalars 119 }

    tnOthOduflexFC3200TxFeBIP8ErrCnt1DayTr OBJECT-TYPE
        SYNTAX      Counter64
        MAX-ACCESS  read-only
        STATUS      current
        DESCRIPTION "1 day threshold value for the number of OduflexFC3200 layer
                     error blocks detected at far-end transmitting direction."
        ::= { tnStatisticsOdukTxScalars 120 }

    tnOthOdutc1StatTxNeBIP8ErrCnt15MinTr OBJECT-TYPE
        SYNTAX      Counter64
        MAX-ACCESS  read-only
        STATUS      current
        DESCRIPTION "15 minute threshold value for the number of ODUTC1 layer
                     error blocks detected at near-end transmitting direction."
        ::= { tnStatisticsOdukTxScalars 121 }

    tnOthOdutc1StatTxNeBIP8ErrCnt15MinRtr OBJECT-TYPE
        SYNTAX      Counter64
        MAX-ACCESS  read-only
        STATUS      current
        DESCRIPTION "15 minute reset threshold value for the number of ODUTC1
                     layer error blocks detected at near-end transmitting
                     direction."
        ::= { tnStatisticsOdukTxScalars 122 }

    tnOthOdutc1StatTxNeBIP8ErrCnt1DayTr OBJECT-TYPE
        SYNTAX      Counter64
        MAX-ACCESS  read-only
        STATUS      current
        DESCRIPTION "1 day threshold value for the number of ODUTC1 layer error
                     blocks detected at near-end transmitting direction."
        ::= { tnStatisticsOdukTxScalars 123 }

    tnOthOdutc1StatTxFeBIP8ErrCnt15MinTr OBJECT-TYPE
        SYNTAX      Counter64
        MAX-ACCESS  read-only
        STATUS      current
        DESCRIPTION "15 minute threshold value for the number of ODUTC1 layer
                     error blocks detected at far-end transmitting direction."
        ::= { tnStatisticsOdukTxScalars 124 }

    tnOthOdutc1StatTxFeBIP8ErrCnt15MinRtr OBJECT-TYPE
        SYNTAX      Counter64
        MAX-ACCESS  read-only
        STATUS      current
        DESCRIPTION "15 minute reset threshold value for the number of ODUTC1
                     layer error blocks detected at far-end transmitting
                     direction."
        ::= { tnStatisticsOdukTxScalars 125 }

    tnOthOdutc1StatTxFeBIP8ErrCnt1DayTr OBJECT-TYPE
        SYNTAX      Counter64
        MAX-ACCESS  read-only
        STATUS      current
        DESCRIPTION "1 day threshold value for the number of ODUTC1 layer error
                     blocks detected at far-end transmitting direction."
        ::= { tnStatisticsOdukTxScalars 126 }

    tnOthOdutc4StatTxNeBIP8ErrCnt15MinTr OBJECT-TYPE
        SYNTAX      Counter64
        MAX-ACCESS  read-only
        STATUS      current
        DESCRIPTION "15 minute threshold value for the number of ODUTC4 layer
                     error blocks detected at near-end transmitting direction."
        ::= { tnStatisticsOdukTxScalars 127 }

    tnOthOdutc4StatTxNeBIP8ErrCnt15MinRtr OBJECT-TYPE
        SYNTAX      Counter64
        MAX-ACCESS  read-only
        STATUS      current
        DESCRIPTION "15 minute reset threshold value for the number of ODUTC4
                     layer error blocks detected at near-end transmitting
                     direction."
        ::= { tnStatisticsOdukTxScalars 128 }

    tnOthOdutc4StatTxNeBIP8ErrCnt1DayTr OBJECT-TYPE
        SYNTAX      Counter64
        MAX-ACCESS  read-only
        STATUS      current
        DESCRIPTION "1 day threshold value for the number of ODUTC4 layer error
                     blocks detected at near-end transmitting direction."
        ::= { tnStatisticsOdukTxScalars 129 }

    tnOthOdutc4StatTxFeBIP8ErrCnt15MinTr OBJECT-TYPE
        SYNTAX      Counter64
        MAX-ACCESS  read-only
        STATUS      current
        DESCRIPTION "15 minute threshold value for the number of ODUTC4 layer
                     error blocks detected at far-end transmitting direction."
        ::= { tnStatisticsOdukTxScalars 130 }

    tnOthOdutc4StatTxFeBIP8ErrCnt15MinRtr OBJECT-TYPE
        SYNTAX      Counter64
        MAX-ACCESS  read-only
        STATUS      current
        DESCRIPTION "15 minute reset threshold value for the number of ODUTC4
                     layer error blocks detected at far-end transmitting
                     direction."
        ::= { tnStatisticsOdukTxScalars 131 }

    tnOthOdutc4StatTxFeBIP8ErrCnt1DayTr OBJECT-TYPE
        SYNTAX      Counter64
        MAX-ACCESS  read-only
        STATUS      current
        DESCRIPTION "1 day threshold value for the number of ODUTC4 layer error
                     blocks detected at far-end transmitting direction."
        ::= { tnStatisticsOdukTxScalars 132 }

--------------------------------------------------------------------------------
-- Statistics OTUk Threshold Scalars
--------------------------------------------------------------------------------
    tnOthOtu1StatRxRsCorrCnt15MinTr OBJECT-TYPE
        SYNTAX      Counter64
        MAX-ACCESS  read-only
        STATUS      current
        DESCRIPTION "15 minute threshold value for OTU1 FEC correctable
                     error bit count at receiving direction."
        ::= { tnStatisticsOtukScalars 1 }

    tnOthOtu1StatRxRsCorrCnt15MinRtr OBJECT-TYPE
        SYNTAX      Counter64
        MAX-ACCESS  read-only
        STATUS      current
        DESCRIPTION "15 minute reset threshold value for OTU1 FEC
                     correctable error bit count at receiving direction."
        ::= { tnStatisticsOtukScalars 2 }

    tnOthOtu1StatRxRsCorrCnt1DayTr OBJECT-TYPE
        SYNTAX      Counter64
        MAX-ACCESS  read-only
        STATUS      current
        DESCRIPTION "1 day threshold value for OTU1 FEC correctable error
                     bit count at receiving direction."
        ::= { tnStatisticsOtukScalars 3 }

    tnOthOtu1StatRxRsUncorrCnt15MinTr OBJECT-TYPE
        SYNTAX      Counter64
        MAX-ACCESS  read-only
        STATUS      current
        DESCRIPTION "15 minute threshold value for OTU1 FEC un-correctable
                     error block count at receiving direction."
        ::= { tnStatisticsOtukScalars 4 }

    tnOthOtu1StatRxRsUncorrCnt15MinRtr OBJECT-TYPE
        SYNTAX      Counter64
        MAX-ACCESS  read-only
        STATUS      current
        DESCRIPTION "15 minute reset threshold value for OTU1 FEC
                     un-correctable error block count at receiving
                     direction."
        ::= { tnStatisticsOtukScalars 5 }

    tnOthOtu1StatRxRsUncorrCnt1DayTr OBJECT-TYPE
        SYNTAX      Counter64
        MAX-ACCESS  read-only
        STATUS      current
        DESCRIPTION "1 day threshold value for OTU1 FEC un-correctable
                     error block count at receiving direction."
        ::= { tnStatisticsOtukScalars 6 }

    tnOthOtu1StatRxNeSMBIP8ErrCnt15MinTr OBJECT-TYPE
        SYNTAX      Counter64
        MAX-ACCESS  read-only
        STATUS      current
        DESCRIPTION "15 minute threshold value for OTU1 near-end section
                     monitor BIP8 error count at receiving direction."
        ::= { tnStatisticsOtukScalars 7 }

    tnOthOtu1StatRxNeSMBIP8ErrCnt15MinRtr OBJECT-TYPE
        SYNTAX      Counter64
        MAX-ACCESS  read-only
        STATUS      current
        DESCRIPTION "15 minute reset threshold value for OTU1 near-end
                     section monitor BIP-8 error count at receiving
                     direction."
        ::= { tnStatisticsOtukScalars 8 }

    tnOthOtu1StatRxNeSMBIP8ErrCnt1DayTr OBJECT-TYPE
        SYNTAX      Counter64
        MAX-ACCESS  read-only
        STATUS      current
        DESCRIPTION "1 day threshold value for OTU1 near-end section
                     monitor BIP-8 error count at receiving direction."
        ::= { tnStatisticsOtukScalars 9 }

    tnOthOtu1StatRxFeSMBIP8ErrCnt15MinTr OBJECT-TYPE
        SYNTAX      Counter64
        MAX-ACCESS  read-only
        STATUS      current
        DESCRIPTION "15 minute threshold value for OTU1 far-end section
                     monitor BIP8 error count at receiving direction."
        ::= { tnStatisticsOtukScalars 10 }

    tnOthOtu1StatRxFeSMBIP8ErrCnt15MinRtr OBJECT-TYPE
        SYNTAX      Counter64
        MAX-ACCESS  read-only
        STATUS      current
        DESCRIPTION "15 minute reset threshold value for OTU1 far-end
                     section monitor BIP-8 error count at receiving
                     direction."
        ::= { tnStatisticsOtukScalars 11 }

    tnOthOtu1StatRxFeSMBIP8ErrCnt1DayTr OBJECT-TYPE
        SYNTAX      Counter64
        MAX-ACCESS  read-only
        STATUS      current
        DESCRIPTION "1 day threshold value for OTU1 far-end section
                     monitor BIP-8 error count at receiving direction."
        ::= { tnStatisticsOtukScalars 12 }

    tnOthOtu2StatRxRsCorrCnt15MinTr OBJECT-TYPE
        SYNTAX      Counter64
        MAX-ACCESS  read-only
        STATUS      current
        DESCRIPTION "15 minute threshold value for OTU2 FEC correctable
                     error bit count at receiving direction."
        ::= { tnStatisticsOtukScalars 13 }

    tnOthOtu2StatRxRsCorrCnt15MinRtr OBJECT-TYPE
        SYNTAX      Counter64
        MAX-ACCESS  read-only
        STATUS      current
        DESCRIPTION "15 minute reset threshold value for OTU2 FEC
                     correctable error bit count at receiving direction."
        ::= { tnStatisticsOtukScalars 14 }

    tnOthOtu2StatRxRsCorrCnt1DayTr OBJECT-TYPE
        SYNTAX      Counter64
        MAX-ACCESS  read-only
        STATUS      current
        DESCRIPTION "1 day threshold value for OTU2 FEC correctable error
                     bit count at receiving direction."
        ::= { tnStatisticsOtukScalars 15 }

    tnOthOtu2StatRxRsUncorrCnt15MinTr OBJECT-TYPE
        SYNTAX      Counter64
        MAX-ACCESS  read-only
        STATUS      current
        DESCRIPTION "15 minute threshold value for OTU2 FEC un-correctable
                     error block count at receiving direction."
        ::= { tnStatisticsOtukScalars 16 }

    tnOthOtu2StatRxRsUncorrCnt15MinRtr OBJECT-TYPE
        SYNTAX      Counter64
        MAX-ACCESS  read-only
        STATUS      current
        DESCRIPTION "15 minute reset threshold value for OTU2 FEC
                     un-correctable error block count at receiving
                     direction."
        ::= { tnStatisticsOtukScalars 17 }

    tnOthOtu2StatRxRsUncorrCnt1DayTr OBJECT-TYPE
        SYNTAX      Counter64
        MAX-ACCESS  read-only
        STATUS      current
        DESCRIPTION "1 day threshold value for OTU2 FEC un-correctable
                     error block count at receiving direction."
        ::= { tnStatisticsOtukScalars 18 }

    tnOthOtu2StatRxNeSMBIP8ErrCnt15MinTr OBJECT-TYPE
        SYNTAX      Counter64
        MAX-ACCESS  read-only
        STATUS      current
        DESCRIPTION "15 minute threshold value for OTU2 near-end section
                     monitor BIP8 error count at receiving direction."
        ::= { tnStatisticsOtukScalars 19 }

    tnOthOtu2StatRxNeSMBIP8ErrCnt15MinRtr OBJECT-TYPE
        SYNTAX      Counter64
        MAX-ACCESS  read-only
        STATUS      current
        DESCRIPTION "15 minute reset threshold value for OTU2 near-end
                     section monitor BIP-8 error count at receiving
                     direction."
        ::= { tnStatisticsOtukScalars 20 }

    tnOthOtu2StatRxNeSMBIP8ErrCnt1DayTr OBJECT-TYPE
        SYNTAX      Counter64
        MAX-ACCESS  read-only
        STATUS      current
        DESCRIPTION "1 day threshold value for OTU2 near-end section
                     monitor BIP-8 error count at receiving direction."
        ::= { tnStatisticsOtukScalars 21 }

    tnOthOtu2StatRxFeSMBIP8ErrCnt15MinTr OBJECT-TYPE
        SYNTAX      Counter64
        MAX-ACCESS  read-only
        STATUS      current
        DESCRIPTION "15 minute threshold value for OTU2 far-end section
                     monitor BIP8 error count at receiving direction."
        ::= { tnStatisticsOtukScalars 22 }

    tnOthOtu2StatRxFeSMBIP8ErrCnt15MinRtr OBJECT-TYPE
        SYNTAX      Counter64
        MAX-ACCESS  read-only
        STATUS      current
        DESCRIPTION "15 minute reset threshold value for OTU2 far-end
                     section monitor BIP-8 error count at receiving
                     direction."
        ::= { tnStatisticsOtukScalars 23 }

    tnOthOtu2StatRxFeSMBIP8ErrCnt1DayTr OBJECT-TYPE
        SYNTAX      Counter64
        MAX-ACCESS  read-only
        STATUS      current
        DESCRIPTION "1 day threshold value for OTU2 far-end section
                     monitor BIP-8 error count at receiving direction."
        ::= { tnStatisticsOtukScalars 24 }

    tnOthOtu3StatRxRsCorrCnt15MinTr OBJECT-TYPE
        SYNTAX      Counter64
        MAX-ACCESS  read-only
        STATUS      current
        DESCRIPTION "15 minute threshold value for OTU3 FEC correctable
                     error bit count at receiving direction."
        ::= { tnStatisticsOtukScalars 25 }

    tnOthOtu3StatRxRsCorrCnt15MinRtr OBJECT-TYPE
        SYNTAX      Counter64
        MAX-ACCESS  read-only
        STATUS      current
        DESCRIPTION "15 minute reset threshold value for OTU3 FEC
                     correctable error bit count at receiving direction."
        ::= { tnStatisticsOtukScalars 26 }

    tnOthOtu3StatRxRsCorrCnt1DayTr OBJECT-TYPE
        SYNTAX      Counter64
        MAX-ACCESS  read-only
        STATUS      current
        DESCRIPTION "1 day threshold value for OTU3 FEC correctable error
                     bit count at receiving direction."
        ::= { tnStatisticsOtukScalars 27 }

    tnOthOtu3StatRxRsUncorrCnt15MinTr OBJECT-TYPE
        SYNTAX      Counter64
        MAX-ACCESS  read-only
        STATUS      current
        DESCRIPTION "15 minute threshold value for OTU3 FEC un-correctable
                     error block count at receiving direction."
        ::= { tnStatisticsOtukScalars 28 }

    tnOthOtu3StatRxRsUncorrCnt15MinRtr OBJECT-TYPE
        SYNTAX      Counter64
        MAX-ACCESS  read-only
        STATUS      current
        DESCRIPTION "15 minute reset threshold value for OTU3 FEC
                     un-correctable error block count at receiving
                     direction"
        ::= { tnStatisticsOtukScalars 29 }

    tnOthOtu3StatRxRsUncorrCnt1DayTr OBJECT-TYPE
        SYNTAX      Counter64
        MAX-ACCESS  read-only
        STATUS      current
        DESCRIPTION "1 day threshold value for OTU3 FEC un-correctable
                     error block count at receiving direction."
        ::= { tnStatisticsOtukScalars 30 }

    tnOthOtu3StatRxNeSMBIP8ErrCnt15MinTr OBJECT-TYPE
        SYNTAX      Counter64
        MAX-ACCESS  read-only
        STATUS      current
        DESCRIPTION "15 minute threshold value for OTU3 near-end section
                     monitor BIP8 error count at receiving direction."
        ::= { tnStatisticsOtukScalars 31 }

    tnOthOtu3StatRxNeSMBIP8ErrCnt15MinRtr OBJECT-TYPE
        SYNTAX      Counter64
        MAX-ACCESS  read-only
        STATUS      current
        DESCRIPTION "15 minute reset threshold value for OTU3 near-end
                     section monitor BIP-8 error count at receiving
                     direction."
        ::= { tnStatisticsOtukScalars 32 }

    tnOthOtu3StatRxNeSMBIP8ErrCnt1DayTr OBJECT-TYPE
        SYNTAX      Counter64
        MAX-ACCESS  read-only
        STATUS      current
        DESCRIPTION "1 day threshold value for OTU3 near-end section
                     monitor BIP-8 error count at receiving direction."
        ::= { tnStatisticsOtukScalars 33 }

    tnOthOtu3StatRxFeSMBIP8ErrCnt15MinTr OBJECT-TYPE
        SYNTAX      Counter64
        MAX-ACCESS  read-only
        STATUS      current
        DESCRIPTION "15 minute threshold value for OTU3 far-end section
                     monitor BIP8 error count at receiving direction."
        ::= { tnStatisticsOtukScalars 34 }

    tnOthOtu3StatRxFeSMBIP8ErrCnt15MinRtr OBJECT-TYPE
        SYNTAX      Counter64
        MAX-ACCESS  read-only
        STATUS      current
        DESCRIPTION "15 minute reset threshold value for OTU3 far-end
                     section monitor BIP-8 error count at receiving
                     direction."
        ::= { tnStatisticsOtukScalars 35 }

    tnOthOtu3StatRxFeSMBIP8ErrCnt1DayTr OBJECT-TYPE
        SYNTAX      Counter64
        MAX-ACCESS  read-only
        STATUS      current
        DESCRIPTION "1 day threshold value for OTU3 far-end section
                     monitor BIP-8 error count at receiving direction."
        ::= { tnStatisticsOtukScalars 36 }

    tnOthOtu4StatRxRsCorrCnt15MinTr OBJECT-TYPE
        SYNTAX      Counter64
        MAX-ACCESS  read-only
        STATUS      current
        DESCRIPTION "15 minute threshold value for OTU4 FEC correctable
                     error bit count at receiving direction."
        ::= { tnStatisticsOtukScalars 37 }

    tnOthOtu4StatRxRsCorrCnt15MinRtr OBJECT-TYPE
        SYNTAX      Counter64
        MAX-ACCESS  read-only
        STATUS      current
        DESCRIPTION "15 minute reset threshold value for OTU4 FEC
                     correctable error bit count at receiving direction."
        ::= { tnStatisticsOtukScalars 38 }

    tnOthOtu4StatRxRsCorrCnt1DayTr OBJECT-TYPE
        SYNTAX      Counter64
        MAX-ACCESS  read-only
        STATUS      current
        DESCRIPTION "1 day threshold value for OTU4 FEC correctable error
                     bit count at receiving direction."
        ::= { tnStatisticsOtukScalars 39 }

    tnOthOtu4StatRxRsUncorrCnt15MinTr OBJECT-TYPE
        SYNTAX      Counter64
        MAX-ACCESS  read-only
        STATUS      current
        DESCRIPTION "15 minute threshold value for OTU4 FEC un-correctable
                     error block count at receiving direction."
        ::= { tnStatisticsOtukScalars 40 }

    tnOthOtu4StatRxRsUncorrCnt15MinRtr OBJECT-TYPE
        SYNTAX      Counter64
        MAX-ACCESS  read-only
        STATUS      current
        DESCRIPTION "15 minute reset threshold value for OTU4 FEC
                     un-correctable error block count at receiving
                     direction."
        ::= { tnStatisticsOtukScalars 41 }

    tnOthOtu4StatRxRsUncorrCnt1DayTr OBJECT-TYPE
        SYNTAX      Counter64
        MAX-ACCESS  read-only
        STATUS      current
        DESCRIPTION "1 day threshold value for OTU4 FEC un-correctable
                     error block count at receiving direction."
        ::= { tnStatisticsOtukScalars 42 }

    tnOthOtu4StatRxNeSMBIP8ErrCnt15MinTr OBJECT-TYPE
        SYNTAX      Counter64
        MAX-ACCESS  read-only
        STATUS      current
        DESCRIPTION "15 minute threshold value for OTU4 near-end section
                     monitor BIP8 error count at receiving direction."
        ::= { tnStatisticsOtukScalars 43 }

    tnOthOtu4StatRxNeSMBIP8ErrCnt15MinRtr OBJECT-TYPE
        SYNTAX      Counter64
        MAX-ACCESS  read-only
        STATUS      current
        DESCRIPTION "15 minute reset threshold value for OTU4 near-end
                     section monitor BIP-8 error count at receiving
                     direction."
        ::= { tnStatisticsOtukScalars 44 }

    tnOthOtu4StatRxNeSMBIP8ErrCnt1DayTr OBJECT-TYPE
        SYNTAX      Counter64
        MAX-ACCESS  read-only
        STATUS      current
        DESCRIPTION "1 day threshold value for OTU4 near-end section
                     monitor BIP-8 error count at receiving direction."
        ::= { tnStatisticsOtukScalars 45 }

    tnOthOtu4StatRxFeSMBIP8ErrCnt15MinTr OBJECT-TYPE
        SYNTAX      Counter64
        MAX-ACCESS  read-only
        STATUS      current
        DESCRIPTION "15 minute threshold value for OTU4 far-end section
                     monitor BIP8 error count at receiving direction."
        ::= { tnStatisticsOtukScalars 46 }

    tnOthOtu4StatRxFeSMBIP8ErrCnt15MinRtr OBJECT-TYPE
        SYNTAX      Counter64
        MAX-ACCESS  read-only
        STATUS      current
        DESCRIPTION "15 minute reset threshold value for OTU4 far-end
                     section monitor BIP-8 error count at receiving
                     direction."
        ::= { tnStatisticsOtukScalars 47 }

    tnOthOtu4StatRxFeSMBIP8ErrCnt1DayTr OBJECT-TYPE
        SYNTAX      Counter64
        MAX-ACCESS  read-only
        STATUS      current
        DESCRIPTION "1 day threshold value for OTU4 far-end section
                     monitor BIP-8 error count at receiving direction."
        ::= { tnStatisticsOtukScalars 48 }

    tnOthOtukStatRxBERPreFEC15MinTr OBJECT-TYPE
        SYNTAX      Counter64
        MAX-ACCESS  read-only
        STATUS      current
        DESCRIPTION "15 minute threshold value for preFEC BER count."
        ::= { tnStatisticsOtukScalars 49 }

    tnOthOtukStatRxBERPreFEC15MinRtr OBJECT-TYPE
        SYNTAX      Counter64
        MAX-ACCESS  read-only
        STATUS      current
        DESCRIPTION "15 minute reset threshold value for preFEC BER count."
        ::= { tnStatisticsOtukScalars 50 }

    tnOthOtukStatRxBERPreFEC1DayTr OBJECT-TYPE
        SYNTAX      Counter64
        MAX-ACCESS  read-only
        STATUS      current
        DESCRIPTION "1 day threshold value for preFEC BER count."
        ::= { tnStatisticsOtukScalars 51 }

    tnOthOtukStatRxBERPostFEC15MinTr OBJECT-TYPE
        SYNTAX      Counter64
        MAX-ACCESS  read-only
        STATUS      current
        DESCRIPTION "15 minute threshold value for postFEC BER count."
        ::= { tnStatisticsOtukScalars 52 }

    tnOthOtukStatRxBERPostFEC15MinRtr OBJECT-TYPE
        SYNTAX      Counter64
        MAX-ACCESS  read-only
        STATUS      current
        DESCRIPTION "15 minute reset threshold value for postFEC BER count."
        ::= { tnStatisticsOtukScalars 53 }

    tnOthOtukStatRxBERPostFEC1DayTr OBJECT-TYPE
        SYNTAX      Counter64
        MAX-ACCESS  read-only
        STATUS      current
        DESCRIPTION "1 day threshold value for postFEC BER count."
        ::= { tnStatisticsOtukScalars 54 }

    tnOthOtukStatRxNeSMES15MinTr OBJECT-TYPE
        SYNTAX      Counter64
        MAX-ACCESS  read-only
        STATUS      current
        DESCRIPTION "15 minute threshold value for near-end receiving
                     direction section monitor  errored seconds count."
        ::= { tnStatisticsOtukScalars 55 }

    tnOthOtukStatRxNeSMES15MinRtr OBJECT-TYPE
        SYNTAX      Counter64
        MAX-ACCESS  read-only
        STATUS      current
        DESCRIPTION "15 minute reset threshold value for near-end
                     receiving direction section monitor errored
                     seconds count."
        ::= { tnStatisticsOtukScalars 56 }

    tnOthOtukStatRxNeSMES1DayTr OBJECT-TYPE
        SYNTAX      Counter64
        MAX-ACCESS  read-only
        STATUS      current
        DESCRIPTION "15 minute threshold value for near-end receiving
                     direction section monitor errored seconds count."
        ::= { tnStatisticsOtukScalars 57 }

    tnOthOtukStatRxFeSMES15MinTr OBJECT-TYPE
        SYNTAX      Counter64
        MAX-ACCESS  read-only
        STATUS      current
        DESCRIPTION "15 minute threshold value for far-end receiving
                     direction section monitor  errored seconds count."
        ::= { tnStatisticsOtukScalars 58 }

    tnOthOtukStatRxFeSMES15MinRtr OBJECT-TYPE
        SYNTAX      Counter64
        MAX-ACCESS  read-only
        STATUS      current
        DESCRIPTION "15 minute reset threshold value for far-end
                     receiving direction section monitor errored
                     seconds count."
        ::= { tnStatisticsOtukScalars 59 }

    tnOthOtukStatRxFeSMES1DayTr OBJECT-TYPE
        SYNTAX      Counter64
        MAX-ACCESS  read-only
        STATUS      current
        DESCRIPTION "15 minute threshold value for far-end receiving
                     direction section monitor  errored seconds count."
        ::= { tnStatisticsOtukScalars 60 }

    tnOthOtukStatRxNeSMSES15MinTr OBJECT-TYPE
        SYNTAX      Counter64
        MAX-ACCESS  read-only
        STATUS      current
        DESCRIPTION "15 minute threshold value for near-end receiving
                     direction section monitor severely errored seconds
                     count."
        ::= { tnStatisticsOtukScalars 61 }

    tnOthOtukStatRxNeSMSES15MinRtr OBJECT-TYPE
        SYNTAX      Counter64
        MAX-ACCESS  read-only
        STATUS      current
        DESCRIPTION "15 minute reset threshold value for near-end
                     receiving direction section monitor severely
                     errored seconds count."
        ::= { tnStatisticsOtukScalars 62 }

    tnOthOtukStatRxNeSMSES1DayTr OBJECT-TYPE
        SYNTAX      Counter64
        MAX-ACCESS  read-only
        STATUS      current
        DESCRIPTION "15 minute threshold value for near-end receiving
                     direction section monitor severely errored seconds
                     count."
        ::= { tnStatisticsOtukScalars 63 }

    tnOthOtukStatRxFeSMSES15MinTr OBJECT-TYPE
        SYNTAX      Counter64
        MAX-ACCESS  read-only
        STATUS      current
        DESCRIPTION "15 minute threshold value for far-end receiving
                     direction section monitor severely errored seconds
                     count."
        ::= { tnStatisticsOtukScalars 64 }

    tnOthOtukStatRxFeSMSES15MinRtr OBJECT-TYPE
        SYNTAX      Counter64
        MAX-ACCESS  read-only
        STATUS      current
        DESCRIPTION "15 minute reset threshold value for far -end receiving
                     direction section monitor severely errored seconds
                     count."
        ::= { tnStatisticsOtukScalars 65 }

    tnOthOtukStatRxFeSMSES1DayTr OBJECT-TYPE
        SYNTAX      Counter64
        MAX-ACCESS  read-only
        STATUS      current
        DESCRIPTION "15 minute threshold value for far -end receiving
                     direction section monitor severely errored seconds
                     count."
        ::= { tnStatisticsOtukScalars 66 }

    tnOthOtukStatRxNeSMUAS15MinTr OBJECT-TYPE
        SYNTAX      Counter64
        MAX-ACCESS  read-only
        STATUS      current
        DESCRIPTION "15 minute threshold value for near-end receiving
                     direction section monitor unavailable seconds count."
        ::= { tnStatisticsOtukScalars 67 }

    tnOthOtukStatRxNeSMUAS15MinRtr OBJECT-TYPE
        SYNTAX      Counter64
        MAX-ACCESS  read-only
        STATUS      current
        DESCRIPTION "15 minute reset threshold value for near-end receiving
                     direction section monitor unavailable seconds count."
        ::= { tnStatisticsOtukScalars 68 }

    tnOthOtukStatRxNeSMUAS1DayTr OBJECT-TYPE
        SYNTAX      Counter64
        MAX-ACCESS  read-only
        STATUS      current
        DESCRIPTION "15 minute threshold value for near-end receiving
                     direction section monitor unavailable seconds count."
        ::= { tnStatisticsOtukScalars 69 }

    tnOthOtukStatRxFeSMUAS15MinTr OBJECT-TYPE
        SYNTAX      Counter64
        MAX-ACCESS  read-only
        STATUS      current
        DESCRIPTION "15 minute threshold value for far-end receiving
                     direction section monitor unavailable seconds count."
        ::= { tnStatisticsOtukScalars 70 }

    tnOthOtukStatRxFeSMUAS15MinRtr OBJECT-TYPE
        SYNTAX      Counter64
        MAX-ACCESS  read-only
        STATUS      current
        DESCRIPTION "15 minute reset threshold value for far -end receiving
                     direction section monitor unavailable seconds count."
        ::= { tnStatisticsOtukScalars 71 }

    tnOthOtukStatRxFeSMUAS1DayTr OBJECT-TYPE
        SYNTAX      Counter64
        MAX-ACCESS  read-only
        STATUS      current
        DESCRIPTION "15 minute threshold value for far -end receiving
                     direction section monitor unavailable seconds count."
        ::= { tnStatisticsOtukScalars 72 }

    tnOthOtukStatRxNeIAES15MinTr OBJECT-TYPE
        SYNTAX      Counter64
        MAX-ACCESS  read-only
        STATUS      current
        DESCRIPTION "15 minute threshold value for near-end receiving
                     direction IAE defect seconds count."
        ::= { tnStatisticsOtukScalars 73 }

    tnOthOtukStatRxNeIAES15MinRtr OBJECT-TYPE
        SYNTAX      Counter64
        MAX-ACCESS  read-only
        STATUS      current
        DESCRIPTION "15 minute reset threshold value for near-end receiving
                     direction IAE defect seconds count."
        ::= { tnStatisticsOtukScalars 74 }

    tnOthOtukStatRxNeIAES1DayTr OBJECT-TYPE
        SYNTAX      Counter64
        MAX-ACCESS  read-only
        STATUS      current
        DESCRIPTION "15 minute threshold value for near-end receiving
                     direction IAE defect seconds count."
        ::= { tnStatisticsOtukScalars 75 }

    tnOthOtukStatRxFeIAES15MinTr OBJECT-TYPE
        SYNTAX      Counter64
        MAX-ACCESS  read-only
        STATUS      current
        DESCRIPTION "15 minute threshold value for far-end receiving
                     direction IAE defect seconds count."
        ::= { tnStatisticsOtukScalars 76 }

    tnOthOtukStatRxFeIAES15MinRtr OBJECT-TYPE
        SYNTAX      Counter64
        MAX-ACCESS  read-only
        STATUS      current
        DESCRIPTION "15 minute reset threshold value for far-end receiving
                     direction IAE defect seconds count."
        ::= { tnStatisticsOtukScalars 77 }

    tnOthOtukStatRxFeIAES1DayTr OBJECT-TYPE
        SYNTAX      Counter64
        MAX-ACCESS  read-only
        STATUS      current
        DESCRIPTION "15 minute threshold value for far -end receiving
                     direction IAE defect seconds count."
        ::= { tnStatisticsOtukScalars 78 }

    tnOthOtucStatRxNeSMBIP8ErrCnt15MinTr OBJECT-TYPE
        SYNTAX      Counter64
        MAX-ACCESS  read-only
        STATUS      current
        DESCRIPTION "."
        ::= { tnStatisticsOtukScalars 79 }

    tnOthOtucStatRxNeSMBIP8ErrCnt15MinRtr OBJECT-TYPE
        SYNTAX      Counter64
        MAX-ACCESS  read-only
        STATUS      current
        DESCRIPTION "."
        ::= { tnStatisticsOtukScalars 80 }

    tnOthOtucStatRxNeSMBIP8ErrCnt1DayTr OBJECT-TYPE
        SYNTAX      Counter64
        MAX-ACCESS  read-only
        STATUS      current
        DESCRIPTION "."
        ::= { tnStatisticsOtukScalars 81 }

    tnOthOtucStatRxFeSMBIP8ErrCnt15MinTr OBJECT-TYPE
        SYNTAX      Counter64
        MAX-ACCESS  read-only
        STATUS      current
        DESCRIPTION "."
        ::= { tnStatisticsOtukScalars 82 }

    tnOthOtucStatRxFeSMBIP8ErrCnt15MinRtr OBJECT-TYPE
        SYNTAX      Counter64
        MAX-ACCESS  read-only
        STATUS      current
        DESCRIPTION "."
        ::= { tnStatisticsOtukScalars 83 }

    tnOthOtucStatRxFeSMBIP8ErrCnt1DayTr OBJECT-TYPE
        SYNTAX      Counter64
        MAX-ACCESS  read-only
        STATUS      current
        DESCRIPTION "."
        ::= { tnStatisticsOtukScalars 84 }

    tnOthOtutc1StatRxNeSMBIP8ErrCnt15MinTr OBJECT-TYPE
        SYNTAX      Counter64
        MAX-ACCESS  read-only
        STATUS      current
        DESCRIPTION "15 minute threshold value for OTUTC1 near-end section
                     monitor BIP8 error count at receiving direction."
        ::= { tnStatisticsOtukScalars 85 }

    tnOthOtutc1StatRxNeSMBIP8ErrCnt15MinRtr OBJECT-TYPE
        SYNTAX      Counter64
        MAX-ACCESS  read-only
        STATUS      current
        DESCRIPTION "15 minute reset threshold value for OTUTC1 near-end section
                     monitor BIP-8 error count at receiving direction."
        ::= { tnStatisticsOtukScalars 86 }

    tnOthOtutc1StatRxNeSMBIP8ErrCnt1DayTr OBJECT-TYPE
        SYNTAX      Counter64
        MAX-ACCESS  read-only
        STATUS      current
        DESCRIPTION "1 day threshold value for OTUTC1 near-end section monitor
                     BIP-8 error count at receiving direction."
        ::= { tnStatisticsOtukScalars 87 }

    tnOthOtutc1StatRxFeSMBIP8ErrCnt15MinTr OBJECT-TYPE
        SYNTAX      Counter64
        MAX-ACCESS  read-only
        STATUS      current
        DESCRIPTION "15 minute threshold value for OTUTC1 far-end section
                     monitor BIP8 error count at receiving direction."
        ::= { tnStatisticsOtukScalars 88 }

    tnOthOtutc1StatRxFeSMBIP8ErrCnt15MinRtr OBJECT-TYPE
        SYNTAX      Counter64
        MAX-ACCESS  read-only
        STATUS      current
        DESCRIPTION "15 minute reset threshold value for OTUTC1 far-end section
                     monitor BIP-8 error count at receiving direction."
        ::= { tnStatisticsOtukScalars 89 }

    tnOthOtutc1StatRxFeSMBIP8ErrCnt1DayTr OBJECT-TYPE
        SYNTAX      Counter64
        MAX-ACCESS  read-only
        STATUS      current
        DESCRIPTION "1 day threshold value for OTUTC1 far-end section monitor
                     BIP-8 error count at receiving direction."
        ::= { tnStatisticsOtukScalars 90 }

    tnOthOtutc4StatRxNeSMBIP8ErrCnt15MinTr OBJECT-TYPE
        SYNTAX      Counter64
        MAX-ACCESS  read-only
        STATUS      current
        DESCRIPTION "15 minute threshold value for OTUTC4 near-end section monitor
                     BIP8 error count at receiving direction."
        ::= { tnStatisticsOtukScalars 91 }

    tnOthOtutc4StatRxNeSMBIP8ErrCnt15MinRtr OBJECT-TYPE
        SYNTAX      Counter64
        MAX-ACCESS  read-only
        STATUS      current
        DESCRIPTION "15 minute reset threshold value for OTUTC4 near-end section
                    monitor BIP-8 error count at receiving direction."
        ::= { tnStatisticsOtukScalars 92 }

    tnOthOtutc4StatRxNeSMBIP8ErrCnt1DayTr OBJECT-TYPE
        SYNTAX      Counter64
        MAX-ACCESS  read-only
        STATUS      current
        DESCRIPTION "1 day threshold value for OTUTC4 near-end section monitor
                     BIP-8 error count at receiving direction."
        ::= { tnStatisticsOtukScalars 93 }

    tnOthOtutc4StatRxFeSMBIP8ErrCnt15MinTr OBJECT-TYPE
        SYNTAX      Counter64
        MAX-ACCESS  read-only
        STATUS      current
        DESCRIPTION "15 minute threshold value for OTUTC4 far-end section monitor
                     BIP8 error count at receiving direction."
        ::= { tnStatisticsOtukScalars 94 }

    tnOthOtutc4StatRxFeSMBIP8ErrCnt15MinRtr OBJECT-TYPE
        SYNTAX      Counter64
        MAX-ACCESS  read-only
        STATUS      current
        DESCRIPTION "15 minute reset threshold value for OTUTC4 far-end section
                     monitor BIP-8 error count at receiving direction."
        ::= { tnStatisticsOtukScalars 95 }

    tnOthOtutc4StatRxFeSMBIP8ErrCnt1DayTr OBJECT-TYPE
        SYNTAX      Counter64
        MAX-ACCESS  read-only
        STATUS      current
        DESCRIPTION "1 day threshold value for OTUTC4 far-end section monitor
                     BIP-8 error count at receiving direction."
        ::= { tnStatisticsOtukScalars 96 }

--------------------------------------------------------------------------------
-- Statistics Sonet Threshold Scalars
--------------------------------------------------------------------------------
    tnSonetStatsOC768RxCVS15MinTr OBJECT-TYPE
        SYNTAX      Counter32
        MAX-ACCESS  read-only
        STATUS      current
        DESCRIPTION "15 minute threshold value of OC768 RX coding violations
                     - section."
        ::= { tnStatisticsSonetScalars 1 }

    tnSonetStatsOC192RxCVS15MinTr OBJECT-TYPE
        SYNTAX      Counter32
        MAX-ACCESS  read-only
        STATUS      current
        DESCRIPTION "15 minute threshold value of OC192 RX coding violations
                     - section."
        ::= { tnStatisticsSonetScalars 2 }

    tnSonetStatsOC48RxCVS15MinTr OBJECT-TYPE
        SYNTAX      Counter32
        MAX-ACCESS  read-only
        STATUS      current
        DESCRIPTION "15 minute threshold value of OC48 RX coding violations
                     - section."
        ::= { tnStatisticsSonetScalars 3 }

    tnSonetStatsOC12RxCVS15MinTr OBJECT-TYPE
        SYNTAX      Counter32
        MAX-ACCESS  read-only
        STATUS      current
        DESCRIPTION "15 minute threshold value of OC12 RX coding violations
                     - section."
        ::= { tnStatisticsSonetScalars 4 }

    tnSonetStatsOC3RxCVS15MinTr OBJECT-TYPE
        SYNTAX      Counter32
        MAX-ACCESS  read-only
        STATUS      current
        DESCRIPTION "15 minute threshold value of OC3 RX coding violations
                     - section."
        ::= { tnStatisticsSonetScalars 5 }

    tnSonetStatsRxESS15MinTr OBJECT-TYPE
        SYNTAX      Counter32
        MAX-ACCESS  read-only
        STATUS      current
        DESCRIPTION "15 minute threshold value of RX errored seconds
                     - section."
        ::= { tnStatisticsSonetScalars 6 }

    tnSonetStatsRxSESS15MinTr OBJECT-TYPE
        SYNTAX      Counter32
        MAX-ACCESS  read-only
        STATUS      current
        DESCRIPTION "15 minute threshold value of RX severely errored
                     seconds - section."
        ::= { tnStatisticsSonetScalars 7 }

    tnSonetStatsRxSEFSS15MinTr OBJECT-TYPE
        SYNTAX      Counter32
        MAX-ACCESS  read-only
        STATUS      current
        DESCRIPTION "15 minute threshold value of RX severely errored
                     frame seconds - section."
        ::= { tnStatisticsSonetScalars 8 }

    tnSonetStatsOC768RxCVL15MinTr OBJECT-TYPE
        SYNTAX      Counter32
        MAX-ACCESS  read-only
        STATUS      current
        DESCRIPTION "15 minute threshold value of OC768 RX coding violations
                     - line."
        ::= { tnStatisticsSonetScalars 9 }

    tnSonetStatsOC192RxCVL15MinTr OBJECT-TYPE
        SYNTAX      Counter32
        MAX-ACCESS  read-only
        STATUS      current
        DESCRIPTION "15 minute threshold value of OC192 RX coding violations
                     - line."
        ::= { tnStatisticsSonetScalars 10 }

    tnSonetStatsOC48RxCVL15MinTr OBJECT-TYPE
        SYNTAX      Counter32
        MAX-ACCESS  read-only
        STATUS      current
        DESCRIPTION "15 minute threshold value of OC48 RX coding violations
                     - line."
        ::= { tnStatisticsSonetScalars 11 }

    tnSonetStatsOC12RxCVL15MinTr OBJECT-TYPE
        SYNTAX      Counter32
        MAX-ACCESS  read-only
        STATUS      current
        DESCRIPTION "15 minute threshold value of OC12 RX coding violations
                     - line."
        ::= { tnStatisticsSonetScalars 12 }

    tnSonetStatsOC3RxCVL15MinTr OBJECT-TYPE
        SYNTAX      Counter32
        MAX-ACCESS  read-only
        STATUS      current
        DESCRIPTION "15 minute threshold value of OC3 RX coding violations
                     - line."
        ::= { tnStatisticsSonetScalars 13 }

    tnSonetStatsRxESL15MinTr OBJECT-TYPE
        SYNTAX      Counter32
        MAX-ACCESS  read-only
        STATUS      current
        DESCRIPTION "15 minute threshold value of RX errored seconds
                     - line."
        ::= { tnStatisticsSonetScalars 14 }

    tnSonetStatsRxSESL15MinTr OBJECT-TYPE
        SYNTAX      Counter32
        MAX-ACCESS  read-only
        STATUS      current
        DESCRIPTION "15 minute threshold value of RX severly errored
                     seconds - line."
        ::= { tnStatisticsSonetScalars 15 }

    tnSonetStatsRxUASL15MinTr OBJECT-TYPE
        SYNTAX      Counter32
        MAX-ACCESS  read-only
        STATUS      current
        DESCRIPTION "15 minute threshold value of RX unavailable seconds
                     - line."
        ::= { tnStatisticsSonetScalars 16 }

    tnSonetStatsOC768TxCVS15MinTr OBJECT-TYPE
        SYNTAX      Counter32
        MAX-ACCESS  read-only
        STATUS      current
        DESCRIPTION "15 minute threshold value of OC768 TX coding violations
                     - section."
        ::= { tnStatisticsSonetScalars 17 }

    tnSonetStatsOC192TxCVS15MinTr OBJECT-TYPE
        SYNTAX      Counter32
        MAX-ACCESS  read-only
        STATUS      current
        DESCRIPTION "15 minute threshold value of OC192 TX coding violations
                     - section."
        ::= { tnStatisticsSonetScalars 18 }

    tnSonetStatsOC48TxCVS15MinTr OBJECT-TYPE
        SYNTAX      Counter32
        MAX-ACCESS  read-only
        STATUS      current
        DESCRIPTION "15 minute threshold value of OC48 TX coding violations
                     - section."
        ::= { tnStatisticsSonetScalars 19 }

    tnSonetStatsOC12TxCVS15MinTr OBJECT-TYPE
        SYNTAX      Counter32
        MAX-ACCESS  read-only
        STATUS      current
        DESCRIPTION "15 minute threshold value of OC12 TX coding violations
                     - section."
        ::= { tnStatisticsSonetScalars 20 }

    tnSonetStatsOC3TxCVS15MinTr OBJECT-TYPE
        SYNTAX      Counter32
        MAX-ACCESS  read-only
        STATUS      current
        DESCRIPTION "15 minute threshold value of OC3 TX coding violations
                     - section."
        ::= { tnStatisticsSonetScalars 21 }

    tnSonetStatsTxESS15MinTr OBJECT-TYPE
        SYNTAX      Counter32
        MAX-ACCESS  read-only
        STATUS      current
        DESCRIPTION "15 minute threshold value of TX errored seconds
                     - section."
        ::= { tnStatisticsSonetScalars 22 }

    tnSonetStatsTxSESS15MinTr OBJECT-TYPE
        SYNTAX      Counter32
        MAX-ACCESS  read-only
        STATUS      current
        DESCRIPTION "15 minute threshold value of TX severely errored
                     seconds - section."
        ::= { tnStatisticsSonetScalars 23 }

    tnSonetStatsTxSEFSS15MinTr OBJECT-TYPE
        SYNTAX      Counter32
        MAX-ACCESS  read-only
        STATUS      current
        DESCRIPTION "15 minute threshold value of TX severely errored
                     frame seconds - section."
        ::= { tnStatisticsSonetScalars 24 }

    tnSonetStatsOC768TxCVL15MinTr OBJECT-TYPE
        SYNTAX      Counter32
        MAX-ACCESS  read-only
        STATUS      current
        DESCRIPTION "15 minute threshold value of OC768 TX coding violations
                     - line."
        ::= { tnStatisticsSonetScalars 25 }

    tnSonetStatsOC192TxCVL15MinTr OBJECT-TYPE
        SYNTAX      Counter32
        MAX-ACCESS  read-only
        STATUS      current
        DESCRIPTION "15 minute threshold value of OC192 TX coding violations
                     - line."
        ::= { tnStatisticsSonetScalars 26 }

    tnSonetStatsOC48TxCVL15MinTr OBJECT-TYPE
        SYNTAX      Counter32
        MAX-ACCESS  read-only
        STATUS      current
        DESCRIPTION "15 minute threshold value of OC48 TX coding violations
                     - line."
        ::= { tnStatisticsSonetScalars 27 }

    tnSonetStatsOC12TxCVL15MinTr OBJECT-TYPE
        SYNTAX      Counter32
        MAX-ACCESS  read-only
        STATUS      current
        DESCRIPTION "15 minute threshold value of OC12 TX coding violations
                     - line."
        ::= { tnStatisticsSonetScalars 28 }

    tnSonetStatsOC3TxCVL15MinTr OBJECT-TYPE
        SYNTAX      Counter32
        MAX-ACCESS  read-only
        STATUS      current
        DESCRIPTION "15 minute threshold value of OC3 TX coding violations
                     - line."
        ::= { tnStatisticsSonetScalars 29 }

    tnSonetStatsTxESL15MinTr OBJECT-TYPE
        SYNTAX      Counter32
        MAX-ACCESS  read-only
        STATUS      current
        DESCRIPTION "15 minute threshold value of TX errored seconds
                     - line."
        ::= { tnStatisticsSonetScalars 30 }

    tnSonetStatsTxSESL15MinTr OBJECT-TYPE
        SYNTAX      Counter32
        MAX-ACCESS  read-only
        STATUS      current
        DESCRIPTION "15 minute threshold value of TX severly errored
                     seconds - line."
        ::= { tnStatisticsSonetScalars 31 }

    tnSonetStatsTxUASL15MinTr OBJECT-TYPE
        SYNTAX      Counter32
        MAX-ACCESS  read-only
        STATUS      current
        DESCRIPTION "15 minute threshold value of TX unavailable seconds
                     - line."
        ::= { tnStatisticsSonetScalars 32 }

    tnSonetStatsRxUASS15MinTr OBJECT-TYPE
        SYNTAX      Counter32
        MAX-ACCESS  read-only
        STATUS      current
        DESCRIPTION "15 minute threshold value of RX unavailable seconds
                     - section."
        ::= { tnStatisticsSonetScalars 33 }

    tnSonetStatsTxUASS15MinTr OBJECT-TYPE
        SYNTAX      Counter32
        MAX-ACCESS  read-only
        STATUS      current
        DESCRIPTION "15 minute threshold value of TX unavailable seconds
                     - section."
        ::= { tnStatisticsSonetScalars 34 }

    tnSonetStatsOC768RxCVS1DayTr OBJECT-TYPE
        SYNTAX      Counter32
        MAX-ACCESS  read-only
        STATUS      current
        DESCRIPTION "1 day threshold value of OC768 RX coding violations
                     - section."
        ::= { tnStatisticsSonetScalars 35 }

    tnSonetStatsOC192RxCVS1DayTr OBJECT-TYPE
        SYNTAX      Counter32
        MAX-ACCESS  read-only
        STATUS      current
        DESCRIPTION "1 day threshold value of OC192 RX coding violations
                     - section."
        ::= { tnStatisticsSonetScalars 36 }

    tnSonetStatsOC48RxCVS1DayTr OBJECT-TYPE
        SYNTAX      Counter32
        MAX-ACCESS  read-only
        STATUS      current
        DESCRIPTION "1 day threshold value of OC48 RX coding violations
                     - section."
        ::= { tnStatisticsSonetScalars 37 }

    tnSonetStatsOC12RxCVS1DayTr OBJECT-TYPE
        SYNTAX      Counter32
        MAX-ACCESS  read-only
        STATUS      current
        DESCRIPTION "1 day threshold value of OC12 RX coding violations
                     - section."
        ::= { tnStatisticsSonetScalars 38 }

    tnSonetStatsOC3RxCVS1DayTr OBJECT-TYPE
        SYNTAX      Counter32
        MAX-ACCESS  read-only
        STATUS      current
        DESCRIPTION "1 day threshold value of OC3 RX coding violations
                     - section."
        ::= { tnStatisticsSonetScalars 39 }

    tnSonetStatsRxESS1DayTr OBJECT-TYPE
        SYNTAX      Counter32
        MAX-ACCESS  read-only
        STATUS      current
        DESCRIPTION "1 day threshold value of RX errored seconds - section."
        ::= { tnStatisticsSonetScalars 40 }

    tnSonetStatsRxSESS1DayTr OBJECT-TYPE
        SYNTAX      Counter32
        MAX-ACCESS  read-only
        STATUS      current
        DESCRIPTION "1 day threshold value of RX severely errored seconds
                     - section."
        ::= { tnStatisticsSonetScalars 41 }

    tnSonetStatsRxSEFSS1DayTr OBJECT-TYPE
        SYNTAX      Counter32
        MAX-ACCESS  read-only
        STATUS      current
        DESCRIPTION "1 day threshold value of RX severely errored frame
                     seconds - section."
        ::= { tnStatisticsSonetScalars 42 }

    tnSonetStatsOC768RxCVL1DayTr OBJECT-TYPE
        SYNTAX      Counter32
        MAX-ACCESS  read-only
        STATUS      current
        DESCRIPTION "1 day threshold value of OC768 RX coding violations
                     - line."
        ::= { tnStatisticsSonetScalars 43 }

    tnSonetStatsOC192RxCVL1DayTr OBJECT-TYPE
        SYNTAX      Counter32
        MAX-ACCESS  read-only
        STATUS      current
        DESCRIPTION "1 day threshold value of OC192 RX coding violations
                     - line."
        ::= { tnStatisticsSonetScalars 44 }

    tnSonetStatsOC48RxCVL1DayTr OBJECT-TYPE
        SYNTAX      Counter32
        MAX-ACCESS  read-only
        STATUS      current
        DESCRIPTION "1 day threshold value of OC48 RX coding violations
                     - line."
        ::= { tnStatisticsSonetScalars 45 }

    tnSonetStatsOC12RxCVL1DayTr OBJECT-TYPE
        SYNTAX      Counter32
        MAX-ACCESS  read-only
        STATUS      current
        DESCRIPTION "1 day threshold value of OC12 RX coding violations
                     - line."
        ::= { tnStatisticsSonetScalars 46 }

    tnSonetStatsOC3RxCVL1DayTr OBJECT-TYPE
        SYNTAX      Counter32
        MAX-ACCESS  read-only
        STATUS      current
        DESCRIPTION "1 day threshold value of OC3 RX coding violations
                     - line."
        ::= { tnStatisticsSonetScalars 47 }

    tnSonetStatsRxESL1DayTr OBJECT-TYPE
        SYNTAX      Counter32
        MAX-ACCESS  read-only
        STATUS      current
        DESCRIPTION "1 day threshold value of RX errored seconds - line."
        ::= { tnStatisticsSonetScalars 48 }

    tnSonetStatsRxSESL1DayTr OBJECT-TYPE
        SYNTAX      Counter32
        MAX-ACCESS  read-only
        STATUS      current
        DESCRIPTION "1 day threshold value of RX severly errored seconds
                     - line."
        ::= { tnStatisticsSonetScalars 49 }

    tnSonetStatsRxUASL1DayTr OBJECT-TYPE
        SYNTAX      Counter32
        MAX-ACCESS  read-only
        STATUS      current
        DESCRIPTION "1 day threshold value of RX unavailable seconds
                     - line."
        ::= { tnStatisticsSonetScalars 50 }

    tnSonetStatsOC768TxCVS1DayTr OBJECT-TYPE
        SYNTAX      Counter32
        MAX-ACCESS  read-only
        STATUS      current
        DESCRIPTION "1 day threshold value of OC768 TX coding violations
                     - section."
        ::= { tnStatisticsSonetScalars 51 }

    tnSonetStatsOC192TxCVS1DayTr OBJECT-TYPE
        SYNTAX      Counter32
        MAX-ACCESS  read-only
        STATUS      current
        DESCRIPTION "1 day threshold value of OC192 TX coding violations
                     - section."
        ::= { tnStatisticsSonetScalars 52 }

    tnSonetStatsOC48TxCVS1DayTr OBJECT-TYPE
        SYNTAX      Counter32
        MAX-ACCESS  read-only
        STATUS      current
        DESCRIPTION "1 day threshold value of OC48 TX coding violations
                     - section."
        ::= { tnStatisticsSonetScalars 53 }

    tnSonetStatsOC12TxCVS1DayTr OBJECT-TYPE
        SYNTAX      Counter32
        MAX-ACCESS  read-only
        STATUS      current
        DESCRIPTION "1 day threshold value of OC12 TX coding violations
                     - section."
        ::= { tnStatisticsSonetScalars 54 }

    tnSonetStatsOC3TxCVS1DayTr OBJECT-TYPE
        SYNTAX      Counter32
        MAX-ACCESS  read-only
        STATUS      current
        DESCRIPTION "1 day threshold value of OC3 TX coding violations
                     - section."
        ::= { tnStatisticsSonetScalars 55 }

    tnSonetStatsTxESS1DayTr OBJECT-TYPE
        SYNTAX      Counter32
        MAX-ACCESS  read-only
        STATUS      current
        DESCRIPTION "1 day threshold value of TX errored seconds - section."
        ::= { tnStatisticsSonetScalars 56 }

    tnSonetStatsTxSESS1DayTr OBJECT-TYPE
        SYNTAX      Counter32
        MAX-ACCESS  read-only
        STATUS      current
        DESCRIPTION "1 day threshold value of TX severely errored seconds
                     - section."
        ::= { tnStatisticsSonetScalars 57 }

    tnSonetStatsTxSEFSS1DayTr OBJECT-TYPE
        SYNTAX      Counter32
        MAX-ACCESS  read-only
        STATUS      current
        DESCRIPTION "1 day threshold value of TX severely errored frame
                     seconds - section."
        ::= { tnStatisticsSonetScalars 58 }

    tnSonetStatsOC768TxCVL1DayTr OBJECT-TYPE
        SYNTAX      Counter32
        MAX-ACCESS  read-only
        STATUS      current
        DESCRIPTION "1 day threshold value of OC768 TX coding violations
                     - line."
        ::= { tnStatisticsSonetScalars 59 }

    tnSonetStatsOC192TxCVL1DayTr OBJECT-TYPE
        SYNTAX      Counter32
        MAX-ACCESS  read-only
        STATUS      current
        DESCRIPTION "1 day threshold value of OC192 TX coding violations
                     - line."
        ::= { tnStatisticsSonetScalars 60 }

    tnSonetStatsOC48TxCVL1DayTr OBJECT-TYPE
        SYNTAX      Counter32
        MAX-ACCESS  read-only
        STATUS      current
        DESCRIPTION "1 day threshold value of OC48 TX coding violations
                     - line."
        ::= { tnStatisticsSonetScalars 61 }

    tnSonetStatsOC12TxCVL1DayTr OBJECT-TYPE
        SYNTAX      Counter32
        MAX-ACCESS  read-only
        STATUS      current
        DESCRIPTION "1 day threshold value of OC12 TX coding violations
                     - line."
        ::= { tnStatisticsSonetScalars 62 }

    tnSonetStatsOC3TxCVL1DayTr OBJECT-TYPE
        SYNTAX      Counter32
        MAX-ACCESS  read-only
        STATUS      current
        DESCRIPTION "1 day threshold value of OC3 TX coding violations
                     - line."
        ::= { tnStatisticsSonetScalars 63 }

    tnSonetStatsTxESL1DayTr OBJECT-TYPE
        SYNTAX      Counter32
        MAX-ACCESS  read-only
        STATUS      current
        DESCRIPTION "1 day threshold value of TX errored seconds - line."
        ::= { tnStatisticsSonetScalars 64 }

    tnSonetStatsTxSESL1DayTr OBJECT-TYPE
        SYNTAX      Counter32
        MAX-ACCESS  read-only
        STATUS      current
        DESCRIPTION "1 day threshold value of TX severly errored seconds
                     - line."
        ::= { tnStatisticsSonetScalars 65 }

    tnSonetStatsTxUASL1DayTr OBJECT-TYPE
        SYNTAX      Counter32
        MAX-ACCESS  read-only
        STATUS      current
        DESCRIPTION "1 day threshold value of TX unavailable seconds
                     - line."
        ::= { tnStatisticsSonetScalars 66 }

    tnSonetStatsRxUASS1DayTr OBJECT-TYPE
        SYNTAX      Counter32
        MAX-ACCESS  read-only
        STATUS      current
        DESCRIPTION "1 day threshold value of RX unavailable seconds
                     - section."
        ::= { tnStatisticsSonetScalars 67 }

    tnSonetStatsTxUASS1DayTr OBJECT-TYPE
        SYNTAX      Counter32
        MAX-ACCESS  read-only
        STATUS      current
        DESCRIPTION "1 day threshold value of TX unavailable seconds
                     - section."
        ::= { tnStatisticsSonetScalars 68 }

    tnSonetStatsOC768RxFECVL15MinTr OBJECT-TYPE
        SYNTAX      Counter32
        MAX-ACCESS  read-only
        STATUS      current
        DESCRIPTION "15 minute threshold value of OC768 RX far end coding
                     violations - line."
        ::= { tnStatisticsSonetScalars 69 }

    tnSonetStatsOC192RxFECVL15MinTr OBJECT-TYPE
        SYNTAX      Counter32
        MAX-ACCESS  read-only
        STATUS      current
        DESCRIPTION "15 minute threshold value of OC192 RX far end coding
                     violations - line."
        ::= { tnStatisticsSonetScalars 70 }

    tnSonetStatsOC48RxFECVL15MinTr OBJECT-TYPE
        SYNTAX      Counter32
        MAX-ACCESS  read-only
        STATUS      current
        DESCRIPTION "15 minute threshold value of OC48 RX far end coding
                     violations - line."
        ::= { tnStatisticsSonetScalars 71 }

    tnSonetStatsOC12RxFECVL15MinTr OBJECT-TYPE
        SYNTAX      Counter32
        MAX-ACCESS  read-only
        STATUS      current
        DESCRIPTION "15 minute threshold value of OC12 RX far end coding
                     violations - line."
        ::= { tnStatisticsSonetScalars 72 }

    tnSonetStatsOC3RxFECVL15MinTr OBJECT-TYPE
        SYNTAX      Counter32
        MAX-ACCESS  read-only
        STATUS      current
        DESCRIPTION "15 minute threshold value of OC3 RX far end coding
                     violations - line."
        ::= { tnStatisticsSonetScalars 73 }

    tnSonetStatsRxFEESL15MinTr OBJECT-TYPE
        SYNTAX      Counter32
        MAX-ACCESS  read-only
        STATUS      current
        DESCRIPTION "15 minute threshold value of RX far end errored
                     seconds - line."
        ::= { tnStatisticsSonetScalars 74 }

    tnSonetStatsRxFESESL15MinTr OBJECT-TYPE
        SYNTAX      Counter32
        MAX-ACCESS  read-only
        STATUS      current
        DESCRIPTION "15 minute threshold value of RX far end severely
                     errored seconds - line."
        ::= { tnStatisticsSonetScalars 75 }

    tnSonetStatsRxFEUASL15MinTr OBJECT-TYPE
        SYNTAX      Counter32
        MAX-ACCESS  read-only
        STATUS      current
        DESCRIPTION "15 minute threshold value of RX far end unavailable
                     seconds - line."
        ::= { tnStatisticsSonetScalars 76 }

    tnSonetStatsOC768RxFECVL1DayTr OBJECT-TYPE
        SYNTAX      Counter32
        MAX-ACCESS  read-only
        STATUS      current
        DESCRIPTION "1 day threshold value of OC768 RX far end coding
                     violations - line."
        ::= { tnStatisticsSonetScalars 77 }

    tnSonetStatsOC192RxFECVL1DayTr OBJECT-TYPE
        SYNTAX      Counter32
        MAX-ACCESS  read-only
        STATUS      current
        DESCRIPTION "1 day threshold value of OC192 RX far end coding
                     violations - line."
        ::= { tnStatisticsSonetScalars 78 }

    tnSonetStatsOC48RxFECVL1DayTr OBJECT-TYPE
        SYNTAX      Counter32
        MAX-ACCESS  read-only
        STATUS      current
        DESCRIPTION "1 day threshold value of OC48 RX far end coding
                     violations - line."
        ::= { tnStatisticsSonetScalars 79 }

    tnSonetStatsOC12RxFECVL1DayTr OBJECT-TYPE
        SYNTAX      Counter32
        MAX-ACCESS  read-only
        STATUS      current
        DESCRIPTION "1 day threshold value of OC12 RX far end coding
                     violations - line."
        ::= { tnStatisticsSonetScalars 80 }

    tnSonetStatsOC3RxFECVL1DayTr OBJECT-TYPE
        SYNTAX      Counter32
        MAX-ACCESS  read-only
        STATUS      current
        DESCRIPTION "1 day threshold value of OC3 RX far end coding
                     violations - line."
        ::= { tnStatisticsSonetScalars 81 }

    tnSonetStatsRxFEESL1DayTr OBJECT-TYPE
        SYNTAX      Counter32
        MAX-ACCESS  read-only
        STATUS      current
        DESCRIPTION "1 day threshold value of RX far end errored seconds
                     - line."
        ::= { tnStatisticsSonetScalars 82 }

    tnSonetStatsRxFESESL1DayTr OBJECT-TYPE
        SYNTAX      Counter32
        MAX-ACCESS  read-only
        STATUS      current
        DESCRIPTION "1 day threshold value of RX far end severely errored
                     seconds - line."
        ::= { tnStatisticsSonetScalars 83 }

    tnSonetStatsRxFEUASL1DayTr OBJECT-TYPE
        SYNTAX      Counter32
        MAX-ACCESS  read-only
        STATUS      current
        DESCRIPTION "1 day threshold value of RX far end unavailable
                     seconds - line."
        ::= { tnStatisticsSonetScalars 84 }

--------------------------------------------------------------------------------
-- Statistics SDH Threshold Scalars
--------------------------------------------------------------------------------
    tnSdhStatsSTM256RxRSEB15MinTr OBJECT-TYPE
        SYNTAX      Counter32
        MAX-ACCESS  read-only
        STATUS      current
        DESCRIPTION "15 minute threshold value of STM256 RX regenerator
                     section - errored blocks."
        ::= { tnStatisticsSdhScalars 1 }

    tnSdhStatsSTM64RxRSEB15MinTr OBJECT-TYPE
        SYNTAX      Counter32
        MAX-ACCESS  read-only
        STATUS      current
        DESCRIPTION "15 minute threshold value of STM64 RX regenerator
                     section - errored blocks."
        ::= { tnStatisticsSdhScalars 2 }

    tnSdhStatsSTM16RxRSEB15MinTr OBJECT-TYPE
        SYNTAX      Counter32
        MAX-ACCESS  read-only
        STATUS      current
        DESCRIPTION "15 minute threshold value of STM16 RX regenerator
                     section - errored blocks."
        ::= { tnStatisticsSdhScalars 3 }

    tnSdhStatsSTM4RxRSEB15MinTr OBJECT-TYPE
        SYNTAX      Counter32
        MAX-ACCESS  read-only
        STATUS      current
        DESCRIPTION "15 minute threshold value of STM4 RX regenerator
                     section - errored blocks."
        ::= { tnStatisticsSdhScalars 4 }

    tnSdhStatsSTM1RxRSEB15MinTr OBJECT-TYPE
        SYNTAX      Counter32
        MAX-ACCESS  read-only
        STATUS      current
        DESCRIPTION "15 minute threshold value of STM1 RX regenerator
                     section - errored blocks."
        ::= { tnStatisticsSdhScalars 5 }

    tnSdhStatsRxRSES15MinTr OBJECT-TYPE
        SYNTAX      Counter32
        MAX-ACCESS  read-only
        STATUS      current
        DESCRIPTION "15 minute threshold value of RX regenerator section
                     - errored seconds."
        ::= { tnStatisticsSdhScalars 6 }

    tnSdhStatsRxRSSES15MinTr OBJECT-TYPE
        SYNTAX      Counter32
        MAX-ACCESS  read-only
        STATUS      current
        DESCRIPTION "15 minute threshold value of RX regenerator section
                     - severely errored seconds."
        ::= { tnStatisticsSdhScalars 7 }

    tnSdhStatsSTM256RxMSEB15MinTr OBJECT-TYPE
        SYNTAX      Counter32
        MAX-ACCESS  read-only
        STATUS      current
        DESCRIPTION "15 minute threshold value of STM256 RX multiplex
                     section - errored blocks."
        ::= { tnStatisticsSdhScalars 8 }

    tnSdhStatsSTM64RxMSEB15MinTr OBJECT-TYPE
        SYNTAX      Counter32
        MAX-ACCESS  read-only
        STATUS      current
        DESCRIPTION "15 minute threshold value of STM64 RX multiplex
                     section - errored blocks."
        ::= { tnStatisticsSdhScalars 9 }

    tnSdhStatsSTM16RxMSEB15MinTr OBJECT-TYPE
        SYNTAX      Counter32
        MAX-ACCESS  read-only
        STATUS      current
        DESCRIPTION "15 minute threshold value of STM16 RX multiplex
                     section - errored blocks."
        ::= { tnStatisticsSdhScalars 10 }

    tnSdhStatsSTM4RxMSEB15MinTr OBJECT-TYPE
        SYNTAX      Counter32
        MAX-ACCESS  read-only
        STATUS      current
        DESCRIPTION "15 minute threshold value of STM4 RX multiplex
                     section - errored blocks."
        ::= { tnStatisticsSdhScalars 11 }

    tnSdhStatsSTM1RxMSEB15MinTr OBJECT-TYPE
        SYNTAX      Counter32
        MAX-ACCESS  read-only
        STATUS      current
        DESCRIPTION "15 minute threshold value of STM1 RX multiplex
                     section - errored blocks."
        ::= { tnStatisticsSdhScalars 12 }

    tnSdhStatsRxMSES15MinTr OBJECT-TYPE
        SYNTAX      Counter32
        MAX-ACCESS  read-only
        STATUS      current
        DESCRIPTION "15 minute threshold value of RX multiplex section
                     - errored seconds."
        ::= { tnStatisticsSdhScalars 13 }

    tnSdhStatsRxMSSES15MinTr OBJECT-TYPE
        SYNTAX      Counter32
        MAX-ACCESS  read-only
        STATUS      current
        DESCRIPTION "15 minute threshold value of RX multiplex section
                     - severely errored seconds."
        ::= { tnStatisticsSdhScalars 14 }

    tnSdhStatsRxMSUAS15MinTr OBJECT-TYPE
        SYNTAX      Counter32
        MAX-ACCESS  read-only
        STATUS      current
        DESCRIPTION "15 minute threshold value of RX multiplex section
                     - unavailable seconds."
        ::= { tnStatisticsSdhScalars 15 }

    tnSdhStatsSTM256TxRSEB15MinTr OBJECT-TYPE
        SYNTAX      Counter32
        MAX-ACCESS  read-only
        STATUS      current
        DESCRIPTION "15 minute threshold value of STM256 TX regenerator
                     section - errored blocks."
        ::= { tnStatisticsSdhScalars 16 }

    tnSdhStatsSTM64TxRSEB15MinTr OBJECT-TYPE
        SYNTAX      Counter32
        MAX-ACCESS  read-only
        STATUS      current
        DESCRIPTION "15 minute threshold value of STM64 TX regenerator
                     section - errored blocks."
        ::= { tnStatisticsSdhScalars 17 }

    tnSdhStatsSTM16TxRSEB15MinTr OBJECT-TYPE
        SYNTAX      Counter32
        MAX-ACCESS  read-only
        STATUS      current
        DESCRIPTION "15 minute threshold value of STM16 TX regenerator
                     section - errored blocks."
        ::= { tnStatisticsSdhScalars 18 }

    tnSdhStatsSTM4TxRSEB15MinTr OBJECT-TYPE
        SYNTAX      Counter32
        MAX-ACCESS  read-only
        STATUS      current
        DESCRIPTION "15 minute threshold value of STM4 TX regenerator
                     section - errored blocks."
        ::= { tnStatisticsSdhScalars 19 }

    tnSdhStatsSTM1TxRSEB15MinTr OBJECT-TYPE
        SYNTAX      Counter32
        MAX-ACCESS  read-only
        STATUS      current
        DESCRIPTION "15 minute threshold value of STM1 TX regenerator
                     section - errored blocks."
        ::= { tnStatisticsSdhScalars 20 }

    tnSdhStatsTxRSES15MinTr OBJECT-TYPE
        SYNTAX      Counter32
        MAX-ACCESS  read-only
        STATUS      current
        DESCRIPTION "15 minute threshold value of TX regenerator section
                     - errored seconds."
        ::= { tnStatisticsSdhScalars 21 }

    tnSdhStatsTxRSSES15MinTr OBJECT-TYPE
        SYNTAX      Counter32
        MAX-ACCESS  read-only
        STATUS      current
        DESCRIPTION "15 minute threshold value of TX regenerator section
                     - severely errored seconds."
        ::= { tnStatisticsSdhScalars 22 }

    tnSdhStatsSTM256TxMSEB15MinTr OBJECT-TYPE
        SYNTAX      Counter32
        MAX-ACCESS  read-only
        STATUS      current
        DESCRIPTION "15 minute threshold value of STM256 TX multiplex
                     section - errored blocks."
        ::= { tnStatisticsSdhScalars 23 }

    tnSdhStatsSTM64TxMSEB15MinTr OBJECT-TYPE
        SYNTAX      Counter32
        MAX-ACCESS  read-only
        STATUS      current
        DESCRIPTION "15 minute threshold value of STM64 TX multiplex
                     section - errored blocks."
        ::= { tnStatisticsSdhScalars 24 }

    tnSdhStatsSTM16TxMSEB15MinTr OBJECT-TYPE
        SYNTAX      Counter32
        MAX-ACCESS  read-only
        STATUS      current
        DESCRIPTION "15 minute threshold value of STM16 TX multiplex
                     section - errored blocks."
        ::= { tnStatisticsSdhScalars 25 }

    tnSdhStatsSTM4TxMSEB15MinTr OBJECT-TYPE
        SYNTAX      Counter32
        MAX-ACCESS  read-only
        STATUS      current
        DESCRIPTION "15 minute threshold value of STM4 TX multiplex
                     section - errored blocks."
        ::= { tnStatisticsSdhScalars 26 }

    tnSdhStatsSTM1TxMSEB15MinTr OBJECT-TYPE
        SYNTAX      Counter32
        MAX-ACCESS  read-only
        STATUS      current
        DESCRIPTION "15 minute threshold value of STM1 TX multiplex
                     section - errored blocks."
        ::= { tnStatisticsSdhScalars 27 }

    tnSdhStatsTxMSES15MinTr OBJECT-TYPE
        SYNTAX      Counter32
        MAX-ACCESS  read-only
        STATUS      current
        DESCRIPTION "15 minute threshold value of TX multiplex section
                     - errored seconds."
        ::= { tnStatisticsSdhScalars 28 }

    tnSdhStatsTxMSSES15MinTr OBJECT-TYPE
        SYNTAX      Counter32
        MAX-ACCESS  read-only
        STATUS      current
        DESCRIPTION "15 minute threshold value of TX multiplex section
                     - severely errored seconds."
        ::= { tnStatisticsSdhScalars 29 }

    tnSdhStatsTxMSUAS15MinTr OBJECT-TYPE
        SYNTAX      Counter32
        MAX-ACCESS  read-only
        STATUS      current
        DESCRIPTION "15 minute threshold value of TX multiplex section
                     - unavailable seconds."
        ::= { tnStatisticsSdhScalars 30 }

    tnSdhStatsRxRSUAS15MinTr OBJECT-TYPE
        SYNTAX      Counter32
        MAX-ACCESS  read-only
        STATUS      current
        DESCRIPTION "15 minute threshold value of RX regenerator section
                     - unavailable seconds."
        ::= { tnStatisticsSdhScalars 31 }

    tnSdhStatsTxRSUAS15MinTr OBJECT-TYPE
        SYNTAX      Counter32
        MAX-ACCESS  read-only
        STATUS      current
        DESCRIPTION "15 minute threshold value of TX regenerator section
                     - unavailable seconds."
        ::= { tnStatisticsSdhScalars 32 }

    tnSdhStatsSTM256RxRSEB1DayTr OBJECT-TYPE
        SYNTAX      Counter32
        MAX-ACCESS  read-only
        STATUS      current
        DESCRIPTION "1 day threshold value of STM256 RX regenerator section
                     - errored blocks."
        ::= { tnStatisticsSdhScalars 33 }

    tnSdhStatsSTM64RxRSEB1DayTr OBJECT-TYPE
        SYNTAX      Counter32
        MAX-ACCESS  read-only
        STATUS      current
        DESCRIPTION "1 day threshold value of STM64 RX regenerator section
                     - errored blocks."
        ::= { tnStatisticsSdhScalars 34 }

    tnSdhStatsSTM16RxRSEB1DayTr OBJECT-TYPE
        SYNTAX      Counter32
        MAX-ACCESS  read-only
        STATUS      current
        DESCRIPTION "1 day threshold value of STM16 RX regenerator section
                     - errored blocks."
        ::= { tnStatisticsSdhScalars 35 }

    tnSdhStatsSTM4RxRSEB1DayTr OBJECT-TYPE
        SYNTAX      Counter32
        MAX-ACCESS  read-only
        STATUS      current
        DESCRIPTION "1 day threshold value of STM4 RX regenerator section
                     - errored blocks."
        ::= { tnStatisticsSdhScalars 36 }

    tnSdhStatsSTM1RxRSEB1DayTr OBJECT-TYPE
        SYNTAX      Counter32
        MAX-ACCESS  read-only
        STATUS      current
        DESCRIPTION "1 day threshold value of STM1 RX regenerator section
                     - errored blocks."
        ::= { tnStatisticsSdhScalars 37 }

    tnSdhStatsRxRSES1DayTr OBJECT-TYPE
        SYNTAX      Counter32
        MAX-ACCESS  read-only
        STATUS      current
        DESCRIPTION "1 day threshold value of RX regenerator section
                     - errored seconds."
        ::= { tnStatisticsSdhScalars 38 }

    tnSdhStatsRxRSSES1DayTr OBJECT-TYPE
        SYNTAX      Counter32
        MAX-ACCESS  read-only
        STATUS      current
        DESCRIPTION "1 day threshold value of RX regenerator section
                     - severely errored seconds."
        ::= { tnStatisticsSdhScalars 39 }

    tnSdhStatsSTM256RxMSEB1DayTr OBJECT-TYPE
        SYNTAX      Counter32
        MAX-ACCESS  read-only
        STATUS      current
        DESCRIPTION "1 day threshold value of STM256 RX multiplex section
                     - errored blocks."
        ::= { tnStatisticsSdhScalars 40 }

    tnSdhStatsSTM64RxMSEB1DayTr OBJECT-TYPE
        SYNTAX      Counter32
        MAX-ACCESS  read-only
        STATUS      current
        DESCRIPTION "1 day threshold value of STM64 RX multiplex section
                     - errored blocks."
        ::= { tnStatisticsSdhScalars 41 }

    tnSdhStatsSTM16RxMSEB1DayTr OBJECT-TYPE
        SYNTAX      Counter32
        MAX-ACCESS  read-only
        STATUS      current
        DESCRIPTION "1 day threshold value of STM16 RX multiplex section
                     - errored blocks."
        ::= { tnStatisticsSdhScalars 42 }

    tnSdhStatsSTM4RxMSEB1DayTr OBJECT-TYPE
        SYNTAX      Counter32
        MAX-ACCESS  read-only
        STATUS      current
        DESCRIPTION "1 day threshold value of STM4 RX multiplex section
                     - errored blocks."
        ::= { tnStatisticsSdhScalars 43 }

    tnSdhStatsSTM1RxMSEB1DayTr OBJECT-TYPE
        SYNTAX      Counter32
        MAX-ACCESS  read-only
        STATUS      current
        DESCRIPTION "1 day threshold value of STM1 RX multiplex section
                     - errored blocks."
        ::= { tnStatisticsSdhScalars 44 }

    tnSdhStatsRxMSES1DayTr OBJECT-TYPE
        SYNTAX      Counter32
        MAX-ACCESS  read-only
        STATUS      current
        DESCRIPTION "1 day threshold value of RX multiplex section
                     - errored seconds."
        ::= { tnStatisticsSdhScalars 45 }

    tnSdhStatsRxMSSES1DayTr OBJECT-TYPE
        SYNTAX      Counter32
        MAX-ACCESS  read-only
        STATUS      current
        DESCRIPTION "1 day threshold value of RX multiplex section
                     - severely errored seconds."
        ::= { tnStatisticsSdhScalars 46 }

    tnSdhStatsRxMSUAS1DayTr OBJECT-TYPE
        SYNTAX      Counter32
        MAX-ACCESS  read-only
        STATUS      current
        DESCRIPTION "1 day threshold value of RX multiplex section
                     - unavailable seconds."
        ::= { tnStatisticsSdhScalars 47 }

    tnSdhStatsSTM256TxRSEB1DayTr OBJECT-TYPE
        SYNTAX      Counter32
        MAX-ACCESS  read-only
        STATUS      current
        DESCRIPTION "1 day threshold value of STM256 TX regenerator section
                     - errored blocks."
        ::= { tnStatisticsSdhScalars 48 }

    tnSdhStatsSTM64TxRSEB1DayTr OBJECT-TYPE
        SYNTAX      Counter32
        MAX-ACCESS  read-only
        STATUS      current
        DESCRIPTION "1 day threshold value of STM64 TX regenerator section
                     - errored blocks."
        ::= { tnStatisticsSdhScalars 49 }

    tnSdhStatsSTM16TxRSEB1DayTr OBJECT-TYPE
        SYNTAX      Counter32
        MAX-ACCESS  read-only
        STATUS      current
        DESCRIPTION "1 day threshold value of STM16 TX regenerator section
                     - errored blocks."
        ::= { tnStatisticsSdhScalars 50 }

    tnSdhStatsSTM4TxRSEB1DayTr OBJECT-TYPE
        SYNTAX      Counter32
        MAX-ACCESS  read-only
        STATUS      current
        DESCRIPTION "1 day threshold value of STM4 TX regenerator section
                     - errored blocks."
        ::= { tnStatisticsSdhScalars 51 }

    tnSdhStatsSTM1TxRSEB1DayTr OBJECT-TYPE
        SYNTAX      Counter32
        MAX-ACCESS  read-only
        STATUS      current
        DESCRIPTION "1 day threshold value of STM1 TX regenerator section
                     - errored blocks."
        ::= { tnStatisticsSdhScalars 52 }

    tnSdhStatsTxRSES1DayTr OBJECT-TYPE
        SYNTAX      Counter32
        MAX-ACCESS  read-only
        STATUS      current
        DESCRIPTION "1 day threshold value of TX regenerator section
                     - errored seconds."
        ::= { tnStatisticsSdhScalars 53 }

    tnSdhStatsTxRSSES1DayTr OBJECT-TYPE
        SYNTAX      Counter32
        MAX-ACCESS  read-only
        STATUS      current
        DESCRIPTION "1 day threshold value of TX regenerator section
                     - severely errored seconds."
        ::= { tnStatisticsSdhScalars 54 }

    tnSdhStatsSTM256TxMSEB1DayTr OBJECT-TYPE
        SYNTAX      Counter32
        MAX-ACCESS  read-only
        STATUS      current
        DESCRIPTION "1 day threshold value of STM256 TX multiplex section
                     - errored blocks."
        ::= { tnStatisticsSdhScalars 55 }

    tnSdhStatsSTM64TxMSEB1DayTr OBJECT-TYPE
        SYNTAX      Counter32
        MAX-ACCESS  read-only
        STATUS      current
        DESCRIPTION "1 day threshold value of STM64 TX multiplex section
                     - errored blocks."
        ::= { tnStatisticsSdhScalars 56 }

    tnSdhStatsSTM16TxMSEB1DayTr OBJECT-TYPE
        SYNTAX      Counter32
        MAX-ACCESS  read-only
        STATUS      current
        DESCRIPTION "1 day threshold value of STM16 TX multiplex section
                     - errored blocks."
        ::= { tnStatisticsSdhScalars 57 }

    tnSdhStatsSTM4TxMSEB1DayTr OBJECT-TYPE
        SYNTAX      Counter32
        MAX-ACCESS  read-only
        STATUS      current
        DESCRIPTION "1 day threshold value of STM4 TX multiplex section
                     - errored blocks."
        ::= { tnStatisticsSdhScalars 58 }

    tnSdhStatsSTM1TxMSEB1DayTr OBJECT-TYPE
        SYNTAX      Counter32
        MAX-ACCESS  read-only
        STATUS      current
        DESCRIPTION "1 day threshold value of STM1 TX multiplex section
                     - errored blocks."
        ::= { tnStatisticsSdhScalars 59 }

    tnSdhStatsTxMSES1DayTr OBJECT-TYPE
        SYNTAX      Counter32
        MAX-ACCESS  read-only
        STATUS      current
        DESCRIPTION "1 day threshold value of TX multiplex section
                     - errored seconds."
        ::= { tnStatisticsSdhScalars 60 }

    tnSdhStatsTxMSSES1DayTr OBJECT-TYPE
        SYNTAX      Counter32
        MAX-ACCESS  read-only
        STATUS      current
        DESCRIPTION "1 day threshold value of TX multiplex section
                     - severely errored seconds."
        ::= { tnStatisticsSdhScalars 61 }

    tnSdhStatsTxMSUAS1DayTr OBJECT-TYPE
        SYNTAX      Counter32
        MAX-ACCESS  read-only
        STATUS      current
        DESCRIPTION "1 day threshold value of TX multiplex section
                     - unavailable seconds."
        ::= { tnStatisticsSdhScalars 62 }

    tnSdhStatsRxRSUAS1DayTr OBJECT-TYPE
        SYNTAX      Counter32
        MAX-ACCESS  read-only
        STATUS      current
        DESCRIPTION "1 day threshold value of RX regenerator section
                     - unavailable seconds."
        ::= { tnStatisticsSdhScalars 63 }

    tnSdhStatsTxRSUAS1DayTr OBJECT-TYPE
        SYNTAX      Counter32
        MAX-ACCESS  read-only
        STATUS      current
        DESCRIPTION "1 day threshold value of TX regenerator section
                     - unavailable seconds."
        ::= { tnStatisticsSdhScalars 64 }

    tnSdhStatsSTM256RxRSEB15MinRtr OBJECT-TYPE
        SYNTAX      Counter32
        MAX-ACCESS  read-only
        STATUS      current
        DESCRIPTION "15 minute reset threshold value of STM256 RX
                     regenerator section - errored blocks."
        ::= { tnStatisticsSdhScalars 65 }

    tnSdhStatsSTM64RxRSEB15MinRtr OBJECT-TYPE
        SYNTAX      Counter32
        MAX-ACCESS  read-only
        STATUS      current
        DESCRIPTION "15 minute reset threshold value of STM64 RX
                     regenerator section - errored blocks."
        ::= { tnStatisticsSdhScalars 66 }

    tnSdhStatsSTM16RxRSEB15MinRtr OBJECT-TYPE
        SYNTAX      Counter32
        MAX-ACCESS  read-only
        STATUS      current
        DESCRIPTION "15 minute reset threshold value of STM16 RX
                     regenerator section - errored blocks."
        ::= { tnStatisticsSdhScalars 67 }

    tnSdhStatsSTM4RxRSEB15MinRtr OBJECT-TYPE
        SYNTAX      Counter32
        MAX-ACCESS  read-only
        STATUS      current
        DESCRIPTION "15 minute reset threshold value of STM4 RX
                     regenerator section - errored blocks."
        ::= { tnStatisticsSdhScalars 68 }

    tnSdhStatsSTM1RxRSEB15MinRtr OBJECT-TYPE
        SYNTAX      Counter32
        MAX-ACCESS  read-only
        STATUS      current
        DESCRIPTION "15 minute reset threshold value of STM1 RX
                     regenerator section - errored blocks."
        ::= { tnStatisticsSdhScalars 69 }

    tnSdhStatsRxRSES15MinRtr OBJECT-TYPE
        SYNTAX      Counter32
        MAX-ACCESS  read-only
        STATUS      current
        DESCRIPTION "15 minute reset threshold value of RX regenerator
                     section - errored seconds."
        ::= { tnStatisticsSdhScalars 70 }

    tnSdhStatsRxRSSES15MinRtr OBJECT-TYPE
        SYNTAX      Counter32
        MAX-ACCESS  read-only
        STATUS      current
        DESCRIPTION "15 minute reset threshold value of RX regenerator
                     section - severely errored seconds."
        ::= { tnStatisticsSdhScalars 71 }

    tnSdhStatsSTM256RxMSEB15MinRtr OBJECT-TYPE
        SYNTAX      Counter32
        MAX-ACCESS  read-only
        STATUS      current
        DESCRIPTION "15 minute reset threshold value of STM256 RX multiplex
                     section - errored blocks."
        ::= { tnStatisticsSdhScalars 72 }

    tnSdhStatsSTM64RxMSEB15MinRtr OBJECT-TYPE
        SYNTAX      Counter32
        MAX-ACCESS  read-only
        STATUS      current
        DESCRIPTION "15 minute reset threshold value of STM64 RX multiplex
                     section - errored blocks."
        ::= { tnStatisticsSdhScalars 73 }

    tnSdhStatsSTM16RxMSEB15MinRtr OBJECT-TYPE
        SYNTAX      Counter32
        MAX-ACCESS  read-only
        STATUS      current
        DESCRIPTION "15 minute reset threshold value of STM16 RX multiplex
                     section - errored blocks."
        ::= { tnStatisticsSdhScalars 74 }

    tnSdhStatsSTM4RxMSEB15MinRtr OBJECT-TYPE
        SYNTAX      Counter32
        MAX-ACCESS  read-only
        STATUS      current
        DESCRIPTION "15 minute reset threshold value of STM4 RX multiplex
                     section - errored blocks."
        ::= { tnStatisticsSdhScalars 75 }

    tnSdhStatsSTM1RxMSEB15MinRtr OBJECT-TYPE
        SYNTAX      Counter32
        MAX-ACCESS  read-only
        STATUS      current
        DESCRIPTION "15 minute reset threshold value of STM1 RX multiplex
                     section - errored blocks."
        ::= { tnStatisticsSdhScalars 76 }

    tnSdhStatsRxMSES15MinRtr OBJECT-TYPE
        SYNTAX      Counter32
        MAX-ACCESS  read-only
        STATUS      current
        DESCRIPTION "15 minute reset threshold value of RX multiplex
                     section - errored seconds."
        ::= { tnStatisticsSdhScalars 77 }

    tnSdhStatsRxMSSES15MinRtr OBJECT-TYPE
        SYNTAX      Counter32
        MAX-ACCESS  read-only
        STATUS      current
        DESCRIPTION "15 minute reset threshold value of RX multiplex
                     section - severely errored seconds."
        ::= { tnStatisticsSdhScalars 78 }

    tnSdhStatsRxMSUAS15MinRtr OBJECT-TYPE
        SYNTAX      Counter32
        MAX-ACCESS  read-only
        STATUS      current
        DESCRIPTION "15 minute reset threshold value of RX multiplex
                     section - unavailable seconds."
        ::= { tnStatisticsSdhScalars 79 }

    tnSdhStatsSTM256TxRSEB15MinRtr OBJECT-TYPE
        SYNTAX      Counter32
        MAX-ACCESS  read-only
        STATUS      current
        DESCRIPTION "15 minute reset threshold value of STM256 TX regenerator
                     section - errored blocks."
        ::= { tnStatisticsSdhScalars 80 }

    tnSdhStatsSTM64TxRSEB15MinRtr OBJECT-TYPE
        SYNTAX      Counter32
        MAX-ACCESS  read-only
        STATUS      current
        DESCRIPTION "15 minute reset threshold value of STM64 TX regenerator
                     section - errored blocks."
        ::= { tnStatisticsSdhScalars 81 }

    tnSdhStatsSTM16TxRSEB15MinRtr OBJECT-TYPE
        SYNTAX      Counter32
        MAX-ACCESS  read-only
        STATUS      current
        DESCRIPTION "15 minute reset threshold value of STM16 TX regenerator
                     section - errored blocks."
        ::= { tnStatisticsSdhScalars 82 }

    tnSdhStatsSTM4TxRSEB15MinRtr OBJECT-TYPE
        SYNTAX      Counter32
        MAX-ACCESS  read-only
        STATUS      current
        DESCRIPTION "15 minute reset threshold value of STM4 TX regenerator
                     section - errored blocks."
        ::= { tnStatisticsSdhScalars 83 }

    tnSdhStatsSTM1TxRSEB15MinRtr OBJECT-TYPE
        SYNTAX      Counter32
        MAX-ACCESS  read-only
        STATUS      current
        DESCRIPTION "15 minute reset threshold value of STM1 TX regenerator
                     section - errored blocks."
        ::= { tnStatisticsSdhScalars 84 }

    tnSdhStatsTxRSES15MinRtr OBJECT-TYPE
        SYNTAX      Counter32
        MAX-ACCESS  read-only
        STATUS      current
        DESCRIPTION "15 minute reset threshold value of RX regenerator
                     section - errored seconds."
        ::= { tnStatisticsSdhScalars 85 }

    tnSdhStatsTxRSSES15MinRtr OBJECT-TYPE
        SYNTAX      Counter32
        MAX-ACCESS  read-only
        STATUS      current
        DESCRIPTION "15 minute reset threshold value of TX regenerator
                     section - severely errored seconds."
        ::= { tnStatisticsSdhScalars 86 }

    tnSdhStatsSTM256TxMSEB15MinRtr OBJECT-TYPE
        SYNTAX      Counter32
        MAX-ACCESS  read-only
        STATUS      current
        DESCRIPTION "15 minute reset threshold value of STM256 TX multiplex
                     section - errored blocks."
        ::= { tnStatisticsSdhScalars 87 }

    tnSdhStatsSTM64TxMSEB15MinRtr OBJECT-TYPE
        SYNTAX      Counter32
        MAX-ACCESS  read-only
        STATUS      current
        DESCRIPTION "15 minute reset threshold value of STM64 TX multiplex
                     section - errored blocks."
        ::= { tnStatisticsSdhScalars 88 }

    tnSdhStatsSTM16TxMSEB15MinRtr OBJECT-TYPE
        SYNTAX      Counter32
        MAX-ACCESS  read-only
        STATUS      current
        DESCRIPTION "15 minute reset threshold value of STM16 TX multiplex
                     section - errored blocks."
        ::= { tnStatisticsSdhScalars 89 }

    tnSdhStatsSTM4TxMSEB15MinRtr OBJECT-TYPE
        SYNTAX      Counter32
        MAX-ACCESS  read-only
        STATUS      current
        DESCRIPTION "15 minute reset threshold value of STM4 TX multiplex
                     section - errored blocks."
        ::= { tnStatisticsSdhScalars 90 }

    tnSdhStatsSTM1TxMSEB15MinRtr OBJECT-TYPE
        SYNTAX      Counter32
        MAX-ACCESS  read-only
        STATUS      current
        DESCRIPTION "15 minute reset threshold value of STM1 TX multiplex
                     section - errored blocks."
        ::= { tnStatisticsSdhScalars 91 }

    tnSdhStatsTxMSES15MinRtr OBJECT-TYPE
        SYNTAX      Counter32
        MAX-ACCESS  read-only
        STATUS      current
        DESCRIPTION "15 minute reset threshold value of TX multiplex
                     section - errored seconds."
        ::= { tnStatisticsSdhScalars 92 }

    tnSdhStatsTxMSSES15MinRtr OBJECT-TYPE
        SYNTAX      Counter32
        MAX-ACCESS  read-only
        STATUS      current
        DESCRIPTION "15 minute reset threshold value of TX multiplex
                     section - severely errored seconds."
        ::= { tnStatisticsSdhScalars 93 }

    tnSdhStatsTxMSUAS15MinRtr OBJECT-TYPE
        SYNTAX      Counter32
        MAX-ACCESS  read-only
        STATUS      current
        DESCRIPTION "15 minute reset threshold value of TX multiplex
                     section - unavailable seconds."
        ::= { tnStatisticsSdhScalars 94 }

    tnSdhStatsRxRSUAS15MinRtr OBJECT-TYPE
        SYNTAX      Counter32
        MAX-ACCESS  read-only
        STATUS      current
        DESCRIPTION "15 minute reset threshold value of TX regenerator
                     section - unavailable seconds."
        ::= { tnStatisticsSdhScalars 95 }

    tnSdhStatsTxRSUAS15MinRtr OBJECT-TYPE
        SYNTAX      Counter32
        MAX-ACCESS  read-only
        STATUS      current
        DESCRIPTION "15 minute reset threshold value of TX regenerator
                     section - unavailable seconds."
        ::= { tnStatisticsSdhScalars 96 }

    tnSdhStatsSTM256RxMSFEEB15MinTr OBJECT-TYPE
        SYNTAX      Counter32
        MAX-ACCESS  read-only
        STATUS      current
        DESCRIPTION "15 minute threshold value of STM256 RX far end multiplex
                     section - errored blocks."
        ::= { tnStatisticsSdhScalars 97 }

    tnSdhStatsSTM64RxMSFEEB15MinTr OBJECT-TYPE
        SYNTAX      Counter32
        MAX-ACCESS  read-only
        STATUS      current
        DESCRIPTION "15 minute threshold value of STM64 RX far end multiplex
                     section - errored blocks."
        ::= { tnStatisticsSdhScalars 98 }

    tnSdhStatsSTM16RxMSFEEB15MinTr OBJECT-TYPE
        SYNTAX      Counter32
        MAX-ACCESS  read-only
        STATUS      current
        DESCRIPTION "15 minute threshold value of STM16 RX far end multiplex
                     section - errored blocks."
        ::= { tnStatisticsSdhScalars 99 }

    tnSdhStatsSTM4RxMSFEEB15MinTr OBJECT-TYPE
        SYNTAX      Counter32
        MAX-ACCESS  read-only
        STATUS      current
        DESCRIPTION "15 minute threshold value of STM4 RX far end multiplex
                     section - errored blocks."
        ::= { tnStatisticsSdhScalars 100 }

    tnSdhStatsSTM1RxMSFEEB15MinTr OBJECT-TYPE
        SYNTAX      Counter32
        MAX-ACCESS  read-only
        STATUS      current
        DESCRIPTION "15 minute threshold value of STM1 RX far end multiplex
                     section - errored blocks."
        ::= { tnStatisticsSdhScalars 101 }

    tnSdhStatsRxMSFEES15MinTr OBJECT-TYPE
        SYNTAX      Counter32
        MAX-ACCESS  read-only
        STATUS      current
        DESCRIPTION "15 minute threshold value of RX far end multiplex
                     section - errored seconds."
        ::= { tnStatisticsSdhScalars 102 }

    tnSdhStatsRxMSFESES15MinTr OBJECT-TYPE
        SYNTAX      Counter32
        MAX-ACCESS  read-only
        STATUS      current
        DESCRIPTION "15 minute threshold value of RX far end multiplex
                     section - severely errored seconds."
        ::= { tnStatisticsSdhScalars 103 }

    tnSdhStatsRxMSFEUAS15MinTr OBJECT-TYPE
        SYNTAX      Counter32
        MAX-ACCESS  read-only
        STATUS      current
        DESCRIPTION "15 minute threshold value of RX far end multiplex
                     section - unavailable seconds."
        ::= { tnStatisticsSdhScalars 104 }

    tnSdhStatsSTM256RxMSFEEB1DayTr OBJECT-TYPE
        SYNTAX      Counter32
        MAX-ACCESS  read-only
        STATUS      current
        DESCRIPTION "1 day threshold value of STM256 RX far end multiplex
                     section - errored blocks."
        ::= { tnStatisticsSdhScalars 105 }

    tnSdhStatsSTM64RxMSFEEB1DayTr OBJECT-TYPE
        SYNTAX      Counter32
        MAX-ACCESS  read-only
        STATUS      current
        DESCRIPTION "1 day threshold value of STM64 RX far end multiplex
                     section - errored blocks."
        ::= { tnStatisticsSdhScalars 106 }

    tnSdhStatsSTM16RxMSFEEB1DayTr OBJECT-TYPE
        SYNTAX      Counter32
        MAX-ACCESS  read-only
        STATUS      current
        DESCRIPTION "1 day threshold value of STM16 RX far end multiplex
                     section - errored blocks."
        ::= { tnStatisticsSdhScalars 107 }

    tnSdhStatsSTM4RxMSFEEB1DayTr OBJECT-TYPE
        SYNTAX      Counter32
        MAX-ACCESS  read-only
        STATUS      current
        DESCRIPTION "1 day threshold value of STM4 RX far end multiplex
                     section - errored blocks."
        ::= { tnStatisticsSdhScalars 108 }

    tnSdhStatsSTM1RxMSFEEB1DayTr OBJECT-TYPE
        SYNTAX      Counter32
        MAX-ACCESS  read-only
        STATUS      current
        DESCRIPTION "1 day threshold value of STM1 RX far end multiplex
                     section - errored blocks."
        ::= { tnStatisticsSdhScalars 109 }

    tnSdhStatsRxMSFEES1DayTr OBJECT-TYPE
        SYNTAX      Counter32
        MAX-ACCESS  read-only
        STATUS      current
        DESCRIPTION "1 day threshold value of RX far end multiplex section
                     - errored seconds."
        ::= { tnStatisticsSdhScalars 110 }

    tnSdhStatsRxMSFESES1DayTr OBJECT-TYPE
        SYNTAX      Counter32
        MAX-ACCESS  read-only
        STATUS      current
        DESCRIPTION "1 day threshold value of RX far end multiplex section
                     - severely errored seconds."
        ::= { tnStatisticsSdhScalars 111 }

    tnSdhStatsRxMSFEUAS1DayTr OBJECT-TYPE
        SYNTAX      Counter32
        MAX-ACCESS  read-only
        STATUS      current
        DESCRIPTION "1 day threshold value of RX far end multiplex section
                     - unavailable seconds."
        ::= { tnStatisticsSdhScalars 112 }

    tnSdhStatsSTM256RxMSFEEB15MinRtr OBJECT-TYPE
        SYNTAX      Counter32
        MAX-ACCESS  read-only
        STATUS      current
        DESCRIPTION "15 minute reset threshold value of STM256 RX far end
                     multiplex section - errored blocks."
        ::= { tnStatisticsSdhScalars 113 }

    tnSdhStatsSTM64RxMSFEEB15MinRtr OBJECT-TYPE
        SYNTAX      Counter32
        MAX-ACCESS  read-only
        STATUS      current
        DESCRIPTION "15 minute reset threshold value of STM64 RX far end
                     multiplex section - errored blocks."
        ::= { tnStatisticsSdhScalars 114 }

    tnSdhStatsSTM16RxMSFEEB15MinRtr OBJECT-TYPE
        SYNTAX      Counter32
        MAX-ACCESS  read-only
        STATUS      current
        DESCRIPTION "15 minute reset threshold value of STM16 RX far end
                     multiplex section - errored blocks."
        ::= { tnStatisticsSdhScalars 115 }

    tnSdhStatsSTM4RxMSFEEB15MinRtr OBJECT-TYPE
        SYNTAX      Counter32
        MAX-ACCESS  read-only
        STATUS      current
        DESCRIPTION "15 minute reset threshold value of STM4 RX far end
                     multiplex section - errored blocks."
        ::= { tnStatisticsSdhScalars 116 }

    tnSdhStatsSTM1RxMSFEEB15MinRtr OBJECT-TYPE
        SYNTAX      Counter32
        MAX-ACCESS  read-only
        STATUS      current
        DESCRIPTION "15 minute reset threshold value of STM1 RX far end
                     multiplex section - errored blocks."
        ::= { tnStatisticsSdhScalars 117 }

    tnSdhStatsRxMSFEES15MinRtr OBJECT-TYPE
        SYNTAX      Counter32
        MAX-ACCESS  read-only
        STATUS      current
        DESCRIPTION "15 minute reset threshold value of RX far end multiplex
                     section - errored seconds."
        ::= { tnStatisticsSdhScalars 118 }

    tnSdhStatsRxMSFESES15MinRtr OBJECT-TYPE
        SYNTAX      Counter32
        MAX-ACCESS  read-only
        STATUS      current
        DESCRIPTION "15 minute reset threshold value of RX far end multiplex
                     section - errored seconds."
        ::= { tnStatisticsSdhScalars 119 }

    tnSdhStatsRxMSFEUAS15MinRtr OBJECT-TYPE
        SYNTAX      Counter32
        MAX-ACCESS  read-only
        STATUS      current
        DESCRIPTION "15 minute reset threshold value of RX far end multiplex
                     section - unavailable seconds."
        ::= { tnStatisticsSdhScalars 120 }

--------------------------------------------------------------------------------
-- Statistics Digital Wrapper Threshold Scalars
--------------------------------------------------------------------------------
    tnDw64BitStatsOtu1RxRSCorrCnt15MinTr OBJECT-TYPE
        SYNTAX      Counter64
        MAX-ACCESS  read-only
        STATUS      current
        DESCRIPTION "15 minute threshold value of digital wrapper OTU1
                     RX regenerator section corrected bits."
        ::= { tnStatisticsDwScalars 1 }

    tnDw64BitStatsOtu2RxRSCorrCnt15MinTr OBJECT-TYPE
        SYNTAX      Counter64
        MAX-ACCESS  read-only
        STATUS      current
        DESCRIPTION "15 minute threshold value of digital wrapper OTU2
                     RX regenerator section corrected bits."
        ::= { tnStatisticsDwScalars 2 }

    tnDw64BitStatsOtu3RxRSCorrCnt15MinTr OBJECT-TYPE
        SYNTAX      Counter64
        MAX-ACCESS  read-only
        STATUS      current
        DESCRIPTION "15 minute threshold value of digital wrapper OTU3
                     RX regenerator section corrected bits."
        ::= { tnStatisticsDwScalars 3 }

    tnDw64BitStatsOtu4RxRSCorrCnt15MinTr OBJECT-TYPE
        SYNTAX      Counter64
        MAX-ACCESS  read-only
        STATUS      current
        DESCRIPTION "15 minute threshold value of digital wrapper OTU4
                     RX regenerator section corrected bits."
        ::= { tnStatisticsDwScalars 4 }

    tnDw64BitStatsOtu1RxRSUncorrCnt15MinTr OBJECT-TYPE
        SYNTAX      Counter64
        MAX-ACCESS  read-only
        STATUS      current
        DESCRIPTION "15 minute threshold value of digital wrapper OTU1
                     RX regenerator section uncorrectable errors."
        ::= { tnStatisticsDwScalars 5 }

    tnDw64BitStatsOtu2RxRSUncorrCnt15MinTr OBJECT-TYPE
        SYNTAX      Counter64
        MAX-ACCESS  read-only
        STATUS      current
        DESCRIPTION "15 minute threshold value of digital wrapper OTU2
                     RX regenerator section uncorrectable errors."
        ::= { tnStatisticsDwScalars 6 }

    tnDw64BitStatsOtu3RxRSUncorrCnt15MinTr OBJECT-TYPE
        SYNTAX      Counter64
        MAX-ACCESS  read-only
        STATUS      current
        DESCRIPTION "15 minute threshold value of digital wrapper OTU3
                     RX regenerator section uncorrectable errors."
        ::= { tnStatisticsDwScalars 7 }

    tnDw64BitStatsOtu4RxRSUncorrCnt15MinTr OBJECT-TYPE
        SYNTAX      Counter64
        MAX-ACCESS  read-only
        STATUS      current
        DESCRIPTION "15 minute threshold value of digital wrapper OTU4
                     RX regenerator section uncorrectable errors."
        ::= { tnStatisticsDwScalars 8 }

    tnDw64BitStatsOtu1RxSMBIP8ErrCnt15MinTr OBJECT-TYPE
        SYNTAX      Counter64
        MAX-ACCESS  read-only
        STATUS      current
        DESCRIPTION "15 minute threshold value of digital wrapper OTU1
                     section monitor bit interleaved parity (BIP-8) errors."
        ::= { tnStatisticsDwScalars 9 }

    tnDw64BitStatsOtu2RxSMBIP8ErrCnt15MinTr OBJECT-TYPE
        SYNTAX      Counter64
        MAX-ACCESS  read-only
        STATUS      current
        DESCRIPTION "15 minute threshold value of digital wrapper OTU2
                     section monitor bit interleaved parity (BIP-8) errors."
        ::= { tnStatisticsDwScalars 10 }

    tnDw64BitStatsOtu3RxSMBIP8ErrCnt15MinTr OBJECT-TYPE
        SYNTAX      Counter64
        MAX-ACCESS  read-only
        STATUS      current
        DESCRIPTION "15 minute threshold value of digital wrapper OTU3
                     section monitor bit interleaved parity (BIP-8) errors."
        ::= { tnStatisticsDwScalars 11 }

    tnDw64BitStatsOtu4RxSMBIP8ErrCnt15MinTr OBJECT-TYPE
        SYNTAX      Counter64
        MAX-ACCESS  read-only
        STATUS      current
        DESCRIPTION "15 minute threshold value of digital wrapper OTU4
                     section monitor bit interleaved parity (BIP-8) errors."
        ::= { tnStatisticsDwScalars 12 }

    tnDw64BitStatsOdu1RxPMBIP8ErrCnt15MinTr OBJECT-TYPE
        SYNTAX      Counter64
        MAX-ACCESS  read-only
        STATUS      current
        DESCRIPTION "15 minute threshold value of digital wrapper ODU1
                     path monitor bit interleaved parity (BIP-8) errors."
        ::= { tnStatisticsDwScalars 13 }

    tnDw64BitStatsOdu2RxPMBIP8ErrCnt15MinTr OBJECT-TYPE
        SYNTAX      Counter64
        MAX-ACCESS  read-only
        STATUS      current
        DESCRIPTION "15 minute threshold value of digital wrapper ODU2
                     path monitor bit interleaved parity (BIP-8) errors."
        ::= { tnStatisticsDwScalars 14 }

    tnDw64BitStatsOdu3RxPMBIP8ErrCnt15MinTr OBJECT-TYPE
        SYNTAX      Counter64
        MAX-ACCESS  read-only
        STATUS      current
        DESCRIPTION "15 minute threshold value of digital wrapper ODU3
                     path monitor bit interleaved parity (BIP-8) errors."
        ::= { tnStatisticsDwScalars 15 }

    tnDw64BitStatsOdu4RxPMBIP8ErrCnt15MinTr OBJECT-TYPE
        SYNTAX      Counter64
        MAX-ACCESS  read-only
        STATUS      current
        DESCRIPTION "15 minute threshold value of digital wrapper ODU4
                     path monitor bit interleaved parity (BIP-8) errors."
        ::= { tnStatisticsDwScalars 16 }

    tnDw64BitStatsRxSMES15MinTr OBJECT-TYPE
        SYNTAX      Counter64
        MAX-ACCESS  read-only
        STATUS      current
        DESCRIPTION "15 minute threshold value of digital wrapper RX
                     section monitor errored seconds."
        ::= { tnStatisticsDwScalars 17 }

    tnDw64BitStatsRxPMES15MinTr OBJECT-TYPE
        SYNTAX      Counter64
        MAX-ACCESS  read-only
        STATUS      current
        DESCRIPTION "15 minute threshold value of digital wrapper RX
                     path monitor errored seconds."
        ::= { tnStatisticsDwScalars 18 }

    tnDw64BitStatsRxSMSES15MinTr OBJECT-TYPE
        SYNTAX      Counter64
        MAX-ACCESS  read-only
        STATUS      current
        DESCRIPTION "15 minute threshold value of digital wrapper RX
                     section monitor severely errored seconds."
        ::= { tnStatisticsDwScalars 19 }

    tnDw64BitStatsRxPMSES15MinTr OBJECT-TYPE
        SYNTAX      Counter64
        MAX-ACCESS  read-only
        STATUS      current
        DESCRIPTION "15 minute threshold value of digital wrapper RX
                     path monitor severely errored seconds."
        ::= { tnStatisticsDwScalars 20 }

    tnDw64BitStatsRxSMUAS15MinTr OBJECT-TYPE
        SYNTAX      Counter64
        MAX-ACCESS  read-only
        STATUS      current
        DESCRIPTION "15 minute threshold value of digital wrapper RX
                     section monitor unavailable seconds."
        ::= { tnStatisticsDwScalars 21 }

    tnDw64BitStatsRxPMUAS15MinTr OBJECT-TYPE
        SYNTAX      Counter64
        MAX-ACCESS  read-only
        STATUS      current
        DESCRIPTION "15 minute threshold value of digital wrapper RX
                     path monitor unavailable seconds."
        ::= { tnStatisticsDwScalars 22 }

    tnDw64BitStatsOtu1RxRSCorrCnt1DayTr OBJECT-TYPE
        SYNTAX      Counter64
        MAX-ACCESS  read-only
        STATUS      current
        DESCRIPTION "1 day threshold value of digital wrapper OTU1 RX
                     regenerator section corrected bits."
        ::= { tnStatisticsDwScalars 23 }

    tnDw64BitStatsOtu2RxRSCorrCnt1DayTr OBJECT-TYPE
        SYNTAX      Counter64
        MAX-ACCESS  read-only
        STATUS      current
        DESCRIPTION "1 day threshold value of digital wrapper OTU2 RX
                     regenerator section corrected bits."
        ::= { tnStatisticsDwScalars 24 }

    tnDw64BitStatsOtu3RxRSCorrCnt1DayTr OBJECT-TYPE
        SYNTAX      Counter64
        MAX-ACCESS  read-only
        STATUS      current
        DESCRIPTION "1 day threshold value of digital wrapper OTU3 RX
                     regenerator section corrected bits."
        ::= { tnStatisticsDwScalars 25 }

    tnDw64BitStatsOtu4RxRSCorrCnt1DayTr OBJECT-TYPE
        SYNTAX      Counter64
        MAX-ACCESS  read-only
        STATUS      current
        DESCRIPTION "1 day threshold value of digital wrapper OTU4 RX
                     regenerator section corrected bits."
        ::= { tnStatisticsDwScalars 26 }

    tnDw64BitStatsOtu1RxRSUncorrCnt1DayTr OBJECT-TYPE
        SYNTAX      Counter64
        MAX-ACCESS  read-only
        STATUS      current
        DESCRIPTION "1 day threshold value of digital wrapper OTU1 RX
                     regenerator section uncorrectable errors."
        ::= { tnStatisticsDwScalars 27 }

    tnDw64BitStatsOtu2RxRSUncorrCnt1DayTr OBJECT-TYPE
        SYNTAX      Counter64
        MAX-ACCESS  read-only
        STATUS      current
        DESCRIPTION "1 day threshold value of digital wrapper OTU2 RX
                     regenerator section uncorrectable errors."
        ::= { tnStatisticsDwScalars 28 }

    tnDw64BitStatsOtu3RxRSUncorrCnt1DayTr OBJECT-TYPE
        SYNTAX      Counter64
        MAX-ACCESS  read-only
        STATUS      current
        DESCRIPTION "1 day threshold value of digital wrapper OTU3 RX
                     regenerator section uncorrectable errors."
        ::= { tnStatisticsDwScalars 29 }

    tnDw64BitStatsOtu4RxRSUncorrCnt1DayTr OBJECT-TYPE
        SYNTAX      Counter64
        MAX-ACCESS  read-only
        STATUS      current
        DESCRIPTION "1 day threshold value of digital wrapper OTU4 RX
                     regenerator section uncorrectable errors."
        ::= { tnStatisticsDwScalars 30 }

    tnDw64BitStatsOtu1RxSMBIP8ErrCnt1DayTr OBJECT-TYPE
        SYNTAX      Counter64
        MAX-ACCESS  read-only
        STATUS      current
        DESCRIPTION "1 day threshold value of digital wrapper OTU1 section
                     monitor bit interleaved parity (BIP-8) errors."
        ::= { tnStatisticsDwScalars 31 }

    tnDw64BitStatsOtu2RxSMBIP8ErrCnt1DayTr OBJECT-TYPE
        SYNTAX      Counter64
        MAX-ACCESS  read-only
        STATUS      current
        DESCRIPTION "1 day threshold value of digital wrapper OTU2 section
                     monitor bit interleaved parity (BIP-8) errors."
        ::= { tnStatisticsDwScalars 32 }

    tnDw64BitStatsOtu3RxSMBIP8ErrCnt1DayTr OBJECT-TYPE
        SYNTAX      Counter64
        MAX-ACCESS  read-only
        STATUS      current
        DESCRIPTION "1 day threshold value of digital wrapper OTU3 section
                     monitor bit interleaved parity (BIP-8) errors."
        ::= { tnStatisticsDwScalars 33 }

    tnDw64BitStatsOtu4RxSMBIP8ErrCnt1DayTr OBJECT-TYPE
        SYNTAX      Counter64
        MAX-ACCESS  read-only
        STATUS      current
        DESCRIPTION "1 day threshold value of digital wrapper OTU4 section
                     monitor bit interleaved parity (BIP-8) errors."
        ::= { tnStatisticsDwScalars 34 }

    tnDw64BitStatsOdu1RxPMBIP8ErrCnt1DayTr OBJECT-TYPE
        SYNTAX      Counter64
        MAX-ACCESS  read-only
        STATUS      current
        DESCRIPTION "1 day threshold value of digital wrapper OTU1 path
                     monitor bit interleaved parity (BIP-8) errors."
        ::= { tnStatisticsDwScalars 35 }

    tnDw64BitStatsOdu2RxPMBIP8ErrCnt1DayTr OBJECT-TYPE
        SYNTAX      Counter64
        MAX-ACCESS  read-only
        STATUS      current
        DESCRIPTION "1 day threshold value of digital wrapper OTU2 path
                     monitor bit interleaved parity (BIP-8) errors."
        ::= { tnStatisticsDwScalars 36 }

    tnDw64BitStatsOdu3RxPMBIP8ErrCnt1DayTr OBJECT-TYPE
        SYNTAX      Counter64
        MAX-ACCESS  read-only
        STATUS      current
        DESCRIPTION "1 day threshold value of digital wrapper OTU3 path
                     monitor bit interleaved parity (BIP-8) errors."
        ::= { tnStatisticsDwScalars 37 }

    tnDw64BitStatsOdu4RxPMBIP8ErrCnt1DayTr OBJECT-TYPE
        SYNTAX      Counter64
        MAX-ACCESS  read-only
        STATUS      current
        DESCRIPTION "1 day threshold value of digital wrapper OTU4 path
                     monitor bit interleaved parity (BIP-8) errors."
        ::= { tnStatisticsDwScalars 38 }

    tnDw64BitStatsRxSMES1DayTr OBJECT-TYPE
        SYNTAX      Counter64
        MAX-ACCESS  read-only
        STATUS      current
        DESCRIPTION "1 day threshold value of digital wrapper RX section
                     monitor errored seconds."
        ::= { tnStatisticsDwScalars 39 }

    tnDw64BitStatsRxPMES1DayTr OBJECT-TYPE
        SYNTAX      Counter64
        MAX-ACCESS  read-only
        STATUS      current
        DESCRIPTION "1 day threshold value of digital wrapper RX path
                     monitor errored seconds."
        ::= { tnStatisticsDwScalars 40 }

    tnDw64BitStatsRxSMSES1DayTr OBJECT-TYPE
        SYNTAX      Counter64
        MAX-ACCESS  read-only
        STATUS      current
        DESCRIPTION "1 day threshold value of digital wrapper RX section
                     monitor severely errored seconds."
        ::= { tnStatisticsDwScalars 41 }

    tnDw64BitStatsRxPMSES1DayTr OBJECT-TYPE
        SYNTAX      Counter64
        MAX-ACCESS  read-only
        STATUS      current
        DESCRIPTION "1 day threshold value of digital wrapper RX path
                     monitor severely errored seconds."
        ::= { tnStatisticsDwScalars 42 }

    tnDw64BitStatsRxSMUAS1DayTr OBJECT-TYPE
        SYNTAX      Counter64
        MAX-ACCESS  read-only
        STATUS      current
        DESCRIPTION "1 day threshold value of digital wrapper RX section
                     monitor unavailable seconds."
        ::= { tnStatisticsDwScalars 43 }

    tnDw64BitStatsRxPMUAS1DayTr OBJECT-TYPE
        SYNTAX      Counter64
        MAX-ACCESS  read-only
        STATUS      current
        DESCRIPTION "1 day threshold value of digital wrapper RX path
                     monitor unavailable seconds."
        ::= { tnStatisticsDwScalars 44 }

    tnDw64BitStatsOtu1RxRSCorrCnt15MinRtr OBJECT-TYPE
        SYNTAX      Counter64
        MAX-ACCESS  read-only
        STATUS      current
        DESCRIPTION "15 minute reset threshold value of digital wrapper
                     OTU1 RX regenerator section corrected bits."
        ::= { tnStatisticsDwScalars 45 }

    tnDw64BitStatsOtu2RxRSCorrCnt15MinRtr OBJECT-TYPE
        SYNTAX      Counter64
        MAX-ACCESS  read-only
        STATUS      current
        DESCRIPTION "15 minute reset threshold value of digital wrapper
                     OTU2 RX regenerator section corrected bits."
        ::= { tnStatisticsDwScalars 46 }

    tnDw64BitStatsOtu3RxRSCorrCnt15MinRtr OBJECT-TYPE
        SYNTAX      Counter64
        MAX-ACCESS  read-only
        STATUS      current
        DESCRIPTION "15 minute reset threshold value of digital wrapper
                     OTU3 RX regenerator section corrected bits."
        ::= { tnStatisticsDwScalars 47 }

    tnDw64BitStatsOtu4RxRSCorrCnt15MinRtr OBJECT-TYPE
        SYNTAX      Counter64
        MAX-ACCESS  read-only
        STATUS      current
        DESCRIPTION "15 minute reset threshold value of digital wrapper
                     OTU4 RX regenerator section corrected bits."
        ::= { tnStatisticsDwScalars 48 }

    tnDw64BitStatsOtu1RxRSUncorrCnt15MinRtr OBJECT-TYPE
        SYNTAX      Counter64
        MAX-ACCESS  read-only
        STATUS      current
        DESCRIPTION "15 minute reset threshold value of digital wrapper
                     OTU1 RX regenerator section uncorrectable errors."
        ::= { tnStatisticsDwScalars 49 }

    tnDw64BitStatsOtu2RxRSUncorrCnt15MinRtr OBJECT-TYPE
        SYNTAX      Counter64
        MAX-ACCESS  read-only
        STATUS      current
        DESCRIPTION "15 minute reset threshold value of digital wrapper
                     OTU2 RX regenerator section uncorrectable errors."
        ::= { tnStatisticsDwScalars 50 }

    tnDw64BitStatsOtu3RxRSUncorrCnt15MinRtr OBJECT-TYPE
        SYNTAX      Counter64
        MAX-ACCESS  read-only
        STATUS      current
        DESCRIPTION "15 minute reset threshold value of digital wrapper
                     OTU3 RX regenerator section uncorrectable errors."
        ::= { tnStatisticsDwScalars 51 }

    tnDw64BitStatsOtu4RxRSUncorrCnt15MinRtr OBJECT-TYPE
        SYNTAX      Counter64
        MAX-ACCESS  read-only
        STATUS      current
        DESCRIPTION "15 minute reset threshold value of digital wrapper
                     OTU4 RX regenerator section uncorrectable errors."
        ::= { tnStatisticsDwScalars 52 }

    tnDw64BitStatsOtu1RxSMBIP8ErrCnt15MinRtr OBJECT-TYPE
        SYNTAX      Counter64
        MAX-ACCESS  read-only
        STATUS      current
        DESCRIPTION "15 minute reset threshold value of digital wrapper
                     OTU1 RX section monitor bit interleaved parity
                     (BIP-8) errors."
        ::= { tnStatisticsDwScalars 53 }

    tnDw64BitStatsOtu2RxSMBIP8ErrCnt15MinRtr OBJECT-TYPE
        SYNTAX      Counter64
        MAX-ACCESS  read-only
        STATUS      current
        DESCRIPTION "15 minute reset threshold value of digital wrapper
                     OTU2 RX section monitor bit interleaved parity
                     (BIP-8) errors."
        ::= { tnStatisticsDwScalars 54 }

    tnDw64BitStatsOtu3RxSMBIP8ErrCnt15MinRtr OBJECT-TYPE
        SYNTAX      Counter64
        MAX-ACCESS  read-only
        STATUS      current
        DESCRIPTION "15 minute reset threshold value of digital wrapper
                     OTU3 RX section monitor bit interleaved parity
                     (BIP-8) errors."
        ::= { tnStatisticsDwScalars 55 }

    tnDw64BitStatsOtu4RxSMBIP8ErrCnt15MinRtr OBJECT-TYPE
        SYNTAX      Counter64
        MAX-ACCESS  read-only
        STATUS      current
        DESCRIPTION "15 minute reset threshold value of digital wrapper
                     OTU4 RX section monitor bit interleaved parity
                     (BIP-8) errors."
        ::= { tnStatisticsDwScalars 56 }

    tnDw64BitStatsOdu1RxPMBIP8ErrCnt15MinRtr OBJECT-TYPE
        SYNTAX      Counter64
        MAX-ACCESS  read-only
        STATUS      current
        DESCRIPTION "15 minute reset threshold value of digital wrapper
                     ODU1 path monitor bit interleaved parity (BIP-8)
                     errors."
        ::= { tnStatisticsDwScalars 57 }

    tnDw64BitStatsOdu2RxPMBIP8ErrCnt15MinRtr OBJECT-TYPE
        SYNTAX      Counter64
        MAX-ACCESS  read-only
        STATUS      current
        DESCRIPTION "15 minute reset threshold value of digital wrapper
                     ODU2 path monitor bit interleaved parity (BIP-8)
                     errors."
        ::= { tnStatisticsDwScalars 58 }

    tnDw64BitStatsOdu3RxPMBIP8ErrCnt15MinRtr OBJECT-TYPE
        SYNTAX      Counter64
        MAX-ACCESS  read-only
        STATUS      current
        DESCRIPTION "15 minute reset threshold value of digital wrapper
                     ODU3 path monitor bit interleaved parity (BIP-8)
                     errors."
        ::= { tnStatisticsDwScalars 59 }

    tnDw64BitStatsOdu4RxPMBIP8ErrCnt15MinRtr OBJECT-TYPE
        SYNTAX      Counter64
        MAX-ACCESS  read-only
        STATUS      current
        DESCRIPTION "15 minute reset threshold value of digital wrapper
                     ODU4 path monitor bit interleaved parity (BIP-8)
                     errors."
        ::= { tnStatisticsDwScalars 60 }

    tnDw64BitStatsRxSMES15MinRtr OBJECT-TYPE
        SYNTAX      Counter64
        MAX-ACCESS  read-only
        STATUS      current
        DESCRIPTION "15 minute reset threshold value of digital wrapper
                     RX section monitor errored seconds."
        ::= { tnStatisticsDwScalars 61 }

    tnDw64BitStatsRxPMES15MinRtr OBJECT-TYPE
        SYNTAX      Counter64
        MAX-ACCESS  read-only
        STATUS      current
        DESCRIPTION "15 minute reset threshold value of digital wrapper
                     RX path monitor errored seconds."
        ::= { tnStatisticsDwScalars 62 }

    tnDw64BitStatsRxSMSES15MinRtr OBJECT-TYPE
        SYNTAX      Counter64
        MAX-ACCESS  read-only
        STATUS      current
        DESCRIPTION "15 minute reset threshold value of digital wrapper
                     RX section monitor severely errored seconds."
        ::= { tnStatisticsDwScalars 63 }

    tnDw64BitStatsRxPMSES15MinRtr OBJECT-TYPE
        SYNTAX      Counter64
        MAX-ACCESS  read-only
        STATUS      current
        DESCRIPTION "15 minute reset threshold value of digital wrapper
                     RX path monitor severely errored seconds."
        ::= { tnStatisticsDwScalars 64 }

    tnDw64BitStatsRxSMUAS15MinRtr OBJECT-TYPE
        SYNTAX      Counter64
        MAX-ACCESS  read-only
        STATUS      current
        DESCRIPTION "15 minute reset threshold value of digital wrapper
                     RX section monitor unavailable seconds."
        ::= { tnStatisticsDwScalars 65 }

    tnDw64BitStatsRxPMUAS15MinRtr OBJECT-TYPE
        SYNTAX      Counter64
        MAX-ACCESS  read-only
        STATUS      current
        DESCRIPTION "15 minute reset threshold value of digital wrapper
                     RX path monitor unavailable seconds."
        ::= { tnStatisticsDwScalars 66 }

    tnDwStatsOtu1RxSMFEBIP8ErrCnt15MinTr OBJECT-TYPE
        SYNTAX      Counter64
        MAX-ACCESS  read-only
        STATUS      current
        DESCRIPTION "15 minute threshold value of digital wrapper OTU1
                     RX section monitor far end bit interleaved parity
                     (BIP-8) errors."
        ::= { tnStatisticsDwScalars 67 }

    tnDwStatsOtu2RxSMFEBIP8ErrCnt15MinTr OBJECT-TYPE
        SYNTAX      Counter64
        MAX-ACCESS  read-only
        STATUS      current
        DESCRIPTION "15 minute threshold value of digital wrapper OTU2
                     RX section monitor far end bit interleaved parity
                     (BIP-8) errors."
        ::= { tnStatisticsDwScalars 68 }

    tnDwStatsOtu3RxSMFEBIP8ErrCnt15MinTr OBJECT-TYPE
        SYNTAX      Counter64
        MAX-ACCESS  read-only
        STATUS      current
        DESCRIPTION "15 minute threshold value of digital wrapper OTU3
                     RX section monitor far end bit interleaved parity
                     (BIP-8) errors."
        ::= { tnStatisticsDwScalars 69 }

    tnDwStatsOtu4RxSMFEBIP8ErrCnt15MinTr OBJECT-TYPE
        SYNTAX      Counter64
        MAX-ACCESS  read-only
        STATUS      current
        DESCRIPTION "15 minute threshold value of digital wrapper OTU4
                     RX section monitor far end bit interleaved parity
                     (BIP-8) errors."
        ::= { tnStatisticsDwScalars 70 }

    tnDwStatsOdu1RxPMFEBIP8ErrCnt15MinTr OBJECT-TYPE
        SYNTAX      Counter64
        MAX-ACCESS  read-only
        STATUS      current
        DESCRIPTION "15 minute threshold value of digital wrapper ODU1
                     RX path monitor far end bit interleaved parity
                     (BIP-8) errors."
        ::= { tnStatisticsDwScalars 71 }

    tnDwStatsOdu2RxPMFEBIP8ErrCnt15MinTr OBJECT-TYPE
        SYNTAX      Counter64
        MAX-ACCESS  read-only
        STATUS      current
        DESCRIPTION "15 minute threshold value of digital wrapper ODU2
                     RX path monitor far end bit interleaved parity
                     (BIP-8) errors."
        ::= { tnStatisticsDwScalars 72 }

    tnDwStatsOdu3RxPMFEBIP8ErrCnt15MinTr OBJECT-TYPE
        SYNTAX      Counter64
        MAX-ACCESS  read-only
        STATUS      current
        DESCRIPTION "15 minute threshold value of digital wrapper ODU3
                     RX path monitor far end bit interleaved parity
                     (BIP-8) errors."
        ::= { tnStatisticsDwScalars 73 }

    tnDwStatsOdu4RxPMFEBIP8ErrCnt15MinTr OBJECT-TYPE
        SYNTAX      Counter64
        MAX-ACCESS  read-only
        STATUS      current
        DESCRIPTION "15 minute threshold value of digital wrapper ODU4
                     RX path monitor far end bit interleaved parity
                     (BIP-8) errors."
        ::= { tnStatisticsDwScalars 74 }

    tnDwStatsRxSMFEES15MinTr OBJECT-TYPE
        SYNTAX      Counter64
        MAX-ACCESS  read-only
        STATUS      current
        DESCRIPTION "15 minute threshold value of digital wrapper RX
                     section monitor far end errored seconds."
        ::= { tnStatisticsDwScalars 75 }

    tnDwStatsRxPMFEES15MinTr OBJECT-TYPE
        SYNTAX      Counter64
        MAX-ACCESS  read-only
        STATUS      current
        DESCRIPTION "15 minute threshold value of digital wrapper RX
                     path monitor far end errored seconds."
        ::= { tnStatisticsDwScalars 76 }

    tnDwStatsRxSMFESES15MinTr OBJECT-TYPE
        SYNTAX      Counter64
        MAX-ACCESS  read-only
        STATUS      current
        DESCRIPTION "15 minute threshold value of digital wrapper RX
                     section monitor far end severely errored seconds."
        ::= { tnStatisticsDwScalars 77 }

    tnDwStatsRxPMFESES15MinTr OBJECT-TYPE
        SYNTAX      Counter64
        MAX-ACCESS  read-only
        STATUS      current
        DESCRIPTION "15 minute threshold value of digital wrapper RX
                     path monitor far end severely errored seconds."
        ::= { tnStatisticsDwScalars 78 }

    tnDwStatsRxSMFEUAS15MinTr OBJECT-TYPE
        SYNTAX      Counter64
        MAX-ACCESS  read-only
        STATUS      current
        DESCRIPTION "15 minute threshold value of digital wrapper RX
                     section monitor far end unavailable seconds."
        ::= { tnStatisticsDwScalars 79 }

    tnDwStatsRxPMFEUAS15MinTr OBJECT-TYPE
        SYNTAX      Counter64
        MAX-ACCESS  read-only
        STATUS      current
        DESCRIPTION "15 minute threshold value of digital wrapper RX
                     section monitor far end unavailable seconds."
        ::= { tnStatisticsDwScalars 80 }

    tnDwStatsRxSMBIAES15MinTr OBJECT-TYPE
        SYNTAX      Counter64
        MAX-ACCESS  read-only
        STATUS      current
        DESCRIPTION "15 minute threshold value of digital wrapper RX
                     section monitor backward error indication (BEI)
                     errors."
        ::= { tnStatisticsDwScalars 81 }

    tnDwStatsRxSMIAES15MinTr OBJECT-TYPE
        SYNTAX      Counter64
        MAX-ACCESS  read-only
        STATUS      current
        DESCRIPTION "15 minute threshold value of digital wrapper RX
                     section monitor incoming alignment errored seconds."
        ::= { tnStatisticsDwScalars 82 }

    tnDwStatsRxBERPreFEC15MinTr OBJECT-TYPE
        SYNTAX      Counter64
        MAX-ACCESS  read-only
        STATUS      current
        DESCRIPTION "15 minute threshold value for digital wrapper RX
                     Pre-FEC error bit rate."
        ::= { tnStatisticsDwScalars 83 }

    tnDwStatsRxBERPostFEC15MinTr OBJECT-TYPE
        SYNTAX      Counter64
        MAX-ACCESS  read-only
        STATUS      current
        DESCRIPTION "15 minute threshold value for digital wrapper RX
                     Post-FEC error bit rate."
        ::= { tnStatisticsDwScalars 84 }

    tnDwStatsOtu1RxSMFEBIP8ErrCnt1DayTr OBJECT-TYPE
        SYNTAX      Counter64
        MAX-ACCESS  read-only
        STATUS      current
        DESCRIPTION "1 day threshold value of digital wrapper OTU1 RX
                     section monitor far end bit interleaved parity
                     (BIP-8) errors."
        ::= { tnStatisticsDwScalars 85 }

    tnDwStatsOtu2RxSMFEBIP8ErrCnt1DayTr OBJECT-TYPE
        SYNTAX      Counter64
        MAX-ACCESS  read-only
        STATUS      current
        DESCRIPTION "1 day threshold value of digital wrapper OTU2 RX
                     section monitor far end bit interleaved parity
                     (BIP-8) errors."
        ::= { tnStatisticsDwScalars 86 }

    tnDwStatsOtu3RxSMFEBIP8ErrCnt1DayTr OBJECT-TYPE
        SYNTAX      Counter64
        MAX-ACCESS  read-only
        STATUS      current
        DESCRIPTION "1 day threshold value of digital wrapper OTU3 RX
                     section monitor far end bit interleaved parity
                     (BIP-8) errors."
        ::= { tnStatisticsDwScalars 87 }

    tnDwStatsOtu4RxSMFEBIP8ErrCnt1DayTr OBJECT-TYPE
        SYNTAX      Counter64
        MAX-ACCESS  read-only
        STATUS      current
        DESCRIPTION "1 day threshold value of digital wrapper OTU4 RX
                     section monitor far end bit interleaved parity
                     (BIP-8) errors."
        ::= { tnStatisticsDwScalars 88 }

    tnDwStatsOdu1RxPMFEBIP8ErrCnt1DayTr OBJECT-TYPE
        SYNTAX      Counter64
        MAX-ACCESS  read-only
        STATUS      current
        DESCRIPTION "1 day threshold value of digital wrapper ODU1 RX
                     path monitor far end bit interleaved parity (BIP-8)
                     errors."
        ::= { tnStatisticsDwScalars 89 }

    tnDwStatsOdu2RxPMFEBIP8ErrCnt1DayTr OBJECT-TYPE
        SYNTAX      Counter64
        MAX-ACCESS  read-only
        STATUS      current
        DESCRIPTION "1 day threshold value of digital wrapper ODU2 RX
                     path monitor far end bit interleaved parity (BIP-8)
                     errors."
        ::= { tnStatisticsDwScalars 90 }

    tnDwStatsOdu3RxPMFEBIP8ErrCnt1DayTr OBJECT-TYPE
        SYNTAX      Counter64
        MAX-ACCESS  read-only
        STATUS      current
        DESCRIPTION "1 day threshold value of digital wrapper ODU3 RX
                     path monitor far end bit interleaved parity (BIP-8)
                     errors."
        ::= { tnStatisticsDwScalars 91 }

    tnDwStatsOdu4RxPMFEBIP8ErrCnt1DayTr OBJECT-TYPE
        SYNTAX      Counter64
        MAX-ACCESS  read-only
        STATUS      current
        DESCRIPTION "1 day threshold value of digital wrapper ODU4 RX
                     path monitor far end bit interleaved parity (BIP-8)
                     errors."
        ::= { tnStatisticsDwScalars 92 }

    tnDwStatsRxSMFEES1DayTr OBJECT-TYPE
        SYNTAX      Counter64
        MAX-ACCESS  read-only
        STATUS      current
        DESCRIPTION "1 day threshold value of digital wrapper RX section
                     monitor far end errored seconds."
        ::= { tnStatisticsDwScalars 93 }

    tnDwStatsRxPMFEES1DayTr OBJECT-TYPE
        SYNTAX      Counter64
        MAX-ACCESS  read-only
        STATUS      current
        DESCRIPTION "1 day threshold value of digital wrapper RX path
                     monitor far end errored seconds."
        ::= { tnStatisticsDwScalars 94 }

    tnDwStatsRxSMFESES1DayTr OBJECT-TYPE
        SYNTAX      Counter64
        MAX-ACCESS  read-only
        STATUS      current
        DESCRIPTION "1 day threshold value of digital wrapper RX section
                     monitor far end severely errored seconds."
        ::= { tnStatisticsDwScalars 95 }

    tnDwStatsRxPMFESES1DayTr OBJECT-TYPE
        SYNTAX      Counter64
        MAX-ACCESS  read-only
        STATUS      current
        DESCRIPTION "1 day threshold value of digital wrapper RX path
                     monitor far end severely errored seconds."
        ::= { tnStatisticsDwScalars 96 }

    tnDwStatsRxSMFEUAS1DayTr OBJECT-TYPE
        SYNTAX      Counter64
        MAX-ACCESS  read-only
        STATUS      current
        DESCRIPTION "1 day threshold value of digital wrapper RX section
                     monitor far end unavailable seconds."
        ::= { tnStatisticsDwScalars 97 }

    tnDwStatsRxPMFEUAS1DayTr OBJECT-TYPE
        SYNTAX      Counter64
        MAX-ACCESS  read-only
        STATUS      current
        DESCRIPTION "1 day threshold value of digital wrapper RX path
                     monitor far end unavailable seconds."
        ::= { tnStatisticsDwScalars 98 }

    tnDwStatsRxSMBIAES1DayTr OBJECT-TYPE
        SYNTAX      Counter64
        MAX-ACCESS  read-only
        STATUS      current
        DESCRIPTION "1 day threshold value of digital wrapper RX section
                     monitor backward error indication (BEI) errors."
        ::= { tnStatisticsDwScalars 99 }

    tnDwStatsRxSMIAES1DayTr OBJECT-TYPE
        SYNTAX      Counter64
        MAX-ACCESS  read-only
        STATUS      current
        DESCRIPTION "1 day threshold value of digital wrapper RX section
                     monitor incoming alignment errored seconds."
        ::= { tnStatisticsDwScalars 100 }

    tnDwStatsRxBERPreFEC1DayTr OBJECT-TYPE
        SYNTAX      Counter64
        MAX-ACCESS  read-only
        STATUS      current
        DESCRIPTION "1 day threshold value for digital wrapper RX Pre-FEC
                     error bit rate."
        ::= { tnStatisticsDwScalars 101 }

    tnDwStatsRxBERPostFEC1DayTr OBJECT-TYPE
        SYNTAX      Counter64
        MAX-ACCESS  read-only
        STATUS      current
        DESCRIPTION "1 day threshold value for digital wrapper RX Post-FEC
                     error bit rate."
        ::= { tnStatisticsDwScalars 102 }

    tnDwStatsOtu1RxSMFEBIP8ErrCnt15MinRtr OBJECT-TYPE
        SYNTAX      Counter64
        MAX-ACCESS  read-only
        STATUS      current
        DESCRIPTION "15 minute reset threshold value of digital wrapper
                     OTU1 RX section monitor far end bit interleaved
                     parity (BIP-8) errors."
        ::= { tnStatisticsDwScalars 103 }

    tnDwStatsOtu2RxSMFEBIP8ErrCnt15MinRtr OBJECT-TYPE
        SYNTAX      Counter64
        MAX-ACCESS  read-only
        STATUS      current
        DESCRIPTION "15 minute reset threshold value of digital wrapper
                     OTU2 RX section monitor far end bit interleaved
                     parity (BIP-8) errors."
        ::= { tnStatisticsDwScalars 104 }

    tnDwStatsOtu3RxSMFEBIP8ErrCnt15MinRtr OBJECT-TYPE
        SYNTAX      Counter64
        MAX-ACCESS  read-only
        STATUS      current
        DESCRIPTION "15 minute reset threshold value of digital wrapper
                     OTU3 RX section monitor far end bit interleaved
                     parity (BIP-8) errors."
        ::= { tnStatisticsDwScalars 105 }

    tnDwStatsOtu4RxSMFEBIP8ErrCnt15MinRtr OBJECT-TYPE
        SYNTAX      Counter64
        MAX-ACCESS  read-only
        STATUS      current
        DESCRIPTION "15 minute reset threshold value of digital wrapper
                     OTU4 RX section monitor far end bit interleaved
                     parity (BIP-8) errors."
        ::= { tnStatisticsDwScalars 106 }

    tnDwStatsOdu1RxPMFEBIP8ErrCnt15MinRtr OBJECT-TYPE
        SYNTAX      Counter64
        MAX-ACCESS  read-only
        STATUS      current
        DESCRIPTION "15 minute reset threshold value of digital wrapper
                     ODU1 RX path monitor far end bit interleaved parity
                     (BIP-8) errors."
        ::= { tnStatisticsDwScalars 107 }

    tnDwStatsOdu2RxPMFEBIP8ErrCnt15MinRtr OBJECT-TYPE
        SYNTAX      Counter64
        MAX-ACCESS  read-only
        STATUS      current
        DESCRIPTION "15 minute reset threshold value of digital wrapper
                     ODU2 RX path monitor far end bit interleaved parity
                     (BIP-8) errors."
        ::= { tnStatisticsDwScalars 108 }

    tnDwStatsOdu3RxPMFEBIP8ErrCnt15MinRtr OBJECT-TYPE
        SYNTAX      Counter64
        MAX-ACCESS  read-only
        STATUS      current
        DESCRIPTION "15 minute reset threshold value of digital wrapper
                     ODU3 RX path monitor far end bit interleaved parity
                     (BIP-8) errors."
        ::= { tnStatisticsDwScalars 109 }

    tnDwStatsOdu4RxPMFEBIP8ErrCnt15MinRtr OBJECT-TYPE
        SYNTAX      Counter64
        MAX-ACCESS  read-only
        STATUS      current
        DESCRIPTION "15 minute reset threshold value of digital wrapper
                     ODU4 path monitor far end bit interleaved parity
                     (BIP-8) errors."
        ::= { tnStatisticsDwScalars 110 }

    tnDwStatsRxSMFEES15MinRtr OBJECT-TYPE
        SYNTAX      Counter64
        MAX-ACCESS  read-only
        STATUS      current
        DESCRIPTION "15 minute reset threshold value of digital wrapper
                     RX section monitor far end errored seconds."
        ::= { tnStatisticsDwScalars 111 }

    tnDwStatsRxPMFEES15MinRtr OBJECT-TYPE
        SYNTAX      Counter64
        MAX-ACCESS  read-only
        STATUS      current
        DESCRIPTION "15 minute reset threshold value of digital wrapper
                     RX path monitor far end errored seconds."
        ::= { tnStatisticsDwScalars 112 }

    tnDwStatsRxSMFESES15MinRtr OBJECT-TYPE
        SYNTAX      Counter64
        MAX-ACCESS  read-only
        STATUS      current
        DESCRIPTION "15 minute threshold value of digital wrapper section
                     monitor far end severely errored seconds."
        ::= { tnStatisticsDwScalars 113 }

    tnDwStatsRxPMFESES15MinRtr OBJECT-TYPE
        SYNTAX      Counter64
        MAX-ACCESS  read-only
        STATUS      current
        DESCRIPTION "15 minute reset threshold value of digital wrapper
                     RX path monitor far end severely errored seconds."
        ::= { tnStatisticsDwScalars 114 }

    tnDwStatsRxSMFEUAS15MinRtr OBJECT-TYPE
        SYNTAX      Counter64
        MAX-ACCESS  read-only
        STATUS      current
        DESCRIPTION "15 minute reset threshold value of digital wrapper
                     RX section monitor far end Unavailable seconds."
        ::= { tnStatisticsDwScalars 115 }

    tnDwStatsRxPMFEUAS15MinRtr OBJECT-TYPE
        SYNTAX      Counter64
        MAX-ACCESS  read-only
        STATUS      current
        DESCRIPTION "15 minute reset threshold value of digital wrapper
                     RX path monitor far end Unavailable seconds."
        ::= { tnStatisticsDwScalars 116 }

    tnDwStatsRxSMBIAES15MinRtr OBJECT-TYPE
        SYNTAX      Counter64
        MAX-ACCESS  read-only
        STATUS      current
        DESCRIPTION "15 minute reset threshold value of digital wrapper
                     RX section monitor backward error indication (BEI)
                     errors."
        ::= { tnStatisticsDwScalars 117 }

    tnDwStatsRxSMIAES15MinRtr OBJECT-TYPE
        SYNTAX      Counter64
        MAX-ACCESS  read-only
        STATUS      current
        DESCRIPTION "15 minute reset threshold value of digital wrapper
                     RX section monitor incoming alignment errored seconds."
        ::= { tnStatisticsDwScalars 118 }

    tnDwStatsRxBERPreFEC15MinRtr OBJECT-TYPE
        SYNTAX      Counter64
        MAX-ACCESS  read-only
        STATUS      current
        DESCRIPTION "15 minute reset threshold value for digital wrapper
                     RX Pre-FEC error bit rate."
        ::= { tnStatisticsDwScalars 119 }

    tnDwStatsRxBERPostFEC15MinRtr OBJECT-TYPE
        SYNTAX      Counter64
        MAX-ACCESS  read-only
        STATUS      current
        DESCRIPTION "15 minute reset threshold value for digital wrapper
                     RX Post-FEC error bit rate."
        ::= { tnStatisticsDwScalars 120 }

--------------------------------------------------------------------------------
-- Statistics Physical Code Sub-layer Threshold Scalars
--------------------------------------------------------------------------------
    tnPcsStats100GBERxCV15MinTr OBJECT-TYPE
        SYNTAX      Counter32
        MAX-ACCESS  read-only
        STATUS      current
        DESCRIPTION "15 minute threshold value of PCS 100GBE RX coding
                     violations."
        ::= { tnStatisticsPcsScalars 1 }

    tnPcsStats40GBERxCV15MinTr OBJECT-TYPE
        SYNTAX      Counter32
        MAX-ACCESS  read-only
        STATUS      current
        DESCRIPTION "15 minute threshold value of PCS 40GBE RX coding
                     violations."
        ::= { tnStatisticsPcsScalars 2 }

    tnPcsStats10GBERxCV15MinTr OBJECT-TYPE
        SYNTAX      Counter32
        MAX-ACCESS  read-only
        STATUS      current
        DESCRIPTION "15 minute threshold value of PCS 10GBE RX coding
                     violations."
        ::= { tnStatisticsPcsScalars 3 }

    tnPcsStatsGBERxCV15MinTr OBJECT-TYPE
        SYNTAX      Counter32
        MAX-ACCESS  read-only
        STATUS      current
        DESCRIPTION "15 minute threshold value of PCS GBE RX coding
                     violations."
        ::= { tnStatisticsPcsScalars 4 }

    tnPcsStats16GFCRxCV15MinTr OBJECT-TYPE
        SYNTAX      Counter32
        MAX-ACCESS  read-only
        STATUS      current
        DESCRIPTION "15 minute threshold value of PCS 16GFC RX coding
                     violations."
        ::= { tnStatisticsPcsScalars 5 }

    tnPcsStats10GFCRxCV15MinTr OBJECT-TYPE
        SYNTAX      Counter32
        MAX-ACCESS  read-only
        STATUS      current
        DESCRIPTION "15 minute threshold value of PCS 10GFC RX coding
                     violations."
        ::= { tnStatisticsPcsScalars 6 }

    tnPcsStats8GFCRxCV15MinTr OBJECT-TYPE
        SYNTAX      Counter32
        MAX-ACCESS  read-only
        STATUS      current
        DESCRIPTION "15 minute threshold value of PCS 8GFC RX coding
                     violations."
        ::= { tnStatisticsPcsScalars 7 }

    tnPcsStats4GFCRxCV15MinTr OBJECT-TYPE
        SYNTAX      Counter32
        MAX-ACCESS  read-only
        STATUS      current
        DESCRIPTION "15 minute threshold value of PCS 4GFC RX coding
                     violations."
        ::= { tnStatisticsPcsScalars 8 }

    tnPcsStats2GFCRxCV15MinTr OBJECT-TYPE
        SYNTAX      Counter32
        MAX-ACCESS  read-only
        STATUS      current
        DESCRIPTION "15 minute threshold value of PCS 2GFC RX coding
                     violations."
        ::= { tnStatisticsPcsScalars 9 }

    tnPcsStatsGFCRxCV15MinTr OBJECT-TYPE
        SYNTAX      Counter32
        MAX-ACCESS  read-only
        STATUS      current
        DESCRIPTION "15 minute threshold value of PCS GFC RX coding
                     violations."
        ::= { tnStatisticsPcsScalars 10 }

    tnPcsStatsRxES15MinTr OBJECT-TYPE
        SYNTAX      Counter32
        MAX-ACCESS  read-only
        STATUS      current
        DESCRIPTION "15 minute threshold value of PCS RX errored seconds."
        ::= { tnStatisticsPcsScalars 11 }

    tnPcsStatsRxSES15MinTr OBJECT-TYPE
        SYNTAX      Counter32
        MAX-ACCESS  read-only
        STATUS      current
        DESCRIPTION "15 minute threshold value of PCS RX severely errored
                     seconds."
        ::= { tnStatisticsPcsScalars 12 }

    tnPcsStatsRxSEFS15MinTr OBJECT-TYPE
        SYNTAX      Counter32
        MAX-ACCESS  read-only
        STATUS      current
        DESCRIPTION "15 minute threshold value of PCS RX severely errored
                     frame seconds."
        ::= { tnStatisticsPcsScalars 13 }

    tnPcsStats100GBERxCV1DayTr OBJECT-TYPE
        SYNTAX      Counter32
        MAX-ACCESS  read-only
        STATUS      current
        DESCRIPTION "1 day threshold value of PCS 100GBE RX coding violations."
        ::= { tnStatisticsPcsScalars 14 }

    tnPcsStats40GBERxCV1DayTr OBJECT-TYPE
        SYNTAX      Counter32
        MAX-ACCESS  read-only
        STATUS      current
        DESCRIPTION "1 day threshold value of PCS 40GBE RX coding violations."
        ::= { tnStatisticsPcsScalars 15 }

    tnPcsStats10GBERxCV1DayTr OBJECT-TYPE
        SYNTAX      Counter32
        MAX-ACCESS  read-only
        STATUS      current
        DESCRIPTION "1 day threshold value of PCS 10GBE RX coding violations."
        ::= { tnStatisticsPcsScalars 16 }

    tnPcsStatsGBERxCV1DayTr OBJECT-TYPE
        SYNTAX      Counter32
        MAX-ACCESS  read-only
        STATUS      current
        DESCRIPTION "1 day threshold value of PCS GBE RX coding violations."
        ::= { tnStatisticsPcsScalars 17 }

    tnPcsStats16GFCRxCV1DayTr OBJECT-TYPE
        SYNTAX      Counter32
        MAX-ACCESS  read-only
        STATUS      current
        DESCRIPTION "1 day threshold value of PCS 16GFC RX coding violations."
        ::= { tnStatisticsPcsScalars 18 }

    tnPcsStats10GFCRxCV1DayTr OBJECT-TYPE
        SYNTAX      Counter32
        MAX-ACCESS  read-only
        STATUS      current
        DESCRIPTION "1 day threshold value of PCS 10GFC RX coding violations."
        ::= { tnStatisticsPcsScalars 19 }

    tnPcsStats8GFCRxCV1DayTr OBJECT-TYPE
        SYNTAX      Counter32
        MAX-ACCESS  read-only
        STATUS      current
        DESCRIPTION "1 day threshold value of PCS 8GFC RX coding violations."
        ::= { tnStatisticsPcsScalars 20 }

    tnPcsStats4GFCRxCV1DayTr OBJECT-TYPE
        SYNTAX      Counter32
        MAX-ACCESS  read-only
        STATUS      current
        DESCRIPTION "1 day threshold value of PCS 4GFC RX coding violations."
        ::= { tnStatisticsPcsScalars 21 }

    tnPcsStats2GFCRxCV1DayTr OBJECT-TYPE
        SYNTAX      Counter32
        MAX-ACCESS  read-only
        STATUS      current
        DESCRIPTION "1 day threshold value of PCS 2GFC RX coding violations."
        ::= { tnStatisticsPcsScalars 22 }

    tnPcsStatsGFCRxCV1DayTr OBJECT-TYPE
        SYNTAX      Counter32
        MAX-ACCESS  read-only
        STATUS      current
        DESCRIPTION "1 day threshold value of PCS GFC RX coding violations."
        ::= { tnStatisticsPcsScalars 23 }

    tnPcsStatsRxES1DayTr OBJECT-TYPE
        SYNTAX      Counter32
        MAX-ACCESS  read-only
        STATUS      current
        DESCRIPTION "1 day threshold value of PCS RX errored seconds."
        ::= { tnStatisticsPcsScalars 24 }

    tnPcsStatsRxSES1DayTr OBJECT-TYPE
        SYNTAX      Counter32
        MAX-ACCESS  read-only
        STATUS      current
        DESCRIPTION "1 day threshold value of PCS RX severely errored
                     seconds."
        ::= { tnStatisticsPcsScalars 25 }

    tnPcsStatsRxSEFS1DayTr OBJECT-TYPE
        SYNTAX      Counter32
        MAX-ACCESS  read-only
        STATUS      current
        DESCRIPTION "1 day threshold value of PCS RX severely errored
                     frame seconds."
        ::= { tnStatisticsPcsScalars 26 }

    tnPcsStats100GBERxCV15MinRtr OBJECT-TYPE
        SYNTAX      Counter32
        MAX-ACCESS  read-only
        STATUS      current
        DESCRIPTION "15 minute reset threshold value of PCS 100GBE RX
                     coding violations."
        ::= { tnStatisticsPcsScalars 27 }

    tnPcsStats40GBERxCV15MinRtr OBJECT-TYPE
        SYNTAX      Counter32
        MAX-ACCESS  read-only
        STATUS      current
        DESCRIPTION "15 minute reset threshold value of PCS 40GBE RX
                     coding violations."
        ::= { tnStatisticsPcsScalars 28 }

    tnPcsStats10GBERxCV15MinRtr OBJECT-TYPE
        SYNTAX      Counter32
        MAX-ACCESS  read-only
        STATUS      current
        DESCRIPTION "15 minute reset threshold value of PCS 10GBE RX
                     coding violations."
        ::= { tnStatisticsPcsScalars 29 }

    tnPcsStatsGBERxCV15MinRtr OBJECT-TYPE
        SYNTAX      Counter32
        MAX-ACCESS  read-only
        STATUS      current
        DESCRIPTION "15 minute reset threshold value of PCS GBE RX coding
                     violations."
        ::= { tnStatisticsPcsScalars 30 }

    tnPcsStats16GFCRxCV15MinRtr OBJECT-TYPE
        SYNTAX      Counter32
        MAX-ACCESS  read-only
        STATUS      current
        DESCRIPTION "15 minute reset threshold value of PCS 16GFC RX
                     coding violations."
        ::= { tnStatisticsPcsScalars 31 }

    tnPcsStats10GFCRxCV15MinRtr OBJECT-TYPE
        SYNTAX      Counter32
        MAX-ACCESS  read-only
        STATUS      current
        DESCRIPTION "15 minute reset threshold value of PCS 10GFC RX
                     coding violations."
        ::= { tnStatisticsPcsScalars 32 }

    tnPcsStats8GFCRxCV15MinRtr OBJECT-TYPE
        SYNTAX      Counter32
        MAX-ACCESS  read-only
        STATUS      current
        DESCRIPTION "15 minute reset threshold value of PCS 8GFC RX
                     coding violations."
        ::= { tnStatisticsPcsScalars 33 }

    tnPcsStats4GFCRxCV15MinRtr OBJECT-TYPE
        SYNTAX      Counter32
        MAX-ACCESS  read-only
        STATUS      current
        DESCRIPTION "15 minute reset threshold value of PCS 4GFC RX coding
                     violations."
        ::= { tnStatisticsPcsScalars 34 }

    tnPcsStats2GFCRxCV15MinRtr OBJECT-TYPE
        SYNTAX      Counter32
        MAX-ACCESS  read-only
        STATUS      current
        DESCRIPTION "15 minute reset threshold value of PCS 2GFC RX coding
                     violations."
        ::= { tnStatisticsPcsScalars 35 }

    tnPcsStatsGFCRxCV15MinRtr OBJECT-TYPE
        SYNTAX      Counter32
        MAX-ACCESS  read-only
        STATUS      current
        DESCRIPTION "15 minute reset threshold value of PCS GFC RX coding
                     violations."
        ::= { tnStatisticsPcsScalars 36 }

    tnPcsStatsRxES15MinRtr OBJECT-TYPE
        SYNTAX      Counter32
        MAX-ACCESS  read-only
        STATUS      current
        DESCRIPTION "15 minute reset threshold value of PCS RX errored
                     seconds."
        ::= { tnStatisticsPcsScalars 37 }

    tnPcsStatsRxSES15MinRtr OBJECT-TYPE
        SYNTAX      Counter32
        MAX-ACCESS  read-only
        STATUS      current
        DESCRIPTION "15 minute reset threshold value of PCS RX severly
                     errored seconds."
        ::= { tnStatisticsPcsScalars 38 }

    tnPcsStatsRxSEFS15MinRtr OBJECT-TYPE
        SYNTAX      Counter32
        MAX-ACCESS  read-only
        STATUS      current
        DESCRIPTION "15 minute reset threshold value of PCS RX severely
                     errored frame seconds."
        ::= { tnStatisticsPcsScalars 39 }

    tnPcsStats100GBETxCV15MinTr OBJECT-TYPE
        SYNTAX      Counter32
        MAX-ACCESS  read-only
        STATUS      current
        DESCRIPTION "15 minute threshold value of PCS 100GBE TX coding
                     violations."
        ::= { tnStatisticsPcsScalars 40 }

    tnPcsStats40GBETxCV15MinTr OBJECT-TYPE
        SYNTAX      Counter32
        MAX-ACCESS  read-only
        STATUS      current
        DESCRIPTION "15 minute threshold value of PCS 40GBE TX coding
                     violations."
        ::= { tnStatisticsPcsScalars 41 }

    tnPcsStats10GBETxCV15MinTr OBJECT-TYPE
        SYNTAX      Counter32
        MAX-ACCESS  read-only
        STATUS      current
        DESCRIPTION "15 minute threshold value of PCS 10GBE TX coding
                     violations."
        ::= { tnStatisticsPcsScalars 42 }

    tnPcsStatsGBETxCV15MinTr OBJECT-TYPE
        SYNTAX      Counter32
        MAX-ACCESS  read-only
        STATUS      current
        DESCRIPTION "15 minute threshold value of PCS GBE TX coding
                     violations."
        ::= { tnStatisticsPcsScalars 43 }

    tnPcsStats16GFCTxCV15MinTr OBJECT-TYPE
        SYNTAX      Counter32
        MAX-ACCESS  read-only
        STATUS      current
        DESCRIPTION "15 minute threshold value of PCS 16GFC TX coding
                     violations."
        ::= { tnStatisticsPcsScalars 44 }

    tnPcsStats10GFCTxCV15MinTr OBJECT-TYPE
        SYNTAX      Counter32
        MAX-ACCESS  read-only
        STATUS      current
        DESCRIPTION "15 minute threshold value of PCS 10GFC TX coding
                     violations."
        ::= { tnStatisticsPcsScalars 45 }

    tnPcsStats8GFCTxCV15MinTr OBJECT-TYPE
        SYNTAX      Counter32
        MAX-ACCESS  read-only
        STATUS      current
        DESCRIPTION "15 minute threshold value of PCS 8GFC TX coding
                     violations."
        ::= { tnStatisticsPcsScalars 46 }

    tnPcsStats4GFCTxCV15MinTr OBJECT-TYPE
        SYNTAX      Counter32
        MAX-ACCESS  read-only
        STATUS      current
        DESCRIPTION "15 minute threshold value of PCS 4GFC TX coding
                     violations."
        ::= { tnStatisticsPcsScalars 47 }

    tnPcsStats2GFCTxCV15MinTr OBJECT-TYPE
        SYNTAX      Counter32
        MAX-ACCESS  read-only
        STATUS      current
        DESCRIPTION "15 minute threshold value of PCS 2GFC TX coding
                     violations."
        ::= { tnStatisticsPcsScalars 48 }

    tnPcsStatsGFCTxCV15MinTr OBJECT-TYPE
        SYNTAX      Counter32
        MAX-ACCESS  read-only
        STATUS      current
        DESCRIPTION "15 minute threshold value of PCS GFC TX coding
                     violations."
        ::= { tnStatisticsPcsScalars 49 }

    tnPcsStatsTxES15MinTr OBJECT-TYPE
        SYNTAX      Counter32
        MAX-ACCESS  read-only
        STATUS      current
        DESCRIPTION "15 minute threshold value of PCS TX errored seconds."
        ::= { tnStatisticsPcsScalars 50 }

    tnPcsStatsTxSES15MinTr OBJECT-TYPE
        SYNTAX      Counter32
        MAX-ACCESS  read-only
        STATUS      current
        DESCRIPTION "15 minute threshold value of PCS TX severly errored
                     seconds."
        ::= { tnStatisticsPcsScalars 51 }

    tnPcsStatsTxSEFS15MinTr OBJECT-TYPE
        SYNTAX      Counter32
        MAX-ACCESS  read-only
        STATUS      current
        DESCRIPTION "15 minute threshold value of PCS TX severly errored
                     frame seconds."
        ::= { tnStatisticsPcsScalars 52 }

    tnPcsStats100GBETxCV1DayTr OBJECT-TYPE
        SYNTAX      Counter32
        MAX-ACCESS  read-only
        STATUS      current
        DESCRIPTION "1 day threshold value of PCS 100GBE TX coding violations."
        ::= { tnStatisticsPcsScalars 53 }

    tnPcsStats40GBETxCV1DayTr OBJECT-TYPE
        SYNTAX      Counter32
        MAX-ACCESS  read-only
        STATUS      current
        DESCRIPTION "1 day threshold value of PCS 40GBE TX coding violations."
        ::= { tnStatisticsPcsScalars 54 }

    tnPcsStats10GBETxCV1DayTr OBJECT-TYPE
        SYNTAX      Counter32
        MAX-ACCESS  read-only
        STATUS      current
        DESCRIPTION "1 day threshold value of PCS 10GBE TX coding violations."
        ::= { tnStatisticsPcsScalars 55 }

    tnPcsStatsGBETxCV1DayTr OBJECT-TYPE
        SYNTAX      Counter32
        MAX-ACCESS  read-only
        STATUS      current
        DESCRIPTION "1 day threshold value of PCS GBE TX coding violations."
        ::= { tnStatisticsPcsScalars 56 }

    tnPcsStats16GFCTxCV1DayTr OBJECT-TYPE
        SYNTAX      Counter32
        MAX-ACCESS  read-only
        STATUS      current
        DESCRIPTION "1 day threshold value of PCS 16GFC TX coding violations."
        ::= { tnStatisticsPcsScalars 57 }

    tnPcsStats10GFCTxCV1DayTr OBJECT-TYPE
        SYNTAX      Counter32
        MAX-ACCESS  read-only
        STATUS      current
        DESCRIPTION "1 day threshold value of PCS 10GFC TX coding violations."
        ::= { tnStatisticsPcsScalars 58 }

    tnPcsStats8GFCTxCV1DayTr OBJECT-TYPE
        SYNTAX      Counter32
        MAX-ACCESS  read-only
        STATUS      current
        DESCRIPTION "1 day threshold value of PCS 8GFC TX coding violations."
        ::= { tnStatisticsPcsScalars 59 }

    tnPcsStats4GFCTxCV1DayTr OBJECT-TYPE
        SYNTAX      Counter32
        MAX-ACCESS  read-only
        STATUS      current
        DESCRIPTION "1 day threshold value of PCS 4GFC TX coding violations."
        ::= { tnStatisticsPcsScalars 60 }

    tnPcsStats2GFCTxCV1DayTr OBJECT-TYPE
        SYNTAX      Counter32
        MAX-ACCESS  read-only
        STATUS      current
        DESCRIPTION "1 day threshold value of PCS 2GFC TX coding violations."
        ::= { tnStatisticsPcsScalars 61 }

    tnPcsStatsGFCTxCV1DayTr OBJECT-TYPE
        SYNTAX      Counter32
        MAX-ACCESS  read-only
        STATUS      current
        DESCRIPTION "1 day threshold value of PCS GFC TX coding violations."
        ::= { tnStatisticsPcsScalars 62 }

    tnPcsStatsTxES1DayTr OBJECT-TYPE
        SYNTAX      Counter32
        MAX-ACCESS  read-only
        STATUS      current
        DESCRIPTION "1 day threshold value of PCS TX errored seconds."
        ::= { tnStatisticsPcsScalars 63 }

    tnPcsStatsTxSES1DayTr OBJECT-TYPE
        SYNTAX      Counter32
        MAX-ACCESS  read-only
        STATUS      current
        DESCRIPTION "1 day threshold value of PCS TX severly errored
                     seconds."
        ::= { tnStatisticsPcsScalars 64 }

    tnPcsStatsTxSEFS1DayTr OBJECT-TYPE
        SYNTAX      Counter32
        MAX-ACCESS  read-only
        STATUS      current
        DESCRIPTION "1 day threshold value of PCS TX severly errored
                     frame seconds."
        ::= { tnStatisticsPcsScalars 65 }

    tnPcsStats100GBETxCV15MinRtr OBJECT-TYPE
        SYNTAX      Counter32
        MAX-ACCESS  read-only
        STATUS      current
        DESCRIPTION "15 minute reset threshold value of PCS 100GBE TX
                     coding violations."
        ::= { tnStatisticsPcsScalars 66 }

    tnPcsStats40GBETxCV15MinRtr OBJECT-TYPE
        SYNTAX      Counter32
        MAX-ACCESS  read-only
        STATUS      current
        DESCRIPTION "15 minute reset threshold value of PCS 40GBE TX
                     coding violations."
        ::= { tnStatisticsPcsScalars 67 }

    tnPcsStats10GBETxCV15MinRtr OBJECT-TYPE
        SYNTAX      Counter32
        MAX-ACCESS  read-only
        STATUS      current
        DESCRIPTION "15 minute reset threshold value of PCS 10GBE TX
                     coding violations."
        ::= { tnStatisticsPcsScalars 68 }

    tnPcsStatsGBETxCV15MinRtr OBJECT-TYPE
        SYNTAX      Counter32
        MAX-ACCESS  read-only
        STATUS      current
        DESCRIPTION "15 minute reset threshold value of PCS GBE TX coding
                     violations."
        ::= { tnStatisticsPcsScalars 69 }

    tnPcsStats16GFCTxCV15MinRtr OBJECT-TYPE
        SYNTAX      Counter32
        MAX-ACCESS  read-only
        STATUS      current
        DESCRIPTION "15 minute reset threshold value of PCS 16GFC TX coding
                     violations."
        ::= { tnStatisticsPcsScalars 70 }

    tnPcsStats10GFCTxCV15MinRtr OBJECT-TYPE
        SYNTAX      Counter32
        MAX-ACCESS  read-only
        STATUS      current
        DESCRIPTION "15 minute reset threshold value of PCS 10GFC TX coding
                     violations."
        ::= { tnStatisticsPcsScalars 71 }

    tnPcsStats8GFCTxCV15MinRtr OBJECT-TYPE
        SYNTAX      Counter32
        MAX-ACCESS  read-only
        STATUS      current
        DESCRIPTION "15 minute reset threshold value of PCS 8GFC TX coding
                     violations."
        ::= { tnStatisticsPcsScalars 72 }

    tnPcsStats4GFCTxCV15MinRtr OBJECT-TYPE
        SYNTAX      Counter32
        MAX-ACCESS  read-only
        STATUS      current
        DESCRIPTION "15 minute reset threshold value of PCS 4GFC TX coding
                     violations."
        ::= { tnStatisticsPcsScalars 73 }

    tnPcsStats2GFCTxCV15MinRtr OBJECT-TYPE
        SYNTAX      Counter32
        MAX-ACCESS  read-only
        STATUS      current
        DESCRIPTION "15 minute reset threshold value of PCS 2GFC TX coding
                     violations."
        ::= { tnStatisticsPcsScalars 74 }

    tnPcsStatsGFCTxCV15MinRtr OBJECT-TYPE
        SYNTAX      Counter32
        MAX-ACCESS  read-only
        STATUS      current
        DESCRIPTION "15 minute reset threshold value of PCS GFC TX coding
                     violations."
        ::= { tnStatisticsPcsScalars 75 }

    tnPcsStatsTxES15MinRtr OBJECT-TYPE
        SYNTAX      Counter32
        MAX-ACCESS  read-only
        STATUS      current
        DESCRIPTION "15 minute reset threshold value of PCS TX errored
                     seconds."
        ::= { tnStatisticsPcsScalars 76 }

    tnPcsStatsTxSES15MinRtr OBJECT-TYPE
        SYNTAX      Counter32
        MAX-ACCESS  read-only
        STATUS      current
        DESCRIPTION "15 minute reset threshold value of PCS TX severly
                     errored seconds."
        ::= { tnStatisticsPcsScalars 77 }

    tnPcsStatsTxSEFS15MinRtr OBJECT-TYPE
        SYNTAX      Counter32
        MAX-ACCESS  read-only
        STATUS      current
        DESCRIPTION "15 minute reset threshold value of PCS TX severly
                     errored frame seconds."
        ::= { tnStatisticsPcsScalars 78 }

    tnPcsStats400GBERxCV15MinTr OBJECT-TYPE
        SYNTAX      Counter32
        MAX-ACCESS  read-only
        STATUS      current
        DESCRIPTION "."
        ::= { tnStatisticsPcsScalars 79 }

    tnPcsStats400GBETxCV15MinTr OBJECT-TYPE
        SYNTAX      Counter32
        MAX-ACCESS  read-only
        STATUS      current
        DESCRIPTION "."
        ::= { tnStatisticsPcsScalars 80 }

    tnPcsStats400GBERxCV1DayTr OBJECT-TYPE
        SYNTAX      Counter32
        MAX-ACCESS  read-only
        STATUS      current
        DESCRIPTION "."
        ::= { tnStatisticsPcsScalars 81 }

    tnPcsStats400GBETxCV1DayTr OBJECT-TYPE
        SYNTAX      Counter32
        MAX-ACCESS  read-only
        STATUS      current
        DESCRIPTION "."
        ::= { tnStatisticsPcsScalars 82 }

    tnPcsStats400GBERxCV15MinRtr OBJECT-TYPE
        SYNTAX      Counter32
        MAX-ACCESS  read-only
        STATUS      current
        DESCRIPTION "."
        ::= { tnStatisticsPcsScalars 83 }

    tnPcsStats400GBETxCV15MinRtr OBJECT-TYPE
        SYNTAX      Counter32
        MAX-ACCESS  read-only
        STATUS      current
        DESCRIPTION "."
        ::= { tnStatisticsPcsScalars 84 }

    tnPcsStats32GFCRxCV15MinTr OBJECT-TYPE
        SYNTAX      Counter32
        MAX-ACCESS  read-only
        STATUS      current
        DESCRIPTION "15 minute threshold value of PCS 32GFC RX coding violations."
        ::= { tnStatisticsPcsScalars 85 }

    tnPcsStats32GFCTxCV15MinTr OBJECT-TYPE
        SYNTAX      Counter32
        MAX-ACCESS  read-only
        STATUS      current
        DESCRIPTION "15 minute threshold value of PCS 32GFC TX coding violations."
        ::= { tnStatisticsPcsScalars 86 }

    tnPcsStats32GFCRxCV1DayTr OBJECT-TYPE
        SYNTAX      Counter32
        MAX-ACCESS  read-only
        STATUS      current
        DESCRIPTION "1 day threshold value of PCS 32GFC RX coding violations."
        ::= { tnStatisticsPcsScalars 87 }

    tnPcsStats32GFCTxCV1DayTr OBJECT-TYPE
        SYNTAX      Counter32
        MAX-ACCESS  read-only
        STATUS      current
        DESCRIPTION "1 day threshold value of PCS 32GFC TX coding violations."
        ::= { tnStatisticsPcsScalars 88 }

    tnPcsStats32GFCRxCV15MinRtr OBJECT-TYPE
        SYNTAX      Counter32
        MAX-ACCESS  read-only
        STATUS      current
        DESCRIPTION "15 minute reset threshold value of PCS 32GFC RX coding violations."
        ::= { tnStatisticsPcsScalars 89 }

    tnPcsStats32GFCTxCV15MinRtr OBJECT-TYPE
        SYNTAX      Counter32
        MAX-ACCESS  read-only
        STATUS      current
        DESCRIPTION "15 minute reset threshold value of PCS 32GFC TX coding violations."
        ::= { tnStatisticsPcsScalars 90 }

--------------------------------------------------------------------------------
-- Statistics Tandem Connection Monitoring (TCM) Threshold Scalars
--------------------------------------------------------------------------------
    tnOthOdu0StatsTcmNeRxBIP8ErrCnt15MinTr OBJECT-TYPE
        SYNTAX      Counter64
        MAX-ACCESS  read-only
        STATUS      current
        DESCRIPTION "15 minute threshold value for the number of ODU0
                     TCM layer error blocks detected at near-end
                     receiving direction."
        ::= { tnStatisticsOthOduTcmScalars 1 }

    tnOthOdu0StatsTcmNeRxBIP8ErrCnt15MinRtr OBJECT-TYPE
        SYNTAX      Counter64
        MAX-ACCESS  read-only
        STATUS      current
        DESCRIPTION "15 minute reset threshold value for the number of
                     ODU0 TCM layer error blocks detected at near-end
                     receiving direction."
        ::= { tnStatisticsOthOduTcmScalars 2 }

    tnOthOdu0StatsTcmNeRxBIP8ErrCnt1DayTr OBJECT-TYPE
        SYNTAX      Counter64
        MAX-ACCESS  read-only
        STATUS      current
        DESCRIPTION "1 day threshold value for the number of ODU0 layer
                     TCM error blocks detected at near-end receiving
                     direction."
        ::= { tnStatisticsOthOduTcmScalars 3 }

    tnOthOdu0StatsTcmFeRxBIP8ErrCnt15MinTr OBJECT-TYPE
        SYNTAX      Counter64
        MAX-ACCESS  read-only
        STATUS      current
        DESCRIPTION "15 minute threshold value for the number of ODU0
                     TCM layer error blocks detected at far-end receiving
                     direction."
        ::= { tnStatisticsOthOduTcmScalars 4 }

    tnOthOdu0StatsTcmFeRxBIP8ErrCnt15MinRtr OBJECT-TYPE
        SYNTAX      Counter64
        MAX-ACCESS  read-only
        STATUS      current
        DESCRIPTION "15 minute reset threshold value for the number of
                     ODU0 TCM layer error blocks detected at far-end
                     receiving direction."
        ::= { tnStatisticsOthOduTcmScalars 5 }

    tnOthOdu0StatsTcmFeRxBIP8ErrCnt1DayTr OBJECT-TYPE
        SYNTAX      Counter64
        MAX-ACCESS  read-only
        STATUS      current
        DESCRIPTION "1 day threshold value for the number of ODU0 TCM
                     layer error blocks detected at far-end receiving
                     direction."
        ::= { tnStatisticsOthOduTcmScalars 6 }

    tnOthOdu1StatsTcmNeRxBIP8ErrCnt15MinTr OBJECT-TYPE
        SYNTAX      Counter64
        MAX-ACCESS  read-only
        STATUS      current
        DESCRIPTION "15 minute threshold value for the number of ODU1
                     TCM layer error blocks detected at near-end
                     receiving direction."
        ::= { tnStatisticsOthOduTcmScalars 7 }

    tnOthOdu1StatsTcmNeRxBIP8ErrCnt15MinRtr OBJECT-TYPE
        SYNTAX      Counter64
        MAX-ACCESS  read-only
        STATUS      current
        DESCRIPTION "15 minute reset threshold value for the number of
                     ODU1 TCM layer error blocks detected at near-end
                     receiving direction."
        ::= { tnStatisticsOthOduTcmScalars 8 }

    tnOthOdu1StatsTcmNeRxBIP8ErrCnt1DayTr OBJECT-TYPE
        SYNTAX      Counter64
        MAX-ACCESS  read-only
        STATUS      current
        DESCRIPTION "1 day threshold value for the number of ODU1 layer
                     TCM error blocks detected at near-end receiving
                     direction."
        ::= { tnStatisticsOthOduTcmScalars 9 }

    tnOthOdu1StatsTcmFeRxBIP8ErrCnt15MinTr OBJECT-TYPE
        SYNTAX      Counter64
        MAX-ACCESS  read-only
        STATUS      current
        DESCRIPTION "15 minute threshold value for the number of ODU1
                     TCM layer error blocks detected at far-end receiving
                     direction."
        ::= { tnStatisticsOthOduTcmScalars 10 }

    tnOthOdu1StatsTcmFeRxBIP8ErrCnt15MinRtr OBJECT-TYPE
        SYNTAX      Counter64
        MAX-ACCESS  read-only
        STATUS      current
        DESCRIPTION "15 minute reset threshold value for the number of
                     ODU1 TCM layer error blocks detected at far-end
                     receiving direction."
        ::= { tnStatisticsOthOduTcmScalars 11 }

    tnOthOdu1StatsTcmFeRxBIP8ErrCnt1DayTr OBJECT-TYPE
        SYNTAX      Counter64
        MAX-ACCESS  read-only
        STATUS      current
        DESCRIPTION "1 day threshold value for the number of ODU1 TCM
                     layer error blocks detected at far-end receiving
                     direction."
        ::= { tnStatisticsOthOduTcmScalars 12 }

    tnOthOdu2StatsTcmNeRxBIP8ErrCnt15MinTr OBJECT-TYPE
        SYNTAX      Counter64
        MAX-ACCESS  read-only
        STATUS      current
        DESCRIPTION "15 minute threshold value for the number of ODU2
                     TCM layer error blocks detected at near-end
                     receiving direction."
        ::= { tnStatisticsOthOduTcmScalars 13 }

    tnOthOdu2StatsTcmNeRxBIP8ErrCnt15MinRtr OBJECT-TYPE
        SYNTAX      Counter64
        MAX-ACCESS  read-only
        STATUS      current
        DESCRIPTION "15 minute reset threshold value for the number of
                     ODU2 TCM layer error blocks detected at near-end
                     receiving direction."
        ::= { tnStatisticsOthOduTcmScalars 14 }

    tnOthOdu2StatsTcmNeRxBIP8ErrCnt1DayTr OBJECT-TYPE
        SYNTAX      Counter64
        MAX-ACCESS  read-only
        STATUS      current
        DESCRIPTION "1 day threshold value for the number of ODU2 layer
                     TCM error blocks detected at near-end receiving
                     direction."
        ::= { tnStatisticsOthOduTcmScalars 15 }

    tnOthOdu2StatsTcmFeRxBIP8ErrCnt15MinTr OBJECT-TYPE
        SYNTAX      Counter64
        MAX-ACCESS  read-only
        STATUS      current
        DESCRIPTION "15 minute threshold value for the number of ODU2
                     TCM layer error blocks detected at far-end receiving
                     direction."
        ::= { tnStatisticsOthOduTcmScalars 16 }

    tnOthOdu2StatsTcmFeRxBIP8ErrCnt15MinRtr OBJECT-TYPE
        SYNTAX      Counter64
        MAX-ACCESS  read-only
        STATUS      current
        DESCRIPTION "15 minute reset threshold value for the number of
                     ODU2 TCM layer error blocks detected at far-end
                     receiving direction."
        ::= { tnStatisticsOthOduTcmScalars 17 }

    tnOthOdu2StatsTcmFeRxBIP8ErrCnt1DayTr OBJECT-TYPE
        SYNTAX      Counter64
        MAX-ACCESS  read-only
        STATUS      current
        DESCRIPTION "1 day threshold value for the number of ODU2 TCM
                     layer error blocks detected at far-end receiving
                     direction."
        ::= { tnStatisticsOthOduTcmScalars 18 }

    tnOthOdu3StatsTcmNeRxBIP8ErrCnt15MinTr OBJECT-TYPE
        SYNTAX      Counter64
        MAX-ACCESS  read-only
        STATUS      current
        DESCRIPTION "15 minute threshold value for the number of ODU3
                     TCM layer error blocks detected at near-end
                     receiving direction."
        ::= { tnStatisticsOthOduTcmScalars 19 }

    tnOthOdu3StatsTcmNeRxBIP8ErrCnt15MinRtr OBJECT-TYPE
        SYNTAX      Counter64
        MAX-ACCESS  read-only
        STATUS      current
        DESCRIPTION "15 minute reset threshold value for the number of
                     ODU3 TCM layer error blocks detected at near-end
                     receiving direction."
        ::= { tnStatisticsOthOduTcmScalars 20 }

    tnOthOdu3StatsTcmNeRxBIP8ErrCnt1DayTr OBJECT-TYPE
        SYNTAX      Counter64
        MAX-ACCESS  read-only
        STATUS      current
        DESCRIPTION "1 day threshold value for the number of ODU3 layer
                     TCM error blocks detected at near-end receiving
                     direction."
        ::= { tnStatisticsOthOduTcmScalars 21 }

    tnOthOdu3StatsTcmFeRxBIP8ErrCnt15MinTr OBJECT-TYPE
        SYNTAX      Counter64
        MAX-ACCESS  read-only
        STATUS      current
        DESCRIPTION "15 minute threshold value for the number of ODU3
                     TCM layer error blocks detected at far-end receiving
                     direction."
        ::= { tnStatisticsOthOduTcmScalars 22 }

    tnOthOdu3StatsTcmFeRxBIP8ErrCnt15MinRtr OBJECT-TYPE
        SYNTAX      Counter64
        MAX-ACCESS  read-only
        STATUS      current
        DESCRIPTION "15 minute reset threshold value for the number of
                     ODU3 TCM layer error blocks detected at far-end
                     receiving direction."
        ::= { tnStatisticsOthOduTcmScalars 23 }

    tnOthOdu3StatsTcmFeRxBIP8ErrCnt1DayTr OBJECT-TYPE
        SYNTAX      Counter64
        MAX-ACCESS  read-only
        STATUS      current
        DESCRIPTION "1 day threshold value for the number of ODU3 TCM
                     layer error blocks detected at far-end receiving
                     direction."
        ::= { tnStatisticsOthOduTcmScalars 24 }

    tnOthOdu4StatsTcmNeRxBIP8ErrCnt15MinTr OBJECT-TYPE
        SYNTAX      Counter64
        MAX-ACCESS  read-only
        STATUS      current
        DESCRIPTION "15 minute threshold value for the number of ODU4
                     TCM layer error blocks detected at near-end
                     receiving direction."
        ::= { tnStatisticsOthOduTcmScalars 25 }

    tnOthOdu4StatsTcmNeRxBIP8ErrCnt15MinRtr OBJECT-TYPE
        SYNTAX      Counter64
        MAX-ACCESS  read-only
        STATUS      current
        DESCRIPTION "15 minute reset threshold value for the number of
                     ODU4 TCM layer error blocks detected at near-end
                     receiving direction."
        ::= { tnStatisticsOthOduTcmScalars 26 }

    tnOthOdu4StatsTcmNeRxBIP8ErrCnt1DayTr OBJECT-TYPE
        SYNTAX      Counter64
        MAX-ACCESS  read-only
        STATUS      current
        DESCRIPTION "1 day threshold value for the number of ODU4 layer
                     TCM error blocks detected at near-end receiving
                     direction."
        ::= { tnStatisticsOthOduTcmScalars 27 }

    tnOthOdu4StatsTcmFeRxBIP8ErrCnt15MinTr OBJECT-TYPE
        SYNTAX      Counter64
        MAX-ACCESS  read-only
        STATUS      current
        DESCRIPTION "15 minute threshold value for the number of ODU4
                     TCM layer error blocks detected at far-end receiving
                     direction."
        ::= { tnStatisticsOthOduTcmScalars 28 }

    tnOthOdu4StatsTcmFeRxBIP8ErrCnt15MinRtr OBJECT-TYPE
        SYNTAX      Counter64
        MAX-ACCESS  read-only
        STATUS      current
        DESCRIPTION "15 minute reset threshold value for the number of
                     ODU4 TCM layer error blocks detected at far-end
                     receiving direction."
        ::= { tnStatisticsOthOduTcmScalars 29 }

    tnOthOdu4StatsTcmFeRxBIP8ErrCnt1DayTr OBJECT-TYPE
        SYNTAX      Counter64
        MAX-ACCESS  read-only
        STATUS      current
        DESCRIPTION "1 day threshold value for the number of ODU4 TCM
                     layer error blocks detected at far-end receiving
                     direction."
        ::= { tnStatisticsOthOduTcmScalars 30 }

    tnOthOdukStatsTcmNeRxES15MinTr OBJECT-TYPE
        SYNTAX      Counter64
        MAX-ACCESS  read-only
        STATUS      current
        DESCRIPTION "15 minute threshold value for the TCM errored seconds
                     detected at near-end receiving direction."
        ::= { tnStatisticsOthOduTcmScalars 31 }

    tnOthOdukStatsTcmNeRxES15MinRtr OBJECT-TYPE
        SYNTAX      Counter64
        MAX-ACCESS  read-only
        STATUS      current
        DESCRIPTION "15 minute reset threshold value for the TCM errored
                     seconds detected at near-end receiving direction."
        ::= { tnStatisticsOthOduTcmScalars 32 }

    tnOthOdukStatsTcmNeRxES1DayTr OBJECT-TYPE
        SYNTAX      Counter64
        MAX-ACCESS  read-only
        STATUS      current
        DESCRIPTION "1 day threshold value for the TCM errored seconds
                    detected at near-end receiving direction."
        ::= { tnStatisticsOthOduTcmScalars 33 }

    tnOthOdukStatsTcmFeRxES15MinTr OBJECT-TYPE
        SYNTAX      Counter64
        MAX-ACCESS  read-only
        STATUS      current
        DESCRIPTION "15 minute threshold value for the TCM errored seconds
                     detected at far-end receiving direction."
        ::= { tnStatisticsOthOduTcmScalars 34 }

    tnOthOdukStatsTcmFeRxES15MinRtr OBJECT-TYPE
        SYNTAX      Counter64
        MAX-ACCESS  read-only
        STATUS      current
        DESCRIPTION "15 minute reset threshold value for the TCM errored
                     seconds detected at far-end receiving direction."
        ::= { tnStatisticsOthOduTcmScalars 35 }

    tnOthOdukStatsTcmFeRxES1DayTr OBJECT-TYPE
        SYNTAX      Counter64
        MAX-ACCESS  read-only
        STATUS      current
        DESCRIPTION "1 day threshold value for the TCM errored seconds
                     detected at far-end receiving direction."
        ::= { tnStatisticsOthOduTcmScalars 36 }

    tnOthOdukStatsTcmNeRxSES15MinTr OBJECT-TYPE
        SYNTAX      Counter64
        MAX-ACCESS  read-only
        STATUS      current
        DESCRIPTION "15 minute threshold value forthe TCM severely errored
                     seconds detected at near-end receiving direction."
        ::= { tnStatisticsOthOduTcmScalars 37 }

    tnOthOdukStatsTcmNeRxSES15MinRtr OBJECT-TYPE
        SYNTAX      Counter64
        MAX-ACCESS  read-only
        STATUS      current
        DESCRIPTION "15 minute reset threshold value forthe TCM severely
                     errored seconds detected at near-end receiving
                     direction."
        ::= { tnStatisticsOthOduTcmScalars 38 }

    tnOthOdukStatsTcmNeRxSES1DayTr OBJECT-TYPE
        SYNTAX      Counter64
        MAX-ACCESS  read-only
        STATUS      current
        DESCRIPTION "1 day threshold value forthe TCM severely errored
                     seconds detected at near-end receiving direction."
        ::= { tnStatisticsOthOduTcmScalars 39 }

    tnOthOdukStatsTcmFeRxSES15MinTr OBJECT-TYPE
        SYNTAX      Counter64
        MAX-ACCESS  read-only
        STATUS      current
        DESCRIPTION "15 minute threshold value forthe TCM severely
                     errored seconds detected at far-end receiving
                     direction."
        ::= { tnStatisticsOthOduTcmScalars 40 }

    tnOthOdukStatsTcmFeRxSES15MinRtr OBJECT-TYPE
        SYNTAX      Counter64
        MAX-ACCESS  read-only
        STATUS      current
        DESCRIPTION "15 minute reset threshold value forthe TCM severely
                     errored seconds detected at far-end receiving
                     direction."
        ::= { tnStatisticsOthOduTcmScalars 41 }

    tnOthOdukStatsTcmFeRxSES1DayTr OBJECT-TYPE
        SYNTAX      Counter64
        MAX-ACCESS  read-only
        STATUS      current
        DESCRIPTION "1 day threshold value forthe TCM severely errored
                     seconds detected at far-end receiving direction."
        ::= { tnStatisticsOthOduTcmScalars 42 }

    tnOthOdukStatsTcmNeRxUAS15MinTr OBJECT-TYPE
        SYNTAX      Counter64
        MAX-ACCESS  read-only
        STATUS      current
        DESCRIPTION "15 minute threshold value forthe TCM unavailable
                     seconds detected at near-end receiving direction."
        ::= { tnStatisticsOthOduTcmScalars 43 }

    tnOthOdukStatsTcmNeRxUAS15MinRtr OBJECT-TYPE
        SYNTAX      Counter64
        MAX-ACCESS  read-only
        STATUS      current
        DESCRIPTION "15 minute reset threshold value forthe TCM unavailable
                     seconds detected at near-end receiving direction."
        ::= { tnStatisticsOthOduTcmScalars 44 }

    tnOthOdukStatsTcmNeRxUAS1DayTr OBJECT-TYPE
        SYNTAX      Counter64
        MAX-ACCESS  read-only
        STATUS      current
        DESCRIPTION "1 day threshold value forthe TCM unavailable seconds
                     detected at near-end receiving direction."
        ::= { tnStatisticsOthOduTcmScalars 45 }

    tnOthOdukStatsTcmFeRxUAS15MinTr OBJECT-TYPE
        SYNTAX      Counter64
        MAX-ACCESS  read-only
        STATUS      current
        DESCRIPTION "15 minute threshold value forthe TCM unavailable
                     seconds detected at far-end receiving direction."
        ::= { tnStatisticsOthOduTcmScalars 46 }

    tnOthOdukStatsTcmFeRxUAS15MinRtr OBJECT-TYPE
        SYNTAX      Counter64
        MAX-ACCESS  read-only
        STATUS      current
        DESCRIPTION "15 minute reset threshold value forthe TCM unavailable
                     seconds detected at far-end receiving direction."
        ::= { tnStatisticsOthOduTcmScalars 47 }

    tnOthOdukStatsTcmFeRxUAS1DayTr OBJECT-TYPE
        SYNTAX      Counter64
        MAX-ACCESS  read-only
        STATUS      current
        DESCRIPTION "1 day threshold value forthe TCM unavailable seconds
                     detected at far-end receiving direction."
        ::= { tnStatisticsOthOduTcmScalars 48 }

    tnOthOduflexGFPStatsTcmNeRxBIP8ErrCnt15MinTr OBJECT-TYPE
        SYNTAX      Counter64
        MAX-ACCESS  read-only
        STATUS      current
        DESCRIPTION "15 minute threshold value
                     detected at near-end receiving direction."
        ::= { tnStatisticsOthOduTcmScalars 49 }

    tnOthOduflexGFPStatsTcmNeRxBIP8ErrCnt1DayTr OBJECT-TYPE
        SYNTAX      Counter64
        MAX-ACCESS  read-only
        STATUS      current
        DESCRIPTION "1 day threshold value
                     detected at near-end receiving direction."
        ::= { tnStatisticsOthOduTcmScalars 50 }

    tnOthOduflexGFPStatsTcmFeRxBIP8ErrCnt15MinTr OBJECT-TYPE
        SYNTAX      Counter64
        MAX-ACCESS  read-only
        STATUS      current
        DESCRIPTION "15 minute threshold value
                     detected at far-end receiving direction."
        ::= { tnStatisticsOthOduTcmScalars 51 }

    tnOthOduflexGFPStatsTcmFeRxBIP8ErrCnt1DayTr OBJECT-TYPE
        SYNTAX      Counter64
        MAX-ACCESS  read-only
        STATUS      current
        DESCRIPTION "1 day threshold value
                     detected at far-end receiving direction."
        ::= { tnStatisticsOthOduTcmScalars 52 }

    tnOthOduflexFC400StatsTcmNeRxBIP8ErrCnt15MinTr OBJECT-TYPE
        SYNTAX      Counter64
        MAX-ACCESS  read-only
        STATUS      current
        DESCRIPTION "15 minute threshold value
                     detected at near-end receiving direction."
        ::= { tnStatisticsOthOduTcmScalars 53 }

    tnOthOduflexFC400StatsTcmNeRxBIP8ErrCnt1DayTr OBJECT-TYPE
        SYNTAX      Counter64
        MAX-ACCESS  read-only
        STATUS      current
        DESCRIPTION "1 day threshold value
                     detected at near-end receiving direction."
        ::= { tnStatisticsOthOduTcmScalars 54 }

    tnOthOduflexFC400StatsTcmFeRxBIP8ErrCnt15MinTr OBJECT-TYPE
        SYNTAX      Counter64
        MAX-ACCESS  read-only
        STATUS      current
        DESCRIPTION "15 minute threshold value
                     detected at far-end receiving direction."
        ::= { tnStatisticsOthOduTcmScalars 55 }

    tnOthOduflexFC400StatsTcmFeRxBIP8ErrCnt1DayTr OBJECT-TYPE
        SYNTAX      Counter64
        MAX-ACCESS  read-only
        STATUS      current
        DESCRIPTION "1 day threshold value
                     detected at far-end receiving direction."
        ::= { tnStatisticsOthOduTcmScalars 56 }

    tnOthOduflexFC800StatsTcmNeRxBIP8ErrCnt15MinTr OBJECT-TYPE
        SYNTAX      Counter64
        MAX-ACCESS  read-only
        STATUS      current
        DESCRIPTION "15 minute threshold value
                     detected at near-end receiving direction."
        ::= { tnStatisticsOthOduTcmScalars 57 }

    tnOthOduflexFC800StatsTcmNeRxBIP8ErrCnt1DayTr OBJECT-TYPE
        SYNTAX      Counter64
        MAX-ACCESS  read-only
        STATUS      current
        DESCRIPTION "1 day threshold value
                     detected at near-end receiving direction."
        ::= { tnStatisticsOthOduTcmScalars 58 }

    tnOthOduflexFC800StatsTcmFeRxBIP8ErrCnt15MinTr OBJECT-TYPE
        SYNTAX      Counter64
        MAX-ACCESS  read-only
        STATUS      current
        DESCRIPTION "15 minute threshold value
                     detected at far-end receiving direction."
        ::= { tnStatisticsOthOduTcmScalars 59 }

    tnOthOduflexFC800StatsTcmFeRxBIP8ErrCnt1DayTr OBJECT-TYPE
        SYNTAX      Counter64
        MAX-ACCESS  read-only
        STATUS      current
        DESCRIPTION "1 day threshold value
                     detected at far-end receiving direction."
        ::= { tnStatisticsOthOduTcmScalars 60 }

    tnOthOduflexFC1600StatsTcmNeRxBIP8ErrCnt15MinTr OBJECT-TYPE
        SYNTAX      Counter64
        MAX-ACCESS  read-only
        STATUS      current
        DESCRIPTION "15 minute threshold value
                     detected at near-end receiving direction."
        ::= { tnStatisticsOthOduTcmScalars 61 }

    tnOthOduflexFC1600StatsTcmNeRxBIP8ErrCnt1DayTr OBJECT-TYPE
        SYNTAX      Counter64
        MAX-ACCESS  read-only
        STATUS      current
        DESCRIPTION "1 day threshold value
                     detected at near-end receiving direction."
        ::= { tnStatisticsOthOduTcmScalars 62 }

    tnOthOduflexFC1600StatsTcmFeRxBIP8ErrCnt15MinTr OBJECT-TYPE
        SYNTAX      Counter64
        MAX-ACCESS  read-only
        STATUS      current
        DESCRIPTION "15 minute threshold value
                     detected at far-end receiving direction."
        ::= { tnStatisticsOthOduTcmScalars 63 }

    tnOthOduflexFC1600StatsTcmFeRxBIP8ErrCnt1DayTr OBJECT-TYPE
        SYNTAX      Counter64
        MAX-ACCESS  read-only
        STATUS      current
        DESCRIPTION "1 day threshold value
                     detected at far-end receiving direction."
        ::= { tnStatisticsOthOduTcmScalars 64 }

    tnOthOduflexIBSDRStatsTcmNeRxBIP8ErrCnt15MinTr OBJECT-TYPE
        SYNTAX      Counter64
        MAX-ACCESS  read-only
        STATUS      current
        DESCRIPTION "15 minute threshold value
                     detected at near-end receiving direction."
        ::= { tnStatisticsOthOduTcmScalars 65 }

    tnOthOduflexIBSDRStatsTcmNeRxBIP8ErrCnt1DayTr OBJECT-TYPE
        SYNTAX      Counter64
        MAX-ACCESS  read-only
        STATUS      current
        DESCRIPTION "1 day threshold value
                     detected at near-end receiving direction."
        ::= { tnStatisticsOthOduTcmScalars 66 }

    tnOthOduflexIBSDRStatsTcmFeRxBIP8ErrCnt15MinTr OBJECT-TYPE
        SYNTAX      Counter64
        MAX-ACCESS  read-only
        STATUS      current
        DESCRIPTION "15 minute threshold value
                     detected at far-end receiving direction."
        ::= { tnStatisticsOthOduTcmScalars 67 }

    tnOthOduflexIBSDRStatsTcmFeRxBIP8ErrCnt1DayTr OBJECT-TYPE
        SYNTAX      Counter64
        MAX-ACCESS  read-only
        STATUS      current
        DESCRIPTION "1 day threshold value
                     detected at far-end receiving direction."
        ::= { tnStatisticsOthOduTcmScalars 68 }

    tnOthOduflexIBDDRStatsTcmNeRxBIP8ErrCnt15MinTr OBJECT-TYPE
        SYNTAX      Counter64
        MAX-ACCESS  read-only
        STATUS      current
        DESCRIPTION "15 minute threshold value
                     detected at near-end receiving direction."
        ::= { tnStatisticsOthOduTcmScalars 69 }

    tnOthOduflexIBDDRStatsTcmNeRxBIP8ErrCnt1DayTr OBJECT-TYPE
        SYNTAX      Counter64
        MAX-ACCESS  read-only
        STATUS      current
        DESCRIPTION "1 day threshold value
                     detected at near-end receiving direction."
        ::= { tnStatisticsOthOduTcmScalars 70 }

    tnOthOduflexIBDDRStatsTcmFeRxBIP8ErrCnt15MinTr OBJECT-TYPE
        SYNTAX      Counter64
        MAX-ACCESS  read-only
        STATUS      current
        DESCRIPTION "15 minute threshold value
                     detected at far-end receiving direction."
        ::= { tnStatisticsOthOduTcmScalars 71 }

    tnOthOduflexIBDDRStatsTcmFeRxBIP8ErrCnt1DayTr OBJECT-TYPE
        SYNTAX      Counter64
        MAX-ACCESS  read-only
        STATUS      current
        DESCRIPTION "1 day threshold value
                     detected at far-end receiving direction."
        ::= { tnStatisticsOthOduTcmScalars 72 }

    tnOthOduflexIBQDRStatsTcmNeRxBIP8ErrCnt15MinTr OBJECT-TYPE
        SYNTAX      Counter64
        MAX-ACCESS  read-only
        STATUS      current
        DESCRIPTION "15 minute threshold value
                     detected at near-end receiving direction."
        ::= { tnStatisticsOthOduTcmScalars 73 }

    tnOthOduflexIBQDRStatsTcmNeRxBIP8ErrCnt1DayTr OBJECT-TYPE
        SYNTAX      Counter64
        MAX-ACCESS  read-only
        STATUS      current
        DESCRIPTION "1 day threshold value
                     detected at near-end receiving direction."
        ::= { tnStatisticsOthOduTcmScalars 74 }

    tnOthOduflexIBQDRStatsTcmFeRxBIP8ErrCnt15MinTr OBJECT-TYPE
        SYNTAX      Counter64
        MAX-ACCESS  read-only
        STATUS      current
        DESCRIPTION "15 minute threshold value
                     detected at far-end receiving direction."
        ::= { tnStatisticsOthOduTcmScalars 75 }

    tnOthOduflexIBQDRStatsTcmFeRxBIP8ErrCnt1DayTr OBJECT-TYPE
        SYNTAX      Counter64
        MAX-ACCESS  read-only
        STATUS      current
        DESCRIPTION "1 day threshold value
                     detected at far-end receiving direction."
        ::= { tnStatisticsOthOduTcmScalars 76 }

    tnOthOduflex3GSDI18StatsTcmNeRxBIP8ErrCnt15MinTr OBJECT-TYPE
        SYNTAX      Counter64
        MAX-ACCESS  read-only
        STATUS      current
        DESCRIPTION "15 minute threshold value
                     detected at near-end receiving direction."
        ::= { tnStatisticsOthOduTcmScalars 77 }

    tnOthOduflex3GSDI18StatsTcmNeRxBIP8ErrCnt1DayTr OBJECT-TYPE
        SYNTAX      Counter64
        MAX-ACCESS  read-only
        STATUS      current
        DESCRIPTION "1 day threshold value
                     detected at near-end receiving direction."
        ::= { tnStatisticsOthOduTcmScalars 78 }

    tnOthOduflex3GSDI18StatsTcmFeRxBIP8ErrCnt15MinTr OBJECT-TYPE
        SYNTAX      Counter64
        MAX-ACCESS  read-only
        STATUS      current
        DESCRIPTION "15 minute threshold value
                     detected at far-end receiving direction."
        ::= { tnStatisticsOthOduTcmScalars 79 }

    tnOthOduflex3GSDI18StatsTcmFeRxBIP8ErrCnt1DayTr OBJECT-TYPE
        SYNTAX      Counter64
        MAX-ACCESS  read-only
        STATUS      current
        DESCRIPTION "1 day threshold value
                     detected at far-end receiving direction."
        ::= { tnStatisticsOthOduTcmScalars 80 }

    tnOthOduflex3GSDI19StatsTcmNeRxBIP8ErrCnt15MinTr OBJECT-TYPE
        SYNTAX      Counter64
        MAX-ACCESS  read-only
        STATUS      current
        DESCRIPTION "15 minute threshold value
                     detected at near-end receiving direction."
        ::= { tnStatisticsOthOduTcmScalars 81 }

    tnOthOduflex3GSDI19StatsTcmNeRxBIP8ErrCnt1DayTr OBJECT-TYPE
        SYNTAX      Counter64
        MAX-ACCESS  read-only
        STATUS      current
        DESCRIPTION "1 day threshold value
                     detected at near-end receiving direction."
        ::= { tnStatisticsOthOduTcmScalars 82 }

    tnOthOduflex3GSDI19StatsTcmFeRxBIP8ErrCnt15MinTr OBJECT-TYPE
        SYNTAX      Counter64
        MAX-ACCESS  read-only
        STATUS      current
        DESCRIPTION "15 minute threshold value
                     detected at far-end receiving direction."
        ::= { tnStatisticsOthOduTcmScalars 83 }

    tnOthOduflex3GSDI19StatsTcmFeRxBIP8ErrCnt1DayTr OBJECT-TYPE
        SYNTAX      Counter64
        MAX-ACCESS  read-only
        STATUS      current
        DESCRIPTION "1 day threshold value
                     detected at far-end receiving direction."
        ::= { tnStatisticsOthOduTcmScalars 84 }

    tnOthOduflexGFPStatsTcmFeRxBIP8ErrCnt15MinRtr OBJECT-TYPE
        SYNTAX      Counter64
        MAX-ACCESS  read-only
        STATUS      current
        DESCRIPTION "15 minute threshold value
                     detected at far-end receiving direction."
        ::= { tnStatisticsOthOduTcmScalars 85 }

    tnOthOduflexGFPStatsTcmNeRxBIP8ErrCnt15MinRtr OBJECT-TYPE
        SYNTAX      Counter64
        MAX-ACCESS  read-only
        STATUS      current
        DESCRIPTION "15 minute threshold value
                     detected at near-end receiving direction."
        ::= { tnStatisticsOthOduTcmScalars 86 }

    tnOthOduflexFC400StatsTcmFeRxBIP8ErrCnt15MinRtr OBJECT-TYPE
        SYNTAX      Counter64
        MAX-ACCESS  read-only
        STATUS      current
        DESCRIPTION "15 minute threshold value
                     detected at far-end receiving direction."
        ::= { tnStatisticsOthOduTcmScalars 87 }

    tnOthOduflexFC400StatsTcmNeRxBIP8ErrCnt15MinRtr OBJECT-TYPE
        SYNTAX      Counter64
        MAX-ACCESS  read-only
        STATUS      current
        DESCRIPTION "15 minute threshold value
                     detected at near-end receiving direction."
        ::= { tnStatisticsOthOduTcmScalars 88 }

    tnOthOduflexFC800StatsTcmFeRxBIP8ErrCnt15MinRtr OBJECT-TYPE
        SYNTAX      Counter64
        MAX-ACCESS  read-only
        STATUS      current
        DESCRIPTION "15 minute threshold value
                     detected at far-end receiving direction."
        ::= { tnStatisticsOthOduTcmScalars 89 }

    tnOthOduflexFC800StatsTcmNeRxBIP8ErrCnt15MinRtr OBJECT-TYPE
        SYNTAX      Counter64
        MAX-ACCESS  read-only
        STATUS      current
        DESCRIPTION "15 minute threshold value
                     detected at near-end receiving direction."
        ::= { tnStatisticsOthOduTcmScalars 90 }

    tnOthOduflexFC1600StatsTcmFeRxBIP8ErrCnt15MinRtr OBJECT-TYPE
        SYNTAX      Counter64
        MAX-ACCESS  read-only
        STATUS      current
        DESCRIPTION "15 minute threshold value
                     detected at far-end receiving direction."
        ::= { tnStatisticsOthOduTcmScalars 91 }

    tnOthOduflexFC1600StatsTcmNeRxBIP8ErrCnt15MinRtr OBJECT-TYPE
        SYNTAX      Counter64
        MAX-ACCESS  read-only
        STATUS      current
        DESCRIPTION "15 minute threshold value
                     detected at near-end receiving direction."
        ::= { tnStatisticsOthOduTcmScalars 92 }

    tnOthOduflexIBSDRStatsTcmFeRxBIP8ErrCnt15MinRtr OBJECT-TYPE
        SYNTAX      Counter64
        MAX-ACCESS  read-only
        STATUS      current
        DESCRIPTION "15 minute threshold value
                     detected at far-end receiving direction."
        ::= { tnStatisticsOthOduTcmScalars 93 }

    tnOthOduflexIBSDRStatsTcmNeRxBIP8ErrCnt15MinRtr OBJECT-TYPE
        SYNTAX      Counter64
        MAX-ACCESS  read-only
        STATUS      current
        DESCRIPTION "15 minute threshold value
                     detected at near-end receiving direction."
        ::= { tnStatisticsOthOduTcmScalars 94 }

    tnOthOduflexIBDDRStatsTcmFeRxBIP8ErrCnt15MinRtr OBJECT-TYPE
        SYNTAX      Counter64
        MAX-ACCESS  read-only
        STATUS      current
        DESCRIPTION "15 minute threshold value
                     detected at far-end receiving direction."
        ::= { tnStatisticsOthOduTcmScalars 95 }

    tnOthOduflexIBDDRStatsTcmNeRxBIP8ErrCnt15MinRtr OBJECT-TYPE
        SYNTAX      Counter64
        MAX-ACCESS  read-only
        STATUS      current
        DESCRIPTION "15 minute threshold value
                     detected at near-end receiving direction."
        ::= { tnStatisticsOthOduTcmScalars 96 }

    tnOthOduflexIBQDRStatsTcmFeRxBIP8ErrCnt15MinRtr OBJECT-TYPE
        SYNTAX      Counter64
        MAX-ACCESS  read-only
        STATUS      current
        DESCRIPTION "15 minute threshold value
                     detected at far-end receiving direction."
        ::= { tnStatisticsOthOduTcmScalars 97 }

    tnOthOduflexIBQDRStatsTcmNeRxBIP8ErrCnt15MinRtr OBJECT-TYPE
        SYNTAX      Counter64
        MAX-ACCESS  read-only
        STATUS      current
        DESCRIPTION "15 minute threshold value
                     detected at near-end receiving direction."
        ::= { tnStatisticsOthOduTcmScalars 98 }

    tnOthOduflex3GSDI18StatsTcmFeRxBIP8ErrCnt15MinRtr OBJECT-TYPE
        SYNTAX      Counter64
        MAX-ACCESS  read-only
        STATUS      current
        DESCRIPTION "15 minute threshold value
                     detected at far-end receiving direction."
        ::= { tnStatisticsOthOduTcmScalars 99 }

    tnOthOduflex3GSDI18StatsTcmNeRxBIP8ErrCnt15MinRtr OBJECT-TYPE
        SYNTAX      Counter64
        MAX-ACCESS  read-only
        STATUS      current
        DESCRIPTION "15 minute threshold value
                     detected at near-end receiving direction."
        ::= { tnStatisticsOthOduTcmScalars 101 }

    tnOthOduflex3GSDI19StatsTcmFeRxBIP8ErrCnt15MinRtr OBJECT-TYPE
        SYNTAX      Counter64
        MAX-ACCESS  read-only
        STATUS      current
        DESCRIPTION "15 minute threshold value
                     detected at far-end receiving direction."
        ::= { tnStatisticsOthOduTcmScalars 102 }

    tnOthOduflex3GSDI19StatsTcmNeRxBIP8ErrCnt15MinRtr OBJECT-TYPE
        SYNTAX      Counter64
        MAX-ACCESS  read-only
        STATUS      current
        DESCRIPTION "15 minute threshold value
                     detected at near-end receiving direction."
        ::= { tnStatisticsOthOduTcmScalars 103 }

    tnOthOducStatsTcmNeRxBIP8ErrCnt15MinTr OBJECT-TYPE
        SYNTAX      Counter64
        MAX-ACCESS  read-only
        STATUS      current
        DESCRIPTION "."
        ::= { tnStatisticsOthOduTcmScalars 104 }

    tnOthOducStatsTcmNeRxBIP8ErrCnt15MinRtr OBJECT-TYPE
        SYNTAX      Counter64
        MAX-ACCESS  read-only
        STATUS      current
        DESCRIPTION "."
        ::= { tnStatisticsOthOduTcmScalars 105 }

    tnOthOducStatsTcmNeRxBIP8ErrCnt1DayTr OBJECT-TYPE
        SYNTAX      Counter64
        MAX-ACCESS  read-only
        STATUS      current
        DESCRIPTION "."
        ::= { tnStatisticsOthOduTcmScalars 106 }

    tnOthOducStatsTcmFeRxBIP8ErrCnt15MinTr OBJECT-TYPE
        SYNTAX      Counter64
        MAX-ACCESS  read-only
        STATUS      current
        DESCRIPTION "."
        ::= { tnStatisticsOthOduTcmScalars 107 }

    tnOthOducStatsTcmFeRxBIP8ErrCnt15MinRtr OBJECT-TYPE
        SYNTAX      Counter64
        MAX-ACCESS  read-only
        STATUS      current
        DESCRIPTION "."
        ::= { tnStatisticsOthOduTcmScalars 108 }

    tnOthOducStatsTcmFeRxBIP8ErrCnt1DayTr OBJECT-TYPE
        SYNTAX      Counter64
        MAX-ACCESS  read-only
        STATUS      current
        DESCRIPTION "."
        ::= { tnStatisticsOthOduTcmScalars 109 }

    tnOthOduflex400GBEStatsTcmNeRxBIP8ErrCnt15MinTr OBJECT-TYPE
        SYNTAX      Counter64
        MAX-ACCESS  read-only
        STATUS      current
        DESCRIPTION "."
        ::= { tnStatisticsOthOduTcmScalars 110 }

    tnOthOduflex400GBEStatsTcmNeRxBIP8ErrCnt15MinRtr OBJECT-TYPE
        SYNTAX      Counter64
        MAX-ACCESS  read-only
        STATUS      current
        DESCRIPTION "."
        ::= { tnStatisticsOthOduTcmScalars 111 }

    tnOthOduflex400GBEStatsTcmNeRxBIP8ErrCnt1DayTr OBJECT-TYPE
        SYNTAX      Counter64
        MAX-ACCESS  read-only
        STATUS      current
        DESCRIPTION "."
        ::= { tnStatisticsOthOduTcmScalars 112 }

    tnOthOduflex400GBEStatsTcmFeRxBIP8ErrCnt15MinTr OBJECT-TYPE
        SYNTAX      Counter64
        MAX-ACCESS  read-only
        STATUS      current
        DESCRIPTION "."
        ::= { tnStatisticsOthOduTcmScalars 113 }

    tnOthOduflex400GBEStatsTcmFeRxBIP8ErrCnt15MinRtr OBJECT-TYPE
        SYNTAX      Counter64
        MAX-ACCESS  read-only
        STATUS      current
        DESCRIPTION "."
        ::= { tnStatisticsOthOduTcmScalars 114 }

    tnOthOduflex400GBEStatsTcmFeRxBIP8ErrCnt1DayTr OBJECT-TYPE
        SYNTAX      Counter64
        MAX-ACCESS  read-only
        STATUS      current
        DESCRIPTION "."
        ::= { tnStatisticsOthOduTcmScalars 115 }

--------------------------------------------------------------------------------
-- Statistics Optical Lane Power Threshold Scalars
--------------------------------------------------------------------------------
    tnOprLaneStatMaxPowerTr OBJECT-TYPE
        SYNTAX      Integer32
        UNITS       "mBm"
        MAX-ACCESS  read-only
        STATUS      current
        DESCRIPTION "High threshold for optical Lane powers in the RX
                     direction."
        ::= { tnStatisticsLanePowerScalars 1 }

    tnOprLaneStatMinPowerTr OBJECT-TYPE
        SYNTAX      Integer32
        UNITS       "mBm"
        MAX-ACCESS  read-only
        STATUS      current
        DESCRIPTION "Low threshold for optical Lane powers in the RX
                     direction."
        ::= { tnStatisticsLanePowerScalars 2 }

    tnOptLaneStatMaxPowerTr OBJECT-TYPE
        SYNTAX      Integer32
        UNITS       "mBm"
        MAX-ACCESS  read-only
        STATUS      current
        DESCRIPTION "High threshold for optical Lane powers in the TX
                     direction."
        ::= { tnStatisticsLanePowerScalars 3 }

    tnOptLaneStatMinPowerTr OBJECT-TYPE
        SYNTAX      Integer32
        UNITS       "mBm"
        MAX-ACCESS  read-only
        STATUS      current
        DESCRIPTION "Low threshold for optical Lane powers in the TX
                     direction."
        ::= { tnStatisticsLanePowerScalars 4 }

------------------------------------------------------------------------
-- Statistics Encryption Fail To Decrypt Scalars
------------------------------------------------------------------------

    tnEncryptRxFailToDecryptCnt15MinTr OBJECT-TYPE
        SYNTAX      Counter64
        MAX-ACCESS  read-only
        STATUS      current
        DESCRIPTION "15 minute threshold value for the count of BIP-8
                     decryption errors."
        ::= { tnStatisticsEncryptRxFTDScalars 1 }

    tnEncryptRxFailToDecryptCnt15MinRtr OBJECT-TYPE
        SYNTAX      Counter64
        MAX-ACCESS  read-only
        STATUS      current
        DESCRIPTION "15 minute reset threshold value for the count of BIP-8
                     decryption errors."
        ::= { tnStatisticsEncryptRxFTDScalars 2 }

    tnEncryptRxFailToDecryptCnt1DayTr OBJECT-TYPE
        SYNTAX      Counter64
        MAX-ACCESS  read-only
        STATUS      current
        DESCRIPTION "1 day threshold value for the count of BIP-8
                     decryption errors."
        ::= { tnStatisticsEncryptRxFTDScalars 3 }

    tnEncryptRxFailToDecryptCnt1DayRtr OBJECT-TYPE
        SYNTAX      Counter64
        MAX-ACCESS  read-only
        STATUS      current
        DESCRIPTION "1 day reset threshold value for the count of BIP-8
                     decryption errors."
        ::= { tnStatisticsEncryptRxFTDScalars 4 }

--------------------------------------------------------------------------------
-- Statistics FECPM Threshold Scalars
--------------------------------------------------------------------------------
    tnFECPMOtu1StatRxRsCorrCnt15MinTr OBJECT-TYPE
        SYNTAX      Counter64
        MAX-ACCESS  read-only
        STATUS      current
        DESCRIPTION "15 minute threshold value for OTU1 FEC correctable
                     error bit count at receiving direction."
        ::= { tnStatisticsFECPMScalars 1 }

    tnFECPMOtu1StatRxRsCorrCnt15MinRtr OBJECT-TYPE
        SYNTAX      Counter64
        MAX-ACCESS  read-only
        STATUS      current
        DESCRIPTION "15 minute reset threshold value for OTU1 FEC
                     correctable error bit count at receiving direction."
        ::= { tnStatisticsFECPMScalars 2 }

    tnFECPMOtu1StatRxRsCorrCnt1DayTr OBJECT-TYPE
        SYNTAX      Counter64
        MAX-ACCESS  read-only
        STATUS      current
        DESCRIPTION "1 day threshold value for OTU1 FEC correctable error
                     bit count at receiving direction."
        ::= { tnStatisticsFECPMScalars 3 }

    tnFECPMOtu1StatRxRsUncorrCnt15MinTr OBJECT-TYPE
        SYNTAX      Counter64
        MAX-ACCESS  read-only
        STATUS      current
        DESCRIPTION "15 minute threshold value for OTU1 FEC un-correctable
                     error block count at receiving direction."
        ::= { tnStatisticsFECPMScalars 4 }

    tnFECPMOtu1StatRxRsUncorrCnt15MinRtr OBJECT-TYPE
        SYNTAX      Counter64
        MAX-ACCESS  read-only
        STATUS      current
        DESCRIPTION "15 minute reset threshold value for OTU1 FEC
                     un-correctable error block count at receiving
                     direction."
        ::= { tnStatisticsFECPMScalars 5 }

    tnFECPMOtu1StatRxRsUncorrCnt1DayTr OBJECT-TYPE
        SYNTAX      Counter64
        MAX-ACCESS  read-only
        STATUS      current
        DESCRIPTION "1 day threshold value for OTU1 FEC un-correctable
                     error block count at receiving direction."
        ::= { tnStatisticsFECPMScalars 6 }

    tnFECPMOtu2StatRxRsCorrCnt15MinTr OBJECT-TYPE
        SYNTAX      Counter64
        MAX-ACCESS  read-only
        STATUS      current
        DESCRIPTION "15 minute threshold value for OTU1 FEC correctable
                     error bit count at receiving direction."
        ::= { tnStatisticsFECPMScalars 7 }

    tnFECPMOtu2StatRxRsCorrCnt15MinRtr OBJECT-TYPE
        SYNTAX      Counter64
        MAX-ACCESS  read-only
        STATUS      current
        DESCRIPTION "15 minute reset threshold value for OTU1 FEC
                     correctable error bit count at receiving direction."
        ::= { tnStatisticsFECPMScalars 8 }

    tnFECPMOtu2StatRxRsCorrCnt1DayTr OBJECT-TYPE
        SYNTAX      Counter64
        MAX-ACCESS  read-only
        STATUS      current
        DESCRIPTION "1 day threshold value for OTU1 FEC correctable error
                     bit count at receiving direction."
        ::= { tnStatisticsFECPMScalars 9 }

    tnFECPMOtu2StatRxRsUncorrCnt15MinTr OBJECT-TYPE
        SYNTAX      Counter64
        MAX-ACCESS  read-only
        STATUS      current
        DESCRIPTION "15 minute threshold value for OTU1 FEC un-correctable
                     error block count at receiving direction."
        ::= { tnStatisticsFECPMScalars 10 }

    tnFECPMOtu2StatRxRsUncorrCnt15MinRtr OBJECT-TYPE
        SYNTAX      Counter64
        MAX-ACCESS  read-only
        STATUS      current
        DESCRIPTION "15 minute reset threshold value for OTU1 FEC
                     un-correctable error block count at receiving
                     direction."
        ::= { tnStatisticsFECPMScalars 11 }

    tnFECPMOtu2StatRxRsUncorrCnt1DayTr OBJECT-TYPE
        SYNTAX      Counter64
        MAX-ACCESS  read-only
        STATUS      current
        DESCRIPTION "1 day threshold value for OTU1 FEC un-correctable
                     error block count at receiving direction."
        ::= { tnStatisticsFECPMScalars 12 }

    tnFECPMOtu3StatRxRsCorrCnt15MinTr OBJECT-TYPE
        SYNTAX      Counter64
        MAX-ACCESS  read-only
        STATUS      current
        DESCRIPTION "15 minute threshold value for OTU1 FEC correctable
                     error bit count at receiving direction."
        ::= { tnStatisticsFECPMScalars 13 }

    tnFECPMOtu3StatRxRsCorrCnt15MinRtr OBJECT-TYPE
        SYNTAX      Counter64
        MAX-ACCESS  read-only
        STATUS      current
        DESCRIPTION "15 minute reset threshold value for OTU1 FEC
                     correctable error bit count at receiving direction."
        ::= { tnStatisticsFECPMScalars 14 }

    tnFECPMOtu3StatRxRsCorrCnt1DayTr OBJECT-TYPE
        SYNTAX      Counter64
        MAX-ACCESS  read-only
        STATUS      current
        DESCRIPTION "1 day threshold value for OTU1 FEC correctable error
                     bit count at receiving direction."
        ::= { tnStatisticsFECPMScalars 15 }

    tnFECPMOtu3StatRxRsUncorrCnt15MinTr OBJECT-TYPE
        SYNTAX      Counter64
        MAX-ACCESS  read-only
        STATUS      current
        DESCRIPTION "15 minute threshold value for OTU1 FEC un-correctable
                     error block count at receiving direction."
        ::= { tnStatisticsFECPMScalars 16 }

    tnFECPMOtu3StatRxRsUncorrCnt15MinRtr OBJECT-TYPE
        SYNTAX      Counter64
        MAX-ACCESS  read-only
        STATUS      current
        DESCRIPTION "15 minute reset threshold value for OTU1 FEC
                     un-correctable error block count at receiving
                     direction."
        ::= { tnStatisticsFECPMScalars 17 }

    tnFECPMOtu3StatRxRsUncorrCnt1DayTr OBJECT-TYPE
        SYNTAX      Counter64
        MAX-ACCESS  read-only
        STATUS      current
        DESCRIPTION "1 day threshold value for OTU1 FEC un-correctable
                     error block count at receiving direction."
        ::= { tnStatisticsFECPMScalars 18 }

    tnFECPMOtu4StatRxRsCorrCnt15MinTr OBJECT-TYPE
        SYNTAX      Counter64
        MAX-ACCESS  read-only
        STATUS      current
        DESCRIPTION "15 minute threshold value for OTU1 FEC correctable
                     error bit count at receiving direction."
        ::= { tnStatisticsFECPMScalars 19 }

    tnFECPMOtu4StatRxRsCorrCnt15MinRtr OBJECT-TYPE
        SYNTAX      Counter64
        MAX-ACCESS  read-only
        STATUS      current
        DESCRIPTION "15 minute reset threshold value for OTU1 FEC
                     correctable error bit count at receiving direction."
        ::= { tnStatisticsFECPMScalars 20 }

    tnFECPMOtu4StatRxRsCorrCnt1DayTr OBJECT-TYPE
        SYNTAX      Counter64
        MAX-ACCESS  read-only
        STATUS      current
        DESCRIPTION "1 day threshold value for OTU1 FEC correctable error
                     bit count at receiving direction."
        ::= { tnStatisticsFECPMScalars 21 }

    tnFECPMOtu4StatRxRsUncorrCnt15MinTr OBJECT-TYPE
        SYNTAX      Counter64
        MAX-ACCESS  read-only
        STATUS      current
        DESCRIPTION "15 minute threshold value for OTU1 FEC un-correctable
                     error block count at receiving direction."
        ::= { tnStatisticsFECPMScalars 22 }

    tnFECPMOtu4StatRxRsUncorrCnt15MinRtr OBJECT-TYPE
        SYNTAX      Counter64
        MAX-ACCESS  read-only
        STATUS      current
        DESCRIPTION "15 minute reset threshold value for OTU1 FEC
                     un-correctable error block count at receiving
                     direction."
        ::= { tnStatisticsFECPMScalars 23 }

    tnFECPMOtu4StatRxRsUncorrCnt1DayTr OBJECT-TYPE
        SYNTAX      Counter64
        MAX-ACCESS  read-only
        STATUS      current
        DESCRIPTION "1 day threshold value for OTU1 FEC un-correctable
                     error block count at receiving direction."
        ::= { tnStatisticsFECPMScalars 24 }

    tnFECPMOtuStatRxBERPreFEC15MinTr OBJECT-TYPE
        SYNTAX      Counter64
        MAX-ACCESS  read-only
        STATUS      current
        DESCRIPTION "15 minute threshold value for preFEC BER count."
        ::= { tnStatisticsFECPMScalars 25 }

    tnFECPMOtuStatRxBERPreFEC15MinRtr OBJECT-TYPE
        SYNTAX      Counter64
        MAX-ACCESS  read-only
        STATUS      current
        DESCRIPTION "15 minute reset threshold value for preFEC BER count."
        ::= { tnStatisticsFECPMScalars 26 }

    tnFECPMOtuStatRxBERPreFEC1DayTr OBJECT-TYPE
        SYNTAX      Counter64
        MAX-ACCESS  read-only
        STATUS      current
        DESCRIPTION "1 day threshold value for preFEC BER count."
        ::= { tnStatisticsFECPMScalars 27 }

    tnFECPMOtuStatRxBERPostFEC15MinTr OBJECT-TYPE
        SYNTAX      Counter64
        MAX-ACCESS  read-only
        STATUS      current
        DESCRIPTION "15 minute threshold value for postFEC BER count."
        ::= { tnStatisticsFECPMScalars 28 }

    tnFECPMOtuStatRxBERPostFEC15MinRtr OBJECT-TYPE
        SYNTAX      Counter64
        MAX-ACCESS  read-only
        STATUS      current
        DESCRIPTION "15 minute reset threshold value for postFEC BER count."
        ::= { tnStatisticsFECPMScalars 29 }

    tnFECPMOtuStatRxBERPostFEC1DayTr OBJECT-TYPE
        SYNTAX      Counter64
        MAX-ACCESS  read-only
        STATUS      current
        DESCRIPTION "1 day threshold value for postFEC BER count."
        ::= { tnStatisticsFECPMScalars 30 }

    tnSDFECPMRxBERPreFEC15MinTr OBJECT-TYPE
        SYNTAX      Counter64
        MAX-ACCESS  read-only
        STATUS      current
        DESCRIPTION "15 minute threshold value for pre SDFEC BER count."
        ::= { tnStatisticsFECPMScalars 31 }

    tnSDFECPMRxBERPreFEC15MinRtr OBJECT-TYPE
        SYNTAX      Counter64
        MAX-ACCESS  read-only
        STATUS      current
        DESCRIPTION "15 minute reset threshold value for pre SDFEC BER count."
        ::= { tnStatisticsFECPMScalars 32 }

    tnSDFECPMRxBERPreFEC1DayTr OBJECT-TYPE
        SYNTAX      Counter64
        MAX-ACCESS  read-only
        STATUS      current
        DESCRIPTION "1 day threshold value for pre SDFEC BER count."
        ::= { tnStatisticsFECPMScalars 33 }

    tnFECPMRSFECRxBERPreFEC15MinTr OBJECT-TYPE
        SYNTAX      Counter64
        MAX-ACCESS  read-only
        STATUS      current
        DESCRIPTION "15 minute threshold value for pre RSFEC BER count."
        ::= { tnStatisticsFECPMScalars 34 }

    tnFECPMRSFECRxBERPreFEC15MinRtr OBJECT-TYPE
        SYNTAX      Counter64
        MAX-ACCESS  read-only
        STATUS      current
        DESCRIPTION "15 minute reset threshold value for pre RSFEC BER count."
        ::= { tnStatisticsFECPMScalars 35 }

    tnFECPMRSFECRxBERPreFEC1DayTr OBJECT-TYPE
        SYNTAX      Counter64
        MAX-ACCESS  read-only
        STATUS      current
        DESCRIPTION "1 day threshold value for pre RSFEC BER count."
        ::= { tnStatisticsFECPMScalars 36 }

--------------------------------------------------------------------------------
-- Statistics preFECBER Threshold Scalars
--------------------------------------------------------------------------------
    tnRxBERPreFEC15MinTr OBJECT-TYPE
        SYNTAX      Counter64
        MAX-ACCESS  read-only
        STATUS      current
        DESCRIPTION "15 minute threshold value for preFEC BER."
        ::= { tnStatisticspreFECBERScalars 1 }

    tnRxBERPreFEC15MinRtr OBJECT-TYPE
        SYNTAX      Counter64
        MAX-ACCESS  read-only
        STATUS      current
        DESCRIPTION "15 minute reset threshold value for preFEC BER."
        ::= { tnStatisticspreFECBERScalars 2 }

    tnRxBERPreFEC1DayTr OBJECT-TYPE
        SYNTAX      Counter64
        MAX-ACCESS  read-only
        STATUS      current
        DESCRIPTION "1 day threshold value for preFEC BER."
        ::= { tnStatisticspreFECBERScalars 3 }

    tnSDFECRxBERPreFEC15MinTr OBJECT-TYPE
        SYNTAX      Counter64
        MAX-ACCESS  read-only
        STATUS      current
        DESCRIPTION "15 minute threshold value for preFEC SDFEC BER."
        ::= { tnStatisticspreFECBERScalars 4 }

    tnSDFECRxBERPreFEC15MinRtr OBJECT-TYPE
        SYNTAX      Counter64
        MAX-ACCESS  read-only
        STATUS      current
        DESCRIPTION "15 minute reset threshold value for preFEC SDFEC BER."
        ::= { tnStatisticspreFECBERScalars 5 }

    tnSDFECRxBERPreFEC1DayTr OBJECT-TYPE
        SYNTAX      Counter64
        MAX-ACCESS  read-only
        STATUS      current
        DESCRIPTION "1 day threshold value for preFFEC SDFEC BER."
        ::= { tnStatisticspreFECBERScalars 6 }

--------------------------------------------------------------------------------
-- Statistics PM Fine Granularity Scalars
--------------------------------------------------------------------------------
    tnOpticalReceivePowerInterval OBJECT-TYPE
        SYNTAX      Integer32
        UNITS       "seconds"
        MAX-ACCESS  read-only
        STATUS      current
        DESCRIPTION "PM streaming OPR Interval."
        DEFVAL      { 1 }
        ::= { tnStatisticsStreamingPMScalars 1 }

    tnOpticalTransmitPowerInterval OBJECT-TYPE
        SYNTAX      Integer32
        UNITS       "seconds"
        MAX-ACCESS  read-write
        STATUS      current
        DESCRIPTION "PM streaming OPT Interval."
        DEFVAL      { 1 }
        ::= { tnStatisticsStreamingPMScalars 2 }

    tnCDRCollectInterval OBJECT-TYPE
        SYNTAX      Integer32
        UNITS       "seconds"
        MAX-ACCESS  read-write
        STATUS      current
        DESCRIPTION "PM streaming CD Interval."
        DEFVAL      { 1 }
        ::= { tnStatisticsStreamingPMScalars 3 }

    tnDGDCollectInterval OBJECT-TYPE
        SYNTAX      Integer32
        UNITS       "seconds"
        MAX-ACCESS  read-write
        STATUS      current
        DESCRIPTION "PM streaming DGD Interval."
        DEFVAL      { 1 }
        ::= { tnStatisticsStreamingPMScalars 4 }

    tnPreFecBerCollectInterval OBJECT-TYPE
        SYNTAX      Counter64
        MAX-ACCESS  read-only
        STATUS      current
        DESCRIPTION "PM streaming preFecBER Interval."
        DEFVAL      { 10 }
        ::= { tnStatisticsStreamingPMScalars 5 }

    tnPostFecBerCollectInterval OBJECT-TYPE
        SYNTAX      Counter64
        MAX-ACCESS  read-only
        STATUS      current
        DESCRIPTION "PM streaming postFecBER Interval."
        DEFVAL      { 10 }
        ::= { tnStatisticsStreamingPMScalars 6 }

    tnPCSESCollectInterval OBJECT-TYPE
        SYNTAX      Integer32
        UNITS       "seconds"
        MAX-ACCESS  read-write
        STATUS      current
        DESCRIPTION "PM streaming PCS-ES Interval."
        DEFVAL      { 10 }
        ::= { tnStatisticsStreamingPMScalars 7 }

--------------------------------------------------------------------------------
-- STREAMING PM THRESHOLD
--------------------------------------------------------------------------------
    tnStreamingPmThresholdAttributeTotal OBJECT-TYPE
        SYNTAX      Integer32
        MAX-ACCESS  read-only
        STATUS      current
        DESCRIPTION "."
        ::= { tnStatisticsTCA 32 }

--------------------------------------------------------------------------------
--  STREAMING PM THRESHOLD TABLE
--------------------------------------------------------------------------------
    tnStreamingPmThresholdTable OBJECT-TYPE
        SYNTAX      SEQUENCE OF TnStreamingPmThresholdEntry
        MAX-ACCESS  not-accessible
        STATUS      current
        DESCRIPTION "."
        ::= { tnStatisticsTCA 33 }

    tnStreamingPmThresholdEntry OBJECT-TYPE
        SYNTAX      TnStreamingPmThresholdEntry
        MAX-ACCESS  not-accessible
        STATUS      current
        DESCRIPTION "."
        INDEX   { ifIndex }
        ::= { tnStreamingPmThresholdTable 1 }

    TnStreamingPmThresholdEntry ::=
        SEQUENCE {
            tnStreamingPmOPRThreshold          Integer32,
            tnStreamingPmOPTThreshold          Integer32,
            tnStreamingPmCDRDeltaThreshold     Integer32,
            tnStreamingPmDGDDeltaThreshold     Integer32,
            tnStreamingPmPreFecBerDeltaThreshold  Counter64,
            tnStreamingPmPostFecBerDeltaThreshold   Counter64,
            tnStreamingPmPCSESDeltaThreshold   Integer32
        }

    tnStreamingPmOPRThreshold OBJECT-TYPE
        SYNTAX      Integer32
        MAX-ACCESS  read-create
        STATUS      current
        DESCRIPTION "PM streaming OPR Threshold."
        ::= { tnStreamingPmThresholdEntry 1 }

    tnStreamingPmOPTThreshold OBJECT-TYPE
        SYNTAX      Integer32
        MAX-ACCESS  read-create
        STATUS      current
        DESCRIPTION "PM streaming OPT Threshold."
        ::= { tnStreamingPmThresholdEntry 2 }

    tnStreamingPmCDRDeltaThreshold OBJECT-TYPE
        SYNTAX      Integer32
        MAX-ACCESS  read-create
        STATUS      current
        DESCRIPTION "PM streaming CD Threshold."
        ::= { tnStreamingPmThresholdEntry 3 }

    tnStreamingPmDGDDeltaThreshold OBJECT-TYPE
        SYNTAX      Integer32
        MAX-ACCESS  read-create
        STATUS      current
        DESCRIPTION "PM streaming DGD Threshold."
        ::= { tnStreamingPmThresholdEntry 4 }

    tnStreamingPmPreFecBerDeltaThreshold OBJECT-TYPE
        SYNTAX      Counter64
        MAX-ACCESS  read-only
        STATUS      current
        DESCRIPTION "PM streaming preFecBER Threshold."
        ::= { tnStreamingPmThresholdEntry 5 }

    tnStreamingPmPostFecBerDeltaThreshold OBJECT-TYPE
        SYNTAX      Counter64
        MAX-ACCESS  read-only
        STATUS      current
        DESCRIPTION "PM streaming postFecBER Threshold."
        ::= { tnStreamingPmThresholdEntry 6 }

    tnStreamingPmPCSESDeltaThreshold OBJECT-TYPE
        SYNTAX      Integer32
        MAX-ACCESS  read-create
        STATUS      current
        DESCRIPTION "PM streaming ES Threshold."
        ::= { tnStreamingPmThresholdEntry 7 }

--------------------------------------------------------------------------------
-- Statistics Fc Pkt Threshold Scalars
--------------------------------------------------------------------------------
    tnFcPktStatGRxCrcAlignErrs15MinTr OBJECT-TYPE
        SYNTAX      Counter64
        MAX-ACCESS  read-only
        STATUS      current
        DESCRIPTION "15 minute threshold value of GFC for the total number of
                     errored packets received."
        ::= { tnStatisticsFcPktScalars 1 }

    tnFcPktStatGTxCrcAlignErrs15MinTr OBJECT-TYPE
        SYNTAX      Counter64
        MAX-ACCESS  read-only
        STATUS      current
        DESCRIPTION "15 minute threshold value of GFC for the total number of
                     errored packets transmitted."
        ::= { tnStatisticsFcPktScalars 2 }

    tnFcPktStatGRxCrcAlignErrs1DayTr OBJECT-TYPE
        SYNTAX      Counter64
        MAX-ACCESS  read-only
        STATUS      current
        DESCRIPTION "1 day threshold value of GFC for the total number of errored
                     packets received."
        ::= { tnStatisticsFcPktScalars 3 }

    tnFcPktStatGTxCrcAlignErrs1DayTr OBJECT-TYPE
        SYNTAX      Counter64
        MAX-ACCESS  read-only
        STATUS      current
        DESCRIPTION "1 day threshold value of GFC for the total number of errored
                     packets transmitted."
        ::= { tnStatisticsFcPktScalars 4 }

    tnFcPktStatGRxCrcAlignErrs15MinRtr OBJECT-TYPE
        SYNTAX      Counter64
        MAX-ACCESS  read-only
        STATUS      current
        DESCRIPTION "15 minute reset threshold value of GFC for the total number
                     of errored packets received."
        ::= { tnStatisticsFcPktScalars 5 }

    tnFcPktStatGTxCrcAlignErrs15MinRtr OBJECT-TYPE
        SYNTAX      Counter64
        MAX-ACCESS  read-only
        STATUS      current
        DESCRIPTION "15 minute reset threshold value of GFC for the total number
                     of errored packets transmitted."
        ::= { tnStatisticsFcPktScalars 6 }

    tnFcPktStat2GRxCrcAlignErrs15MinTr OBJECT-TYPE
        SYNTAX      Counter64
        MAX-ACCESS  read-only
        STATUS      current
        DESCRIPTION "15 minute threshold value of 2GFC for the total number of
                     errored packets received."
        ::= { tnStatisticsFcPktScalars 7 }

    tnFcPktStat2GTxCrcAlignErrs15MinTr OBJECT-TYPE
        SYNTAX      Counter64
        MAX-ACCESS  read-only
        STATUS      current
        DESCRIPTION "15 minute threshold value of 2GFC for the total number of
                     errored packets transmitted."
        ::= { tnStatisticsFcPktScalars 8 }

    tnFcPktStat2GRxCrcAlignErrs1DayTr OBJECT-TYPE
        SYNTAX      Counter64
        MAX-ACCESS  read-only
        STATUS      current
        DESCRIPTION "1 day threshold value of 2GFC for the total number of errored
                     packets received."
        ::= { tnStatisticsFcPktScalars 9 }

    tnFcPktStat2GTxCrcAlignErrs1DayTr OBJECT-TYPE
        SYNTAX      Counter64
        MAX-ACCESS  read-only
        STATUS      current
        DESCRIPTION "1 day threshold value of 2GFC for the total number of errored
                     packets transmitted."
        ::= { tnStatisticsFcPktScalars 10 }

    tnFcPktStat2GRxCrcAlignErrs15MinRtr OBJECT-TYPE
        SYNTAX      Counter64
        MAX-ACCESS  read-only
        STATUS      current
        DESCRIPTION "15 minute reset threshold value of 2GFC for the total number
                     of errored packets received."
        ::= { tnStatisticsFcPktScalars 11 }

    tnFcPktStat2GTxCrcAlignErrs15MinRtr OBJECT-TYPE
        SYNTAX      Counter64
        MAX-ACCESS  read-only
        STATUS      current
        DESCRIPTION "15 minute reset threshold value of 2GFC for the total number
             of errored packets transmitted."
        ::= { tnStatisticsFcPktScalars 12 }

    tnFcPktStat4GRxCrcAlignErrs15MinTr OBJECT-TYPE
        SYNTAX      Counter64
        MAX-ACCESS  read-only
        STATUS      current
        DESCRIPTION "15 minute threshold value of 4GFC for the total number of
                     errored packets received."
        ::= { tnStatisticsFcPktScalars 13 }

    tnFcPktStat4GTxCrcAlignErrs15MinTr OBJECT-TYPE
        SYNTAX      Counter64
        MAX-ACCESS  read-only
        STATUS      current
        DESCRIPTION "15 minute threshold value of 4GFC for the total number of
                     errored packets transmitted."
        ::= { tnStatisticsFcPktScalars 14 }

    tnFcPktStat4GRxCrcAlignErrs1DayTr OBJECT-TYPE
        SYNTAX      Counter64
        MAX-ACCESS  read-only
        STATUS      current
        DESCRIPTION "1 day threshold value of 4GFC for the total number of errored
                     packets received."
        ::= { tnStatisticsFcPktScalars 15 }

    tnFcPktStat4GTxCrcAlignErrs1DayTr OBJECT-TYPE
        SYNTAX      Counter64
        MAX-ACCESS  read-only
        STATUS      current
        DESCRIPTION "1 day threshold value of 4GFC for the total number of errored
                     packets transmitted."
        ::= { tnStatisticsFcPktScalars 16 }

    tnFcPktStat4GRxCrcAlignErrs15MinRtr OBJECT-TYPE
        SYNTAX      Counter64
        MAX-ACCESS  read-only
        STATUS      current
        DESCRIPTION "15 minute reset threshold value of 4GFC for the total number of
                     errored packets received."
        ::= { tnStatisticsFcPktScalars 17 }

    tnFcPktStat4GTxCrcAlignErrs15MinRtr OBJECT-TYPE
        SYNTAX      Counter64
        MAX-ACCESS  read-only
        STATUS      current
        DESCRIPTION "15 minute reset threshold value of 4GFC for the total number of
                     errored packets transmitted."
        ::= { tnStatisticsFcPktScalars 18 }

    tnFcPktStat8GRxCrcAlignErrs15MinTr OBJECT-TYPE
        SYNTAX      Counter64
        MAX-ACCESS  read-only
        STATUS      current
        DESCRIPTION "15 minute threshold value of 8GFC for the total number of errored
                     packets received."
        ::= { tnStatisticsFcPktScalars 19 }

    tnFcPktStat8GTxCrcAlignErrs15MinTr OBJECT-TYPE
        SYNTAX      Counter64
        MAX-ACCESS  read-only
        STATUS      current
        DESCRIPTION "15 minute threshold value of 8GFC for the total number of errored
                     packets transmitted."
        ::= { tnStatisticsFcPktScalars 20 }

    tnFcPktStat8GRxCrcAlignErrs1DayTr OBJECT-TYPE
        SYNTAX      Counter64
        MAX-ACCESS  read-only
        STATUS      current
        DESCRIPTION "1 day threshold value of 8GFC for the total number of errored
                     packets received."
        ::= { tnStatisticsFcPktScalars 21 }

    tnFcPktStat8GTxCrcAlignErrs1DayTr OBJECT-TYPE
        SYNTAX      Counter64
        MAX-ACCESS  read-only
        STATUS      current
        DESCRIPTION "1 day threshold value of 8GFC for the total number of errored
                     packets transmitted."
        ::= { tnStatisticsFcPktScalars 22 }

    tnFcPktStat8GRxCrcAlignErrs15MinRtr OBJECT-TYPE
        SYNTAX      Counter64
        MAX-ACCESS  read-only
        STATUS      current
        DESCRIPTION "15 minute reset threshold value of 8GFC for the total number of
                     errored packets received."
        ::= { tnStatisticsFcPktScalars 23 }

    tnFcPktStat8GTxCrcAlignErrs15MinRtr OBJECT-TYPE
        SYNTAX      Counter64
        MAX-ACCESS  read-only
        STATUS      current
        DESCRIPTION "15 minute reset threshold value of 8GFC for the total number of
                     errored packets transmitted."
        ::= { tnStatisticsFcPktScalars 24 }

    tnFcPktStat10GRxCrcAlignErrs15MinTr OBJECT-TYPE
        SYNTAX      Counter64
        MAX-ACCESS  read-only
        STATUS      current
        DESCRIPTION "15 minute threshold value of 10GFC for the total number of errored
                     packets received."
        ::= { tnStatisticsFcPktScalars 25 }

    tnFcPktStat10GTxCrcAlignErrs15MinTr OBJECT-TYPE
        SYNTAX      Counter64
        MAX-ACCESS  read-only
        STATUS      current
        DESCRIPTION "15 minute threshold value of 10GFC for the total number of errored
                     packets transmitted."
        ::= { tnStatisticsFcPktScalars 26 }

    tnFcPktStat10GRxCrcAlignErrs1DayTr OBJECT-TYPE
        SYNTAX      Counter64
        MAX-ACCESS  read-only
        STATUS      current
        DESCRIPTION "1 day threshold value of 10GFC for the total number of errored
                     packets received."
        ::= { tnStatisticsFcPktScalars 27 }

    tnFcPktStat10GTxCrcAlignErrs1DayTr OBJECT-TYPE
        SYNTAX      Counter64
        MAX-ACCESS  read-only
        STATUS      current
        DESCRIPTION "1 day threshold value of 10GFC for the total number of errored
                     packets transmitted."
        ::= { tnStatisticsFcPktScalars 28 }

    tnFcPktStat10GRxCrcAlignErrs15MinRtr OBJECT-TYPE
        SYNTAX      Counter64
        MAX-ACCESS  read-only
        STATUS      current
        DESCRIPTION "15 minute reset threshold value of 10GFC for the total number of
                     errored packets received."
        ::= { tnStatisticsFcPktScalars 29 }

    tnFcPktStat10GTxCrcAlignErrs15MinRtr OBJECT-TYPE
        SYNTAX      Counter64
        MAX-ACCESS  read-only
        STATUS      current
        DESCRIPTION "15 minute reset threshold value of 10GFC for the total number of
                     errored packets transmitted."
        ::= { tnStatisticsFcPktScalars 30 }

    tnFcPktStat16GRxCrcAlignErrs15MinTr OBJECT-TYPE
        SYNTAX      Counter64
        MAX-ACCESS  read-only
        STATUS      current
        DESCRIPTION "15 minute threshold value of 16GFC for the total number of errored
                     packets received."
        ::= { tnStatisticsFcPktScalars 31 }

    tnFcPktStat16GTxCrcAlignErrs15MinTr OBJECT-TYPE
        SYNTAX      Counter64
        MAX-ACCESS  read-only
        STATUS      current
        DESCRIPTION "15 minute threshold value of 16GFC for the total number of errored
                     packets transmitted."
        ::= { tnStatisticsFcPktScalars 32 }

    tnFcPktStat16GRxCrcAlignErrs1DayTr OBJECT-TYPE
        SYNTAX      Counter64
        MAX-ACCESS  read-only
        STATUS      current
        DESCRIPTION "1 day threshold value of 16GFC for the total number of errored
                     packets received."
        ::= { tnStatisticsFcPktScalars 33 }

    tnFcPktStat16GTxCrcAlignErrs1DayTr OBJECT-TYPE
        SYNTAX      Counter64
        MAX-ACCESS  read-only
        STATUS      current
        DESCRIPTION "1 day threshold value of 16GFC for the total number of errored
                     packets transmitted."
        ::= { tnStatisticsFcPktScalars 34 }

    tnFcPktStat16GRxCrcAlignErrs15MinRtr OBJECT-TYPE
        SYNTAX      Counter64
        MAX-ACCESS  read-only
        STATUS      current
        DESCRIPTION "15 minute reset threshold value of 16GFC for the total number of
                     errored packets received."
        ::= { tnStatisticsFcPktScalars 35 }

    tnFcPktStat16GTxCrcAlignErrs15MinRtr OBJECT-TYPE
        SYNTAX      Counter64
        MAX-ACCESS  read-only
        STATUS      current
        DESCRIPTION "15 minute reset threshold value of 16GFC for the total number of
                     errored packets transmitted."
        ::= { tnStatisticsFcPktScalars 36 }

--------------------------------------------------------------------------------
-- Statistics SyncE Configuration Scalar
--------------------------------------------------------------------------------
    tnSyncEStatsConfigAttributeTotal OBJECT-TYPE
        SYNTAX      Integer32
        MAX-ACCESS  read-only
        STATUS      current
        DESCRIPTION "."
        ::= { tnStatisticsTCA 34 }

--------------------------------------------------------------------------------
-- Statistics SyncE Configuration Table
--------------------------------------------------------------------------------
    tnSyncEStatsConfigTable OBJECT-TYPE
        SYNTAX      SEQUENCE OF TnSyncEStatsConfigEntry
        MAX-ACCESS  not-accessible
        STATUS      current
        DESCRIPTION "."
        ::= { tnStatisticsTCA 35 }

    tnSyncEStatsConfigEntry OBJECT-TYPE
        SYNTAX      TnSyncEStatsConfigEntry
        MAX-ACCESS  not-accessible
        STATUS      current
        DESCRIPTION "."
        INDEX   { tnShelfIndex,
                  tnSlotIndex,
                  tnSyncELineRefIndex,
                  tnStatsInterval }
        ::= { tnSyncEStatsConfigTable 1 }

    TnSyncEStatsConfigEntry ::=
        SEQUENCE {
            tnSyncEStatsNumberofBins       TnStatsBinType,
            tnSyncEStatsProfileid          TnStatsProfileId,
            tnSyncEStatsClear              TnCommand,
            tnSyncEStatsIntervalLength     Unsigned32,
            tnSyncEStatsEnable             INTEGER
        }

    tnSyncEStatsNumberofBins OBJECT-TYPE
        SYNTAX      TnStatsBinType
        MAX-ACCESS  read-create
        STATUS      current
        DESCRIPTION "The number of collection bins in the interval."
        ::= { tnSyncEStatsConfigEntry 1 }

    tnSyncEStatsProfileid OBJECT-TYPE
        SYNTAX      TnStatsProfileId
        MAX-ACCESS  read-create
        STATUS      current
        DESCRIPTION "The profile identifier associated with an interval
                     on a particular SyncE entity and group."
        ::= { tnSyncEStatsConfigEntry 2 }

    tnSyncEStatsClear OBJECT-TYPE
        SYNTAX      TnCommand
        MAX-ACCESS  read-create
        STATUS      current
        DESCRIPTION "This attribute is used to clear the current bin in
                     an interval on a particular entity and group."
        ::= { tnSyncEStatsConfigEntry 3 }

    tnSyncEStatsIntervalLength OBJECT-TYPE
        SYNTAX      Unsigned32
        UNITS       "seconds"
        MAX-ACCESS  read-create
        STATUS      current
        DESCRIPTION "The collection interval length in seconds.
                     Sets to this attribute are currently not supported."
        ::= { tnSyncEStatsConfigEntry 4 }

    tnSyncEStatsEnable OBJECT-TYPE
        SYNTAX      INTEGER {
                      enable(1),
                      disable(2)
                    }
        MAX-ACCESS  read-create
        STATUS      current
        DESCRIPTION "."
        ::= { tnSyncEStatsConfigEntry 5 }

--------------------------------------------------------------------------------
-- Statistics SyncE Threshold Scalars
--------------------------------------------------------------------------------
    tnSyncEStatsOffsetMinTr OBJECT-TYPE
        SYNTAX      Integer32
        UNITS       "ppb"
        MAX-ACCESS  read-only
        STATUS      current
        DESCRIPTION "Provides a count of the number of SyncE Line Refference
                     offset min value."
        ::= { tnSyncEStatsOffsetScalars 1 }

    tnSyncEStatsOffsetMaxTr OBJECT-TYPE
        SYNTAX      Integer32
        UNITS       "ppb"
        MAX-ACCESS  read-only
        STATUS      current
        DESCRIPTION "Provides a count of the number of SyncE Line Refference
                     offset Max value."
        ::= { tnSyncEStatsOffsetScalars 2 }

    tnSyncEStatsOffsetAverageTr OBJECT-TYPE
        SYNTAX      Integer32
        UNITS       "ppb"
        MAX-ACCESS  read-only
        STATUS      current
        DESCRIPTION "Provides a count of the number of SyncE Line Refference
                     offset Average value."
        ::= { tnSyncEStatsOffsetScalars 3 }

    tnSyncEStatsOffsetMin15MinTr OBJECT-TYPE
        SYNTAX      Integer32
        UNITS       "ppb"
        MAX-ACCESS  read-only
        STATUS      current
        DESCRIPTION "15 minute threshold value for SyncE Offset Min."
        ::= { tnSyncEStatsOffsetScalars 4 }

    tnSyncEStatsOffsetMin15MinRtr OBJECT-TYPE
        SYNTAX      Integer32
        UNITS       "ppb"
        MAX-ACCESS  read-only
        STATUS      current
        DESCRIPTION "15 minute reset threshold value for SyncE Offset Min."
        ::= { tnSyncEStatsOffsetScalars 5 }

    tnSyncEStatsOffsetMin1DayTr OBJECT-TYPE
        SYNTAX      Integer32
        UNITS       "ppb"
        MAX-ACCESS  read-only
        STATUS      current
        DESCRIPTION "1 day threshold value for SyncE Offset Min."
        ::= { tnSyncEStatsOffsetScalars 6 }

    tnSyncEStatsOffsetMin1DayRtr OBJECT-TYPE
        SYNTAX      Integer32
        UNITS       "ppb"
        MAX-ACCESS  read-only
        STATUS      current
        DESCRIPTION "1 day reset threshold value for SyncE Offset Min."
        ::= { tnSyncEStatsOffsetScalars 7 }

    tnSyncEStatsOffsetMax15MinTr OBJECT-TYPE
        SYNTAX      Integer32
        UNITS       "ppb"
        MAX-ACCESS  read-only
        STATUS      current
        DESCRIPTION "15 minute threshold value for SyncE Offset Max."
        ::= { tnSyncEStatsOffsetScalars 8 }

    tnSyncEStatsOffsetMax15MinRtr OBJECT-TYPE
        SYNTAX      Integer32
        UNITS       "ppb"
        MAX-ACCESS  read-only
        STATUS      current
        DESCRIPTION "15 minute reset threshold value for SyncE Offset Max."
        ::= { tnSyncEStatsOffsetScalars 9 }

    tnSyncEStatsOffsetMax1DayTr OBJECT-TYPE
        SYNTAX      Integer32
        UNITS       "ppb"
        MAX-ACCESS  read-only
        STATUS      current
        DESCRIPTION "1 day threshold value for SyncE Offset Max."
        ::= { tnSyncEStatsOffsetScalars 10 }

    tnSyncEStatsOffsetMax1DayRtr OBJECT-TYPE
        SYNTAX      Integer32
        UNITS       "ppb"
        MAX-ACCESS  read-only
        STATUS      current
        DESCRIPTION "1 day reset threshold value for SyncE Offset Max."
        ::= { tnSyncEStatsOffsetScalars 11 }

--------------------------------------------------------------------------------
-- Statistics Sync Configuration Scalar
--------------------------------------------------------------------------------
    tnSyncStatsConfigAttributeTotal OBJECT-TYPE
        SYNTAX      Integer32
        MAX-ACCESS  read-only
        STATUS      current
        DESCRIPTION "."
        ::= { tnStatisticsTCA 36 }

--------------------------------------------------------------------------------
-- Statistics Sync Configuration Table
--------------------------------------------------------------------------------
    tnSyncStatsConfigTable OBJECT-TYPE
        SYNTAX      SEQUENCE OF TnSyncStatsConfigEntry
        MAX-ACCESS  not-accessible
        STATUS      current
        DESCRIPTION "."
        ::= { tnStatisticsTCA 37 }

    tnSyncStatsConfigEntry OBJECT-TYPE
        SYNTAX      TnSyncStatsConfigEntry
        MAX-ACCESS  not-accessible
        STATUS      current
        DESCRIPTION "."
        INDEX   { tnShelfIndex,
                  tnSlotIndex,
                  tnStatsInterval }
        ::= { tnSyncStatsConfigTable 1 }

    TnSyncStatsConfigEntry ::=
        SEQUENCE {
            tnSyncStatsNumberofBins       TnStatsBinType,
            tnSyncStatsProfileid          TnStatsProfileId,
            tnSyncStatsClear              TnCommand,
            tnSyncStatsIntervalLength     Unsigned32,
            tnSyncStatsEnable             INTEGER
        }

    tnSyncStatsNumberofBins OBJECT-TYPE
        SYNTAX      TnStatsBinType
        MAX-ACCESS  read-create
        STATUS      current
        DESCRIPTION "The number of collection bins in the interval."
        ::= { tnSyncStatsConfigEntry 1 }

    tnSyncStatsProfileid OBJECT-TYPE
        SYNTAX      TnStatsProfileId
        MAX-ACCESS  read-create
        STATUS      current
        DESCRIPTION "The profile identifier associated with an interval
                     on a particular Sync entity and group."
        ::= { tnSyncStatsConfigEntry 2 }

    tnSyncStatsClear OBJECT-TYPE
        SYNTAX      TnCommand
        MAX-ACCESS  read-create
        STATUS      current
        DESCRIPTION "This attribute is used to clear the current bin in
                     an interval on a particular entity and group."
        ::= { tnSyncStatsConfigEntry 3 }

    tnSyncStatsIntervalLength OBJECT-TYPE
        SYNTAX      Unsigned32
        UNITS       "seconds"
        MAX-ACCESS  read-create
        STATUS      current
        DESCRIPTION "The collection interval length in seconds.
                     Sets to this attribute are currently not supported."
        ::= { tnSyncStatsConfigEntry 4 }

    tnSyncStatsEnable OBJECT-TYPE
        SYNTAX      INTEGER {
                      enable(1),
                      disable(2)
                    }
        MAX-ACCESS  read-create
        STATUS      current
        DESCRIPTION "."
        ::= { tnSyncStatsConfigEntry 5 }

--------------------------------------------------------------------------------
-- PTP Time Offset (PTOFF) Configuration Scalar
--------------------------------------------------------------------------------
    tnPTOFFStatsConfigAttributeTotal OBJECT-TYPE
        SYNTAX      Integer32
        MAX-ACCESS  read-only
        STATUS      current
        DESCRIPTION "."
        ::= { tnStatisticsTCA 38 }

--------------------------------------------------------------------------------
-- PTP Time Offset (PTOFF) Configuration Table
--------------------------------------------------------------------------------
    tnPTOFFStatsConfigTable OBJECT-TYPE
        SYNTAX      SEQUENCE OF TnPTOFFStatsConfigEntry
        MAX-ACCESS  not-accessible
        STATUS      current
        DESCRIPTION "."
        ::= { tnStatisticsTCA 39 }

    tnPTOFFStatsConfigEntry OBJECT-TYPE
        SYNTAX      TnPTOFFStatsConfigEntry
        MAX-ACCESS  not-accessible
        STATUS      current
        DESCRIPTION "."
        INDEX   { ifIndex,
                  tnStatsInterval }
        ::= { tnPTOFFStatsConfigTable 1 }

    TnPTOFFStatsConfigEntry ::=
        SEQUENCE {
            tnPTOFFStatsNumberofBins       TnStatsBinType,
            tnPTOFFStatsProfileid          TnStatsProfileId,
            tnPTOFFStatsClear              TnCommand,
            tnPTOFFStatsIntervalLength     Unsigned32,
            tnPTOFFStatsEnable             INTEGER
        }

    tnPTOFFStatsNumberofBins OBJECT-TYPE
        SYNTAX      TnStatsBinType
        MAX-ACCESS  read-create
        STATUS      current
        DESCRIPTION "The number of collection bins in the interval."
        ::= { tnPTOFFStatsConfigEntry 1 }

    tnPTOFFStatsProfileid OBJECT-TYPE
        SYNTAX      TnStatsProfileId
        MAX-ACCESS  read-create
        STATUS      current
        DESCRIPTION "The profile identifier associated with an interval
                     on a particular PTOFF entity and group."
        ::= { tnPTOFFStatsConfigEntry 2 }

    tnPTOFFStatsClear OBJECT-TYPE
        SYNTAX      TnCommand
        MAX-ACCESS  read-create
        STATUS      current
        DESCRIPTION "This attribute is used to clear the current bin in
                     an interval on a particular entity and group."
        ::= { tnPTOFFStatsConfigEntry 3 }

    tnPTOFFStatsIntervalLength OBJECT-TYPE
        SYNTAX      Unsigned32
        UNITS       "seconds"
        MAX-ACCESS  read-create
        STATUS      current
        DESCRIPTION "The collection interval length in seconds.
                     Sets to this attribute are currently not supported."
        ::= { tnPTOFFStatsConfigEntry 4 }

    tnPTOFFStatsEnable OBJECT-TYPE
        SYNTAX      INTEGER {
                      enable(1),
                      disable(2)
                    }
        MAX-ACCESS  read-create
        STATUS      current
        DESCRIPTION "."
        ::= { tnPTOFFStatsConfigEntry 5 }

--------------------------------------------------------------------------------
-- PTP T-MS Delay (PTMSDLY) Configuration Scalar
--------------------------------------------------------------------------------
    tnPTMSDLYStatsConfigAttributeTotal OBJECT-TYPE
        SYNTAX      Integer32
        MAX-ACCESS  read-only
        STATUS      current
        DESCRIPTION "."
        ::= { tnStatisticsTCA 40 }

--------------------------------------------------------------------------------
-- PTP T-MS Delay (PTMSDLY) Configuration Table
--------------------------------------------------------------------------------
    tnPTMSDLYStatsConfigTable OBJECT-TYPE
        SYNTAX      SEQUENCE OF TnPTMSDLYStatsConfigEntry
        MAX-ACCESS  not-accessible
        STATUS      current
        DESCRIPTION "."
        ::= { tnStatisticsTCA 41 }

    tnPTMSDLYStatsConfigEntry OBJECT-TYPE
        SYNTAX      TnPTMSDLYStatsConfigEntry
        MAX-ACCESS  not-accessible
        STATUS      current
        DESCRIPTION "."
        INDEX   { ifIndex,
                  tnStatsInterval }
        ::= { tnPTMSDLYStatsConfigTable 1 }

    TnPTMSDLYStatsConfigEntry ::=
        SEQUENCE {
            tnPTMSDLYStatsNumberofBins       TnStatsBinType,
            tnPTMSDLYStatsProfileid          TnStatsProfileId,
            tnPTMSDLYStatsClear              TnCommand,
            tnPTMSDLYStatsIntervalLength     Unsigned32,
            tnPTMSDLYStatsEnable             INTEGER
        }

    tnPTMSDLYStatsNumberofBins OBJECT-TYPE
        SYNTAX      TnStatsBinType
        MAX-ACCESS  read-create
        STATUS      current
        DESCRIPTION "The number of collection bins in the interval."
        ::= { tnPTMSDLYStatsConfigEntry 1 }

    tnPTMSDLYStatsProfileid OBJECT-TYPE
        SYNTAX      TnStatsProfileId
        MAX-ACCESS  read-create
        STATUS      current
        DESCRIPTION "The profile identifier associated with an interval
                     on a particular PTMSDLY entity and group."
        ::= { tnPTMSDLYStatsConfigEntry 2 }

    tnPTMSDLYStatsClear OBJECT-TYPE
        SYNTAX      TnCommand
        MAX-ACCESS  read-create
        STATUS      current
        DESCRIPTION "This attribute is used to clear the current bin in
                     an interval on a particular entity and group."
        ::= { tnPTMSDLYStatsConfigEntry 3 }

    tnPTMSDLYStatsIntervalLength OBJECT-TYPE
        SYNTAX      Unsigned32
        UNITS       "seconds"
        MAX-ACCESS  read-create
        STATUS      current
        DESCRIPTION "The collection interval length in seconds.
                     Sets to this attribute are currently not supported."
        ::= { tnPTMSDLYStatsConfigEntry 4 }

    tnPTMSDLYStatsEnable OBJECT-TYPE
        SYNTAX      INTEGER {
                      enable(1),
                      disable(2)
                    }
        MAX-ACCESS  read-create
        STATUS      current
        DESCRIPTION "."
        ::= { tnPTMSDLYStatsConfigEntry 5 }

--------------------------------------------------------------------------------
-- PTP T-SM Delay (PTSMDLY) Configuration Scalar
--------------------------------------------------------------------------------
    tnPTSMDLYStatsConfigAttributeTotal OBJECT-TYPE
        SYNTAX      Integer32
        MAX-ACCESS  read-only
        STATUS      current
        DESCRIPTION "."
        ::= { tnStatisticsTCA 42 }

--------------------------------------------------------------------------------
-- PTP T-SM Delay (PTSMDLY) Configuration Table
--------------------------------------------------------------------------------
    tnPTSMDLYStatsConfigTable OBJECT-TYPE
        SYNTAX      SEQUENCE OF TnPTSMDLYStatsConfigEntry
        MAX-ACCESS  not-accessible
        STATUS      current
        DESCRIPTION "."
        ::= { tnStatisticsTCA 43 }

    tnPTSMDLYStatsConfigEntry OBJECT-TYPE
        SYNTAX      TnPTSMDLYStatsConfigEntry
        MAX-ACCESS  not-accessible
        STATUS      current
        DESCRIPTION "."
        INDEX   { ifIndex,
                  tnStatsInterval }
        ::= { tnPTSMDLYStatsConfigTable 1 }

    TnPTSMDLYStatsConfigEntry ::=
        SEQUENCE {
            tnPTSMDLYStatsNumberofBins       TnStatsBinType,
            tnPTSMDLYStatsProfileid          TnStatsProfileId,
            tnPTSMDLYStatsClear              TnCommand,
            tnPTSMDLYStatsIntervalLength     Unsigned32,
            tnPTSMDLYStatsEnable             INTEGER
        }

    tnPTSMDLYStatsNumberofBins OBJECT-TYPE
        SYNTAX      TnStatsBinType
        MAX-ACCESS  read-create
        STATUS      current
        DESCRIPTION "The number of collection bins in the interval."
        ::= { tnPTSMDLYStatsConfigEntry 1 }

    tnPTSMDLYStatsProfileid OBJECT-TYPE
        SYNTAX      TnStatsProfileId
        MAX-ACCESS  read-create
        STATUS      current
        DESCRIPTION "The profile identifier associated with an interval
                     on a particular PTSMDLY entity and group."
        ::= { tnPTSMDLYStatsConfigEntry 2 }

    tnPTSMDLYStatsClear OBJECT-TYPE
        SYNTAX      TnCommand
        MAX-ACCESS  read-create
        STATUS      current
        DESCRIPTION "This attribute is used to clear the current bin in
                     an interval on a particular entity and group."
        ::= { tnPTSMDLYStatsConfigEntry 3 }

    tnPTSMDLYStatsIntervalLength OBJECT-TYPE
        SYNTAX      Unsigned32
        UNITS       "seconds"
        MAX-ACCESS  read-create
        STATUS      current
        DESCRIPTION "The collection interval length in seconds.
                     Sets to this attribute are currently not supported."
        ::= { tnPTSMDLYStatsConfigEntry 4 }

    tnPTSMDLYStatsEnable OBJECT-TYPE
        SYNTAX      INTEGER {
                      enable(1),
                      disable(2)
                    }
        MAX-ACCESS  read-create
        STATUS      current
        DESCRIPTION "."
        ::= { tnPTSMDLYStatsConfigEntry 5 }

--------------------------------------------------------------------------------
-- PTP Mean Path Delay (PTMPDLY) Configuration Scalar
--------------------------------------------------------------------------------
    tnPTMPDLYStatsConfigAttributeTotal OBJECT-TYPE
        SYNTAX      Integer32
        MAX-ACCESS  read-only
        STATUS      current
        DESCRIPTION "."
        ::= { tnStatisticsTCA 44 }

--------------------------------------------------------------------------------
-- PTP Mean Path Delay (PTMPDLY) Configuration Table
--------------------------------------------------------------------------------
    tnPTMPDLYStatsConfigTable OBJECT-TYPE
        SYNTAX      SEQUENCE OF TnPTMPDLYStatsConfigEntry
        MAX-ACCESS  not-accessible
        STATUS      current
        DESCRIPTION "."
        ::= { tnStatisticsTCA 45 }

    tnPTMPDLYStatsConfigEntry OBJECT-TYPE
        SYNTAX      TnPTMPDLYStatsConfigEntry
        MAX-ACCESS  not-accessible
        STATUS      current
        DESCRIPTION "."
        INDEX   { ifIndex,
                  tnStatsInterval }
        ::= { tnPTMPDLYStatsConfigTable 1 }

    TnPTMPDLYStatsConfigEntry ::=
        SEQUENCE {
            tnPTMPDLYStatsNumberofBins       TnStatsBinType,
            tnPTMPDLYStatsProfileid          TnStatsProfileId,
            tnPTMPDLYStatsClear              TnCommand,
            tnPTMPDLYStatsIntervalLength     Unsigned32,
            tnPTMPDLYStatsEnable             INTEGER
        }

    tnPTMPDLYStatsNumberofBins OBJECT-TYPE
        SYNTAX      TnStatsBinType
        MAX-ACCESS  read-create
        STATUS      current
        DESCRIPTION "The number of collection bins in the interval."
        ::= { tnPTMPDLYStatsConfigEntry 1 }

    tnPTMPDLYStatsProfileid OBJECT-TYPE
        SYNTAX      TnStatsProfileId
        MAX-ACCESS  read-create
        STATUS      current
        DESCRIPTION "The profile identifier associated with an interval
                     on a particular PTMPDLY entity and group."
        ::= { tnPTMPDLYStatsConfigEntry 2 }

    tnPTMPDLYStatsClear OBJECT-TYPE
        SYNTAX      TnCommand
        MAX-ACCESS  read-create
        STATUS      current
        DESCRIPTION "This attribute is used to clear the current bin in
                     an interval on a particular entity and group."
        ::= { tnPTMPDLYStatsConfigEntry 3 }

    tnPTMPDLYStatsIntervalLength OBJECT-TYPE
        SYNTAX      Unsigned32
        UNITS       "seconds"
        MAX-ACCESS  read-create
        STATUS      current
        DESCRIPTION "The collection interval length in seconds.
                     Sets to this attribute are currently not supported."
        ::= { tnPTMPDLYStatsConfigEntry 4 }

    tnPTMPDLYStatsEnable OBJECT-TYPE
        SYNTAX      INTEGER {
                      enable(1),
                      disable(2)
                    }
        MAX-ACCESS  read-create
        STATUS      current
        DESCRIPTION "."
        ::= { tnPTMPDLYStatsConfigEntry 5 }

--------------------------------------------------------------------------------
-- PTP Time Error by Reference comparison (PTERREF) Configuration Scalar
--------------------------------------------------------------------------------
    tnPTERREFStatsConfigAttributeTotal OBJECT-TYPE
        SYNTAX      Integer32
        MAX-ACCESS  read-only
        STATUS      current
        DESCRIPTION "."
        ::= { tnStatisticsTCA 46 }

--------------------------------------------------------------------------------
-- PTP Time Error by Reference comparison (PTERREF) Configuration Table
--------------------------------------------------------------------------------
    tnPTERREFStatsConfigTable OBJECT-TYPE
        SYNTAX      SEQUENCE OF TnPTERREFStatsConfigEntry
        MAX-ACCESS  not-accessible
        STATUS      current
        DESCRIPTION "."
        ::= { tnStatisticsTCA 47 }

    tnPTERREFStatsConfigEntry OBJECT-TYPE
        SYNTAX      TnPTERREFStatsConfigEntry
        MAX-ACCESS  not-accessible
        STATUS      current
        DESCRIPTION "."
        INDEX   { ifIndex,
                  tnStatsInterval }
        ::= { tnPTERREFStatsConfigTable 1 }

    TnPTERREFStatsConfigEntry ::=
        SEQUENCE {
            tnPTERREFStatsNumberofBins       TnStatsBinType,
            tnPTERREFStatsProfileid          TnStatsProfileId,
            tnPTERREFStatsClear              TnCommand,
            tnPTERREFStatsIntervalLength     Unsigned32,
            tnPTERREFStatsEnable             INTEGER
        }

    tnPTERREFStatsNumberofBins OBJECT-TYPE
        SYNTAX      TnStatsBinType
        MAX-ACCESS  read-create
        STATUS      current
        DESCRIPTION "The number of collection bins in the interval."
        ::= { tnPTERREFStatsConfigEntry 1 }

    tnPTERREFStatsProfileid OBJECT-TYPE
        SYNTAX      TnStatsProfileId
        MAX-ACCESS  read-create
        STATUS      current
        DESCRIPTION "The profile identifier associated with an interval
                     on a particular PTERREF entity and group."
        ::= { tnPTERREFStatsConfigEntry 2 }

    tnPTERREFStatsClear OBJECT-TYPE
        SYNTAX      TnCommand
        MAX-ACCESS  read-create
        STATUS      current
        DESCRIPTION "This attribute is used to clear the current bin in
                     an interval on a particular entity and group."
        ::= { tnPTERREFStatsConfigEntry 3 }

    tnPTERREFStatsIntervalLength OBJECT-TYPE
        SYNTAX      Unsigned32
        UNITS       "seconds"
        MAX-ACCESS  read-create
        STATUS      current
        DESCRIPTION "The collection interval length in seconds.
                     Sets to this attribute are currently not supported."
        ::= { tnPTERREFStatsConfigEntry 4 }

    tnPTERREFStatsEnable OBJECT-TYPE
        SYNTAX      INTEGER {
                      enable(1),
                      disable(2)
                    }
        MAX-ACCESS  read-create
        STATUS      current
        DESCRIPTION "."
        ::= { tnPTERREFStatsConfigEntry 5 }

--------------------------------------------------------------------------------
-- PTP Time Offset Accumulation (PTOFFACUM) Configuration Scalar
--------------------------------------------------------------------------------
    tnPTOFFACUMStatsConfigAttributeTotal OBJECT-TYPE
        SYNTAX      Integer32
        MAX-ACCESS  read-only
        STATUS      current
        DESCRIPTION "."
        ::= { tnStatisticsTCA 48 }

--------------------------------------------------------------------------------
-- PTP Time Offset Accumulation (PTOFFACUM) Configuration Table
--------------------------------------------------------------------------------
    tnPTOFFACUMStatsConfigTable OBJECT-TYPE
        SYNTAX      SEQUENCE OF TnPTOFFACUMStatsConfigEntry
        MAX-ACCESS  not-accessible
        STATUS      current
        DESCRIPTION "."
        ::= { tnStatisticsTCA 49 }

    tnPTOFFACUMStatsConfigEntry OBJECT-TYPE
        SYNTAX      TnPTOFFACUMStatsConfigEntry
        MAX-ACCESS  not-accessible
        STATUS      current
        DESCRIPTION "."
        INDEX   { ifIndex,
                  tnStatsInterval }
        ::= { tnPTOFFACUMStatsConfigTable 1 }

    TnPTOFFACUMStatsConfigEntry ::=
        SEQUENCE {
            tnPTOFFACUMStatsNumberofBins       TnStatsBinType,
            tnPTOFFACUMStatsProfileid          TnStatsProfileId,
            tnPTOFFACUMStatsClear              TnCommand,
            tnPTOFFACUMStatsIntervalLength     Unsigned32,
            tnPTOFFACUMStatsEnable             INTEGER
        }

    tnPTOFFACUMStatsNumberofBins OBJECT-TYPE
        SYNTAX      TnStatsBinType
        MAX-ACCESS  read-create
        STATUS      current
        DESCRIPTION "The number of collection bins in the interval."
        ::= { tnPTOFFACUMStatsConfigEntry 1 }

    tnPTOFFACUMStatsProfileid OBJECT-TYPE
        SYNTAX      TnStatsProfileId
        MAX-ACCESS  read-create
        STATUS      current
        DESCRIPTION "The profile identifier associated with an interval
                     on a particular PTOFFACUM entity and group."
        ::= { tnPTOFFACUMStatsConfigEntry 2 }

    tnPTOFFACUMStatsClear OBJECT-TYPE
        SYNTAX      TnCommand
        MAX-ACCESS  read-create
        STATUS      current
        DESCRIPTION "This attribute is used to clear the current bin in
                     an interval on a particular entity and group."
        ::= { tnPTOFFACUMStatsConfigEntry 3 }

    tnPTOFFACUMStatsIntervalLength OBJECT-TYPE
        SYNTAX      Unsigned32
        UNITS       "seconds"
        MAX-ACCESS  read-create
        STATUS      current
        DESCRIPTION "The collection interval length in seconds.
                     Sets to this attribute are currently not supported."
        ::= { tnPTOFFACUMStatsConfigEntry 4 }

    tnPTOFFACUMStatsEnable OBJECT-TYPE
        SYNTAX      INTEGER {
                      enable(1),
                      disable(2)
                    }
        MAX-ACCESS  read-create
        STATUS      current
        DESCRIPTION "."
        ::= { tnPTOFFACUMStatsConfigEntry 5 }

--------------------------------------------------------------------------------
-- Statistics PTP Clear All Table Scalar
--------------------------------------------------------------------------------
    tnStatsPTPClearAllAttributeTotal OBJECT-TYPE
        SYNTAX      Integer32
        MAX-ACCESS  read-only
        STATUS      current
        DESCRIPTION "."
        ::= { tnStatisticsTCA 50 }

--------------------------------------------------------------------------------
-- Statistics PTP Clear All Table
--------------------------------------------------------------------------------
    tnStatsPTPClearAllTable OBJECT-TYPE
        SYNTAX      SEQUENCE OF TnStatsPTPClearAllEntry
        MAX-ACCESS  not-accessible
        STATUS      current
        DESCRIPTION "."
        ::= { tnStatisticsTCA 51 }

    tnStatsPTPClearAllEntry OBJECT-TYPE
        SYNTAX      TnStatsPTPClearAllEntry
        MAX-ACCESS  not-accessible
        STATUS      current
        DESCRIPTION "."
        INDEX   { ifIndex }
        ::= { tnStatsPTPClearAllTable 1 }

    TnStatsPTPClearAllEntry ::=
        SEQUENCE {
            tnStatsPTPClearAll  TnCommand
        }

    tnStatsPTPClearAll OBJECT-TYPE
        SYNTAX      TnCommand
        MAX-ACCESS  read-create
        STATUS      current
        DESCRIPTION "This attribute is used to clear all the bins
                     in all intervals in all groups on a particular
                     interface."
        ::= { tnStatsPTPClearAllEntry 1 }

--------------------------------------------------------------------------------
-- Statistics PKT WANIF Control Scalar
--------------------------------------------------------------------------------
    tnPktWanifStatsControlAttributeTotal OBJECT-TYPE
        SYNTAX      Integer32
        MAX-ACCESS  read-only
        STATUS      current
        DESCRIPTION "."
        ::= { tnStatisticsTCA 52 }

--------------------------------------------------------------------------------
-- Statistics PKT WANIF Stats Control Table
--------------------------------------------------------------------------------
    tnPktWanifStatsControlTable OBJECT-TYPE
        SYNTAX      SEQUENCE OF TnPktWanifStatsControlEntry
        MAX-ACCESS  not-accessible
        STATUS      current
        DESCRIPTION "."
        ::= { tnStatisticsTCA 53 }

    tnPktWanifStatsControlEntry OBJECT-TYPE
        SYNTAX      TnPktWanifStatsControlEntry
        MAX-ACCESS  not-accessible
        STATUS      current
        DESCRIPTION "."
        INDEX   { ifIndex }
        ::= { tnPktWanifStatsControlTable 1 }

    TnPktWanifStatsControlEntry ::=
        SEQUENCE {
            tnPktWanifStatsEnable     INTEGER
        }

    tnPktWanifStatsEnable OBJECT-TYPE
        SYNTAX      INTEGER {
                      enable(1),
                      disable(2)
                    }
        MAX-ACCESS  read-create
        STATUS      current
        DESCRIPTION "This attribute is used to enable and disable the PKT WANIF
                     Stats PM."

        ::= { tnPktWanifStatsControlEntry 1 }

--------------------------------------------------------------------------------
-- Conformance Group Definitions
--------------------------------------------------------------------------------
    tnStatsPortIntervalGroup OBJECT-GROUP
        OBJECTS {
            tnStatsPortNumberOfIntervals,
            tnStatPortEnable
        }
        STATUS         current
        DESCRIPTION    "."
        ::= { tnStatisticsGroups 1 }

    tnStatsCardIntervalGroup OBJECT-GROUP
        OBJECTS {
            tnStatsCardNumberOfIntervals
        }
        STATUS         current
        DESCRIPTION    "."
        ::= { tnStatisticsGroups 2 }

    tnStatsPortConfGroup OBJECT-GROUP
        OBJECTS {
            tnStatsPortIntervalLength,
            tnStatsPortNumberOfBins,
            tnStatsPortProfileId,
            tnStatsPortClear
        }
        STATUS         current
        DESCRIPTION    "."
        ::= { tnStatisticsGroups 3 }

    tnStatsCardConfGroup OBJECT-GROUP
        OBJECTS {
            tnStatsCardIntervalLength,
            tnStatsCardNumberOfBins,
            tnStatsCardProfileId,
            tnStatsCardClear
        }
        STATUS         current
        DESCRIPTION    "."
        ::= { tnStatisticsGroups 4 }

    tnStatsTCAProfileGroup OBJECT-GROUP
        OBJECTS {
            tnStatsTCAProfileDescr
        }
        STATUS         current
        DESCRIPTION    "."
        ::= { tnStatisticsGroups 5 }

    tnStatsTCAGroup OBJECT-GROUP
        OBJECTS {
            tnStatsTCAVariable,
--            obsolete
--            tnStatsTCACriticalInterval,
--            tnStatsTCAMajorInterval,
--            tnStatsTCAMinorInterval,
--            tnStatsTCAWarningInterval,
            tnStatsTCAValue
        }
        STATUS         current
        DESCRIPTION    "."
        ::= { tnStatisticsGroups 6 }

    tnCardStatsScalarsGroup OBJECT-GROUP
        OBJECTS {
            tnCardStatsTotalMembers
        }
        STATUS         current
        DESCRIPTION    "."
        ::= { tnStatisticsGroups 7 }

    tnCardStatsGroup OBJECT-GROUP
        OBJECTS {
            tnCardStatsBinStatus,
            tnCardStatsStartTime,
            tnCardStatCpuAverage,
            tnCardStatHeapUsage,
            tnCardStatPoolUsage
        }
        STATUS         current
        DESCRIPTION    "."
        ::= { tnStatisticsGroups 8 }

    tnInterfaceStatsScalarsGroup OBJECT-GROUP
        OBJECTS {
            tnInterfaceStatsTotalMembers
        }
        STATUS         current
        DESCRIPTION    "."
        ::= { tnStatisticsGroups 9 }

    tnInterfaceStatsGroup OBJECT-GROUP
        OBJECTS {
            tnIfStatsBinStatus,
            tnIfStatsStartTime,
            tnIfStatInOctets,
            tnIfStatInUcastPkts,
            tnIfStatInDiscards,
            tnIfStatInErrors,
            tnIfStatInUnknownProtos,
            tnIfStatOutOctets,
            tnIfStatOutUcastPkts,
            tnIfStatOutDiscards,
            tnIfStatOutErrors,
            tnIfStatInMulticastPkts,
            tnIfStatInBroadcastPkts,
            tnIfStatOutMulticastPkts,
            tnIfStatOutBroadcastPkts,
            tnIfStatInPacketsNotClassified
        }
        STATUS         current
        DESCRIPTION    "."
        ::= { tnStatisticsGroups 10 }

    tnEtherStatsScalarsGroup OBJECT-GROUP
        OBJECTS {
            tnEtherStatsTotalMembers
        }
        STATUS         current
        DESCRIPTION    "."
        ::= { tnStatisticsGroups 11 }

    tnEtherStatsGroup OBJECT-GROUP
        OBJECTS {
            tnEtherStatsBinStatus,
            tnEtherStatsStartTime,
            tnEtherStatRxDropEvents,
            tnEtherStatRxFragments,
            tnEtherStatRxJabbers,
            tnEtherStatRxMcastPkts,
            tnEtherStatRxOctets,
            tnEtherStatRxOversizedPkts,
            tnEtherStatRxPkts,
            tnEtherStatRxPktsSize1024to1518,
            tnEtherStatRxPktsSize128to255,
            tnEtherStatRxPktsSize256to511,
            tnEtherStatRxPktsSize512to1023,
--            obsolete
--            tnEtherStatRxPktsSize64orLess,
            tnEtherStatRxPktsSize65to127,
            tnEtherStatRxUndersizedPkts,
            tnEtherStatTxBcastPkts,
            tnEtherStatTxCrcAlignErrs,
            tnEtherStatTxDropEvents,
            tnEtherStatTxFragments,
            tnEtherStatTxJabbers,
            tnEtherStatTxMcastPkts,
            tnEtherStatTxOctets,
            tnEtherStatTxOversizedPkts,
            tnEtherStatTxPkts,
            tnEtherStatTxPktsSize1024to1518,
            tnEtherStatTxPktsSize128to255,
            tnEtherStatTxPktsSize256to511,
            tnEtherStatTxPktsSize512to1023,
--            obsolete
--            tnEtherStatTxPktsSize64orLess,
            tnEtherStatTxPktsSize65to127,
            tnEtherStatTxUndersizedPkts,
            tnEtherStatRxBcastPkts,
            tnEtherStatRxCrcAlignErrs,
            tnEtherStatRxCollisions,
            tnEtherStatRxJumboPkts,
            tnEtherStatTxCollisions,
            tnEtherStatTxJumboPkts,
            tnEtherStatRxPktsSize64,
            tnEtherStatTxPktsSize64,
            tnEtherStatRxPktErrRatio,
            tnEtherStatTxPktErrRatio,
            tnEtherStatRxPktErrRatio15MinTr,
            tnEtherStatTxPktErrRatio15MinTr,
            tnEtherStatRxPktErrRatio1DayTr,
            tnEtherStatTxPktErrRatio1DayTr,
            tnEtherStatRxPktErrRatio15MinRtr,
            tnEtherStatTxPktErrRatio15MinRtr
        }
        STATUS         current
        DESCRIPTION    "."
        ::= { tnStatisticsGroups 12 }

    tnSonetStatsScalarsGroup OBJECT-GROUP
        OBJECTS {
            tnSonetStatsTotalMembers
        }
        STATUS         current
        DESCRIPTION    "."
        ::= { tnStatisticsGroups 13 }

    tnSonetStatsGroup OBJECT-GROUP
        OBJECTS {
            tnSonetStatsBinStatus,
            tnSonetStatsStartTime,
            tnSonetStatRxCVS,
            tnSonetStatRxESS,
            tnSonetStatRxSESS,
            tnSonetStatRxSEFSS,
            tnSonetStatRxCVL,
            tnSonetStatRxESL,
            tnSonetStatRxSESL,
            tnSonetStatRxUASL,
            tnSonetStatRxFCL,
            tnSonetStatTxCVS,
            tnSonetStatTxESS,
            tnSonetStatTxSESS,
            tnSonetStatTxSEFSS,
            tnSonetStatTxCVL,
            tnSonetStatTxESL,
            tnSonetStatTxSESL,
            tnSonetStatTxUASL,
            tnSonetStatTxFCL,
            tnSonetStatRxUASS,
            tnSonetStatTxUASS,
--            obsolete
--            tnSonetStatRxCVS15MinTr,
--            tnSonetStatRxESS15MinTr,
--            tnSonetStatRxSESS15MinTr,
--            tnSonetStatRxSEFSS15MinTr,
--            tnSonetStatRxCVL15MinTr,
--            tnSonetStatRxESL15MinTr,
--            tnSonetStatRxSESL15MinTr,
--            tnSonetStatRxUASL15MinTr,
--            tnSonetStatRxFCL15MinTr,
--            tnSonetStatTxCVS15MinTr,
--            tnSonetStatTxESS15MinTr,
--            tnSonetStatTxSESS15MinTr,
--            tnSonetStatTxSEFSS15MinTr,
--            tnSonetStatTxCVL15MinTr,
--            tnSonetStatTxESL15MinTr,
--            tnSonetStatTxSESL15MinTr,
--            tnSonetStatTxUASL15MinTr,
--            tnSonetStatTxFCL15MinTr,
--            tnSonetStatRxUASS15MinTr,
--            tnSonetStatTxUASS15MinTr,
--            tnSonetStatRxCVS1DayTr,
--            tnSonetStatRxESS1DayTr,
--            tnSonetStatRxSESS1DayTr,
--            tnSonetStatRxSEFSS1DayTr,
--            tnSonetStatRxCVL1DayTr,
--            tnSonetStatRxESL1DayTr,
--            tnSonetStatRxSESL1DayTr,
--            tnSonetStatRxUASL1DayTr,
--            tnSonetStatRxFCL1DayTr,
--            tnSonetStatTxCVS1DayTr,
--            tnSonetStatTxESS1DayTr,
--            tnSonetStatTxSESS1DayTr,
--            tnSonetStatTxSEFSS1DayTr,
--            tnSonetStatTxCVL1DayTr,
--            tnSonetStatTxESL1DayTr,
--            tnSonetStatTxSESL1DayTr,
--            tnSonetStatTxUASL1DayTr,
--            tnSonetStatTxFCL1DayTr,
--            tnSonetStatRxUASS1DayTr,
--            tnSonetStatTxUASS1DayTr,
--            tnSonetStatRxCVS15MinRtr,
--            tnSonetStatRxESS15MinRtr,
--            tnSonetStatRxSESS15MinRtr,
--            tnSonetStatRxSEFSS15MinRtr,
--            tnSonetStatRxCVL15MinRtr,
--            tnSonetStatRxESL15MinRtr,
--            tnSonetStatRxSESL15MinRtr,
--            tnSonetStatRxUASL15MinRtr,
--            tnSonetStatRxFCL15MinRtr,
--            tnSonetStatTxCVS15MinRtr,
--            tnSonetStatTxESS15MinRtr,
--            tnSonetStatTxSESS15MinRtr,
--            tnSonetStatTxSEFSS15MinRtr,
--            tnSonetStatTxCVL15MinRtr,
--            tnSonetStatTxESL15MinRtr,
--            tnSonetStatTxSESL15MinRtr,
--            tnSonetStatTxUASL15MinRtr,
--            tnSonetStatTxFCL15MinRtr,
--            tnSonetStatRxUASS15MinRtr,
--            tnSonetStatTxUASS15MinRtr,
            tnSonetStatRxFECVL,
            tnSonetStatRxFEESL,
            tnSonetStatRxFESESL,
            tnSonetStatRxFEUASL
--            obsolete
--            tnSonetStatRxFECVL15MinTr,
--            tnSonetStatRxFEESL15MinTr,
--            tnSonetStatRxFESESL15MinTr,
--            tnSonetStatRxFEUASL15MinTr,
--            tnSonetStatRxFECVL1DayTr,
--            tnSonetStatRxFEESL1DayTr,
--            tnSonetStatRxFESESL1DayTr,
--            tnSonetStatRxFEUASL1DayTr,
--            tnSonetStatRxFECVL15MinRtr,
--            tnSonetStatRxFEESL15MinRtr,
--            tnSonetStatRxFESESL15MinRtr,
--            tnSonetStatRxFEUASL15MinRtr
        }
        STATUS         current
        DESCRIPTION    "."
        ::= { tnStatisticsGroups 14 }

--    obsolete
--    tnDigitalWrapperStatsScalarsGroup OBJECT-GROUP ::= { tnStatisticsGroups 15 }
--    tnDigitalWrapperStatsGroup        OBJECT-GROUP ::= { tnStatisticsGroups 16 }
--    tnL1ProtStatsScalarsGroup         OBJECT-GROUP ::= { tnStatisticsGroups 17 }
--    tnL1ProtStatsGroup                OBJECT-GROUP ::= { tnStatisticsGroups 18 }

    tnControlNetworkLinkRawCountStatsScalarsGroup OBJECT-GROUP
        OBJECTS {
            tnControlNetworkLinkRawCountStatsTotalMembers
        }
        STATUS         current
        DESCRIPTION    "."
        ::= { tnStatisticsGroups 19 }

    tnControlNetworkLinkRawCountStatsGroup OBJECT-GROUP
        OBJECTS {
            tnCNLinkRawCountStatIpInReceives,
            tnCNLinkRawCountStatIpInDiscards,
            tnCNLinkRawCountStatIpOutRequests,
            tnCNLinkRawCountStatIpOutDiscards,
            tnCNLinkRawCountStatIpForwDatagrams
        }
        STATUS         current
        DESCRIPTION    "."
        ::= { tnStatisticsGroups 20 }

    tnCardRawCountStatsScalarsGroup OBJECT-GROUP
        OBJECTS {
            tnCardRawCountStatsTotalMembers
        }
        STATUS         current
        DESCRIPTION    "."
        ::= { tnStatisticsGroups 21 }

    tnCardRawCountStatsGroup OBJECT-GROUP
        OBJECTS {
            tnCardRawCountStatsClear,
            tnCardRawCountStatCpuAverage,
            tnCardRawCountStatHeapUsage,
            tnCardRawCountStatPoolUsage,
            tnCardRawCountStatStartTime
        }
        STATUS         current
        DESCRIPTION    "."
        ::= { tnStatisticsGroups 22 }

    tnInterfaceRawCountStatsScalarsGroup OBJECT-GROUP
        OBJECTS {
            tnInterfaceRawCountStatsTotalMembers
        }
        STATUS         current
        DESCRIPTION    "."
        ::= { tnStatisticsGroups 23 }

    tnInterfaceRawCountStatsGroup OBJECT-GROUP
        OBJECTS {
            tnIfRawCountStatsClear,
            tnIfRawCountStatInOctets,
            tnIfRawCountStatInUcastPkts,
            tnIfRawCountStatInDiscards,
            tnIfRawCountStatInErrors,
            tnIfRawCountStatInUnknownProtos,
            tnIfRawCountStatOutOctets,
            tnIfRawCountStatOutUcastPkts,
            tnIfRawCountStatOutDiscards,
            tnIfRawCountStatOutErrors,
            tnIfRawCountStatInMulticastPkts,
            tnIfRawCountStatInBroadcastPkts,
            tnIfRawCountStatOutMulticastPkts,
            tnIfRawCountStatOutBroadcastPkts,
            tnIfRawCountStatInPacketsNotClassified,
            tnIfRawCountStatStartTime
        }
        STATUS         current
        DESCRIPTION    "."
        ::= { tnStatisticsGroups 24 }

    tnEtherRawCountStatsScalarsGroup OBJECT-GROUP
        OBJECTS {
            tnEtherRawCountStatsTotalMembers
        }
        STATUS         current
        DESCRIPTION    "."
        ::= { tnStatisticsGroups 25 }

    tnEtherRawCountStatsGroup OBJECT-GROUP
        OBJECTS {
            tnEtherRawCountStatsClear,
            tnEtherRawCountStatRxDropEvents,
            tnEtherRawCountStatRxFragments,
            tnEtherRawCountStatRxJabbers,
            tnEtherRawCountStatRxMcastPkts,
            tnEtherRawCountStatRxOctets,
            tnEtherRawCountStatRxOversizedPkts,
            tnEtherRawCountStatRxPkts,
            tnEtherRawCountStatRxPktsSize1024to1518,
            tnEtherRawCountStatRxPktsSize128to255,
            tnEtherRawCountStatRxPktsSize256to511,
            tnEtherRawCountStatRxPktsSize512to1023,
--            obsolete
--            tnEtherRawCountStatRxPktsSize64orLess,
            tnEtherRawCountStatRxPktsSize65to127,
            tnEtherRawCountStatRxUndersizedPkts,
            tnEtherRawCountStatTxBcastPkts,
            tnEtherRawCountStatTxCrcAlignErrs,
            tnEtherRawCountStatTxDropEvents,
            tnEtherRawCountStatTxFragments,
            tnEtherRawCountStatTxJabbers,
            tnEtherRawCountStatTxMcastPkts,
            tnEtherRawCountStatTxOctets,
            tnEtherRawCountStatTxOversizedPkts,
            tnEtherRawCountStatTxPkts,
            tnEtherRawCountStatTxPktsSize1024to1518,
            tnEtherRawCountStatTxPktsSize128to255,
            tnEtherRawCountStatTxPktsSize256to511,
            tnEtherRawCountStatTxPktsSize512to1023,
--            obsolete
--            tnEtherRawCountStatTxPktsSize64orLess,
            tnEtherRawCountStatTxPktsSize65to127,
            tnEtherRawCountStatTxUndersizedPkts,
            tnEtherRawCountStatRxBcastPkts,
            tnEtherRawCountStatRxCrcAlignErrs,
            tnEtherRawCountStatRxCollisions,
            tnEtherRawCountStatRxJumboPkts,
            tnEtherRawCountStatTxCollisions,
            tnEtherRawCountStatTxJumboPkts,
            tnEtherRawCountStatRmonIndex,
            tnEtherRawCountStatRxPktsSize64,
            tnEtherRawCountStatTxPktsSize64,
            tnEtherRawCountStatRxPktErrRatio,
            tnEtherRawCountStatTxPktErrRatio,
            tnEtherRawCountStatStartTime
        }
        STATUS         current
        DESCRIPTION    "."
        ::= { tnStatisticsGroups 26 }

    tnSonetRawCountStatsScalarsGroup OBJECT-GROUP
        OBJECTS {
            tnSonetRawCountStatsTotalMembers
        }
        STATUS         current
        DESCRIPTION    "."
        ::= { tnStatisticsGroups 27 }

    tnSonetRawCountStatsGroup OBJECT-GROUP
        OBJECTS {
            tnSonetRawCountStatsClear,
            tnSonetRawCountStatRxCVS,
            tnSonetRawCountStatRxESS,
            tnSonetRawCountStatRxSESS,
            tnSonetRawCountStatRxSEFSS,
            tnSonetRawCountStatRxCVL,
            tnSonetRawCountStatRxESL,
            tnSonetRawCountStatRxSESL,
            tnSonetRawCountStatRxUASL,
            tnSonetRawCountStatRxFCL,
            tnSonetRawCountStatTxCVS,
            tnSonetRawCountStatTxESS,
            tnSonetRawCountStatTxSESS,
            tnSonetRawCountStatTxSEFSS,
            tnSonetRawCountStatTxCVL,
            tnSonetRawCountStatTxESL,
            tnSonetRawCountStatTxSESL,
            tnSonetRawCountStatTxUASL,
            tnSonetRawCountStatTxFCL,
            tnSonetRawCountStatRxUASS,
            tnSonetRawCountStatTxUASS,
            tnSonetRawCountStatStartTime,
            tnSonetRawCountStatRxFECVL,
            tnSonetRawCountStatRxFEESL,
            tnSonetRawCountStatRxFESESL,
            tnSonetRawCountStatRxFEUASL
        }
        STATUS         current
        DESCRIPTION    "."
        ::= { tnStatisticsGroups 28 }

--    obsolete
--    tnDigitalWrapperRawCountStatsScalarsGroup OBJECT-GROUP ::= { tnStatisticsGroups 29 }
--    tnDigitalWrapperRawCountStatsGroup        OBJECT-GROUP ::= { tnStatisticsGroups 30 }
--    tnL1ProtRawCountStatsScalarsGroup         OBJECT-GROUP ::= { tnStatisticsGroups 31 }
--    tnL1ProtRawCountStatsGroup                OBJECT-GROUP ::= { tnStatisticsGroups 32 }

    tnOptStatsScalarsGroup OBJECT-GROUP
        OBJECTS {
            tnOptStatsTotalMembers
        }
        STATUS         current
        DESCRIPTION    "."
        ::= { tnStatisticsGroups 33 }

    tnOptStatsGroup OBJECT-GROUP
        OBJECTS {
            tnOptStatsBinStatus,
            tnOptStatsStartTime,
            tnOptStatMinPower,
            tnOptStatMaxPower,
            tnOptStatAveragePower,
            tnOptStatMinPowerTr,
            tnOptStatMaxPowerTr,
            tnOptStatMinPowerRtr,
            tnOptStatMaxPowerRtr
        }
        STATUS         current
        DESCRIPTION    "."
        ::= { tnStatisticsGroups 34 }

    tnOprStatsScalarsGroup OBJECT-GROUP
        OBJECTS {
            tnOprStatsTotalMembers
        }
        STATUS         current
        DESCRIPTION    "."
        ::= { tnStatisticsGroups 35 }

    tnOprStatsGroup OBJECT-GROUP
        OBJECTS {
            tnOprStatsBinStatus,
            tnOprStatsStartTime,
            tnOprStatMinPower,
            tnOprStatMaxPower,
            tnOprStatAveragePower,
            tnOprStatMinPowerTr,
            tnOprStatMaxPowerTr,
            tnOprStatMinPowerRtr,
            tnOprStatMaxPowerRtr
        }
        STATUS         current
        DESCRIPTION    "."
        ::= { tnStatisticsGroups 36 }

    tnOptRawCountStatsScalarsGroup OBJECT-GROUP
        OBJECTS {
            tnOptRawCountStatsTotalMembers
        }
        STATUS         current
        DESCRIPTION    "."
        ::= { tnStatisticsGroups 37 }

    tnOptRawCountStatsGroup OBJECT-GROUP
        OBJECTS {
            tnOptRawCountStatsClear,
            tnOptRawCountStatMinPower,
            tnOptRawCountStatMaxPower,
            tnOptRawCountStatAveragePower,
            tnOptRawCountStatStartTime
        }
        STATUS         current
        DESCRIPTION    "."
        ::= { tnStatisticsGroups 38 }

    tnOprRawCountStatsScalarsGroup OBJECT-GROUP
        OBJECTS {
            tnOprRawCountStatsTotalMembers
        }
        STATUS         current
        DESCRIPTION    "."
        ::= { tnStatisticsGroups 39 }

    tnOprRawCountStatsGroup OBJECT-GROUP
        OBJECTS {
            tnOprRawCountStatsClear,
            tnOprRawCountStatMinPower,
            tnOprRawCountStatMaxPower,
            tnOprRawCountStatAveragePower,
            tnOprRawCountStatStartTime
        }
        STATUS         current
        DESCRIPTION    "."
        ::= { tnStatisticsGroups 40 }

    tnOpOutStatsScalarsGroup OBJECT-GROUP
        OBJECTS {
            tnOpOutStatsTotalMembers
        }
        STATUS         current
        DESCRIPTION    "."
        ::= { tnStatisticsGroups 41 }

    tnOpOutStatsGroup OBJECT-GROUP
        OBJECTS {
            tnOpOutStatsBinStatus,
            tnOpOutStatsStartTime,
            tnOpOutStatMinPower,
            tnOpOutStatMaxPower,
            tnOpOutStatAveragePower
        }
        STATUS         current
        DESCRIPTION    "."
        ::= { tnStatisticsGroups 42 }

    tnOpInStatsScalarsGroup OBJECT-GROUP
        OBJECTS {
            tnOpInStatsTotalMembers
        }
        STATUS         current
        DESCRIPTION    "."
        ::= { tnStatisticsGroups 43 }

    tnOpInStatsGroup OBJECT-GROUP
        OBJECTS {
            tnOpInStatsBinStatus,
            tnOpInStatsStartTime,
            tnOpInStatMinPower,
            tnOpInStatMaxPower,
            tnOpInStatAveragePower
        }
        STATUS         current
        DESCRIPTION    "."
        ::= { tnStatisticsGroups 44 }

    tnOpOutRawCountStatsScalarsGroup OBJECT-GROUP
        OBJECTS {
            tnOpOutRawCountStatsTotalMembers
        }
        STATUS         current
        DESCRIPTION    "."
        ::= { tnStatisticsGroups 45 }

    tnOpOutRawCountStatsGroup OBJECT-GROUP
        OBJECTS {
            tnOpOutRawCountStatsClear,
            tnOpOutRawCountStatMinPower,
            tnOpOutRawCountStatMaxPower,
            tnOpOutRawCountStatAveragePower,
            tnOpOutRawCountStatStartTime
        }
        STATUS         current
        DESCRIPTION    "."
        ::= { tnStatisticsGroups 46 }

    tnOpInRawCountStatsScalarsGroup OBJECT-GROUP
        OBJECTS {
            tnOpInRawCountStatsTotalMembers
        }
        STATUS         current
        DESCRIPTION    "."
        ::= { tnStatisticsGroups 47 }

    tnOpInRawCountStatsGroup OBJECT-GROUP
        OBJECTS {
            tnOpInRawCountStatsClear,
            tnOpInRawCountStatMinPower,
            tnOpInRawCountStatMaxPower,
            tnOpInRawCountStatAveragePower,
            tnOpInRawCountStatStartTime
        }
        STATUS         current
        DESCRIPTION    "."
        ::= { tnStatisticsGroups 48 }

--    obsolete
--    tnStatsTCAItuGroup OBJECT-GROUP ::= { tnStatisticsGroups 49 }

    tnOpOchOutStatsScalarsGroup OBJECT-GROUP
        OBJECTS {
            tnOpOchOutStatsTotalMembers
        }
        STATUS         current
        DESCRIPTION    "."
        ::= { tnStatisticsGroups 50 }

    tnOpOchOutStatsGroup OBJECT-GROUP
        OBJECTS {
            tnOpOchOutStatsBinStatus,
            tnOpOchOutStatsStartTime,
            tnOpOchOutStatMinPower,
            tnOpOchOutStatMaxPower,
            tnOpOchOutStatAveragePower,
            tnOpOchOutStatWidth
        }
        STATUS         current
        DESCRIPTION    "."
        ::= { tnStatisticsGroups 51 }

    tnOpOchInStatsScalarsGroup OBJECT-GROUP
        OBJECTS {
            tnOpOchInStatsTotalMembers
        }
        STATUS         current
        DESCRIPTION    "."
        ::= { tnStatisticsGroups 52 }

    tnOpOchInStatsGroup OBJECT-GROUP
        OBJECTS {
            tnOpOchInStatsBinStatus,
            tnOpOchInStatsStartTime,
            tnOpOchInStatMinPower,
            tnOpOchInStatMaxPower,
            tnOpOchInStatAveragePower,
            tnOpOchInStatWidth
        }
        STATUS         current
        DESCRIPTION    "."
        ::= { tnStatisticsGroups 53 }

    tnOpOchOutRawCountStatsScalarsGroup OBJECT-GROUP
        OBJECTS {
            tnOpOchOutRawCountStatsTotalMembers
        }
        STATUS         current
        DESCRIPTION    "."
        ::= { tnStatisticsGroups 54 }

    tnOpOchOutRawCountStatsGroup OBJECT-GROUP
        OBJECTS {
            tnOpOchOutRawCountStatsClear,
            tnOpOchOutRawCountStatMinPower,
            tnOpOchOutRawCountStatMaxPower,
            tnOpOchOutRawCountStatAveragePower,
            tnOpOchOutRawCountStatStartTime,
            tnOpOchOutRawCountStatWidth
        }
        STATUS         current
        DESCRIPTION    "."
        ::= { tnStatisticsGroups 55 }

    tnOpOchInRawCountStatsScalarsGroup OBJECT-GROUP
        OBJECTS {
            tnOpOchInRawCountStatsTotalMembers
        }
        STATUS         current
        DESCRIPTION    "."
        ::= { tnStatisticsGroups 56 }

    tnOpOchInRawCountStatsGroup OBJECT-GROUP
        OBJECTS {
            tnOpOchInRawCountStatsClear,
            tnOpOchInRawCountStatMinPower,
            tnOpOchInRawCountStatMaxPower,
            tnOpOchInRawCountStatAveragePower,
            tnOpOchInRawCountStatStartTime,
            tnOpOchInRawCountStatWidth
        }
        STATUS         current
        DESCRIPTION    "."
        ::= { tnStatisticsGroups 57 }

    tnStatsPortClearAllGroup OBJECT-GROUP
        OBJECTS {
            tnStatsPortClearAll
        }
        STATUS         current
        DESCRIPTION    "."
        ::= { tnStatisticsGroups 58 }

    tnStatsTCAScalarsGroup OBJECT-GROUP
        OBJECTS {
            tnStatsClearAll
--            obsolete
--            tnStatsTcmTCAAttributeTotal,
--            tnStatsTcmTCAProfileAttributeTotal,
--            tnStatsTcmPortAttributeTotal,
        }
        STATUS         current
        DESCRIPTION    "."
        ::= { tnStatisticsGroups 59 }

    tnSdhStatsScalarsGroup OBJECT-GROUP
        OBJECTS {
            tnSdhStatsTotalMembers
        }
        STATUS         current
        DESCRIPTION    "."
        ::= { tnStatisticsGroups 60 }

    tnSdhStatsGroup OBJECT-GROUP
        OBJECTS {
            tnSdhStatsBinStatus,
            tnSdhStatsStartTime,
            tnSdhStatRxRSEB,
            tnSdhStatRxRSES,
            tnSdhStatRxRSSES,
            tnSdhStatRxMSEB,
            tnSdhStatRxMSES,
            tnSdhStatRxMSSES,
            tnSdhStatRxMSUAS,
            tnSdhStatTxRSEB,
            tnSdhStatTxRSES,
            tnSdhStatTxRSSES,
            tnSdhStatTxMSEB,
            tnSdhStatTxMSES,
            tnSdhStatTxMSSES,
            tnSdhStatTxMSUAS,
            tnSdhStatRxRSUAS,
            tnSdhStatTxRSUAS,
--            obsolete
--            tnSdhStatRxRSEB15MinTr,
--            tnSdhStatRxRSES15MinTr,
--            tnSdhStatRxRSSES15MinTr,
--            tnSdhStatRxMSEB15MinTr,
--            tnSdhStatRxMSES15MinTr,
--            tnSdhStatRxMSSES15MinTr,
--            tnSdhStatRxMSUAS15MinTr,
--            tnSdhStatTxRSEB15MinTr,
--            tnSdhStatTxRSES15MinTr,
--            tnSdhStatTxRSSES15MinTr,
--            tnSdhStatTxMSEB15MinTr,
--            tnSdhStatTxMSES15MinTr,
--            tnSdhStatTxMSSES15MinTr,
--            tnSdhStatTxMSUAS15MinTr,
--            tnSdhStatRxRSUAS15MinTr,
--            tnSdhStatTxRSUAS15MinTr,
--            tnSdhStatRxRSEB1DayTr,
--            tnSdhStatRxRSES1DayTr,
--            tnSdhStatRxRSSES1DayTr,
--            tnSdhStatRxMSEB1DayTr,
--            tnSdhStatRxMSES1DayTr,
--            tnSdhStatRxMSSES1DayTr,
--            tnSdhStatRxMSUAS1DayTr,
--            tnSdhStatTxRSEB1DayTr,
--            tnSdhStatTxRSES1DayTr,
--            tnSdhStatTxRSSES1DayTr,
--            tnSdhStatTxMSEB1DayTr,
--            tnSdhStatTxMSES1DayTr,
--            tnSdhStatTxMSSES1DayTr,
--            tnSdhStatTxMSUAS1DayTr,
--            tnSdhStatRxRSUAS1DayTr,
--            tnSdhStatTxRSUAS1DayTr,
--            tnSdhStatRxRSEB15MinRtr,
--            tnSdhStatRxRSES15MinRtr,
--            tnSdhStatRxRSSES15MinRtr,
--            tnSdhStatRxMSEB15MinRtr,
--            tnSdhStatRxMSES15MinRtr,
--            tnSdhStatRxMSSES15MinRtr,
--            tnSdhStatRxMSUAS15MinRtr,
--            tnSdhStatTxRSEB15MinRtr,
--            tnSdhStatTxRSES15MinRtr,
--            tnSdhStatTxRSSES15MinRtr,
--            tnSdhStatTxMSEB15MinRtr,
--            tnSdhStatTxMSES15MinRtr,
--            tnSdhStatTxMSSES15MinRtr,
--            tnSdhStatTxMSUAS15MinRtr,
--            tnSdhStatRxRSUAS15MinRtr,
--            tnSdhStatTxRSUAS15MinRtr,
            tnSdhStatRxMSFEEB,
            tnSdhStatRxMSFEES,
            tnSdhStatRxMSFESES,
            tnSdhStatRxMSFEUAS
--            obsolete
--            tnSdhStatRxMSFEEB15MinTr,
--            tnSdhStatRxMSFEES15MinTr,
--            tnSdhStatRxMSFESES15MinTr,
--            tnSdhStatRxMSFEUAS15MinTr,
--            tnSdhStatRxMSFEEB1DayTr,
--            tnSdhStatRxMSFEES1DayTr,
--            tnSdhStatRxMSFESES1DayTr,
--            tnSdhStatRxMSFEUAS1DayTr,
--            tnSdhStatRxMSFEEB15MinRtr,
--            tnSdhStatRxMSFEES15MinRtr,
--            tnSdhStatRxMSFESES15MinRtr,
--            tnSdhStatRxMSFEUAS15MinRtr
        }
        STATUS         current
        DESCRIPTION    "."
        ::= { tnStatisticsGroups 61 }

    tnSdhRawCountStatsScalarsGroup OBJECT-GROUP
        OBJECTS {
            tnSdhRawCountStatsTotalMembers
        }
        STATUS         current
        DESCRIPTION    "."
        ::= { tnStatisticsGroups 62 }

    tnSdhRawCountStatsGroup OBJECT-GROUP
        OBJECTS {
            tnSdhRawCountStatsClear,
            tnSdhRawCountStatRxRSEB,
            tnSdhRawCountStatRxRSES,
            tnSdhRawCountStatRxRSSES,
            tnSdhRawCountStatRxMSEB,
            tnSdhRawCountStatRxMSES,
            tnSdhRawCountStatRxMSSES,
            tnSdhRawCountStatRxMSUAS,
            tnSdhRawCountStatTxRSEB,
            tnSdhRawCountStatTxRSES,
            tnSdhRawCountStatTxRSSES,
            tnSdhRawCountStatTxMSEB,
            tnSdhRawCountStatTxMSES,
            tnSdhRawCountStatTxMSSES,
            tnSdhRawCountStatTxMSUAS,
            tnSdhRawCountStatRxRSUAS,
            tnSdhRawCountStatTxRSUAS,
            tnSdhRawCountStatStartTime,
            tnSdhRawCountStatRxMSFEEB,
            tnSdhRawCountStatRxMSFEES,
            tnSdhRawCountStatRxMSFESES,
            tnSdhRawCountStatRxMSFEUAS
        }
        STATUS         current
        DESCRIPTION    "."
        ::= { tnStatisticsGroups 63 }

--    obsolete
--    tnPathSummaryStatsScalarsGroup          OBJECT-GROUP ::= { tnStatisticsGroups 64 }
--    tnPathSummaryStatsGroup                 OBJECT-GROUP ::= { tnStatisticsGroups 65 }
--    tnPathSummaryRawCountStatsScalarsGroup  OBJECT-GROUP ::= { tnStatisticsGroups 66 }
--    tnPathSummaryRawCountStatsGroup         OBJECT-GROUP ::= { tnStatisticsGroups 67 }
--    tnFibreChannelStatsScalarsGroup         OBJECT-GROUP ::= { tnStatisticsGroups 68 }
--    tnFibreChannelStatsGroup                OBJECT-GROUP ::= { tnStatisticsGroups 69 }
--    tnFibreChannelRawCountStatsScalarsGroup OBJECT-GROUP ::= { tnStatisticsGroups 70 }
--    tnFibreChannelRawCountStatsGroup        OBJECT-GROUP ::= { tnStatisticsGroups 71 }

    tnPhyCodeSublayerStatsScalarsGroup OBJECT-GROUP
        OBJECTS {
            tnPhyCodeSublayerStatsTotalMembers
        }
        STATUS         current
        DESCRIPTION    "."
        ::= { tnStatisticsGroups 72 }

    tnPhyCodeSublayerStatsGroup OBJECT-GROUP
        OBJECTS {
            tnPhyCodeSublayerStatsBinStatus,
            tnPhyCodeSublayerStatsStartTime,
            tnPhyCodeSublayerStatRxCV,
            tnPhyCodeSublayerStatRxES,
            tnPhyCodeSublayerStatRxSES,
            tnPhyCodeSublayerStatRxSEFS,
            tnPhyCodeSublayerStatTxCV,
            tnPhyCodeSublayerStatTxES,
            tnPhyCodeSublayerStatTxSES,
            tnPhyCodeSublayerStatTxSEFS,
--            obsolete
--            tnPhyCodeSublayerStatRxCV15MinTr,
--            tnPhyCodeSublayerStatRxES15MinTr,
--            tnPhyCodeSublayerStatRxSES15MinTr,
--            tnPhyCodeSublayerStatRxSEFS15MinTr,
--            tnPhyCodeSublayerStatTxCV15MinTr,
--            tnPhyCodeSublayerStatTxES15MinTr,
--            tnPhyCodeSublayerStatTxSES15MinTr,
--            tnPhyCodeSublayerStatTxSEFS15MinTr,
--            tnPhyCodeSublayerStatRxCV1DayTr,
--            tnPhyCodeSublayerStatRxES1DayTr,
--            tnPhyCodeSublayerStatRxSES1DayTr,
--            tnPhyCodeSublayerStatRxSEFS1DayTr,
--            tnPhyCodeSublayerStatTxCV1DayTr,
--            tnPhyCodeSublayerStatTxES1DayTr,
--            tnPhyCodeSublayerStatTxSES1DayTr,
--            tnPhyCodeSublayerStatTxSEFS1DayTr,
--            tnPhyCodeSublayerStatRxCV15MinRtr,
--            tnPhyCodeSublayerStatRxES15MinRtr,
--            tnPhyCodeSublayerStatRxSES15MinRtr,
--            tnPhyCodeSublayerStatRxSEFS15MinRtr,
--            tnPhyCodeSublayerStatTxCV15MinRtr,
--            tnPhyCodeSublayerStatTxES15MinRtr,
--            tnPhyCodeSublayerStatTxSES15MinRtr,
--            tnPhyCodeSublayerStatTxSEFS15MinRtr,
            tnPhyCodeSublayerStatsRxBIP8,
            tnPhyCodeSublayerStatsTxBIP8,
            tnPhyCodeSublayerStatsRxUAS,
            tnPhyCodeSublayerStatsTxUAS
        }
        STATUS         current
        DESCRIPTION    "."
        ::= { tnStatisticsGroups 73 }

    tnPhyCodeSublayerRawCountStatsScalarsGroup OBJECT-GROUP
        OBJECTS {
            tnPhyCodeSublayerRawCountStatsTotalMembers
        }
        STATUS         current
        DESCRIPTION    "."
        ::= { tnStatisticsGroups 74 }

    tnPhyCodeSublayerRawCountStatsGroup OBJECT-GROUP
        OBJECTS {
            tnPhyCodeSublayerRawCountStatsClear,
            tnPhyCodeSublayerRawCountStatRxCV,
            tnPhyCodeSublayerRawCountStatRxES,
            tnPhyCodeSublayerRawCountStatRxSES,
            tnPhyCodeSublayerRawCountStatRxSEFS,
            tnPhyCodeSublayerRawCountStatTxCV,
            tnPhyCodeSublayerRawCountStatTxES,
            tnPhyCodeSublayerRawCountStatTxSES,
            tnPhyCodeSublayerRawCountStatTxSEFS,
            tnPhyCodeSublayerRawCountStatStartTime
        }
        STATUS         current
        DESCRIPTION    "."
        ::= { tnStatisticsGroups 75 }

    tnDigitalWrapper64BitStatsScalarsGroup OBJECT-GROUP
        OBJECTS {
            tnDigitalWrapper64BitStatsTotalMembers
        }
        STATUS         current
        DESCRIPTION    "."
        ::= { tnStatisticsGroups 76 }

    tnDigitalWrapper64BitStatsGroup OBJECT-GROUP
        OBJECTS {
            tnDw64BitStatsBinStatus,
            tnDw64BitStatsStartTime,
            tnDw64BitStatRxRSCorrCnt,
            tnDw64BitStatRxRSUncorrCnt,
            tnDw64BitStatRxSMBIP8ErrCnt,
            tnDw64BitStatRxPMBIP8ErrCnt,
--            obsolete
--            tnDw64BitStatRxSMBEIErrCnt,
--            tnDw64BitStatRxPMBEIErrCnt,
--            tnDw64BitStatRxRSSES,
            tnDw64BitStatRxSMES,
            tnDw64BitStatRxPMES,
            tnDw64BitStatRxSMSES,
            tnDw64BitStatRxPMSES,
            tnDw64BitStatRxSMUAS,
            tnDw64BitStatRxPMUAS,
--            obsolete
--            tnDw64BitStatRxRSCorrCnt15MinTr,
--            tnDw64BitStatRxRSUncorrCnt15MinTr,
--            tnDw64BitStatRxSMBIP8ErrCnt15MinTr,
--            tnDw64BitStatRxPMBIP8ErrCnt15MinTr,
--            tnDw64BitStatRxSMES15MinTr,
--            tnDw64BitStatRxPMES15MinTr,
--            tnDw64BitStatRxSMSES15MinTr,
--            tnDw64BitStatRxPMSES15MinTr,
--            tnDw64BitStatRxSMUAS15MinTr,
--            tnDw64BitStatRxPMUAS15MinTr,
--            tnDw64BitStatRxRSCorrCnt1DayTr,
--            tnDw64BitStatRxRSUncorrCnt1DayTr,
--            tnDw64BitStatRxSMBIP8ErrCnt1DayTr,
--            tnDw64BitStatRxPMBIP8ErrCnt1DayTr,
--            tnDw64BitStatRxSMES1DayTr,
--            tnDw64BitStatRxPMES1DayTr,
--            tnDw64BitStatRxSMSES1DayTr,
--            tnDw64BitStatRxPMSES1DayTr,
--            tnDw64BitStatRxSMUAS1DayTr,
--            tnDw64BitStatRxPMUAS1DayTr,
--            tnDw64BitStatRxRSCorrCnt15MinRtr,
--            tnDw64BitStatRxRSUncorrCnt15MinRtr,
--            tnDw64BitStatRxSMBIP8ErrCnt15MinRtr,
--            tnDw64BitStatRxPMBIP8ErrCnt15MinRtr,
--            tnDw64BitStatRxSMES15MinRtr,
--            tnDw64BitStatRxPMES15MinRtr,
--            tnDw64BitStatRxSMSES15MinRtr,
--            tnDw64BitStatRxPMSES15MinRtr,
--            tnDw64BitStatRxSMUAS15MinRtr,
--            tnDw64BitStatRxPMUAS15MinRtr,
            tnDw64BitStatRxBERPreFEC,
            tnDw64BitStatRxBERPostFEC,
            tnDw64BitStatRxSMFEBIP8ErrCnt,
            tnDw64BitStatRxPMFEBIP8ErrCnt,
            tnDw64BitStatRxSMBIAESErrCnt,
            tnDw64BitStatRxSMIAESErrCnt,
            tnDw64BitStatRxSMFEES,
            tnDw64BitStatRxPMFEES,
            tnDw64BitStatRxSMFESES,
            tnDw64BitStatRxPMFESES,
            tnDw64BitStatRxSMFEUAS,
            tnDw64BitStatRxPMFEUAS
--            obsolete
--            tnDwRxSMFEBIP8ErrCnt15MinTr,
--            tnDwRxPMFEBIP8ErrCnt15MinTr,
--            tnDwRxSMFEES15MinTr,
--            tnDwRxPMFEES15MinTr,
--            tnDwRxSMFESES15MinTr,
--            tnDwRxPMFESES15MinTr,
--            tnDwRxSMFEUAS15MinTr,
--            tnDwRxPMFEUAS15MinTr,
--            tnDwRxSMBIAES15MinTr,
--            tnDwRxSMIAES15MinTr,
--            tnDwRxBERPreFEC15MinTr,
--            tnDwRxBERPostFEC15MinTr,
--            tnDwRxSMFEBIP8ErrCnt1DayTr,
--            tnDwRxPMFEBIP8ErrCnt1DayTr,
--            tnDwRxSMFEES1DayTr,
--            tnDwRxPMFEES1DayTr,
--            tnDwRxSMFESES1DayTr,
--            tnDwRxPMFESES1DayTr,
--            tnDwRxSMFEUAS1DayTr,
--            tnDwRxPMFEUAS1DayTr,
--            tnDwRxSMBIAES1DayTr,
--            tnDwRxSMIAES1DayTr,
--            tnDwRxBERPreFEC1DayTr,
--            tnDwRxBERPostFEC1DayTr,
--            tnDwRxSMFEBIP8ErrCnt15MinRtr,
--            tnDwRxPMFEBIP8ErrCnt15MinRtr,
--            tnDwRxSMFEES15MinRtr,
--            tnDwRxPMFEES15MinRtr,
--            tnDwRxSMFESES15MinRtr,
--            tnDwRxPMFESES15MinRtr,
--            tnDwRxSMFEUAS15MinRtr,
--            tnDwRxPMFEUAS15MinRtr,
--            tnDwRxSMBIAES15MinRtr,
--            tnDwRxSMIAES15MinRtr,
--            tnDwRxBERPreFEC15MinRtr
--            tnDwRxBERPostFEC15MinRtr
        }
        STATUS         current
        DESCRIPTION    "."
        ::= { tnStatisticsGroups 77 }

    tnDigitalWrapper64BitRawCountStatsScalarsGroup OBJECT-GROUP
        OBJECTS {
            tnDigitalWrapper64BitRawCountStatsTotalMembers
        }
        STATUS         current
        DESCRIPTION    "."
        ::= { tnStatisticsGroups 78 }

    tnDigitalWrapper64BitRawCountStatsGroup OBJECT-GROUP
        OBJECTS {
            tnDw64BitRawCountStatsClear,
            tnDw64BitRawCountStatRxRSCorrCnt,
            tnDw64BitRawCountStatRxRSUncorrCnt,
            tnDw64BitRawCountStatRxSMBIP8ErrCnt,
            tnDw64BitRawCountStatRxPMBIP8ErrCnt,
            tnDw64BitRawCountStatRxSMBEIErrCnt,
            tnDw64BitRawCountStatRxPMBEIErrCnt,
            tnDw64BitRawCountStatRxRSSES,
            tnDw64BitRawCountStatRxSMES,
            tnDw64BitRawCountStatRxPMES,
            tnDw64BitRawCountStatRxSMSES,
            tnDw64BitRawCountStatRxPMSES,
            tnDw64BitRawCountStatRxSMUAS,
            tnDw64BitRawCountStatRxPMUAS,
            tnDw64BitRawCountStatStartTime,
            tnDw64BitRawCountStatRxBERPreFEC,
            tnDw64BitRawCountStatRxBERPostFEC,
            tnDw64BitRawCountStatRxSMFEBIP8ErrCnt,
            tnDw64BitRawCountStatRxPMFEBIP8ErrCnt,
            tnDw64BitRawCountStatRxSMBIAESErrCnt,
            tnDw64BitRawCountStatRxSMIAESErrCnt,
            tnDw64BitRawCountStatRxSMFEES,
            tnDw64BitRawCountStatRxPMFEES,
            tnDw64BitRawCountStatRxSMFESES,
            tnDw64BitRawCountStatRxPMFESES,
            tnDw64BitRawCountStatRxSMFEUAS,
            tnDw64BitRawCountStatRxPMFEUAS
        }
        STATUS         current
        DESCRIPTION    "."
        ::= { tnStatisticsGroups 79 }

    tnStatsBaselineGroup OBJECT-GROUP
        OBJECTS {
            tnStatsBaselineReason,
            tnStatsBaselineValue,
            tnStatsBaselineTime
        }
        STATUS         current
        DESCRIPTION    "."
        ::= { tnStatisticsGroups 80 }

    tnCdrStatsScalarsGroup OBJECT-GROUP
        OBJECTS {
            tnCdrStatsTotalMembers
        }
        STATUS         current
        DESCRIPTION    "."
        ::= { tnStatisticsGroups 81 }

    tnCdrStatsGroup OBJECT-GROUP
        OBJECTS {
            tnCdrStatsBinStatus,
            tnCdrStatsStartTime,
            tnCdrStatMin,
            tnCdrStatMax,
            tnCdrStatAverage
        }
        STATUS         current
        DESCRIPTION    "."
        ::= { tnStatisticsGroups 82 }

    tnCdrRawCountStatsScalarsGroup OBJECT-GROUP
        OBJECTS {
            tnCdrRawCountStatsTotalMembers
        }
        STATUS         current
        DESCRIPTION    "."
        ::= { tnStatisticsGroups 83 }

    tnCdrRawCountStatsGroup OBJECT-GROUP
        OBJECTS {
            tnCdrRawCountStatsClear,
            tnCdrRawCountStatMin,
            tnCdrRawCountStatMax,
            tnCdrRawCountStatAverage,
            tnCdrRawCountStatStartTime
        }
        STATUS         current
        DESCRIPTION    "."
        ::= { tnStatisticsGroups 84 }

    tnDgdrStatsScalarsGroup OBJECT-GROUP
        OBJECTS {
            tnDgdrStatsTotalMembers
        }
        STATUS         current
        DESCRIPTION    "."
        ::= { tnStatisticsGroups 85 }

    tnDgdrStatsGroup OBJECT-GROUP
        OBJECTS {
            tnDgdrStatsBinStatus,
            tnDgdrStatsStartTime,
            tnDgdrStatMin,
            tnDgdrStatMax,
            tnDgdrStatAverage
        }
        STATUS         current
        DESCRIPTION    "."
        ::= { tnStatisticsGroups 86 }

    tnDgdrRawCountStatsScalarsGroup OBJECT-GROUP
        OBJECTS {
            tnDgdrRawCountStatsTotalMembers
        }
        STATUS         current
        DESCRIPTION    "."
        ::= { tnStatisticsGroups 87 }

    tnDgdrRawCountStatsGroup OBJECT-GROUP
        OBJECTS {
            tnDgdrRawCountStatsClear,
            tnDgdrRawCountStatMin,
            tnDgdrRawCountStatMax,
            tnDgdrRawCountStatAverage,
            tnDgdrRawCountStatStartTime
        }
        STATUS         current
        DESCRIPTION    "."
        ::= { tnStatisticsGroups 88 }

    tnFoffrStatsScalarsGroup OBJECT-GROUP
        OBJECTS {
            tnFoffrStatsTotalMembers
        }
        STATUS         current
        DESCRIPTION    "."
        ::= { tnStatisticsGroups 89 }

    tnFoffrStatsGroup OBJECT-GROUP
        OBJECTS {
            tnFoffrStatsBinStatus,
            tnFoffrStatsStartTime,
            tnFoffrStatMin,
            tnFoffrStatMax,
            tnFoffrStatAverage
        }
        STATUS         current
        DESCRIPTION    "."
        ::= { tnStatisticsGroups 90 }

    tnFoffrRawCountStatsScalarsGroup OBJECT-GROUP
        OBJECTS {
            tnFoffrRawCountStatsTotalMembers
        }
        STATUS         current
        DESCRIPTION    "."
        ::= { tnStatisticsGroups 91 }

    tnFoffrRawCountStatsGroup OBJECT-GROUP
        OBJECTS {
            tnFoffrRawCountStatsClear,
            tnFoffrRawCountStatMin,
            tnFoffrRawCountStatMax,
            tnFoffrRawCountStatAverage,
            tnFoffrRawCountStatStartTime
        }
        STATUS         current
        DESCRIPTION    "."
        ::= { tnStatisticsGroups 92 }

    tnE1StatsScalarsGroup OBJECT-GROUP
        OBJECTS {
            tnE1StatsTotalMembers
        }
        STATUS         current
        DESCRIPTION    "."
        ::= { tnStatisticsGroups 93 }

    tnE1StatsGroup OBJECT-GROUP
        OBJECTS {
            tnE1StatsBinStatus,
            tnE1StatsStartTime,
            tnE1StatRxBBEP,
            tnE1StatRxESP,
            tnE1StatRxSESP,
            tnE1StatRxUASP,
            tnE1StatRxESL,
            tnE1StatRxSESL,
            tnE1StatTxBBEP,
            tnE1StatTxESP,
            tnE1StatTxSESP,
            tnE1StatTxUASP,
            tnE1StatRxBBEP15MinTr,
            tnE1StatRxESP15MinTr,
            tnE1StatRxSESP15MinTr,
            tnE1StatRxUASP15MinTr,
            tnE1StatRxESL15MinTr,
            tnE1StatRxSESL15MinTr,
            tnE1StatTxBBEP15MinTr,
            tnE1StatTxESP15MinTr,
            tnE1StatTxSESP15MinTr,
            tnE1StatTxUASP15MinTr,
            tnE1StatRxBBEP1DayTr,
            tnE1StatRxESP1DayTr,
            tnE1StatRxSESP1DayTr,
            tnE1StatRxUASP1DayTr,
            tnE1StatRxESL1DayTr,
            tnE1StatRxSESL1DayTr,
            tnE1StatTxBBEP1DayTr,
            tnE1StatTxESP1DayTr,
            tnE1StatTxSESP1DayTr,
            tnE1StatTxUASP1DayTr,
            tnE1StatRxBBEP15MinRtr,
            tnE1StatRxESP15MinRtr,
            tnE1StatRxSESP15MinRtr,
            tnE1StatRxUASP15MinRtr,
            tnE1StatRxESL15MinRtr,
            tnE1StatRxSESL15MinRtr,
            tnE1StatTxBBEP15MinRtr,
            tnE1StatTxESP15MinRtr,
            tnE1StatTxSESP15MinRtr,
            tnE1StatTxUASP15MinRtr
        }
        STATUS         current
        DESCRIPTION    "."
        ::= { tnStatisticsGroups 94 }

    tnE1RawCountStatsScalarsGroup OBJECT-GROUP
        OBJECTS {
            tnE1RawCountStatsTotalMembers
        }
        STATUS         current
        DESCRIPTION    "."
        ::= { tnStatisticsGroups 95 }

    tnE1RawCountStatsGroup OBJECT-GROUP
        OBJECTS {
            tnE1RawCountStatsClear,
            tnE1RawCountStatRxBBEP,
            tnE1RawCountStatRxESP,
            tnE1RawCountStatRxSESP,
            tnE1RawCountStatRxUASP,
            tnE1RawCountStatRxESL,
            tnE1RawCountStatRxSESL,
            tnE1RawCountStatTxBBEP,
            tnE1RawCountStatTxESP,
            tnE1RawCountStatTxSESP,
            tnE1RawCountStatTxUASP,
            tnE1RawCountStatStartTime
        }
        STATUS         current
        DESCRIPTION    "."
        ::= { tnStatisticsGroups 96 }

    tnPreFECBitsStatsScalarsGroup OBJECT-GROUP
        OBJECTS {
            tnPreFECBitsStatsTotalMembers
        }
        STATUS         current
        DESCRIPTION    "."
        ::= { tnStatisticsGroups 97 }

    tnPreFECBitsStatsGroup OBJECT-GROUP
        OBJECTS {
            tnPreFECBitsStatsBinStatus,
            tnPreFECBitsStatsStartTime,
            tnPreFECBitsStatMin,
            tnPreFECBitsStatMax,
            tnPreFECBitsStatAverage
        }
        STATUS         current
        DESCRIPTION    "."
        ::= { tnStatisticsGroups 98 }

    tnPreFECBitsRawCountStatsScalarsGroup OBJECT-GROUP
        OBJECTS {
            tnPreFECBitsRawCountStatsTotalMembers
        }
        STATUS         current
        DESCRIPTION    "."
        ::= { tnStatisticsGroups 99 }

    tnPreFECBitsRawCountStatsGroup OBJECT-GROUP
        OBJECTS {
            tnPreFECBitsRawCountStatsClear,
            tnPreFECBitsRawCountStatMin,
            tnPreFECBitsRawCountStatMax,
            tnPreFECBitsRawCountStatAverage,
            tnPreFECBitsRawCountStatStartTime
        }
        STATUS         current
        DESCRIPTION    "."
        ::= { tnStatisticsGroups 100 }

--    obsolete
--    tnStatsTcmTCAGroup                  OBJECT-GROUP ::= { tnStatisticsGroups 101 }
--    tnStatsTcmTCAProfileGroup           OBJECT-GROUP ::= { tnStatisticsGroups 102 }
--    tnStatsTcmPortGroup                 OBJECT-GROUP ::= { tnStatisticsGroups 103 }
--    tnTcm64BitStatsScalarsGroup         OBJECT-GROUP ::= { tnStatisticsGroups 104 }
--    tnTcm64BitStatsGroup                OBJECT-GROUP ::= { tnStatisticsGroups 105 }
--    tnTcm64BitRawCountStatsScalarsGroup OBJECT-GROUP ::= { tnStatisticsGroups 106 }
--    tnTcm64BitRawCountStatsGroup        OBJECT-GROUP ::= { tnStatisticsGroups 107 }

    tnEncrypt64BitStatsScalarsGroup OBJECT-GROUP
        OBJECTS {
            tnEncrypt64BitStatsTotalMembers
        }
        STATUS         current
        DESCRIPTION    "."
        ::= { tnStatisticsGroups 108 }

    tnEncrypt64BitStatsGroup OBJECT-GROUP
        OBJECTS {
            tnEncrypt64BitStatsBinStatus,
            tnEncrypt64BitStatsStartTime,
            tnEncrypt64BitStatTx128BitBlkCnt,
            tnEncrypt64BitStatRxFailToDecryptCnt
        }
        STATUS         current
        DESCRIPTION    "."
        ::= { tnStatisticsGroups 109 }

    tnEncrypt64BitRawCountStatsScalarsGroup OBJECT-GROUP
        OBJECTS {
            tnEncrypt64BitRawCountStatsTotalMembers
        }
        STATUS         current
        DESCRIPTION    "."
        ::= { tnStatisticsGroups 110 }

    tnEncrypt64BitRawCountStatsGroup OBJECT-GROUP
        OBJECTS {
            tnEncrypt64BitRawCountStatsClear,
            tnEncrypt64BitRawCountStatTx128BitBlkCnt,
            tnEncrypt64BitRawCountStatRxFailToDecryptCnt,
            tnEncrypt64BitRawCountStatStartTime
        }
        STATUS         current
        DESCRIPTION    "."
        ::= { tnStatisticsGroups 111 }

    tnOthOdukStatsRxConfigScalarsGroup OBJECT-GROUP
        OBJECTS {
            tnOthOdukStatsRxConfigAttributeTotal
        }
        STATUS         current
        DESCRIPTION    "."
        ::= { tnStatisticsGroups 112 }

    tnOthOdukStatsRxConfigGroup OBJECT-GROUP
        OBJECTS {
            tnOthOdukStatsRxNumberofBins,
            tnOthOdukStatsRxProfileid,
            tnOthOdukStatsRxClear,
            tnOthOdukStatsRxIntervalLength
        }
        STATUS         current
        DESCRIPTION    "."
        ::= { tnStatisticsGroups 113 }

    tnOthOdukStatsTxConfigScalarsGroup OBJECT-GROUP
        OBJECTS {
            tnOthOdukStatsTxConfigAttributeTotal
        }
        STATUS         current
        DESCRIPTION    "."
        ::= { tnStatisticsGroups 114 }

    tnOthOdukStatsTxConfigGroup OBJECT-GROUP
        OBJECTS {
            tnOthOdukStatsTxNumberofBins,
            tnOthOdukStatsTxProfileid,
            tnOthOdukStatsTxClear,
            tnOthOdukStatsTxIntervalLength
        }
        STATUS         current
        DESCRIPTION    "."
        ::= { tnStatisticsGroups 115 }

    tnOthOdukStatsControlScalarsGroup OBJECT-GROUP
        OBJECTS {
            tnOthOdukStatsControlAttributeTotal
        }
        STATUS         current
        DESCRIPTION    "."
        ::= { tnStatisticsGroups 116 }

    tnOthOdukStatsControlGroup OBJECT-GROUP
        OBJECTS {
            tnOthOdukStatsClearAll,
            tnOthOdukStatsRxEnable,
            tnOthOdukStatsTxEnable
        }
        STATUS         current
        DESCRIPTION    "."
        ::= { tnStatisticsGroups 117 }

    tnOthOdukStatsRxScalarsGroup OBJECT-GROUP
        OBJECTS {
            tnOthOdukStatsRxTotalMembers
        }
        STATUS         current
        DESCRIPTION    "."
        ::= { tnStatisticsGroups 118 }

    tnOthOdukStatsRxGroup OBJECT-GROUP
        OBJECTS {
            tnOthOdukStatsRxBinStatus,
            tnOthOdukStatsRxStartTime,
            tnOthOdukStatsRxNeBIP8ErrCnt,
            tnOthOdukStatsRxNeES,
            tnOthOdukStatsRxNeSES,
            tnOthOdukStatsRxNeUAS,
            tnOthOdukStatsRxFeBIP8ErrCnt,
            tnOthOdukStatsRxFeES,
            tnOthOdukStatsRxFeSES,
            tnOthOdukStatsRxFeUAS
        }
        STATUS         current
        DESCRIPTION    "."
        ::= { tnStatisticsGroups 119 }

    tnOthOdukStatsTxScalarsGroup OBJECT-GROUP
        OBJECTS {
            tnOthOdukStatsTxTotalMembers
        }
        STATUS         current
        DESCRIPTION    "."
        ::= { tnStatisticsGroups 120 }

    tnOthOdukStatsTxGroup OBJECT-GROUP
        OBJECTS {
            tnOthOdukStatsTxBinStatus,
            tnOthOdukStatsTxStartTime,
            tnOthOdukStatsTxNeBIP8ErrCnt,
            tnOthOdukStatsTxNeES,
            tnOthOdukStatsTxNeSES,
            tnOthOdukStatsTxNeUAS,
            tnOthOdukStatsTxFeBIP8ErrCnt,
            tnOthOdukStatsTxFeES,
            tnOthOdukStatsTxFeSES,
            tnOthOdukStatsTxFeUAS
        }
        STATUS         current
        DESCRIPTION    "."
        ::= { tnStatisticsGroups 121 }

    tnOthOtukStatsScalarsGroup OBJECT-GROUP
        OBJECTS {
            tnOthOdukStatsTxTotalMembers
        }
        STATUS         current
        DESCRIPTION    "."
        ::= { tnStatisticsGroups 122 }

    tnOthOtukStatsGroup OBJECT-GROUP
        OBJECTS {
            tnOthOtukStatsBinStatus,
            tnOthOtukStatsStartTime,
            tnOthOtukStatRxRsCorrCnt,
            tnOthOtukStatRxRsUncorrCnt,
            tnOthOtukStatRxBERPreFEC,
            tnOthOtukStatRxBERPostFEC,
            tnOthOtukStatNeRxSMBIP8ErrCnt,
            tnOthOtukStatNeRxBIAESErrCnt,
            tnOthOtukStatNeRxSMES,
            tnOthOtukStatNeRxSMSES,
            tnOthOtukStatNeRxSMUAS,
            tnOthOtukStatNeRxIAES,
            tnOthOtukStatFeRxSMBIP8ErrCnt,
            tnOthOtukStatFeRxSMES,
            tnOthOtukStatFeRxSMSES,
            tnOthOtukStatFeRxSMUAS,
            tnOthOtukStatFeRxIAES
        }
        STATUS         current
        DESCRIPTION    "."
        ::= { tnStatisticsGroups 123 }

    tnOthOdukStatsRxThresholdScalarsGroup OBJECT-GROUP
        OBJECTS {
            tnOthOdu0StatRxNeBIP8ErrCnt15MinTr,
            tnOthOdu0StatRxNeBIP8ErrCnt15MinRtr,
            tnOthOdu0StatRxNeBIP8ErrCnt1DayTr,
            tnOthOdu0StatRxFeBIP8ErrCnt15MinTr,
            tnOthOdu0StatRxFeBIP8ErrCnt15MinRtr,
            tnOthOdu0StatRxFeBIP8ErrCnt1DayTr,
            tnOthOdu1StatRxNeBIP8ErrCnt15MinTr,
            tnOthOdu1StatRxNeBIP8ErrCnt15MinRtr,
            tnOthOdu1StatRxNeBIP8ErrCnt1DayTr,
            tnOthOdu1StatRxFeBIP8ErrCnt15MinTr,
            tnOthOdu1StatRxFeBIP8ErrCnt15MinRtr,
            tnOthOdu1StatRxFeBIP8ErrCnt1DayTr,
            tnOthOdu2StatRxNeBIP8ErrCnt15MinTr,
            tnOthOdu2StatRxNeBIP8ErrCnt15MinRtr,
            tnOthOdu2StatRxNeBIP8ErrCnt1DayTr,
            tnOthOdu2StatRxFeBIP8ErrCnt15MinTr,
            tnOthOdu2StatRxFeBIP8ErrCnt15MinRtr,
            tnOthOdu2StatRxFeBIP8ErrCnt1DayTr,
            tnOthOdu3StatRxNeBIP8ErrCnt15MinTr,
            tnOthOdu3StatRxNeBIP8ErrCnt15MinRtr,
            tnOthOdu3StatRxNeBIP8ErrCnt1DayTr,
            tnOthOdu3StatRxFeBIP8ErrCnt15MinTr,
            tnOthOdu3StatRxFeBIP8ErrCnt15MinRtr,
            tnOthOdu3StatRxFeBIP8ErrCnt1DayTr,
            tnOthOdu4StatRxNeBIP8ErrCnt15MinTr,
            tnOthOdu4StatRxNeBIP8ErrCnt15MinRtr,
            tnOthOdu4StatRxNeBIP8ErrCnt1DayTr,
            tnOthOdu4StatRxFeBIP8ErrCnt15MinTr,
            tnOthOdu4StatRxFeBIP8ErrCnt15MinRtr,
            tnOthOdu4StatRxFeBIP8ErrCnt1DayTr,
            tnOthOdukStatRxNeES15MinTr,
            tnOthOdukStatRxNeES15MinRtr,
            tnOthOdukStatRxNeES1DayTr,
            tnOthOdukStatRxFeES15MinTr,
            tnOthOdukStatRxFeES15MinRtr,
            tnOthOdukStatRxFeES1DayTr,
            tnOthOdukStatRxNeSES15MinTr,
            tnOthOdukStatRxNeSES15MinRtr,
            tnOthOdukStatRxNeSES1DayTr,
            tnOthOdukStatRxFeSES15MinTr,
            tnOthOdukStatRxFeSES15MinRtr,
            tnOthOdukStatRxFeSES1DayTr,
            tnOthOdukStatRxNeUAS15MinTr,
            tnOthOdukStatRxNeUAS15MinRtr,
            tnOthOdukStatRxNeUAS1DayTr,
            tnOthOdukStatRxFeUAS15MinTr,
            tnOthOdukStatRxFeUAS15MinRtr,
            tnOthOdukStatRxFeUAS1DayTr,
            tnOthOduflexGFPRxNeBIP8ErrCnt15MinTr,
            tnOthOduflexGFPRxNeBIP8ErrCnt15MinRtr,
            tnOthOduflexGFPRxNeBIP8ErrCnt1DayTr,
            tnOthOduflexGFPRxFeBIP8ErrCnt15MinTr,
            tnOthOduflexGFPRxFeBIP8ErrCnt15MinRtr,
            tnOthOduflexGFPRxFeBIP8ErrCnt1DayTr,
            tnOthOduflexFC400RxNeBIP8ErrCnt15MinTr,
            tnOthOduflexFC400RxNeBIP8ErrCnt15MinRtr,
            tnOthOduflexFC400RxNeBIP8ErrCnt1DayTr,
            tnOthOduflexFC400RxFeBIP8ErrCnt15MinTr,
            tnOthOduflexFC400RxFeBIP8ErrCnt15MinRtr,
            tnOthOduflexFC400RxFeBIP8ErrCnt1DayTr,
            tnOthOduflexFC800RxNeBIP8ErrCnt15MinTr,
            tnOthOduflexFC800RxNeBIP8ErrCnt15MinRtr,
            tnOthOduflexFC800RxNeBIP8ErrCnt1DayTr,
            tnOthOduflexFC800RxFeBIP8ErrCnt15MinTr,
            tnOthOduflexFC800RxFeBIP8ErrCnt15MinRtr,
            tnOthOduflexFC800RxFeBIP8ErrCnt1DayTr,
            tnOthOduflexFC1600RxNeBIP8ErrCnt15MinTr,
            tnOthOduflexFC1600RxNeBIP8ErrCnt15MinRtr,
            tnOthOduflexFC1600RxNeBIP8ErrCnt1DayTr,
            tnOthOduflexFC1600RxFeBIP8ErrCnt15MinTr,
            tnOthOduflexFC1600RxFeBIP8ErrCnt15MinRtr,
            tnOthOduflexFC1600RxFeBIP8ErrCnt1DayTr,
            tnOthOduflexIBSDRRxNeBIP8ErrCnt15MinTr,
            tnOthOduflexIBSDRRxNeBIP8ErrCnt15MinRtr,
            tnOthOduflexIBSDRRxNeBIP8ErrCnt1DayTr,
            tnOthOduflexIBSDRRxFeBIP8ErrCnt15MinTr,
            tnOthOduflexIBSDRRxFeBIP8ErrCnt15MinRtr,
            tnOthOduflexIBSDRRxFeBIP8ErrCnt1DayTr,
            tnOthOduflexIBDDRRxNeBIP8ErrCnt15MinTr,
            tnOthOduflexIBDDRRxNeBIP8ErrCnt15MinRtr,
            tnOthOduflexIBDDRRxNeBIP8ErrCnt1DayTr,
            tnOthOduflexIBDDRRxFeBIP8ErrCnt15MinTr,
            tnOthOduflexIBDDRRxFeBIP8ErrCnt15MinRtr,
            tnOthOduflexIBDDRRxFeBIP8ErrCnt1DayTr,
            tnOthOduflexIBQDRRxNeBIP8ErrCnt15MinTr,
            tnOthOduflexIBQDRRxNeBIP8ErrCnt15MinRtr,
            tnOthOduflexIBQDRRxNeBIP8ErrCnt1DayTr,
            tnOthOduflexIBQDRRxFeBIP8ErrCnt15MinTr,
            tnOthOduflexIBQDRRxFeBIP8ErrCnt15MinRtr,
            tnOthOduflexIBQDRRxFeBIP8ErrCnt1DayTr,
            tnOthOduflex3GSDI18RxNeBIP8ErrCnt15MinTr,
            tnOthOduflex3GSDI18RxNeBIP8ErrCnt15MinRtr,
            tnOthOduflex3GSDI18RxNeBIP8ErrCnt1DayTr,
            tnOthOduflex3GSDI18RxFeBIP8ErrCnt15MinTr,
            tnOthOduflex3GSDI18RxFeBIP8ErrCnt15MinRtr,
            tnOthOduflex3GSDI18RxFeBIP8ErrCnt1DayTr,
            tnOthOduflex3GSDI19RxNeBIP8ErrCnt15MinTr,
            tnOthOduflex3GSDI19RxNeBIP8ErrCnt15MinRtr,
            tnOthOduflex3GSDI19RxNeBIP8ErrCnt1DayTr,
            tnOthOduflex3GSDI19RxFeBIP8ErrCnt15MinTr,
            tnOthOduflex3GSDI19RxFeBIP8ErrCnt15MinRtr,
            tnOthOduflex3GSDI19RxFeBIP8ErrCnt1DayTr,
            tnOthOducStatRxNeBIP8ErrCnt15MinTr,
            tnOthOducStatRxNeBIP8ErrCnt15MinRtr,
            tnOthOducStatRxNeBIP8ErrCnt1DayTr,
            tnOthOducStatRxFeBIP8ErrCnt15MinTr,
            tnOthOducStatRxFeBIP8ErrCnt15MinRtr,
            tnOthOducStatRxFeBIP8ErrCnt1DayTr,
            tnOthOduflex400GBERxNeBIP8ErrCnt15MinTr,
            tnOthOduflex400GBERxNeBIP8ErrCnt15MinRtr,
            tnOthOduflex400GBERxNeBIP8ErrCnt1DayTr,
            tnOthOduflex400GBERxFeBIP8ErrCnt15MinTr,
            tnOthOduflex400GBERxFeBIP8ErrCnt15MinRtr,
            tnOthOduflex400GBERxFeBIP8ErrCnt1DayTr,
            tnOthOduflexFC3200RxNeBIP8ErrCnt15MinTr,
            tnOthOduflexFC3200RxNeBIP8ErrCnt15MinRtr,
            tnOthOduflexFC3200RxNeBIP8ErrCnt1DayTr,
            tnOthOduflexFC3200RxFeBIP8ErrCnt15MinTr,
            tnOthOduflexFC3200RxFeBIP8ErrCnt15MinRtr,
            tnOthOduflexFC3200RxFeBIP8ErrCnt1DayTr,
            tnOthOdutc1StatRxNeBIP8ErrCnt15MinTr,
            tnOthOdutc1StatRxNeBIP8ErrCnt15MinRtr,
            tnOthOdutc1StatRxNeBIP8ErrCnt1DayTr,
            tnOthOdutc1StatRxFeBIP8ErrCnt15MinTr,
            tnOthOdutc1StatRxFeBIP8ErrCnt15MinRtr,
            tnOthOdutc1StatRxFeBIP8ErrCnt1DayTr,
            tnOthOdutc4StatRxNeBIP8ErrCnt15MinTr,
            tnOthOdutc4StatRxNeBIP8ErrCnt15MinRtr,
            tnOthOdutc4StatRxNeBIP8ErrCnt1DayTr,
            tnOthOdutc4StatRxFeBIP8ErrCnt15MinTr,
            tnOthOdutc4StatRxFeBIP8ErrCnt15MinRtr,
            tnOthOdutc4StatRxFeBIP8ErrCnt1DayTr
        }
        STATUS         current
        DESCRIPTION    "."
        ::= { tnStatisticsGroups 124 }

    tnOthOdukStatsTxThresholdScalarsGroup OBJECT-GROUP
        OBJECTS {
            tnOthOdu0StatTxNeBIP8ErrCnt15MinTr,
            tnOthOdu0StatTxNeBIP8ErrCnt15MinRtr,
            tnOthOdu0StatTxNeBIP8ErrCnt1DayTr,
            tnOthOdu0StatTxFeBIP8ErrCnt15MinTr,
            tnOthOdu0StatTxFeBIP8ErrCnt15MinRtr,
            tnOthOdu0StatTxFeBIP8ErrCnt1DayTr,
            tnOthOdu1StatTxNeBIP8ErrCnt15MinTr,
            tnOthOdu1StatTxNeBIP8ErrCnt15MinRtr,
            tnOthOdu1StatTxNeBIP8ErrCnt1DayTr,
            tnOthOdu1StatTxFeBIP8ErrCnt15MinTr,
            tnOthOdu1StatTxFeBIP8ErrCnt15MinRtr,
            tnOthOdu1StatTxFeBIP8ErrCnt1DayTr,
            tnOthOdu2StatTxNeBIP8ErrCnt15MinTr,
            tnOthOdu2StatTxNeBIP8ErrCnt15MinRtr,
            tnOthOdu2StatTxNeBIP8ErrCnt1DayTr,
            tnOthOdu2StatTxFeBIP8ErrCnt15MinTr,
            tnOthOdu2StatTxFeBIP8ErrCnt15MinRtr,
            tnOthOdu2StatTxFeBIP8ErrCnt1DayTr,
            tnOthOdu3StatTxNeBIP8ErrCnt15MinTr,
            tnOthOdu3StatTxNeBIP8ErrCnt15MinRtr,
            tnOthOdu3StatTxNeBIP8ErrCnt1DayTr,
            tnOthOdu3StatTxFeBIP8ErrCnt15MinTr,
            tnOthOdu3StatTxFeBIP8ErrCnt15MinRtr,
            tnOthOdu3StatTxFeBIP8ErrCnt1DayTr,
            tnOthOdu4StatTxNeBIP8ErrCnt15MinTr,
            tnOthOdu4StatTxNeBIP8ErrCnt15MinRtr,
            tnOthOdu4StatTxNeBIP8ErrCnt1DayTr,
            tnOthOdu4StatTxFeBIP8ErrCnt15MinTr,
            tnOthOdu4StatTxFeBIP8ErrCnt15MinRtr,
            tnOthOdu4StatTxFeBIP8ErrCnt1DayTr,
            tnOthOdukStatTxNeES15MinTr,
            tnOthOdukStatTxNeES15MinRtr,
            tnOthOdukStatTxNeES1DayTr,
            tnOthOdukStatTxFeES15MinTr,
            tnOthOdukStatTxFeES15MinRtr,
            tnOthOdukStatTxFeES1DayTr,
            tnOthOdukStatTxNeSES15MinTr,
            tnOthOdukStatTxNeSES15MinRtr,
            tnOthOdukStatTxNeSES1DayTr,
            tnOthOdukStatTxFeSES15MinTr,
            tnOthOdukStatTxFeSES15MinRtr,
            tnOthOdukStatTxFeSES1DayTr,
            tnOthOdukStatTxNeUAS15MinTr,
            tnOthOdukStatTxNeUAS15MinRtr,
            tnOthOdukStatTxNeUAS1DayTr,
            tnOthOdukStatTxFeUAS15MinTr,
            tnOthOdukStatTxFeUAS15MinRtr,
            tnOthOdukStatTxFeUAS1DayTr,
            tnOthOduflexGFPTxNeBIP8ErrCnt15MinTr,
            tnOthOduflexGFPTxNeBIP8ErrCnt15MinRtr,
            tnOthOduflexGFPTxNeBIP8ErrCnt1DayTr,
            tnOthOduflexGFPTxFeBIP8ErrCnt15MinTr,
            tnOthOduflexGFPTxFeBIP8ErrCnt15MinRtr,
            tnOthOduflexGFPTxFeBIP8ErrCnt1DayTr,
            tnOthOduflexFC400TxNeBIP8ErrCnt15MinTr,
            tnOthOduflexFC400TxNeBIP8ErrCnt15MinRtr,
            tnOthOduflexFC400TxNeBIP8ErrCnt1DayTr,
            tnOthOduflexFC400TxFeBIP8ErrCnt15MinTr,
            tnOthOduflexFC400TxFeBIP8ErrCnt15MinRtr,
            tnOthOduflexFC400TxFeBIP8ErrCnt1DayTr,
            tnOthOduflexFC800TxNeBIP8ErrCnt15MinTr,
            tnOthOduflexFC800TxNeBIP8ErrCnt15MinRtr,
            tnOthOduflexFC800TxNeBIP8ErrCnt1DayTr,
            tnOthOduflexFC800TxFeBIP8ErrCnt15MinTr,
            tnOthOduflexFC800TxFeBIP8ErrCnt15MinRtr,
            tnOthOduflexFC800TxFeBIP8ErrCnt1DayTr,
            tnOthOduflexFC1600TxNeBIP8ErrCnt15MinTr,
            tnOthOduflexFC1600TxNeBIP8ErrCnt15MinRtr,
            tnOthOduflexFC1600TxNeBIP8ErrCnt1DayTr,
            tnOthOduflexFC1600TxFeBIP8ErrCnt15MinTr,
            tnOthOduflexFC1600TxFeBIP8ErrCnt15MinRtr,
            tnOthOduflexFC1600TxFeBIP8ErrCnt1DayTr,
            tnOthOduflexIBSDRTxNeBIP8ErrCnt15MinTr,
            tnOthOduflexIBSDRTxNeBIP8ErrCnt15MinRtr,
            tnOthOduflexIBSDRTxNeBIP8ErrCnt1DayTr,
            tnOthOduflexIBSDRTxFeBIP8ErrCnt15MinTr,
            tnOthOduflexIBSDRTxFeBIP8ErrCnt15MinRtr,
            tnOthOduflexIBSDRTxFeBIP8ErrCnt1DayTr,
            tnOthOduflexIBDDRTxNeBIP8ErrCnt15MinTr,
            tnOthOduflexIBDDRTxNeBIP8ErrCnt15MinRtr,
            tnOthOduflexIBDDRTxNeBIP8ErrCnt1DayTr,
            tnOthOduflexIBDDRTxFeBIP8ErrCnt15MinTr,
            tnOthOduflexIBDDRTxFeBIP8ErrCnt15MinRtr,
            tnOthOduflexIBDDRTxFeBIP8ErrCnt1DayTr,
            tnOthOduflexIBQDRTxNeBIP8ErrCnt15MinTr,
            tnOthOduflexIBQDRTxNeBIP8ErrCnt15MinRtr,
            tnOthOduflexIBQDRTxNeBIP8ErrCnt1DayTr,
            tnOthOduflexIBQDRTxFeBIP8ErrCnt15MinTr,
            tnOthOduflexIBQDRTxFeBIP8ErrCnt15MinRtr,
            tnOthOduflexIBQDRTxFeBIP8ErrCnt1DayTr,
            tnOthOduflex3GSDI18TxNeBIP8ErrCnt15MinTr,
            tnOthOduflex3GSDI18TxNeBIP8ErrCnt15MinRtr,
            tnOthOduflex3GSDI18TxNeBIP8ErrCnt1DayTr,
            tnOthOduflex3GSDI18TxFeBIP8ErrCnt15MinTr,
            tnOthOduflex3GSDI18TxFeBIP8ErrCnt15MinRtr,
            tnOthOduflex3GSDI18TxFeBIP8ErrCnt1DayTr,
            tnOthOduflex3GSDI19TxNeBIP8ErrCnt15MinTr,
            tnOthOduflex3GSDI19TxNeBIP8ErrCnt15MinRtr,
            tnOthOduflex3GSDI19TxNeBIP8ErrCnt1DayTr,
            tnOthOduflex3GSDI19TxFeBIP8ErrCnt15MinTr,
            tnOthOduflex3GSDI19TxFeBIP8ErrCnt15MinRtr,
            tnOthOduflex3GSDI19TxFeBIP8ErrCnt1DayTr,
            tnOthOducStatTxNeBIP8ErrCnt15MinTr,
            tnOthOducStatTxNeBIP8ErrCnt15MinRtr,
            tnOthOducStatTxNeBIP8ErrCnt1DayTr,
            tnOthOducStatTxFeBIP8ErrCnt15MinTr,
            tnOthOducStatTxFeBIP8ErrCnt15MinRtr,
            tnOthOducStatTxFeBIP8ErrCnt1DayTr,
            tnOthOduflex400GBETxNeBIP8ErrCnt15MinTr,
            tnOthOduflex400GBETxNeBIP8ErrCnt15MinRtr,
            tnOthOduflex400GBETxNeBIP8ErrCnt1DayTr,
            tnOthOduflex400GBETxFeBIP8ErrCnt15MinTr,
            tnOthOduflex400GBETxFeBIP8ErrCnt15MinRtr,
            tnOthOduflex400GBETxFeBIP8ErrCnt1DayTr,
            tnOthOduflexFC3200TxNeBIP8ErrCnt15MinTr,
            tnOthOduflexFC3200TxNeBIP8ErrCnt15MinRtr,
            tnOthOduflexFC3200TxNeBIP8ErrCnt1DayTr,
            tnOthOduflexFC3200TxFeBIP8ErrCnt15MinTr,
            tnOthOduflexFC3200TxFeBIP8ErrCnt15MinRtr,
            tnOthOduflexFC3200TxFeBIP8ErrCnt1DayTr,
            tnOthOdutc1StatTxNeBIP8ErrCnt15MinTr,
            tnOthOdutc1StatTxNeBIP8ErrCnt15MinRtr,
            tnOthOdutc1StatTxNeBIP8ErrCnt1DayTr,
            tnOthOdutc1StatTxFeBIP8ErrCnt15MinTr,
            tnOthOdutc1StatTxFeBIP8ErrCnt15MinRtr,
            tnOthOdutc1StatTxFeBIP8ErrCnt1DayTr,
            tnOthOdutc4StatTxNeBIP8ErrCnt15MinTr,
            tnOthOdutc4StatTxNeBIP8ErrCnt15MinRtr,
            tnOthOdutc4StatTxNeBIP8ErrCnt1DayTr,
            tnOthOdutc4StatTxFeBIP8ErrCnt15MinTr,
            tnOthOdutc4StatTxFeBIP8ErrCnt15MinRtr,
            tnOthOdutc4StatTxFeBIP8ErrCnt1DayTr
        }
        STATUS         current
        DESCRIPTION    "."
        ::= { tnStatisticsGroups 125 }

    tnOthOtukStatsThresholdScalarsGroup OBJECT-GROUP
        OBJECTS {
            tnOthOtu1StatRxRsCorrCnt15MinTr,
            tnOthOtu1StatRxRsCorrCnt15MinRtr,
            tnOthOtu1StatRxRsCorrCnt1DayTr,
            tnOthOtu1StatRxRsUncorrCnt15MinTr,
            tnOthOtu1StatRxRsUncorrCnt15MinRtr,
            tnOthOtu1StatRxRsUncorrCnt1DayTr,
            tnOthOtu1StatRxNeSMBIP8ErrCnt15MinTr,
            tnOthOtu1StatRxNeSMBIP8ErrCnt15MinRtr,
            tnOthOtu1StatRxNeSMBIP8ErrCnt1DayTr,
            tnOthOtu1StatRxFeSMBIP8ErrCnt15MinTr,
            tnOthOtu1StatRxFeSMBIP8ErrCnt15MinRtr,
            tnOthOtu1StatRxFeSMBIP8ErrCnt1DayTr,
            tnOthOtu2StatRxRsCorrCnt15MinTr,
            tnOthOtu2StatRxRsCorrCnt15MinRtr,
            tnOthOtu2StatRxRsCorrCnt1DayTr,
            tnOthOtu2StatRxRsUncorrCnt15MinTr,
            tnOthOtu2StatRxRsUncorrCnt15MinRtr,
            tnOthOtu2StatRxRsUncorrCnt1DayTr,
            tnOthOtu2StatRxNeSMBIP8ErrCnt15MinTr,
            tnOthOtu2StatRxNeSMBIP8ErrCnt15MinRtr,
            tnOthOtu2StatRxNeSMBIP8ErrCnt1DayTr,
            tnOthOtu2StatRxFeSMBIP8ErrCnt15MinTr,
            tnOthOtu2StatRxFeSMBIP8ErrCnt15MinRtr,
            tnOthOtu2StatRxFeSMBIP8ErrCnt1DayTr,
            tnOthOtu3StatRxRsCorrCnt15MinTr,
            tnOthOtu3StatRxRsCorrCnt15MinRtr,
            tnOthOtu3StatRxRsCorrCnt1DayTr,
            tnOthOtu3StatRxRsUncorrCnt15MinTr,
            tnOthOtu3StatRxRsUncorrCnt15MinRtr,
            tnOthOtu3StatRxRsUncorrCnt1DayTr,
            tnOthOtu3StatRxNeSMBIP8ErrCnt15MinTr,
            tnOthOtu3StatRxNeSMBIP8ErrCnt15MinRtr,
            tnOthOtu3StatRxNeSMBIP8ErrCnt1DayTr,
            tnOthOtu3StatRxFeSMBIP8ErrCnt15MinTr,
            tnOthOtu3StatRxFeSMBIP8ErrCnt15MinRtr,
            tnOthOtu3StatRxFeSMBIP8ErrCnt1DayTr,
            tnOthOtu4StatRxRsCorrCnt15MinTr,
            tnOthOtu4StatRxRsCorrCnt15MinRtr,
            tnOthOtu4StatRxRsCorrCnt1DayTr,
            tnOthOtu4StatRxRsUncorrCnt15MinTr,
            tnOthOtu4StatRxRsUncorrCnt15MinRtr,
            tnOthOtu4StatRxRsUncorrCnt1DayTr,
            tnOthOtu4StatRxNeSMBIP8ErrCnt15MinTr,
            tnOthOtu4StatRxNeSMBIP8ErrCnt15MinRtr,
            tnOthOtu4StatRxNeSMBIP8ErrCnt1DayTr,
            tnOthOtu4StatRxFeSMBIP8ErrCnt15MinTr,
            tnOthOtu4StatRxFeSMBIP8ErrCnt15MinRtr,
            tnOthOtu4StatRxFeSMBIP8ErrCnt1DayTr,
            tnOthOtukStatRxBERPreFEC15MinTr,
            tnOthOtukStatRxBERPreFEC15MinRtr,
            tnOthOtukStatRxBERPreFEC1DayTr,
            tnOthOtukStatRxBERPostFEC15MinTr,
            tnOthOtukStatRxBERPostFEC15MinRtr,
            tnOthOtukStatRxBERPostFEC1DayTr,
            tnOthOtukStatRxNeSMES15MinTr,
            tnOthOtukStatRxNeSMES15MinRtr,
            tnOthOtukStatRxNeSMES1DayTr,
            tnOthOtukStatRxFeSMES15MinTr,
            tnOthOtukStatRxFeSMES15MinRtr,
            tnOthOtukStatRxFeSMES1DayTr,
            tnOthOtukStatRxNeSMSES15MinTr,
            tnOthOtukStatRxNeSMSES15MinRtr,
            tnOthOtukStatRxNeSMSES1DayTr,
            tnOthOtukStatRxFeSMSES15MinTr,
            tnOthOtukStatRxFeSMSES15MinRtr,
            tnOthOtukStatRxFeSMSES1DayTr,
            tnOthOtukStatRxNeSMUAS15MinTr,
            tnOthOtukStatRxNeSMUAS15MinRtr,
            tnOthOtukStatRxNeSMUAS1DayTr,
            tnOthOtukStatRxFeSMUAS15MinTr,
            tnOthOtukStatRxFeSMUAS15MinRtr,
            tnOthOtukStatRxFeSMUAS1DayTr,
            tnOthOtukStatRxNeIAES15MinTr,
            tnOthOtukStatRxNeIAES15MinRtr,
            tnOthOtukStatRxNeIAES1DayTr,
            tnOthOtukStatRxFeIAES15MinTr,
            tnOthOtukStatRxFeIAES15MinRtr,
            tnOthOtukStatRxFeIAES1DayTr,
            tnOthOtucStatRxNeSMBIP8ErrCnt15MinTr,
            tnOthOtucStatRxNeSMBIP8ErrCnt15MinRtr,
            tnOthOtucStatRxNeSMBIP8ErrCnt1DayTr,
            tnOthOtucStatRxFeSMBIP8ErrCnt15MinTr,
            tnOthOtucStatRxFeSMBIP8ErrCnt15MinRtr,
            tnOthOtucStatRxFeSMBIP8ErrCnt1DayTr,
            tnOthOtutc1StatRxNeSMBIP8ErrCnt15MinTr,
            tnOthOtutc1StatRxNeSMBIP8ErrCnt15MinRtr,
            tnOthOtutc1StatRxNeSMBIP8ErrCnt1DayTr,
            tnOthOtutc1StatRxFeSMBIP8ErrCnt15MinTr,
            tnOthOtutc1StatRxFeSMBIP8ErrCnt15MinRtr,
            tnOthOtutc1StatRxFeSMBIP8ErrCnt1DayTr,
            tnOthOtutc4StatRxNeSMBIP8ErrCnt15MinTr,
            tnOthOtutc4StatRxNeSMBIP8ErrCnt15MinRtr,
            tnOthOtutc4StatRxNeSMBIP8ErrCnt1DayTr,
            tnOthOtutc4StatRxFeSMBIP8ErrCnt15MinTr,
            tnOthOtutc4StatRxFeSMBIP8ErrCnt15MinRtr,
            tnOthOtutc4StatRxFeSMBIP8ErrCnt1DayTr
        }
        STATUS         current
        DESCRIPTION    "."
        ::= { tnStatisticsGroups 126 }

    tnOthOdukRawCountStatsRxScalarsGroup OBJECT-GROUP
        OBJECTS {
            tnOthOdukRawCountStatsRxTotalMembers
        }
        STATUS         current
        DESCRIPTION    "."
        ::= { tnStatisticsGroups 127 }

    tnOthOdukRawCountStatsRxGroup OBJECT-GROUP
        OBJECTS {
            tnOthOdukRawCountStatsRxClear,
            tnOthOdukRawCountStatsRxStartTime,
            tnOthOdukRawCountStatRxNeBIP8ErrCnt,
            tnOthOdukRawCountStatRxNeES,
            tnOthOdukRawCountStatRxNeSES,
            tnOthOdukRawCountStatRxNeUAS,
            tnOthOdukRawCountStatRxFeBIP8ErrCnt,
            tnOthOdukRawCountStatRxFeES,
            tnOthOdukRawCountStatRxFeSES,
            tnOthOdukRawCountStatRxFeUAS
        }
        STATUS         current
        DESCRIPTION    "."
        ::= { tnStatisticsGroups 128 }

    tnOthOdukRawCountStatsTxScalarsGroup OBJECT-GROUP
        OBJECTS {
            tnOthOdukRawCountStatsTxTotalMembers
        }
        STATUS         current
        DESCRIPTION    "."
        ::= { tnStatisticsGroups 129 }

    tnOthOdukRawCountStatsTxGroup OBJECT-GROUP
        OBJECTS {
            tnOthOdukRawCountStatsTxClear,
            tnOthOdukRawCountStatsTxStartTime,
            tnOthOdukRawCountStatTxNeBIP8ErrCnt,
            tnOthOdukRawCountStatTxNeES,
            tnOthOdukRawCountStatTxNeSES,
            tnOthOdukRawCountStatTxNeUAS,
            tnOthOdukRawCountStatTxFeBIP8ErrCnt,
            tnOthOdukRawCountStatTxFeES,
            tnOthOdukRawCountStatTxFeSES,
            tnOthOdukRawCountStatTxFeUAS
        }
        STATUS         current
        DESCRIPTION    "."
        ::= { tnStatisticsGroups 130 }

    tnOthOtukRawCountStatsScalarsGroup OBJECT-GROUP
        OBJECTS {
            tnOthOtukRawCountStatsTotalMembers
        }
        STATUS         current
        DESCRIPTION    "."
        ::= { tnStatisticsGroups 131 }

    tnOthOtukRawCountStatsGroup OBJECT-GROUP
        OBJECTS {
            tnOthOtukRawCountStatsClear,
            tnOthOtukRawCountStatsStartTime,
            tnOthOtukRawCountStatRxRsCorrCnt,
            tnOthOtukRawCountStatRxRsUncorrCnt,
            tnOthOtukRawCountStatRxBERPreFEC,
            tnOthOtukRawCountStatRxBERPostFEC,
            tnOthOtukRawCountStatRxNeSMBIP8ErrCnt,
            tnOthOtukRawCountStatRxNeSMES,
            tnOthOtukRawCountStatRxNeSMSES,
            tnOthOtukRawCountStatRxNeSMUAS,
            tnOthOtukRawCountStatRxNeIAES,
            tnOthOtukRawCountStatRxFeSMBIP8ErrCnt,
            tnOthOtukRawCountStatRxFeSMES,
            tnOthOtukRawCountStatRxFeSMSES,
            tnOthOtukRawCountStatRxFeSMUAS,
            tnOthOtukRawCountStatRxFeIAES,
            tnOthOtukRawCountStatRxNeBIAES
        }
        STATUS         current
        DESCRIPTION    "."
        ::= { tnStatisticsGroups 132 }

    tnOsnrStatsScalarsGroup OBJECT-GROUP
        OBJECTS {
            tnOsnrStatsTotalMembers
        }
        STATUS         current
        DESCRIPTION    "."
        ::= { tnStatisticsGroups 133 }

    tnOsnrStatsGroup OBJECT-GROUP
        OBJECTS {
            tnOsnrStatsBinStatus,
            tnOsnrStatsStartTime,
            tnOsnrStatMinOSNR,
            tnOsnrStatMaxOSNR,
            tnOsnrStatAverageOSNR,
            tnOsnrStatStatusOSNR
        }
        STATUS         current
        DESCRIPTION    "."
        ::= { tnStatisticsGroups 134 }

    tnOsnrRawCountStatsScalarsGroup OBJECT-GROUP
        OBJECTS {
            tnOsnrRawCountStatsTotalMembers
        }
        STATUS         current
        DESCRIPTION    "."
        ::= { tnStatisticsGroups 135 }

    tnOsnrRawCountStatsGroup OBJECT-GROUP
        OBJECTS {
            tnOsnrRawCountStatsClear,
            tnOsnrRawCountStatStartTime,
            tnOsnrRawCountStatMinOSNR,
            tnOsnrRawCountStatMaxOSNR,
            tnOsnrRawCountStatAverageOSNR
        }
        STATUS         current
        DESCRIPTION    "."
        ::= { tnStatisticsGroups 136 }

    tnSonetStatsThresholdScalarsGroup OBJECT-GROUP
        OBJECTS {
            tnSonetStatsOC768RxCVS15MinTr,
            tnSonetStatsOC192RxCVS15MinTr,
            tnSonetStatsOC48RxCVS15MinTr,
            tnSonetStatsOC12RxCVS15MinTr,
            tnSonetStatsOC3RxCVS15MinTr,
            tnSonetStatsRxESS15MinTr,
            tnSonetStatsRxSESS15MinTr,
            tnSonetStatsRxSEFSS15MinTr,
            tnSonetStatsOC768RxCVL15MinTr,
            tnSonetStatsOC192RxCVL15MinTr,
            tnSonetStatsOC48RxCVL15MinTr,
            tnSonetStatsOC12RxCVL15MinTr,
            tnSonetStatsOC3RxCVL15MinTr,
            tnSonetStatsRxESL15MinTr,
            tnSonetStatsRxSESL15MinTr,
            tnSonetStatsRxUASL15MinTr,
            tnSonetStatsOC768TxCVS15MinTr,
            tnSonetStatsOC192TxCVS15MinTr,
            tnSonetStatsOC48TxCVS15MinTr,
            tnSonetStatsOC12TxCVS15MinTr,
            tnSonetStatsOC3TxCVS15MinTr,
            tnSonetStatsTxESS15MinTr,
            tnSonetStatsTxSESS15MinTr,
            tnSonetStatsTxSEFSS15MinTr,
            tnSonetStatsOC768TxCVL15MinTr,
            tnSonetStatsOC192TxCVL15MinTr,
            tnSonetStatsOC48TxCVL15MinTr,
            tnSonetStatsOC12TxCVL15MinTr,
            tnSonetStatsOC3TxCVL15MinTr,
            tnSonetStatsTxESL15MinTr,
            tnSonetStatsTxSESL15MinTr,
            tnSonetStatsTxUASL15MinTr,
            tnSonetStatsRxUASS15MinTr,
            tnSonetStatsTxUASS15MinTr,
            tnSonetStatsOC768RxCVS1DayTr,
            tnSonetStatsOC192RxCVS1DayTr,
            tnSonetStatsOC48RxCVS1DayTr,
            tnSonetStatsOC12RxCVS1DayTr,
            tnSonetStatsOC3RxCVS1DayTr,
            tnSonetStatsRxESS1DayTr,
            tnSonetStatsRxSESS1DayTr,
            tnSonetStatsRxSEFSS1DayTr,
            tnSonetStatsOC768RxCVL1DayTr,
            tnSonetStatsOC192RxCVL1DayTr,
            tnSonetStatsOC48RxCVL1DayTr,
            tnSonetStatsOC12RxCVL1DayTr,
            tnSonetStatsOC3RxCVL1DayTr,
            tnSonetStatsRxESL1DayTr,
            tnSonetStatsRxSESL1DayTr,
            tnSonetStatsRxUASL1DayTr,
            tnSonetStatsOC768TxCVS1DayTr,
            tnSonetStatsOC192TxCVS1DayTr,
            tnSonetStatsOC48TxCVS1DayTr,
            tnSonetStatsOC12TxCVS1DayTr,
            tnSonetStatsOC3TxCVS1DayTr,
            tnSonetStatsTxESS1DayTr,
            tnSonetStatsTxSESS1DayTr,
            tnSonetStatsTxSEFSS1DayTr,
            tnSonetStatsOC768TxCVL1DayTr,
            tnSonetStatsOC192TxCVL1DayTr,
            tnSonetStatsOC48TxCVL1DayTr,
            tnSonetStatsOC12TxCVL1DayTr,
            tnSonetStatsOC3TxCVL1DayTr,
            tnSonetStatsTxESL1DayTr,
            tnSonetStatsTxSESL1DayTr,
            tnSonetStatsTxUASL1DayTr,
            tnSonetStatsRxUASS1DayTr,
            tnSonetStatsTxUASS1DayTr,
            tnSonetStatsOC768RxFECVL15MinTr,
            tnSonetStatsOC192RxFECVL15MinTr,
            tnSonetStatsOC48RxFECVL15MinTr,
            tnSonetStatsOC12RxFECVL15MinTr,
            tnSonetStatsOC3RxFECVL15MinTr,
            tnSonetStatsRxFEESL15MinTr,
            tnSonetStatsRxFESESL15MinTr,
            tnSonetStatsRxFEUASL15MinTr,
            tnSonetStatsOC768RxFECVL1DayTr,
            tnSonetStatsOC192RxFECVL1DayTr,
            tnSonetStatsOC48RxFECVL1DayTr,
            tnSonetStatsOC12RxFECVL1DayTr,
            tnSonetStatsOC3RxFECVL1DayTr,
            tnSonetStatsRxFEESL1DayTr,
            tnSonetStatsRxFESESL1DayTr,
            tnSonetStatsRxFEUASL1DayTr
        }
        STATUS         current
        DESCRIPTION    "."
        ::= { tnStatisticsGroups 137 }

    tnSdhStatsThresholdScalarsGroup OBJECT-GROUP
        OBJECTS {
            tnSdhStatsSTM256RxRSEB15MinTr,
            tnSdhStatsSTM64RxRSEB15MinTr,
            tnSdhStatsSTM16RxRSEB15MinTr,
            tnSdhStatsSTM4RxRSEB15MinTr,
            tnSdhStatsSTM1RxRSEB15MinTr,
            tnSdhStatsRxRSES15MinTr,
            tnSdhStatsRxRSSES15MinTr,
            tnSdhStatsSTM256RxMSEB15MinTr,
            tnSdhStatsSTM64RxMSEB15MinTr,
            tnSdhStatsSTM16RxMSEB15MinTr,
            tnSdhStatsSTM4RxMSEB15MinTr,
            tnSdhStatsSTM1RxMSEB15MinTr,
            tnSdhStatsRxMSES15MinTr,
            tnSdhStatsRxMSSES15MinTr,
            tnSdhStatsRxMSUAS15MinTr,
            tnSdhStatsSTM256TxRSEB15MinTr,
            tnSdhStatsSTM64TxRSEB15MinTr,
            tnSdhStatsSTM16TxRSEB15MinTr,
            tnSdhStatsSTM4TxRSEB15MinTr,
            tnSdhStatsSTM1TxRSEB15MinTr,
            tnSdhStatsTxRSES15MinTr,
            tnSdhStatsTxRSSES15MinTr,
            tnSdhStatsSTM256TxMSEB15MinTr,
            tnSdhStatsSTM64TxMSEB15MinTr,
            tnSdhStatsSTM16TxMSEB15MinTr,
            tnSdhStatsSTM4TxMSEB15MinTr,
            tnSdhStatsSTM1TxMSEB15MinTr,
            tnSdhStatsTxMSES15MinTr,
            tnSdhStatsTxMSSES15MinTr,
            tnSdhStatsTxMSUAS15MinTr,
            tnSdhStatsRxRSUAS15MinTr,
            tnSdhStatsTxRSUAS15MinTr,
            tnSdhStatsSTM256RxRSEB1DayTr,
            tnSdhStatsSTM64RxRSEB1DayTr,
            tnSdhStatsSTM16RxRSEB1DayTr,
            tnSdhStatsSTM4RxRSEB1DayTr,
            tnSdhStatsSTM1RxRSEB1DayTr,
            tnSdhStatsRxRSES1DayTr,
            tnSdhStatsRxRSSES1DayTr,
            tnSdhStatsSTM256RxMSEB1DayTr,
            tnSdhStatsSTM64RxMSEB1DayTr,
            tnSdhStatsSTM16RxMSEB1DayTr,
            tnSdhStatsSTM4RxMSEB1DayTr,
            tnSdhStatsSTM1RxMSEB1DayTr,
            tnSdhStatsRxMSES1DayTr,
            tnSdhStatsRxMSSES1DayTr,
            tnSdhStatsRxMSUAS1DayTr,
            tnSdhStatsSTM256TxRSEB1DayTr,
            tnSdhStatsSTM64TxRSEB1DayTr,
            tnSdhStatsSTM16TxRSEB1DayTr,
            tnSdhStatsSTM4TxRSEB1DayTr,
            tnSdhStatsSTM1TxRSEB1DayTr,
            tnSdhStatsTxRSES1DayTr,
            tnSdhStatsTxRSSES1DayTr,
            tnSdhStatsSTM256TxMSEB1DayTr,
            tnSdhStatsSTM64TxMSEB1DayTr,
            tnSdhStatsSTM16TxMSEB1DayTr,
            tnSdhStatsSTM4TxMSEB1DayTr,
            tnSdhStatsSTM1TxMSEB1DayTr,
            tnSdhStatsTxMSES1DayTr,
            tnSdhStatsTxMSSES1DayTr,
            tnSdhStatsTxMSUAS1DayTr,
            tnSdhStatsRxRSUAS1DayTr,
            tnSdhStatsTxRSUAS1DayTr,
            tnSdhStatsSTM256RxRSEB15MinRtr,
            tnSdhStatsSTM64RxRSEB15MinRtr,
            tnSdhStatsSTM16RxRSEB15MinRtr,
            tnSdhStatsSTM4RxRSEB15MinRtr,
            tnSdhStatsSTM1RxRSEB15MinRtr,
            tnSdhStatsRxRSES15MinRtr,
            tnSdhStatsRxRSSES15MinRtr,
            tnSdhStatsSTM256RxMSEB15MinRtr,
            tnSdhStatsSTM64RxMSEB15MinRtr,
            tnSdhStatsSTM16RxMSEB15MinRtr,
            tnSdhStatsSTM4RxMSEB15MinRtr,
            tnSdhStatsSTM1RxMSEB15MinRtr,
            tnSdhStatsRxMSES15MinRtr,
            tnSdhStatsRxMSSES15MinRtr,
            tnSdhStatsRxMSUAS15MinRtr,
            tnSdhStatsSTM256TxRSEB15MinRtr,
            tnSdhStatsSTM64TxRSEB15MinRtr,
            tnSdhStatsSTM16TxRSEB15MinRtr,
            tnSdhStatsSTM4TxRSEB15MinRtr,
            tnSdhStatsSTM1TxRSEB15MinRtr,
            tnSdhStatsTxRSES15MinRtr,
            tnSdhStatsTxRSSES15MinRtr,
            tnSdhStatsSTM256TxMSEB15MinRtr,
            tnSdhStatsSTM64TxMSEB15MinRtr,
            tnSdhStatsSTM16TxMSEB15MinRtr,
            tnSdhStatsSTM4TxMSEB15MinRtr,
            tnSdhStatsSTM1TxMSEB15MinRtr,
            tnSdhStatsTxMSES15MinRtr,
            tnSdhStatsTxMSSES15MinRtr,
            tnSdhStatsTxMSUAS15MinRtr,
            tnSdhStatsRxRSUAS15MinRtr,
            tnSdhStatsTxRSUAS15MinRtr,
            tnSdhStatsSTM256RxMSFEEB15MinTr,
            tnSdhStatsSTM64RxMSFEEB15MinTr,
            tnSdhStatsSTM16RxMSFEEB15MinTr,
            tnSdhStatsSTM4RxMSFEEB15MinTr,
            tnSdhStatsSTM1RxMSFEEB15MinTr,
            tnSdhStatsRxMSFEES15MinTr,
            tnSdhStatsRxMSFESES15MinTr,
            tnSdhStatsRxMSFEUAS15MinTr,
            tnSdhStatsSTM256RxMSFEEB1DayTr,
            tnSdhStatsSTM64RxMSFEEB1DayTr,
            tnSdhStatsSTM16RxMSFEEB1DayTr,
            tnSdhStatsSTM4RxMSFEEB1DayTr,
            tnSdhStatsSTM1RxMSFEEB1DayTr,
            tnSdhStatsRxMSFEES1DayTr,
            tnSdhStatsRxMSFESES1DayTr,
            tnSdhStatsRxMSFEUAS1DayTr,
            tnSdhStatsSTM256RxMSFEEB15MinRtr,
            tnSdhStatsSTM64RxMSFEEB15MinRtr,
            tnSdhStatsSTM16RxMSFEEB15MinRtr,
            tnSdhStatsSTM4RxMSFEEB15MinRtr,
            tnSdhStatsSTM1RxMSFEEB15MinRtr,
            tnSdhStatsRxMSFEES15MinRtr,
            tnSdhStatsRxMSFESES15MinRtr,
            tnSdhStatsRxMSFEUAS15MinRtr
        }
        STATUS         current
        DESCRIPTION    "."
        ::= { tnStatisticsGroups 138 }

    tnDwStatsThresholdScalarsGroup OBJECT-GROUP
        OBJECTS {
            tnDw64BitStatsOtu1RxRSCorrCnt15MinTr,
            tnDw64BitStatsOtu2RxRSCorrCnt15MinTr,
            tnDw64BitStatsOtu3RxRSCorrCnt15MinTr,
            tnDw64BitStatsOtu4RxRSCorrCnt15MinTr,
            tnDw64BitStatsOtu1RxRSUncorrCnt15MinTr,
            tnDw64BitStatsOtu2RxRSUncorrCnt15MinTr,
            tnDw64BitStatsOtu3RxRSUncorrCnt15MinTr,
            tnDw64BitStatsOtu4RxRSUncorrCnt15MinTr,
            tnDw64BitStatsOtu1RxSMBIP8ErrCnt15MinTr,
            tnDw64BitStatsOtu2RxSMBIP8ErrCnt15MinTr,
            tnDw64BitStatsOtu3RxSMBIP8ErrCnt15MinTr,
            tnDw64BitStatsOtu4RxSMBIP8ErrCnt15MinTr,
            tnDw64BitStatsOdu1RxPMBIP8ErrCnt15MinTr,
            tnDw64BitStatsOdu2RxPMBIP8ErrCnt15MinTr,
            tnDw64BitStatsOdu3RxPMBIP8ErrCnt15MinTr,
            tnDw64BitStatsOdu4RxPMBIP8ErrCnt15MinTr,
            tnDw64BitStatsRxSMES15MinTr,
            tnDw64BitStatsRxPMES15MinTr,
            tnDw64BitStatsRxSMSES15MinTr,
            tnDw64BitStatsRxPMSES15MinTr,
            tnDw64BitStatsRxSMUAS15MinTr,
            tnDw64BitStatsRxPMUAS15MinTr,
            tnDw64BitStatsOtu1RxRSCorrCnt1DayTr,
            tnDw64BitStatsOtu2RxRSCorrCnt1DayTr,
            tnDw64BitStatsOtu3RxRSCorrCnt1DayTr,
            tnDw64BitStatsOtu4RxRSCorrCnt1DayTr,
            tnDw64BitStatsOtu1RxRSUncorrCnt1DayTr,
            tnDw64BitStatsOtu2RxRSUncorrCnt1DayTr,
            tnDw64BitStatsOtu3RxRSUncorrCnt1DayTr,
            tnDw64BitStatsOtu4RxRSUncorrCnt1DayTr,
            tnDw64BitStatsOtu1RxSMBIP8ErrCnt1DayTr,
            tnDw64BitStatsOtu2RxSMBIP8ErrCnt1DayTr,
            tnDw64BitStatsOtu3RxSMBIP8ErrCnt1DayTr,
            tnDw64BitStatsOtu4RxSMBIP8ErrCnt1DayTr,
            tnDw64BitStatsOdu1RxPMBIP8ErrCnt1DayTr,
            tnDw64BitStatsOdu2RxPMBIP8ErrCnt1DayTr,
            tnDw64BitStatsOdu3RxPMBIP8ErrCnt1DayTr,
            tnDw64BitStatsOdu4RxPMBIP8ErrCnt1DayTr,
            tnDw64BitStatsRxSMES1DayTr,
            tnDw64BitStatsRxPMES1DayTr,
            tnDw64BitStatsRxSMSES1DayTr,
            tnDw64BitStatsRxPMSES1DayTr,
            tnDw64BitStatsRxSMUAS1DayTr,
            tnDw64BitStatsRxPMUAS1DayTr,
            tnDw64BitStatsOtu1RxRSCorrCnt15MinRtr,
            tnDw64BitStatsOtu2RxRSCorrCnt15MinRtr,
            tnDw64BitStatsOtu3RxRSCorrCnt15MinRtr,
            tnDw64BitStatsOtu4RxRSCorrCnt15MinRtr,
            tnDw64BitStatsOtu1RxRSUncorrCnt15MinRtr,
            tnDw64BitStatsOtu2RxRSUncorrCnt15MinRtr,
            tnDw64BitStatsOtu3RxRSUncorrCnt15MinRtr,
            tnDw64BitStatsOtu4RxRSUncorrCnt15MinRtr,
            tnDw64BitStatsOtu1RxSMBIP8ErrCnt15MinRtr,
            tnDw64BitStatsOtu2RxSMBIP8ErrCnt15MinRtr,
            tnDw64BitStatsOtu3RxSMBIP8ErrCnt15MinRtr,
            tnDw64BitStatsOtu4RxSMBIP8ErrCnt15MinRtr,
            tnDw64BitStatsOdu1RxPMBIP8ErrCnt15MinRtr,
            tnDw64BitStatsOdu2RxPMBIP8ErrCnt15MinRtr,
            tnDw64BitStatsOdu3RxPMBIP8ErrCnt15MinRtr,
            tnDw64BitStatsOdu4RxPMBIP8ErrCnt15MinRtr,
            tnDw64BitStatsRxSMES15MinRtr,
            tnDw64BitStatsRxPMES15MinRtr,
            tnDw64BitStatsRxSMSES15MinRtr,
            tnDw64BitStatsRxPMSES15MinRtr,
            tnDw64BitStatsRxSMUAS15MinRtr,
            tnDw64BitStatsRxPMUAS15MinRtr,
            tnDwStatsOtu1RxSMFEBIP8ErrCnt15MinTr,
            tnDwStatsOtu2RxSMFEBIP8ErrCnt15MinTr,
            tnDwStatsOtu3RxSMFEBIP8ErrCnt15MinTr,
            tnDwStatsOtu4RxSMFEBIP8ErrCnt15MinTr,
            tnDwStatsOdu1RxPMFEBIP8ErrCnt15MinTr,
            tnDwStatsOdu2RxPMFEBIP8ErrCnt15MinTr,
            tnDwStatsOdu3RxPMFEBIP8ErrCnt15MinTr,
            tnDwStatsOdu4RxPMFEBIP8ErrCnt15MinTr,
            tnDwStatsRxSMFEES15MinTr,
            tnDwStatsRxPMFEES15MinTr,
            tnDwStatsRxSMFESES15MinTr,
            tnDwStatsRxPMFESES15MinTr,
            tnDwStatsRxSMFEUAS15MinTr,
            tnDwStatsRxPMFEUAS15MinTr,
            tnDwStatsRxSMBIAES15MinTr,
            tnDwStatsRxSMIAES15MinTr,
            tnDwStatsRxBERPreFEC15MinTr,
            tnDwStatsRxBERPostFEC15MinTr,
            tnDwStatsOtu1RxSMFEBIP8ErrCnt1DayTr,
            tnDwStatsOtu2RxSMFEBIP8ErrCnt1DayTr,
            tnDwStatsOtu3RxSMFEBIP8ErrCnt1DayTr,
            tnDwStatsOtu4RxSMFEBIP8ErrCnt1DayTr,
            tnDwStatsOdu1RxPMFEBIP8ErrCnt1DayTr,
            tnDwStatsOdu2RxPMFEBIP8ErrCnt1DayTr,
            tnDwStatsOdu3RxPMFEBIP8ErrCnt1DayTr,
            tnDwStatsOdu4RxPMFEBIP8ErrCnt1DayTr,
            tnDwStatsRxSMFEES1DayTr,
            tnDwStatsRxPMFEES1DayTr,
            tnDwStatsRxSMFESES1DayTr,
            tnDwStatsRxPMFESES1DayTr,
            tnDwStatsRxSMFEUAS1DayTr,
            tnDwStatsRxPMFEUAS1DayTr,
            tnDwStatsRxSMBIAES1DayTr,
            tnDwStatsRxSMIAES1DayTr,
            tnDwStatsRxBERPreFEC1DayTr,
            tnDwStatsRxBERPostFEC1DayTr,
            tnDwStatsOtu1RxSMFEBIP8ErrCnt15MinRtr,
            tnDwStatsOtu2RxSMFEBIP8ErrCnt15MinRtr,
            tnDwStatsOtu3RxSMFEBIP8ErrCnt15MinRtr,
            tnDwStatsOtu4RxSMFEBIP8ErrCnt15MinRtr,
            tnDwStatsOdu1RxPMFEBIP8ErrCnt15MinRtr,
            tnDwStatsOdu2RxPMFEBIP8ErrCnt15MinRtr,
            tnDwStatsOdu3RxPMFEBIP8ErrCnt15MinRtr,
            tnDwStatsOdu4RxPMFEBIP8ErrCnt15MinRtr,
            tnDwStatsRxSMFEES15MinRtr,
            tnDwStatsRxPMFEES15MinRtr,
            tnDwStatsRxSMFESES15MinRtr,
            tnDwStatsRxPMFESES15MinRtr,
            tnDwStatsRxSMFEUAS15MinRtr,
            tnDwStatsRxPMFEUAS15MinRtr,
            tnDwStatsRxSMBIAES15MinRtr,
            tnDwStatsRxSMIAES15MinRtr,
            tnDwStatsRxBERPreFEC15MinRtr,
            tnDwStatsRxBERPostFEC15MinRtr
        }
        STATUS         current
        DESCRIPTION    "."
        ::= { tnStatisticsGroups 139 }

    tnPcsStatsThresholdScalarsGroup OBJECT-GROUP
        OBJECTS {
            tnPcsStats100GBERxCV15MinTr,
            tnPcsStats40GBERxCV15MinTr,
            tnPcsStats10GBERxCV15MinTr,
            tnPcsStatsGBERxCV15MinTr,
            tnPcsStats16GFCRxCV15MinTr,
            tnPcsStats10GFCRxCV15MinTr,
            tnPcsStats8GFCRxCV15MinTr,
            tnPcsStats4GFCRxCV15MinTr,
            tnPcsStats2GFCRxCV15MinTr,
            tnPcsStatsGFCRxCV15MinTr,
            tnPcsStatsRxES15MinTr,
            tnPcsStatsRxSES15MinTr,
            tnPcsStatsRxSEFS15MinTr,
            tnPcsStats100GBERxCV1DayTr,
            tnPcsStats40GBERxCV1DayTr,
            tnPcsStats10GBERxCV1DayTr,
            tnPcsStatsGBERxCV1DayTr,
            tnPcsStats16GFCRxCV1DayTr,
            tnPcsStats10GFCRxCV1DayTr,
            tnPcsStats8GFCRxCV1DayTr,
            tnPcsStats4GFCRxCV1DayTr,
            tnPcsStats2GFCRxCV1DayTr,
            tnPcsStatsGFCRxCV1DayTr,
            tnPcsStatsRxES1DayTr,
            tnPcsStatsRxSES1DayTr,
            tnPcsStatsRxSEFS1DayTr,
            tnPcsStats100GBERxCV15MinRtr,
            tnPcsStats40GBERxCV15MinRtr,
            tnPcsStats10GBERxCV15MinRtr,
            tnPcsStatsGBERxCV15MinRtr,
            tnPcsStats16GFCRxCV15MinRtr,
            tnPcsStats10GFCRxCV15MinRtr,
            tnPcsStats8GFCRxCV15MinRtr,
            tnPcsStats4GFCRxCV15MinRtr,
            tnPcsStats2GFCRxCV15MinRtr,
            tnPcsStatsGFCRxCV15MinRtr,
            tnPcsStatsRxES15MinRtr,
            tnPcsStatsRxSES15MinRtr,
            tnPcsStatsRxSEFS15MinRtr,
            tnPcsStats100GBETxCV15MinTr,
            tnPcsStats40GBETxCV15MinTr,
            tnPcsStats10GBETxCV15MinTr,
            tnPcsStatsGBETxCV15MinTr,
            tnPcsStats16GFCTxCV15MinTr,
            tnPcsStats10GFCTxCV15MinTr,
            tnPcsStats8GFCTxCV15MinTr,
            tnPcsStats4GFCTxCV15MinTr,
            tnPcsStats2GFCTxCV15MinTr,
            tnPcsStatsGFCTxCV15MinTr,
            tnPcsStatsTxES15MinTr,
            tnPcsStatsTxSES15MinTr,
            tnPcsStatsTxSEFS15MinTr,
            tnPcsStats100GBETxCV1DayTr,
            tnPcsStats40GBETxCV1DayTr,
            tnPcsStats10GBETxCV1DayTr,
            tnPcsStatsGBETxCV1DayTr,
            tnPcsStats16GFCTxCV1DayTr,
            tnPcsStats10GFCTxCV1DayTr,
            tnPcsStats8GFCTxCV1DayTr,
            tnPcsStats4GFCTxCV1DayTr,
            tnPcsStats2GFCTxCV1DayTr,
            tnPcsStatsGFCTxCV1DayTr,
            tnPcsStatsTxES1DayTr,
            tnPcsStatsTxSES1DayTr,
            tnPcsStatsTxSEFS1DayTr,
            tnPcsStats100GBETxCV15MinRtr,
            tnPcsStats40GBETxCV15MinRtr,
            tnPcsStats10GBETxCV15MinRtr,
            tnPcsStatsGBETxCV15MinRtr,
            tnPcsStats16GFCTxCV15MinRtr,
            tnPcsStats10GFCTxCV15MinRtr,
            tnPcsStats8GFCTxCV15MinRtr,
            tnPcsStats4GFCTxCV15MinRtr,
            tnPcsStats2GFCTxCV15MinRtr,
            tnPcsStatsGFCTxCV15MinRtr,
            tnPcsStatsTxES15MinRtr,
            tnPcsStatsTxSES15MinRtr,
            tnPcsStatsTxSEFS15MinRtr,
            tnPcsStats400GBERxCV15MinTr,
            tnPcsStats400GBETxCV15MinTr,
            tnPcsStats400GBERxCV1DayTr,
            tnPcsStats400GBETxCV1DayTr,
            tnPcsStats400GBERxCV15MinRtr,
            tnPcsStats400GBETxCV15MinRtr,
            tnPcsStats32GFCRxCV15MinTr,
            tnPcsStats32GFCTxCV15MinTr,
            tnPcsStats32GFCRxCV1DayTr,
            tnPcsStats32GFCTxCV1DayTr,
            tnPcsStats32GFCRxCV15MinRtr,
            tnPcsStats32GFCTxCV15MinRtr
        }
        STATUS         current
        DESCRIPTION    "."
        ::= { tnStatisticsGroups 140 }

    tnOthOdukStatsDMConfigScalarsGroup OBJECT-GROUP
        OBJECTS {
            tnOthOdukStatsDMConfigAttributeTotal
        }
        STATUS         current
        DESCRIPTION    "."
        ::= { tnStatisticsGroups 141 }

    tnOthOdukStatsDMConfigGroup OBJECT-GROUP
        OBJECTS {
            tnOthOdukStatsDMNumberofBins,
            tnOthOdukStatsDMProfileid,
            tnOthOdukStatsDMClear,
            tnOthOdukStatsDMIntervalLength
        }
        STATUS         current
        DESCRIPTION    "."
        ::= { tnStatisticsGroups 142 }

    tnOthOdukStatsDMScalarsGroup OBJECT-GROUP
        OBJECTS {
            tnOthOdukStatsDMTotalMembers
        }
        STATUS         current
        DESCRIPTION    "."
        ::= { tnStatisticsGroups 143 }

    tnOthOdukStatsDMGroup OBJECT-GROUP
        OBJECTS {
            tnOthOdukStatsDMBinStatus,
            tnOthOdukStatsDMStartTime,
            tnOthOdukStatsDMMinDm,
            tnOthOdukStatsDMMaxDm,
            tnOthOdukStatsDMAverageDm
        }
        STATUS         current
        DESCRIPTION    "."
        ::= { tnStatisticsGroups 144 }

    tnOthOdukRawCountStatsDMScalarsGroup OBJECT-GROUP
        OBJECTS {
            tnOthOdukRawCountStatsDMTotalMembers
        }
        STATUS         current
        DESCRIPTION    "."
        ::= { tnStatisticsGroups 145 }

    tnOthOdukRawCountStatsDMGroup OBJECT-GROUP
        OBJECTS {
            tnOthOdukRawCountStatsDMClear,
            tnOthOdukRawCountStatsDMStartTime,
            tnOthOdukRawCountStatsDMMinDm,
            tnOthOdukRawCountStatsDMMaxDm,
            tnOthOdukRawCountStatsDMAverageDm
        }
        STATUS         current
        DESCRIPTION    "."
        ::= { tnStatisticsGroups 146 }

    tnOthOdukStatsTcmConfigScalarsGroup OBJECT-GROUP
        OBJECTS {
            tnOthOdukStatsTcmConfigAttributeTotal
        }
        STATUS         current
        DESCRIPTION    "."
        ::= { tnStatisticsGroups 147 }

    tnOthOdukStatsTcmConfigGroup OBJECT-GROUP
        OBJECTS {
            tnOthOdukStatsTcmConfigNumberOfBins,
            tnOthOdukStatsTcmConfigProfileId,
            tnOthOdukStatsTcmConfigClear,
            tnOthOdukStatsTcmConfigIntervalLength
        }
        STATUS         current
        DESCRIPTION    "."
        ::= { tnStatisticsGroups 148 }

    tnOthOdukStatsTcmEnableScalarsGroup OBJECT-GROUP
        OBJECTS {
            tnOthOdukStatsTcmEnableAttributeTotal
        }
        STATUS         current
        DESCRIPTION    "."
        ::= { tnStatisticsGroups 149 }

    tnOthOdukStatsTcmEnableGroup OBJECT-GROUP
        OBJECTS {
            tnOthOdukStatsTcmClearAll,
            tnOthOdukStatsTcmEnable
        }
        STATUS         current
        DESCRIPTION    "."
        ::= { tnStatisticsGroups 150 }

    tnStatsLanePwrsConfigScalarsGroup OBJECT-GROUP
        OBJECTS {
            tnStatsLanePwrsConfigAttributeTotal
        }
        STATUS         current
        DESCRIPTION    "."
        ::= { tnStatisticsGroups 151 }

    tnStatsLanePwrsConfigGroup OBJECT-GROUP
        OBJECTS {
            tnStatsLanePwrsConfigProfileId
        }
        STATUS         current
        DESCRIPTION    "."
        ::= { tnStatisticsGroups 152 }

    tnOthOdukStatsTcmScalarsGroup OBJECT-GROUP
        OBJECTS {
            tnOthOdukStatsTcmTotalMembers
        }
        STATUS         current
        DESCRIPTION    "."
        ::= { tnStatisticsGroups 153 }

    tnOthOdukStatsTcmGroup OBJECT-GROUP
        OBJECTS {
            tnOthOdukStatsTcmBinStatus,
            tnOthOdukStatsTcmStartTime,
            tnOthOdukStatsTcmNeRxBIP8ErrCnt,
            tnOthOdukStatsTcmNeRxIAESErrCnt,
            tnOthOdukStatsTcmNeRxES,
            tnOthOdukStatsTcmNeRxSES,
            tnOthOdukStatsTcmNeRxUAS,
            tnOthOdukStatsTcmFeRxBIP8ErrCnt,
            tnOthOdukStatsTcmFeRxBIAESErrCnt,
            tnOthOdukStatsTcmFeRxES,
            tnOthOdukStatsTcmFeRxSES,
            tnOthOdukStatsTcmFeRxUAS
        }
        STATUS         current
        DESCRIPTION    "."
        ::= { tnStatisticsGroups 154 }

    tnTcmStatsThresholdScalarsGroup OBJECT-GROUP
        OBJECTS {
            tnOthOdu0StatsTcmNeRxBIP8ErrCnt15MinTr,
            tnOthOdu0StatsTcmNeRxBIP8ErrCnt15MinRtr,
            tnOthOdu0StatsTcmNeRxBIP8ErrCnt1DayTr,
            tnOthOdu0StatsTcmFeRxBIP8ErrCnt15MinTr,
            tnOthOdu0StatsTcmFeRxBIP8ErrCnt15MinRtr,
            tnOthOdu0StatsTcmFeRxBIP8ErrCnt1DayTr,
            tnOthOdu1StatsTcmNeRxBIP8ErrCnt15MinTr,
            tnOthOdu1StatsTcmNeRxBIP8ErrCnt15MinRtr,
            tnOthOdu1StatsTcmNeRxBIP8ErrCnt1DayTr,
            tnOthOdu1StatsTcmFeRxBIP8ErrCnt15MinTr,
            tnOthOdu1StatsTcmFeRxBIP8ErrCnt15MinRtr,
            tnOthOdu1StatsTcmFeRxBIP8ErrCnt1DayTr,
            tnOthOdu2StatsTcmNeRxBIP8ErrCnt15MinTr,
            tnOthOdu2StatsTcmNeRxBIP8ErrCnt15MinRtr,
            tnOthOdu2StatsTcmNeRxBIP8ErrCnt1DayTr,
            tnOthOdu2StatsTcmFeRxBIP8ErrCnt15MinTr,
            tnOthOdu2StatsTcmFeRxBIP8ErrCnt15MinRtr,
            tnOthOdu2StatsTcmFeRxBIP8ErrCnt1DayTr,
            tnOthOdu3StatsTcmNeRxBIP8ErrCnt15MinTr,
            tnOthOdu3StatsTcmNeRxBIP8ErrCnt15MinRtr,
            tnOthOdu3StatsTcmNeRxBIP8ErrCnt1DayTr,
            tnOthOdu3StatsTcmFeRxBIP8ErrCnt15MinTr,
            tnOthOdu3StatsTcmFeRxBIP8ErrCnt15MinRtr,
            tnOthOdu3StatsTcmFeRxBIP8ErrCnt1DayTr,
            tnOthOdu4StatsTcmNeRxBIP8ErrCnt15MinTr,
            tnOthOdu4StatsTcmNeRxBIP8ErrCnt15MinRtr,
            tnOthOdu4StatsTcmNeRxBIP8ErrCnt1DayTr,
            tnOthOdu4StatsTcmFeRxBIP8ErrCnt15MinTr,
            tnOthOdu4StatsTcmFeRxBIP8ErrCnt15MinRtr,
            tnOthOdu4StatsTcmFeRxBIP8ErrCnt1DayTr,
            tnOthOdukStatsTcmNeRxES15MinTr,
            tnOthOdukStatsTcmNeRxES15MinRtr,
            tnOthOdukStatsTcmNeRxES1DayTr,
            tnOthOdukStatsTcmFeRxES15MinTr,
            tnOthOdukStatsTcmFeRxES15MinRtr,
            tnOthOdukStatsTcmFeRxES1DayTr,
            tnOthOdukStatsTcmNeRxSES15MinTr,
            tnOthOdukStatsTcmNeRxSES15MinRtr,
            tnOthOdukStatsTcmNeRxSES1DayTr,
            tnOthOdukStatsTcmFeRxSES15MinTr,
            tnOthOdukStatsTcmFeRxSES15MinRtr,
            tnOthOdukStatsTcmFeRxSES1DayTr,
            tnOthOdukStatsTcmNeRxUAS15MinTr,
            tnOthOdukStatsTcmNeRxUAS15MinRtr,
            tnOthOdukStatsTcmNeRxUAS1DayTr,
            tnOthOdukStatsTcmFeRxUAS15MinTr,
            tnOthOdukStatsTcmFeRxUAS15MinRtr,
            tnOthOdukStatsTcmFeRxUAS1DayTr,
            tnOthOduflexGFPStatsTcmNeRxBIP8ErrCnt15MinTr,
            tnOthOduflexGFPStatsTcmNeRxBIP8ErrCnt1DayTr,
            tnOthOduflexGFPStatsTcmFeRxBIP8ErrCnt15MinTr,
            tnOthOduflexGFPStatsTcmFeRxBIP8ErrCnt1DayTr,
            tnOthOduflexFC400StatsTcmNeRxBIP8ErrCnt15MinTr,
            tnOthOduflexFC400StatsTcmNeRxBIP8ErrCnt1DayTr,
            tnOthOduflexFC400StatsTcmFeRxBIP8ErrCnt15MinTr,
            tnOthOduflexFC400StatsTcmFeRxBIP8ErrCnt1DayTr,
            tnOthOduflexFC800StatsTcmNeRxBIP8ErrCnt15MinTr,
            tnOthOduflexFC800StatsTcmNeRxBIP8ErrCnt1DayTr,
            tnOthOduflexFC800StatsTcmFeRxBIP8ErrCnt15MinTr,
            tnOthOduflexFC800StatsTcmFeRxBIP8ErrCnt1DayTr,
            tnOthOduflexFC1600StatsTcmNeRxBIP8ErrCnt15MinTr,
            tnOthOduflexFC1600StatsTcmNeRxBIP8ErrCnt1DayTr,
            tnOthOduflexFC1600StatsTcmFeRxBIP8ErrCnt15MinTr,
            tnOthOduflexFC1600StatsTcmFeRxBIP8ErrCnt1DayTr,
            tnOthOduflexIBSDRStatsTcmNeRxBIP8ErrCnt15MinTr,
            tnOthOduflexIBSDRStatsTcmNeRxBIP8ErrCnt1DayTr,
            tnOthOduflexIBSDRStatsTcmFeRxBIP8ErrCnt15MinTr,
            tnOthOduflexIBSDRStatsTcmFeRxBIP8ErrCnt1DayTr,
            tnOthOduflexIBDDRStatsTcmNeRxBIP8ErrCnt15MinTr,
            tnOthOduflexIBDDRStatsTcmNeRxBIP8ErrCnt1DayTr,
            tnOthOduflexIBDDRStatsTcmFeRxBIP8ErrCnt15MinTr,
            tnOthOduflexIBDDRStatsTcmFeRxBIP8ErrCnt1DayTr,
            tnOthOduflexIBQDRStatsTcmNeRxBIP8ErrCnt15MinTr,
            tnOthOduflexIBQDRStatsTcmNeRxBIP8ErrCnt1DayTr,
            tnOthOduflexIBQDRStatsTcmFeRxBIP8ErrCnt15MinTr,
            tnOthOduflexIBQDRStatsTcmFeRxBIP8ErrCnt1DayTr,
            tnOthOduflex3GSDI18StatsTcmNeRxBIP8ErrCnt15MinTr,
            tnOthOduflex3GSDI18StatsTcmNeRxBIP8ErrCnt1DayTr,
            tnOthOduflex3GSDI18StatsTcmFeRxBIP8ErrCnt15MinTr,
            tnOthOduflex3GSDI18StatsTcmFeRxBIP8ErrCnt1DayTr,
            tnOthOduflex3GSDI19StatsTcmNeRxBIP8ErrCnt15MinTr,
            tnOthOduflex3GSDI19StatsTcmNeRxBIP8ErrCnt1DayTr,
            tnOthOduflex3GSDI19StatsTcmFeRxBIP8ErrCnt15MinTr,
            tnOthOduflex3GSDI19StatsTcmFeRxBIP8ErrCnt1DayTr,
            tnOthOduflexGFPStatsTcmFeRxBIP8ErrCnt15MinRtr,
            tnOthOduflexGFPStatsTcmNeRxBIP8ErrCnt15MinRtr,
            tnOthOduflexFC400StatsTcmFeRxBIP8ErrCnt15MinRtr,
            tnOthOduflexFC400StatsTcmNeRxBIP8ErrCnt15MinRtr,
            tnOthOduflexFC800StatsTcmFeRxBIP8ErrCnt15MinRtr,
            tnOthOduflexFC800StatsTcmNeRxBIP8ErrCnt15MinRtr,
            tnOthOduflexFC1600StatsTcmFeRxBIP8ErrCnt15MinRtr,
            tnOthOduflexFC1600StatsTcmNeRxBIP8ErrCnt15MinRtr,
            tnOthOduflexIBSDRStatsTcmFeRxBIP8ErrCnt15MinRtr,
            tnOthOduflexIBSDRStatsTcmNeRxBIP8ErrCnt15MinRtr,
            tnOthOduflexIBDDRStatsTcmFeRxBIP8ErrCnt15MinRtr,
            tnOthOduflexIBDDRStatsTcmNeRxBIP8ErrCnt15MinRtr,
            tnOthOduflexIBQDRStatsTcmFeRxBIP8ErrCnt15MinRtr,
            tnOthOduflexIBQDRStatsTcmNeRxBIP8ErrCnt15MinRtr,
            tnOthOduflex3GSDI18StatsTcmFeRxBIP8ErrCnt15MinRtr,
            tnOthOduflex3GSDI18StatsTcmNeRxBIP8ErrCnt15MinRtr,
            tnOthOduflex3GSDI19StatsTcmFeRxBIP8ErrCnt15MinRtr,
            tnOthOduflex3GSDI19StatsTcmNeRxBIP8ErrCnt15MinRtr,
            tnOthOducStatsTcmNeRxBIP8ErrCnt15MinTr,
            tnOthOducStatsTcmNeRxBIP8ErrCnt15MinRtr,
            tnOthOducStatsTcmNeRxBIP8ErrCnt1DayTr,
            tnOthOducStatsTcmFeRxBIP8ErrCnt15MinTr,
            tnOthOducStatsTcmFeRxBIP8ErrCnt15MinRtr,
            tnOthOducStatsTcmFeRxBIP8ErrCnt1DayTr,
            tnOthOduflex400GBEStatsTcmNeRxBIP8ErrCnt15MinTr,
            tnOthOduflex400GBEStatsTcmNeRxBIP8ErrCnt15MinRtr,
            tnOthOduflex400GBEStatsTcmNeRxBIP8ErrCnt1DayTr,
            tnOthOduflex400GBEStatsTcmFeRxBIP8ErrCnt15MinTr,
            tnOthOduflex400GBEStatsTcmFeRxBIP8ErrCnt15MinRtr,
            tnOthOduflex400GBEStatsTcmFeRxBIP8ErrCnt1DayTr
        }
        STATUS         current
        DESCRIPTION    "."
        ::= { tnStatisticsGroups 155 }

    tnOpticalLaneStatPowerScalarsGroup OBJECT-GROUP
        OBJECTS {
            tnOprLaneStatMaxPowerTr,
            tnOprLaneStatMinPowerTr,
            tnOptLaneStatMaxPowerTr,
            tnOptLaneStatMinPowerTr
        }
        STATUS         current
        DESCRIPTION    "."
        ::= { tnStatisticsGroups 156 }

    tnTcmRawCountStatsScalarsGroup OBJECT-GROUP
        OBJECTS {
            tnOthOdukTcmRawCountStatsTotalMembers
        }
        STATUS         current
        DESCRIPTION    "."
        ::= { tnStatisticsGroups 157 }

    tnTcmRawCountStatsGroup OBJECT-GROUP
        OBJECTS {
            tnOthOdukTcmRawCountStatsClear,
            tnOthOdukTcmRawCountStatsNeRxBIP8ErrCnt,
            tnOthOdukTcmRawCountStatsNeRxIAESErrCnt,
            tnOthOdukTcmRawCountStatsNeRxES,
            tnOthOdukTcmRawCountStatsNeRxSES,
            tnOthOdukTcmRawCountStatsNeRxUAS,
            tnOthOdukTcmRawCountStatsFeRxBIP8ErrCnt,
            tnOthOdukTcmRawCountStatsFeRxBIAESErrCnt,
            tnOthOdukTcmRawCountStatsFeRxES,
            tnOthOdukTcmRawCountStatsFeRxSES,
            tnOthOdukTcmRawCountStatsFeRxUAS,
            tnOthOdukTcmRawCountStatsStartTime
        }
        STATUS         current
        DESCRIPTION    "."
        ::= { tnStatisticsGroups 158 }

    tnEncryptionFailToDecryptScalarsGroup OBJECT-GROUP
        OBJECTS {
            tnEncryptRxFailToDecryptCnt15MinTr,
            tnEncryptRxFailToDecryptCnt15MinRtr,
            tnEncryptRxFailToDecryptCnt1DayTr,
            tnEncryptRxFailToDecryptCnt1DayRtr
        }
        STATUS         current
        DESCRIPTION    "."
        ::= { tnStatisticsGroups 159 }

    tnFECPMStatsScalarsGroup OBJECT-GROUP
        OBJECTS {
            tnFECPMStatsTotalMembers
        }
        STATUS         current
        DESCRIPTION    "."
        ::= { tnStatisticsGroups 160 }

    tnFECPMStatsGroup OBJECT-GROUP
        OBJECTS {
            tnFECPMStatsBinStatus,
            tnFECPMStatsStartTime,
            tnFECPMStatRxRsCorrCnt,
            tnFECPMStatRxRsUncorrCnt,
            tnFECPMStatRxBERPreFEC,  -- deprecated
            tnFECPMStatRxBERPostFEC,
            tnFECPMStatRxSUS
        }
        STATUS         current
        DESCRIPTION    "."
        ::= { tnStatisticsGroups 161 }

    tnFECPMStatsThresholdScalarsGroup OBJECT-GROUP
        OBJECTS {
            tnFECPMOtu1StatRxRsCorrCnt15MinTr,
            tnFECPMOtu1StatRxRsCorrCnt15MinRtr,
            tnFECPMOtu1StatRxRsCorrCnt1DayTr,
            tnFECPMOtu1StatRxRsUncorrCnt15MinTr,
            tnFECPMOtu1StatRxRsUncorrCnt15MinRtr,
            tnFECPMOtu1StatRxRsUncorrCnt1DayTr,
            tnFECPMOtu2StatRxRsCorrCnt15MinTr,
            tnFECPMOtu2StatRxRsCorrCnt15MinRtr,
            tnFECPMOtu2StatRxRsCorrCnt1DayTr,
            tnFECPMOtu2StatRxRsUncorrCnt15MinTr,
            tnFECPMOtu2StatRxRsUncorrCnt15MinRtr,
            tnFECPMOtu2StatRxRsUncorrCnt1DayTr,
            tnFECPMOtu3StatRxRsCorrCnt15MinTr,
            tnFECPMOtu3StatRxRsCorrCnt15MinRtr,
            tnFECPMOtu3StatRxRsCorrCnt1DayTr,
            tnFECPMOtu3StatRxRsUncorrCnt15MinTr,
            tnFECPMOtu3StatRxRsUncorrCnt15MinRtr,
            tnFECPMOtu3StatRxRsUncorrCnt1DayTr,
            tnFECPMOtu4StatRxRsCorrCnt15MinTr,
            tnFECPMOtu4StatRxRsCorrCnt15MinRtr,
            tnFECPMOtu4StatRxRsCorrCnt1DayTr,
            tnFECPMOtu4StatRxRsUncorrCnt15MinTr,
            tnFECPMOtu4StatRxRsUncorrCnt15MinRtr,
            tnFECPMOtu4StatRxRsUncorrCnt1DayTr,
            tnFECPMOtuStatRxBERPreFEC15MinTr,
            tnFECPMOtuStatRxBERPreFEC15MinRtr,
            tnFECPMOtuStatRxBERPreFEC1DayTr,
            tnFECPMOtuStatRxBERPostFEC15MinTr,
            tnFECPMOtuStatRxBERPostFEC15MinRtr,
            tnFECPMOtuStatRxBERPostFEC1DayTr,
            tnSDFECPMRxBERPreFEC15MinTr,
            tnSDFECPMRxBERPreFEC15MinRtr,
            tnSDFECPMRxBERPreFEC1DayTr,
            tnFECPMRSFECRxBERPreFEC15MinTr,
            tnFECPMRSFECRxBERPreFEC15MinRtr,
            tnFECPMRSFECRxBERPreFEC1DayTr
        }
        STATUS         current
        DESCRIPTION    "."
        ::= { tnStatisticsGroups 162 }

    tnFECPMRawCountStatsScalarsGroup OBJECT-GROUP
        OBJECTS {
            tnFECPMRawCountStatsTotalMembers
        }
        STATUS         current
        DESCRIPTION    "."
        ::= { tnStatisticsGroups 163 }

    tnFECPMRawCountStatsGroup OBJECT-GROUP
        OBJECTS {
            tnFECPMRawCountStatsClear,
            tnFECPMRawCountStatsStartTime,
            tnFECPMRawCountStatRxRsCorrCnt,
            tnFECPMRawCountStatRxRsUncorrCnt,
            tnFECPMRawCountStatRxBERPreFEC,
            tnFECPMRawCountStatRxBERPostFEC
        }
        STATUS         current
        DESCRIPTION    "."
        ::= { tnStatisticsGroups 164 }

    tnOtuStatsPortIntervalGroup OBJECT-GROUP
        OBJECTS {
            tnOtuStatsPortNumberOfIntervals
        }
        STATUS         current
        DESCRIPTION    "."
        ::= { tnStatisticsGroups 165 }

    tnOtuStatsPortGroup OBJECT-GROUP
        OBJECTS {
            tnOtuStatsPortIntervalLength,
            tnOtuStatsPortNumberOfBins,
            tnOtuStatsPortProfileId,
            tnOtuStatsPortClear,
            tnOtuStatsPortIntervalLength1day,
            tnOtuStatsPortNumberOfBins1day,
            tnOtuStatsPortProfileId1day,
            tnOtuStatsPortEnable
        }
        STATUS         current
        DESCRIPTION    "."
        ::= { tnStatisticsGroups 166 }

    tnpreFECBERStatsScalarsGroup OBJECT-GROUP
        OBJECTS {
            tnpreFECBERStatsTotalMembers
        }
        STATUS         current
        DESCRIPTION    "."
        ::= { tnStatisticsGroups 167 }

    tnpreFECBERStatsGroup OBJECT-GROUP
        OBJECTS {
            tnpreFECBERStatsBinStatus,
            tnpreFECBERStatsStartTime,
            tnpreFECBERStatRxBERPreFEC
        }
        STATUS         current
        DESCRIPTION    "."
        ::= { tnStatisticsGroups 168 }

    tnStatisticspreFECBERScalarsGroup OBJECT-GROUP
        OBJECTS {
            tnRxBERPreFEC15MinTr,
            tnRxBERPreFEC15MinRtr,
            tnRxBERPreFEC1DayTr,
            tnSDFECRxBERPreFEC15MinTr,
            tnSDFECRxBERPreFEC15MinRtr,
            tnSDFECRxBERPreFEC1DayTr
        }
        STATUS         current
        DESCRIPTION    "."
        ::= { tnStatisticsGroups 169 }

    tnpreFECBERRawCountStatsScalarsGroup OBJECT-GROUP
        OBJECTS {
            tnpreFECBERRawCountStatsTotalMembers
        }
        STATUS         current
        DESCRIPTION    "."
        ::= { tnStatisticsGroups 170 }

    tnpreFECBERRawCountStatsGroup OBJECT-GROUP
        OBJECTS {
            tnpreFECBERRawCountStatsClear,
            tnpreFECBERRawCountStatsStartTime,
            tnpreFECBERRawCountStatRxBERPreFEC
        }
        STATUS         current
        DESCRIPTION    "."
        ::= { tnStatisticsGroups 171 }

    tnStatisticsStreamingPMScalarsGroup OBJECT-GROUP
        OBJECTS {
            tnOpticalReceivePowerInterval,
            tnOpticalTransmitPowerInterval,
            tnCDRCollectInterval,
            tnDGDCollectInterval,
            tnPreFecBerCollectInterval,
            tnPostFecBerCollectInterval,
            tnPCSESCollectInterval
        }
        STATUS         current
        DESCRIPTION    "."
        ::= { tnStatisticsGroups 172 }

    tnStreamingPmThresholdScalarsGroup OBJECT-GROUP
        OBJECTS {
            tnStreamingPmThresholdAttributeTotal
        }
        STATUS         current
        DESCRIPTION    "."
        ::= { tnStatisticsGroups 173 }

    tnStreamingPmThresholdGroup OBJECT-GROUP
        OBJECTS {
          tnStreamingPmOPRThreshold,
          tnStreamingPmOPTThreshold,
          tnStreamingPmCDRDeltaThreshold,
          tnStreamingPmDGDDeltaThreshold,
          tnStreamingPmPreFecBerDeltaThreshold,
          tnStreamingPmPostFecBerDeltaThreshold,
          tnStreamingPmPCSESDeltaThreshold
        }
        STATUS         current
        DESCRIPTION    "."
        ::= { tnStatisticsGroups 174 }

    tnOpInCRawCountStatsScalarsGroup OBJECT-GROUP
        OBJECTS {
            tnOpInCRawCountStatsTotalMembers
        }
        STATUS         current
        DESCRIPTION    "."
        ::= { tnStatisticsGroups 175 }

    tnOpInCRawCountStatsGroup OBJECT-GROUP
        OBJECTS {
            tnOpInCRawCountStatsClear,
            tnOpInCRawCountStatMinPower,
            tnOpInCRawCountStatMaxPower,
            tnOpInCRawCountStatAveragePower,
            tnOpInCRawCountStatStartTime
        }
        STATUS         current
        DESCRIPTION    "."
        ::= { tnStatisticsGroups 176 }

    tnOpOutCRawCountStatsScalarsGroup OBJECT-GROUP
        OBJECTS {
            tnOpOutCRawCountStatsTotalMembers
        }
        STATUS         current
        DESCRIPTION    "."
        ::= { tnStatisticsGroups 177 }

    tnOpOutCRawCountStatsGroup OBJECT-GROUP
        OBJECTS {
            tnOpOutCRawCountStatsClear,
            tnOpOutCRawCountStatMinPower,
            tnOpOutCRawCountStatMaxPower,
            tnOpOutCRawCountStatAveragePower,
            tnOpOutCRawCountStatStartTime
        }
        STATUS         current
        DESCRIPTION    "."
        ::= { tnStatisticsGroups 178 }

    tnOpOutCStatsScalarsGroup OBJECT-GROUP
        OBJECTS {
            tnOpOutCStatsTotalMembers
        }
        STATUS         current
        DESCRIPTION    "."
        ::= { tnStatisticsGroups 179 }

    tnOpOutCStatsGroup OBJECT-GROUP
        OBJECTS {
            tnOpOutCStatsBinStatus,
            tnOpOutCStatsStartTime,
            tnOpOutCStatMinPower,
            tnOpOutCStatMaxPower,
            tnOpOutCStatAveragePower
        }
        STATUS         current
        DESCRIPTION    "."
        ::= { tnStatisticsGroups 180 }

    tnOpInCStatsScalarsGroup OBJECT-GROUP
        OBJECTS {
            tnOpInCStatsTotalMembers
        }
        STATUS         current
        DESCRIPTION    "."
        ::= { tnStatisticsGroups 181 }

    tnOpInCStatsGroup OBJECT-GROUP
        OBJECTS {
            tnOpInCStatsBinStatus,
            tnOpInCStatsStartTime,
            tnOpInCStatMinPower,
            tnOpInCStatMaxPower,
            tnOpInCStatAveragePower
        }
        STATUS         current
        DESCRIPTION    "."
        ::= { tnStatisticsGroups 182 }

    tnOpInLRawCountStatsScalarsGroup OBJECT-GROUP
        OBJECTS {
            tnOpInLRawCountStatsTotalMembers
        }
        STATUS         current
        DESCRIPTION    "."
        ::= { tnStatisticsGroups 183 }

    tnOpInLRawCountStatsGroup OBJECT-GROUP
        OBJECTS {
            tnOpInLRawCountStatsClear,
            tnOpInLRawCountStatMinPower,
            tnOpInLRawCountStatMaxPower,
            tnOpInLRawCountStatAveragePower,
            tnOpInLRawCountStatStartTime
        }
        STATUS         current
        DESCRIPTION    "."
        ::= { tnStatisticsGroups 184 }

    tnOpOutLRawCountStatsScalarsGroup OBJECT-GROUP
        OBJECTS {
            tnOpOutLRawCountStatsTotalMembers
        }
        STATUS         current
        DESCRIPTION    "."
        ::= { tnStatisticsGroups 185 }

    tnOpOutLRawCountStatsGroup OBJECT-GROUP
        OBJECTS {
            tnOpOutLRawCountStatsClear,
            tnOpOutLRawCountStatMinPower,
            tnOpOutLRawCountStatMaxPower,
            tnOpOutLRawCountStatAveragePower,
            tnOpOutLRawCountStatStartTime
        }
        STATUS         current
        DESCRIPTION    "."
        ::= { tnStatisticsGroups 186 }


    tnOpOutLStatsScalarsGroup OBJECT-GROUP
        OBJECTS {
            tnOpOutLStatsTotalMembers
        }
        STATUS         current
        DESCRIPTION    "."
        ::= { tnStatisticsGroups 187 }

    tnOpOutLStatsGroup OBJECT-GROUP
        OBJECTS {
            tnOpOutLStatsBinStatus,
            tnOpOutLStatsStartTime,
            tnOpOutLStatMinPower,
            tnOpOutLStatMaxPower,
            tnOpOutLStatAveragePower
        }
        STATUS         current
        DESCRIPTION    "."
        ::= { tnStatisticsGroups 188 }

    tnOpInLStatsScalarsGroup OBJECT-GROUP
        OBJECTS {
            tnOpInLStatsTotalMembers
        }
        STATUS         current
        DESCRIPTION    "."
        ::= { tnStatisticsGroups 189 }

    tnOpInLStatsGroup OBJECT-GROUP
        OBJECTS {
            tnOpInLStatsBinStatus,
            tnOpInLStatsStartTime,
            tnOpInLStatMinPower,
            tnOpInLStatMaxPower,
            tnOpInLStatAveragePower
        }
        STATUS         current
        DESCRIPTION    "."
        ::= { tnStatisticsGroups 190 }

    tnETHFECPMStatsScalarsGroup OBJECT-GROUP
        OBJECTS {
            tnFECPMStatsTotalMembers
        }
        STATUS         current
        DESCRIPTION    "."
        ::= { tnStatisticsGroups 191 }

    tnETHFECPMStatsGroup OBJECT-GROUP
        OBJECTS {
            tnETHFECPMStatsBinStatus,
            tnETHFECPMStatsStartTime,
--            obsolete
--            tnETHPHYFECPMStatRxRsCorrCnt,
--            tnETHPHYFECPMStatRxRsUncorrCnt,
            tnETHFECPMStatRxRsCorrCnt,
            tnETHFECPMStatRxRsUncorrCnt,
            tnETHFECPMStatRxBERpreFEC,
            tnETHFECPMStatRxBERPostFEC,
            tnETHFECPMStatBERpreFECCnt
        }
        STATUS         current
        DESCRIPTION    "."
        ::= { tnStatisticsGroups 192 }

    tnETHFECPMRawCountStatsScalarsGroup OBJECT-GROUP
        OBJECTS {
            tnETHFECPMRawCountStatsTotalMembers
        }
        STATUS         current
        DESCRIPTION    "."
        ::= { tnStatisticsGroups 193 }

    tnETHFECPMRawCountStatsGroup OBJECT-GROUP
        OBJECTS {
            tnETHFECPMRawCountStatsClear,
            tnETHFECPMRawCountStatsStartTime,
            tnETHFECPMRawCountStatRxRsCorrCnt,
            tnETHFECPMRawCountStatRxRsUncorrCnt,
            tnETHFECPMRawCountStatRxBERpreFEC,
            tnETHFECPMRawCountStatRxBERPostFEC
        }
        STATUS         current
        DESCRIPTION    "."
        ::= { tnStatisticsGroups 194 }

    tnSyncEStatsScalarsGroup OBJECT-GROUP
        OBJECTS {
            tnSyncEStatsTotalMembers
        }
        STATUS         current
        DESCRIPTION    "."
        ::= { tnStatisticsGroups 195 }

    tnSyncEStatsGroup OBJECT-GROUP
        OBJECTS {
            tnSyncEStatsBinStatus,
            tnSyncEStatsStartTime,
            tnSyncEStatsOffsetMin,
            tnSyncEStatsOffsetMax,
            tnSyncEStatsOffsetAverage
        }
        STATUS         current
        DESCRIPTION    "."
        ::= { tnStatisticsGroups 196 }

    tnSyncERawCountStatsScalarsGroup OBJECT-GROUP
        OBJECTS {
            tnSyncERawCountStatsTotalMembers
        }
        STATUS         current
        DESCRIPTION    "."
        ::= { tnStatisticsGroups 197 }

    tnSyncERawCountStatsGroup OBJECT-GROUP
        OBJECTS {
            tnSyncERawCountStatsClear,
            tnSyncERawCountStatsStartTime,
            tnSyncERawCountStatsOffsetMin,
            tnSyncERawCountStatsOffsetMax,
            tnSyncERawCountStatsOffsetAverage
        }
        STATUS         current
        DESCRIPTION    "."
        ::= { tnStatisticsGroups 198 }

    tnSyncEStatsConfigScalarsGroup OBJECT-GROUP
        OBJECTS {
            tnSyncEStatsConfigAttributeTotal
        }
        STATUS         current
        DESCRIPTION    "."
        ::= { tnStatisticsGroups 199 }

    tnSyncEStatsConfigGroup OBJECT-GROUP
        OBJECTS {
            tnSyncEStatsNumberofBins,
            tnSyncEStatsProfileid,
            tnSyncEStatsClear,
            tnSyncEStatsIntervalLength,
            tnSyncEStatsEnable
        }
        STATUS         current
        DESCRIPTION    "."
        ::= { tnStatisticsGroups 200 }

    tnSyncEStatsOffsetScalarsGroup OBJECT-GROUP
        OBJECTS {
            tnSyncEStatsOffsetMinTr,
            tnSyncEStatsOffsetMaxTr,
            tnSyncEStatsOffsetAverageTr,
            tnSyncEStatsOffsetMin15MinTr,
            tnSyncEStatsOffsetMin15MinRtr,
            tnSyncEStatsOffsetMin1DayTr,
            tnSyncEStatsOffsetMin1DayRtr,
            tnSyncEStatsOffsetMax15MinTr,
            tnSyncEStatsOffsetMax15MinRtr,
            tnSyncEStatsOffsetMax1DayTr,
            tnSyncEStatsOffsetMax1DayRtr
        }
        STATUS         current
        DESCRIPTION    "."
        ::= { tnStatisticsGroups 201 }

    tnSyncStatsScalarsGroup OBJECT-GROUP
        OBJECTS {
            tnSyncStatsTotalMembers
        }
        STATUS         current
        DESCRIPTION    "."
        ::= { tnStatisticsGroups 202 }

    tnSyncStatsGroup OBJECT-GROUP
        OBJECTS {
            tnSyncStatsBinStatus,
            tnSyncStatsStartTime,
            tnSyncStatsOffsetMin,
            tnSyncStatsOffsetMax,
            tnSyncStatsOffsetAverage
        }
        STATUS         current
        DESCRIPTION    "."
        ::= { tnStatisticsGroups 203 }

    tnSyncRawCountStatsScalarsGroup OBJECT-GROUP
        OBJECTS {
            tnSyncRawCountStatsTotalMembers
        }
        STATUS         current
        DESCRIPTION    "."
        ::= { tnStatisticsGroups 204 }

    tnSyncRawCountStatsGroup OBJECT-GROUP
        OBJECTS {
            tnSyncRawCountStatsClear,
            tnSyncRawCountStatsStartTime,
            tnSyncRawCountStatsOffsetMin,
            tnSyncRawCountStatsOffsetMax,
            tnSyncRawCountStatsOffsetAverage
        }
        STATUS         current
        DESCRIPTION    "."
        ::= { tnStatisticsGroups 205 }

    tnSyncStatsConfigScalarsGroup OBJECT-GROUP
        OBJECTS {
            tnSyncStatsConfigAttributeTotal
        }
        STATUS         current
        DESCRIPTION    "."
        ::= { tnStatisticsGroups 206 }

    tnSyncStatsConfigGroup OBJECT-GROUP
        OBJECTS {
            tnSyncStatsNumberofBins,
            tnSyncStatsProfileid,
            tnSyncStatsClear,
            tnSyncStatsIntervalLength,
            tnSyncStatsEnable
        }
        STATUS         current
        DESCRIPTION    "."
        ::= { tnStatisticsGroups 207 }

    tnPTOFFScalarsGroup OBJECT-GROUP
        OBJECTS {
            tnPTOFFTotalMembers
        }
        STATUS         current
        DESCRIPTION    "."
        ::= { tnStatisticsGroups 208 }

    tnPTOFFGroup OBJECT-GROUP
        OBJECTS {
            tnPTOFFBinStatus,
            tnPTOFFStartTime,
            tnPTOFFMin,
            tnPTOFFMax,
            tnPTOFFAverage,
            tnPTOFFMin15MinTr,
            tnPTOFFMin15MinRtr,
            tnPTOFFMin1DayTr,
            tnPTOFFMax15MinTr,
            tnPTOFFMax15MinRtr,
            tnPTOFFMax1DayTr
        }
        STATUS         current
        DESCRIPTION    "."
        ::= { tnStatisticsGroups 209 }

    tnPTOFFRawCountScalarsGroup OBJECT-GROUP
        OBJECTS {
            tnPTOFFRawCountTotalMembers
        }
        STATUS         current
        DESCRIPTION    "."
        ::= { tnStatisticsGroups 210 }

    tnPTOFFRawCountGroup OBJECT-GROUP
        OBJECTS {
            tnPTOFFRawCountClear,
            tnPTOFFRawCountMin,
            tnPTOFFRawCountMax,
            tnPTOFFRawCountAverage,
            tnPTOFFRawCountStartTime
        }
        STATUS         current
        DESCRIPTION    "."
        ::= { tnStatisticsGroups 211 }

    tnPTOFFStatsConfigScalarsGroup OBJECT-GROUP
        OBJECTS {
            tnPTOFFStatsConfigAttributeTotal
        }
        STATUS         current
        DESCRIPTION    "."
        ::= { tnStatisticsGroups 212 }

    tnPTOFFStatsConfigGroup OBJECT-GROUP
        OBJECTS {
            tnPTOFFStatsNumberofBins,
            tnPTOFFStatsProfileid,
            tnPTOFFStatsClear,
            tnPTOFFStatsIntervalLength,
            tnPTOFFStatsEnable
        }
        STATUS         current
        DESCRIPTION    "."
        ::= { tnStatisticsGroups 213 }

    tnPTMSDLYScalarsGroup OBJECT-GROUP
        OBJECTS {
            tnPTMSDLYTotalMembers
        }
        STATUS         current
        DESCRIPTION    "."
        ::= { tnStatisticsGroups 214 }

    tnPTMSDLYGroup OBJECT-GROUP
        OBJECTS {
            tnPTMSDLYBinStatus,
            tnPTMSDLYStartTime,
            tnPTMSDLYMin,
            tnPTMSDLYMax,
            tnPTMSDLYAverage,
            tnPTMSDLYMin15MinTr,
            tnPTMSDLYMin15MinRtr,
            tnPTMSDLYMin1DayTr,
            tnPTMSDLYMax15MinTr,
            tnPTMSDLYMax15MinRtr,
            tnPTMSDLYMax1DayTr
        }
        STATUS         current
        DESCRIPTION    "."
        ::= { tnStatisticsGroups 215 }

    tnPTMSDLYRawCountScalarsGroup OBJECT-GROUP
        OBJECTS {
            tnPTMSDLYRawCountTotalMembers
        }
        STATUS         current
        DESCRIPTION    "."
        ::= { tnStatisticsGroups 216 }

    tnPTMSDLYRawCountGroup OBJECT-GROUP
        OBJECTS {
            tnPTMSDLYRawCountClear,
            tnPTMSDLYRawCountMin,
            tnPTMSDLYRawCountMax,
            tnPTMSDLYRawCountAverage,
            tnPTMSDLYRawCountStartTime
        }
        STATUS         current
        DESCRIPTION    "."
        ::= { tnStatisticsGroups 217 }

    tnPTMSDLYStatsConfigScalarsGroup OBJECT-GROUP
        OBJECTS {
            tnPTMSDLYStatsConfigAttributeTotal
        }
        STATUS         current
        DESCRIPTION    "."
        ::= { tnStatisticsGroups 218 }

    tnPTMSDLYStatsConfigGroup OBJECT-GROUP
        OBJECTS {
            tnPTMSDLYStatsNumberofBins,
            tnPTMSDLYStatsProfileid,
            tnPTMSDLYStatsClear,
            tnPTMSDLYStatsIntervalLength,
            tnPTMSDLYStatsEnable
        }
        STATUS         current
        DESCRIPTION    "."
        ::= { tnStatisticsGroups 219 }

    tnPTSMDLYScalarsGroup OBJECT-GROUP
        OBJECTS {
            tnPTSMDLYTotalMembers
        }
        STATUS         current
        DESCRIPTION    "."
        ::= { tnStatisticsGroups 220 }

    tnPTSMDLYGroup OBJECT-GROUP
        OBJECTS {
            tnPTSMDLYBinStatus,
            tnPTSMDLYStartTime,
            tnPTSMDLYMin,
            tnPTSMDLYMax,
            tnPTSMDLYAverage,
            tnPTSMDLYMin15MinTr,
            tnPTSMDLYMin15MinRtr,
            tnPTSMDLYMin1DayTr,
            tnPTSMDLYMax15MinTr,
            tnPTSMDLYMax15MinRtr,
            tnPTSMDLYMax1DayTr
        }
        STATUS         current
        DESCRIPTION    "."
        ::= { tnStatisticsGroups 221 }

    tnPTSMDLYRawCountScalarsGroup OBJECT-GROUP
        OBJECTS {
            tnPTSMDLYRawCountTotalMembers
        }
        STATUS         current
        DESCRIPTION    "."
        ::= { tnStatisticsGroups 222 }

    tnPTSMDLYRawCountGroup OBJECT-GROUP
        OBJECTS {
            tnPTSMDLYRawCountClear,
            tnPTSMDLYRawCountMin,
            tnPTSMDLYRawCountMax,
            tnPTSMDLYRawCountAverage,
            tnPTSMDLYRawCountStartTime
        }
        STATUS         current
        DESCRIPTION    "."
        ::= { tnStatisticsGroups 223 }

    tnPTSMDLYStatsConfigScalarsGroup OBJECT-GROUP
        OBJECTS {
            tnPTSMDLYStatsConfigAttributeTotal
        }
        STATUS         current
        DESCRIPTION    "."
        ::= { tnStatisticsGroups 224 }

    tnPTSMDLYStatsConfigGroup OBJECT-GROUP
        OBJECTS {
            tnPTSMDLYStatsNumberofBins,
            tnPTSMDLYStatsProfileid,
            tnPTSMDLYStatsClear,
            tnPTSMDLYStatsIntervalLength,
            tnPTSMDLYStatsEnable
        }
        STATUS         current
        DESCRIPTION    "."
        ::= { tnStatisticsGroups 225 }

    tnPTMPDLYScalarsGroup OBJECT-GROUP
        OBJECTS {
            tnPTMPDLYTotalMembers
        }
        STATUS         current
        DESCRIPTION    "."
        ::= { tnStatisticsGroups 226 }

    tnPTMPDLYGroup OBJECT-GROUP
        OBJECTS {
            tnPTMPDLYBinStatus,
            tnPTMPDLYStartTime,
            tnPTMPDLYMin,
            tnPTMPDLYMax,
            tnPTMPDLYAverage,
            tnPTMPDLYMin15MinTr,
            tnPTMPDLYMin15MinRtr,
            tnPTMPDLYMin1DayTr,
            tnPTMPDLYMax15MinTr,
            tnPTMPDLYMax15MinRtr,
            tnPTMPDLYMax1DayTr
        }
        STATUS         current
        DESCRIPTION    "."
        ::= { tnStatisticsGroups 227 }

    tnPTMPDLYRawCountScalarsGroup OBJECT-GROUP
        OBJECTS {
            tnPTMPDLYRawCountTotalMembers
        }
        STATUS         current
        DESCRIPTION    "."
        ::= { tnStatisticsGroups 228 }

    tnPTMPDLYRawCountGroup OBJECT-GROUP
        OBJECTS {
            tnPTMPDLYRawCountClear,
            tnPTMPDLYRawCountMin,
            tnPTMPDLYRawCountMax,
            tnPTMPDLYRawCountAverage,
            tnPTMPDLYRawCountStartTime
        }
        STATUS         current
        DESCRIPTION    "."
        ::= { tnStatisticsGroups 229 }

    tnPTMPDLYStatsConfigScalarsGroup OBJECT-GROUP
        OBJECTS {
            tnPTMPDLYStatsConfigAttributeTotal
        }
        STATUS         current
        DESCRIPTION    "."
        ::= { tnStatisticsGroups 230 }

    tnPTMPDLYStatsConfigGroup OBJECT-GROUP
        OBJECTS {
            tnPTMPDLYStatsNumberofBins,
            tnPTMPDLYStatsProfileid,
            tnPTMPDLYStatsClear,
            tnPTMPDLYStatsIntervalLength,
            tnPTMPDLYStatsEnable
        }
        STATUS         current
        DESCRIPTION    "."
        ::= { tnStatisticsGroups 231 }

    tnPTERREFScalarsGroup OBJECT-GROUP
        OBJECTS {
            tnPTERREFTotalMembers
        }
        STATUS         current
        DESCRIPTION    "."
        ::= { tnStatisticsGroups 232 }

    tnPTERREFGroup OBJECT-GROUP
        OBJECTS {
            tnPTERREFBinStatus,
            tnPTERREFStartTime,
            tnPTERREFMin,
            tnPTERREFMax,
            tnPTERREFAverage,
            tnPTERREFMin15MinTr,
            tnPTERREFMin15MinRtr,
            tnPTERREFMin1DayTr,
            tnPTERREFMax15MinTr,
            tnPTERREFMax15MinRtr,
            tnPTERREFMax1DayTr
        }
        STATUS         current
        DESCRIPTION    "."
        ::= { tnStatisticsGroups 233 }

    tnPTERREFRawCountScalarsGroup OBJECT-GROUP
        OBJECTS {
            tnPTERREFRawCountTotalMembers
        }
        STATUS         current
        DESCRIPTION    "."
        ::= { tnStatisticsGroups 234 }

    tnPTERREFRawCountGroup OBJECT-GROUP
        OBJECTS {
            tnPTERREFRawCountClear,
            tnPTERREFRawCountMin,
            tnPTERREFRawCountMax,
            tnPTERREFRawCountAverage,
            tnPTERREFRawCountStartTime
        }
        STATUS         current
        DESCRIPTION    "."
        ::= { tnStatisticsGroups 235 }

    tnPTERREFStatsConfigScalarsGroup OBJECT-GROUP
        OBJECTS {
            tnPTERREFStatsConfigAttributeTotal
        }
        STATUS         current
        DESCRIPTION    "."
        ::= { tnStatisticsGroups 236 }

    tnPTERREFStatsConfigGroup OBJECT-GROUP
        OBJECTS {
            tnPTERREFStatsNumberofBins,
            tnPTERREFStatsProfileid,
            tnPTERREFStatsClear,
            tnPTERREFStatsIntervalLength,
            tnPTERREFStatsEnable
        }
        STATUS         current
        DESCRIPTION    "."
        ::= { tnStatisticsGroups 237 }

    tnPTOFFACUMScalarsGroup OBJECT-GROUP
        OBJECTS {
            tnPTOFFACUMTotalMembers
        }
        STATUS         current
        DESCRIPTION    "."
        ::= { tnStatisticsGroups 238 }

    tnPTOFFACUMGroup OBJECT-GROUP
        OBJECTS {
            tnPTOFFACUMBinStatus,
            tnPTOFFACUMStartTime,
            tnPTOFFACUMMin,
            tnPTOFFACUMMax,
            tnPTOFFACUMPeakToPeak,
            tnPTOFFACUMAverage,
            tnPTOFFACUMSum,
            tnPTOFFACUMPeakToPeakTr,
            tnPTOFFACUMPeakToPeakRtr,
            tnPTOFFACUMPeakToPeak1DayTr
        }
        STATUS         current
        DESCRIPTION    "."
        ::= { tnStatisticsGroups 239 }

    tnPTOFFACUMRawCountScalarsGroup OBJECT-GROUP
        OBJECTS {
            tnPTOFFACUMRawCountTotalMembers
        }
        STATUS         current
        DESCRIPTION    "."
        ::= { tnStatisticsGroups 240 }

    tnPTOFFACUMRawCountGroup OBJECT-GROUP
        OBJECTS {
            tnPTOFFACUMRawCountClear,
            tnPTOFFACUMRawCountPeakToPeak,
            tnPTOFFACUMRawCountAverage,
            tnPTOFFACUMRawCountSum,
            tnPTOFFACUMRawCountStartTime
        }
        STATUS         current
        DESCRIPTION    "."
        ::= { tnStatisticsGroups 241 }

    tnPTOFFACUMStatsConfigScalarsGroup OBJECT-GROUP
        OBJECTS {
            tnPTOFFACUMStatsConfigAttributeTotal
        }
        STATUS         current
        DESCRIPTION    "."
        ::= { tnStatisticsGroups 242 }

    tnPTOFFACUMStatsConfigGroup OBJECT-GROUP
        OBJECTS {
            tnPTOFFACUMStatsNumberofBins,
            tnPTOFFACUMStatsProfileid,
            tnPTOFFACUMStatsClear,
            tnPTOFFACUMStatsIntervalLength,
            tnPTOFFACUMStatsEnable
        }
        STATUS         current
        DESCRIPTION    "."
        ::= { tnStatisticsGroups 243 }

    tnStatsPTPClearAllScalarsGroup OBJECT-GROUP
        OBJECTS {
            tnStatsPTPClearAllAttributeTotal
        }
        STATUS         current
        DESCRIPTION    "."
        ::= { tnStatisticsGroups 244 }

    tnStatsPTPClearAllGroup OBJECT-GROUP
        OBJECTS {
            tnStatsPTPClearAll
        }
        STATUS         current
        DESCRIPTION    "."
        ::= { tnStatisticsGroups 245 }

    tnPktWanifStatsControlScalarsGroup OBJECT-GROUP
        OBJECTS {
            tnPktWanifStatsControlAttributeTotal
        }
        STATUS         current
        DESCRIPTION    "."
        ::= { tnStatisticsGroups 246 }

    tnPktWanifStatsControlGroup OBJECT-GROUP
        OBJECTS {
            tnPktWanifStatsEnable
        }
        STATUS         current
        DESCRIPTION    "."
        ::= { tnStatisticsGroups 247 }

    tnCsrStatsScalarsGroup OBJECT-GROUP
        OBJECTS {
            tnCsrStatsTotalMembers
        }
        STATUS         current
        DESCRIPTION    "."
        ::= { tnStatisticsGroups 248 }

    tnCsrStatsGroup OBJECT-GROUP
        OBJECTS {
            tnCsrStatsBinStatus,
            tnCsrStatsStartTime,
            tnCsrStatMin,
            tnCsrStatMax,
            tnCsrStatAverage
        }
        STATUS         current
        DESCRIPTION    "."
        ::= { tnStatisticsGroups 249 }

    tnCsrRawCountStatsScalarsGroup OBJECT-GROUP
        OBJECTS {
            tnCsrRawCountStatsTotalMembers
        }
        STATUS         current
        DESCRIPTION    "."
        ::= { tnStatisticsGroups 250 }

    tnCsrRawCountStatsGroup OBJECT-GROUP
        OBJECTS {
            tnCsrRawCountStatsClear,
            tnCsrRawCountStatMin,
            tnCsrRawCountStatMax,
            tnCsrRawCountStatAverage,
            tnCsrRawCountStatStartTime
        }
        STATUS         current
        DESCRIPTION    "."
        ::= { tnStatisticsGroups 251 }

    tnQmarginStatsScalarsGroup OBJECT-GROUP
        OBJECTS {
            tnQmarginStatsTotalMembers
        }
        STATUS         current
        DESCRIPTION    "."
        ::= { tnStatisticsGroups 252 }

    tnQmarginStatsGroup OBJECT-GROUP
        OBJECTS {
            tnQmarginStatsBinStatus,
            tnQmarginStatsStartTime,
            tnQmarginStatMin,
            tnQmarginStatMax,
            tnQmarginStatAverage,
            tnQmarginStatMin15MinTr,
            tnQmarginStatMin15MinRtr,
            tnQmarginStatMin1DayTr
        }
        STATUS         current
        DESCRIPTION    "."
        ::= { tnStatisticsGroups 253 }

    tnQmarginRawCountStatsScalarsGroup OBJECT-GROUP
        OBJECTS {
            tnQmarginRawCountStatsTotalMembers
        }
        STATUS         current
        DESCRIPTION    "."
        ::= { tnStatisticsGroups 254 }

    tnQmarginRawCountStatsGroup OBJECT-GROUP
        OBJECTS {
            tnQmarginRawCountStatsClear,
            tnQmarginRawCountStatMin,
            tnQmarginRawCountStatMax,
            tnQmarginRawCountStatAverage,
            tnQmarginRawCountStatStartTime
        }
        STATUS         current
        DESCRIPTION    "."
        ::= { tnStatisticsGroups 255 }

    tnPdlStatsScalarsGroup OBJECT-GROUP
        OBJECTS {
            tnPdlStatsTotalMembers
        }
        STATUS         current
        DESCRIPTION    "."
        ::= { tnStatisticsGroups 256 }

    tnPdlStatsGroup OBJECT-GROUP
        OBJECTS {
            tnPdlStatsBinStatus,
            tnPdlStatsStartTime,
            tnPdlStatMin,
            tnPdlStatMax,
            tnPdlStatAverage
        }
        STATUS         current
        DESCRIPTION    "."
        ::= { tnStatisticsGroups 257 }

    tnPdlRawCountStatsScalarsGroup OBJECT-GROUP
        OBJECTS {
            tnPdlRawCountStatsTotalMembers
        }
        STATUS         current
        DESCRIPTION    "."
        ::= { tnStatisticsGroups 258 }

    tnPdlRawCountStatsGroup OBJECT-GROUP
        OBJECTS {
            tnPdlRawCountStatsClear,
            tnPdlRawCountStatMin,
            tnPdlRawCountStatMax,
            tnPdlRawCountStatAverage,
            tnPdlRawCountStatStartTime
        }
        STATUS         current
        DESCRIPTION    "."
        ::= { tnStatisticsGroups 259 }

    tnSoprStatsScalarsGroup OBJECT-GROUP
        OBJECTS {
            tnSoprStatsTotalMembers
        }
        STATUS         current
        DESCRIPTION    "."
        ::= { tnStatisticsGroups 260 }

    tnSoprStatsGroup OBJECT-GROUP
        OBJECTS {
            tnSoprStatsBinStatus,
            tnSoprStatsStartTime,
            tnSoprStatMin,
            tnSoprStatMax,
            tnSoprStatAverage
        }
        STATUS         current
        DESCRIPTION    "."
        ::= { tnStatisticsGroups 261 }

    tnSoprRawCountStatsScalarsGroup OBJECT-GROUP
        OBJECTS {
            tnSoprRawCountStatsTotalMembers
        }
        STATUS         current
        DESCRIPTION    "."
        ::= { tnStatisticsGroups 262 }

    tnSoprRawCountStatsGroup OBJECT-GROUP
        OBJECTS {
            tnSoprRawCountStatsClear,
            tnSoprRawCountStatMin,
            tnSoprRawCountStatMax,
            tnSoprRawCountStatAverage,
            tnSoprRawCountStatStartTime
        }
        STATUS         current
        DESCRIPTION    "."
        ::= { tnStatisticsGroups 263 }

    tnEsnrStatsScalarsGroup OBJECT-GROUP
        OBJECTS {
            tnEsnrStatsTotalMembers
        }
        STATUS         current
        DESCRIPTION    "."
        ::= { tnStatisticsGroups 264 }

    tnEsnrStatsGroup OBJECT-GROUP
        OBJECTS {
            tnEsnrStatsBinStatus,
            tnEsnrStatsStartTime,
            tnEsnrStatMin,
            tnEsnrStatMax,
            tnEsnrStatAverage
        }
        STATUS         current
        DESCRIPTION    "."
        ::= { tnStatisticsGroups 265 }

    tnEsnrRawCountStatsScalarsGroup OBJECT-GROUP
        OBJECTS {
            tnEsnrRawCountStatsTotalMembers
        }
        STATUS         current
        DESCRIPTION    "."
        ::= { tnStatisticsGroups 266 }

    tnEsnrRawCountStatsGroup OBJECT-GROUP
        OBJECTS {
            tnEsnrRawCountStatsClear,
            tnEsnrRawCountStatMin,
            tnEsnrRawCountStatMax,
            tnEsnrRawCountStatAverage,
            tnEsnrRawCountStatStartTime
        }
        STATUS         current
        DESCRIPTION    "."
        ::= { tnStatisticsGroups 267 }

    tnOpSupChInStatsScalarsGroup OBJECT-GROUP
        OBJECTS {
            tnOpSupChInStatsTotalMembers
        }
        STATUS         current
        DESCRIPTION    "."
        ::= { tnStatisticsGroups 268 }

    tnOpSupChInStatsGroup OBJECT-GROUP
        OBJECTS {
            tnOpSupChInStatsBinStatus,
            tnOpSupChInStatsStartTime,
            tnOpSupChInStatMinPower,
            tnOpSupChInStatMaxPower,
            tnOpSupChInStatAveragePower,
            tnOpSupChInStatWidth
        }
        STATUS         current
        DESCRIPTION    "."
        ::= { tnStatisticsGroups 269 }

    tnOpSupChInRawCountStatsScalarsGroup OBJECT-GROUP
        OBJECTS {
            tnOpSupChInRawCountStatsTotalMembers
        }
        STATUS         current
        DESCRIPTION    "."
        ::= { tnStatisticsGroups 270 }

    tnOpSupChInRawCountStatsGroup OBJECT-GROUP
        OBJECTS {
            tnOpSupChInRawCountStatsClear,
            tnOpSupChInRawCountStatMinPower,
            tnOpSupChInRawCountStatMaxPower,
            tnOpSupChInRawCountStatAveragePower,
            tnOpSupChInRawCountStatStartTime,
            tnOpSupChInRawCountStatWidth
        }
        STATUS         current
        DESCRIPTION    "."
        ::= { tnStatisticsGroups 271 }

    tnOpSupChOutStatsScalarsGroup OBJECT-GROUP
        OBJECTS {
            tnOpSupChOutStatsTotalMembers
        }
        STATUS         current
        DESCRIPTION    "."
        ::= { tnStatisticsGroups 272 }

    tnOpSupChOutStatsGroup OBJECT-GROUP
        OBJECTS {
            tnOpSupChOutStatsBinStatus,
            tnOpSupChOutStatsStartTime,
            tnOpSupChOutStatMinPower,
            tnOpSupChOutStatMaxPower,
            tnOpSupChOutStatAveragePower,
            tnOpSupChOutStatWidth
        }
        STATUS         current
        DESCRIPTION    "."
        ::= { tnStatisticsGroups 273 }

    tnOpSupChOutRawCountStatsScalarsGroup OBJECT-GROUP
        OBJECTS {
            tnOpSupChOutRawCountStatsTotalMembers
        }
        STATUS         current
        DESCRIPTION    "."
        ::= { tnStatisticsGroups 274 }

    tnOpSupChOutRawCountStatsGroup OBJECT-GROUP
        OBJECTS {
            tnOpSupChOutRawCountStatsClear,
            tnOpSupChOutRawCountStatMinPower,
            tnOpSupChOutRawCountStatMaxPower,
            tnOpSupChOutRawCountStatAveragePower,
            tnOpSupChOutRawCountStatStartTime,
            tnOpSupChOutRawCountStatWidth
        }
        STATUS         current
        DESCRIPTION    "."
        ::= { tnStatisticsGroups 275 }

    tnEvmStatsScalarsGroup OBJECT-GROUP
        OBJECTS {
            tnEvmStatsTotalMembers
        }
        STATUS         current
        DESCRIPTION    "."
        ::= { tnStatisticsGroups 276 }

    tnEvmStatsGroup OBJECT-GROUP
        OBJECTS {
            tnEvmStatsBinStatus,
            tnEvmStatsStartTime,
            tnEvmStatMin,
            tnEvmStatMax,
            tnEvmStatAverage
        }
        STATUS         current
        DESCRIPTION    "."
        ::= { tnStatisticsGroups 277 }

    tnEvmRawCountStatsScalarsGroup OBJECT-GROUP
        OBJECTS {
            tnEvmRawCountStatsTotalMembers
        }
        STATUS         current
        DESCRIPTION    "."
        ::= { tnStatisticsGroups 278 }

    tnEvmRawCountStatsGroup OBJECT-GROUP
        OBJECTS {
            tnEvmRawCountStatsClear,
            tnEvmRawCountStatMin,
            tnEvmRawCountStatMax,
            tnEvmRawCountStatAverage,
            tnEvmRawCountStatStartTime
        }
        STATUS         current
        DESCRIPTION    "."
        ::= { tnStatisticsGroups 279 }

    tnOsnrRxStatsScalarsGroup OBJECT-GROUP
        OBJECTS {
            tnOsnrRxStatsTotalMembers
        }
        STATUS         current
        DESCRIPTION    "."
        ::= { tnStatisticsGroups 280 }

    tnOsnrRxStatsGroup OBJECT-GROUP
        OBJECTS {
            tnOsnrRxStatsBinStatus,
            tnOsnrRxStatsStartTime,
            tnOsnrRxStatMin,
            tnOsnrRxStatMax,
            tnOsnrRxStatAverage
        }
        STATUS         current
        DESCRIPTION    "."
        ::= { tnStatisticsGroups 281 }

    tnOsnrRxRawCountStatsScalarsGroup OBJECT-GROUP
        OBJECTS {
            tnOsnrRxRawCountStatsTotalMembers
        }
        STATUS         current
        DESCRIPTION    "."
        ::= { tnStatisticsGroups 282 }

    tnOsnrRxRawCountStatsGroup OBJECT-GROUP
        OBJECTS {
            tnOsnrRxRawCountStatsClear,
            tnOsnrRxRawCountStatMin,
            tnOsnrRxRawCountStatMax,
            tnOsnrRxRawCountStatAverage,
            tnOsnrRxRawCountStatStartTime
        }
        STATUS         current
        DESCRIPTION    "."
        ::= { tnStatisticsGroups 283 }

    tnQfactorStatsScalarsGroup OBJECT-GROUP
        OBJECTS {
            tnQfactorStatsTotalMembers
        }
        STATUS         current
        DESCRIPTION    "."
        ::= { tnStatisticsGroups 284 }

    tnQfactorStatsGroup OBJECT-GROUP
        OBJECTS {
            tnQfactorStatsBinStatus,
            tnQfactorStatsStartTime,
            tnQfactorStatMin,
            tnQfactorStatMax,
            tnQfactorStatAverage
        }
        STATUS         current
        DESCRIPTION    "."
        ::= { tnStatisticsGroups 285 }

    tnQfactorRawCountStatsScalarsGroup OBJECT-GROUP
        OBJECTS {
            tnQfactorRawCountStatsTotalMembers
        }
        STATUS         current
        DESCRIPTION    "."
        ::= { tnStatisticsGroups 286 }

    tnQfactorRawCountStatsGroup OBJECT-GROUP
        OBJECTS {
            tnQfactorRawCountStatsClear,
            tnQfactorRawCountStatMin,
            tnQfactorRawCountStatMax,
            tnQfactorRawCountStatAverage,
            tnQfactorRawCountStatStartTime
        }
        STATUS         current
        DESCRIPTION    "."
        ::= { tnStatisticsGroups 287 }

    tnOchOprStatsScalarsGroup OBJECT-GROUP
        OBJECTS {
            tnOchOprStatsTotalMembers
        }
        STATUS         current
        DESCRIPTION    "."
        ::= { tnStatisticsGroups 288 }

    tnOchOprStatsGroup OBJECT-GROUP
        OBJECTS {
            tnOchOprStatsBinStatus,
            tnOchOprStatsStartTime,
            tnOchOprStatMinPower,
            tnOchOprStatMaxPower,
            tnOchOprStatAveragePower,
            tnOchOprStatMinPowerTr,
            tnOchOprStatMaxPowerTr,
            tnOchOprStatMinPowerRtr,
            tnOchOprStatMaxPowerRtr
        }
        STATUS         current
        DESCRIPTION    "."
        ::= { tnStatisticsGroups 289 }

    tnOchOprRawCountStatsScalarsGroup OBJECT-GROUP
        OBJECTS {
            tnOchOprRawCountStatsTotalMembers
        }
        STATUS         current
        DESCRIPTION    "."
        ::= { tnStatisticsGroups 290 }

    tnOchOprRawCountStatsGroup OBJECT-GROUP
        OBJECTS {
            tnOchOprRawCountStatsClear,
            tnOchOprRawCountStatMinPower,
            tnOchOprRawCountStatMaxPower,
            tnOchOprRawCountStatAveragePower,
            tnOchOprRawCountStatStartTime
        }
        STATUS         current
        DESCRIPTION    "."
        ::= { tnStatisticsGroups 291 }

    tnFcPktStatsScalarsGroup OBJECT-GROUP
        OBJECTS {
            tnFcPktStatsTotalMembers
        }
        STATUS         current
        DESCRIPTION    "."
        ::= { tnStatisticsGroups 292 }

    tnFcPktStatsGroup OBJECT-GROUP
        OBJECTS {
            tnFcPktStatsBinStatus,
            tnFcPktStatsStartTime,
            tnFcPktStatRxOctets,
            tnFcPktStatRxPkts,
            tnFcPktStatRxCrcAlignErrs,
            tnFcPktStatTxOctets,
            tnFcPktStatTxPkts,
            tnFcPktStatTxCrcAlignErrs
        }
        STATUS         current
        DESCRIPTION    "."
        ::= { tnStatisticsGroups 293 }

    tnFcPktRawCountStatsScalarsGroup OBJECT-GROUP
        OBJECTS {
            tnFcPktRawCountStatsTotalMembers
        }
        STATUS         current
        DESCRIPTION    "."
        ::= { tnStatisticsGroups 294 }

    tnFcPktRawCountStatsGroup OBJECT-GROUP
        OBJECTS {
            tnFcPktRawCountStatsClear,
            tnFcPktRawCountStatRxOctets,
            tnFcPktRawCountStatRxPkts,
            tnFcPktRawCountStatRxCrcAlignErrs,
            tnFcPktRawCountStatTxOctets,
            tnFcPktRawCountStatTxPkts,
            tnFcPktRawCountStatTxCrcAlignErrs,
            tnFcPktRawCountStatStartTime
        }
        STATUS         current
        DESCRIPTION    "."
        ::= { tnStatisticsGroups 295 }

    tnFcPktStatsThresholdScalarsGroup OBJECT-GROUP
        OBJECTS {
            tnFcPktStatGRxCrcAlignErrs15MinTr,
            tnFcPktStatGTxCrcAlignErrs15MinTr,
            tnFcPktStatGRxCrcAlignErrs1DayTr,
            tnFcPktStatGTxCrcAlignErrs1DayTr,
            tnFcPktStatGRxCrcAlignErrs15MinRtr,
            tnFcPktStatGTxCrcAlignErrs15MinRtr,
            tnFcPktStat2GRxCrcAlignErrs15MinTr,
            tnFcPktStat2GTxCrcAlignErrs15MinTr,
            tnFcPktStat2GRxCrcAlignErrs1DayTr,
            tnFcPktStat2GTxCrcAlignErrs1DayTr,
            tnFcPktStat2GRxCrcAlignErrs15MinRtr,
            tnFcPktStat2GTxCrcAlignErrs15MinRtr,
            tnFcPktStat4GRxCrcAlignErrs15MinTr,
            tnFcPktStat4GTxCrcAlignErrs15MinTr,
            tnFcPktStat4GRxCrcAlignErrs1DayTr,
            tnFcPktStat4GTxCrcAlignErrs1DayTr,
            tnFcPktStat4GRxCrcAlignErrs15MinRtr,
            tnFcPktStat4GTxCrcAlignErrs15MinRtr,
            tnFcPktStat8GRxCrcAlignErrs15MinTr,
            tnFcPktStat8GTxCrcAlignErrs15MinTr,
            tnFcPktStat8GRxCrcAlignErrs1DayTr,
            tnFcPktStat8GTxCrcAlignErrs1DayTr,
            tnFcPktStat8GRxCrcAlignErrs15MinRtr,
            tnFcPktStat8GTxCrcAlignErrs15MinRtr,
            tnFcPktStat10GRxCrcAlignErrs15MinTr,
            tnFcPktStat10GTxCrcAlignErrs15MinTr,
            tnFcPktStat10GRxCrcAlignErrs1DayTr,
            tnFcPktStat10GTxCrcAlignErrs1DayTr,
            tnFcPktStat10GRxCrcAlignErrs15MinRtr,
            tnFcPktStat10GTxCrcAlignErrs15MinRtr,
            tnFcPktStat16GRxCrcAlignErrs15MinTr,
            tnFcPktStat16GTxCrcAlignErrs15MinTr,
            tnFcPktStat16GRxCrcAlignErrs1DayTr,
            tnFcPktStat16GTxCrcAlignErrs1DayTr,
            tnFcPktStat16GRxCrcAlignErrs15MinRtr,
            tnFcPktStat16GTxCrcAlignErrs15MinRtr
        }
        STATUS         current
        DESCRIPTION    "."
        ::= { tnStatisticsGroups 296 }

--------------------------------------------------------------------------------
-- Compliance Statements (mandatory)
--------------------------------------------------------------------------------
    tnStatisticsCompliance MODULE-COMPLIANCE
        STATUS         current
        DESCRIPTION    "."
        MODULE
        MANDATORY-GROUPS  {
          tnStatsPortIntervalGroup,
          tnStatsCardIntervalGroup,
          tnStatsPortConfGroup,
          tnStatsCardConfGroup,
          tnStatsTCAProfileGroup,
          tnStatsTCAGroup,
          tnCardStatsScalarsGroup,
          tnCardStatsGroup,
          tnInterfaceStatsScalarsGroup,
          tnInterfaceStatsGroup,
          tnEtherStatsScalarsGroup,
          tnEtherStatsGroup,
          tnSonetStatsScalarsGroup,
          tnSonetStatsGroup,
--          obsolete
--          tnDigitalWrapperStatsScalarsGroup,
--          tnDigitalWrapperStatsGroup,
--          tnL1ProtStatsScalarsGroup,
--          tnL1ProtStatsGroup,
          tnControlNetworkLinkRawCountStatsScalarsGroup,
          tnControlNetworkLinkRawCountStatsGroup,
          tnCardRawCountStatsScalarsGroup,
          tnCardRawCountStatsGroup,
          tnInterfaceRawCountStatsScalarsGroup,
          tnInterfaceRawCountStatsGroup,
          tnEtherRawCountStatsScalarsGroup,
          tnEtherRawCountStatsGroup,
          tnSonetRawCountStatsScalarsGroup,
          tnSonetRawCountStatsGroup,
--          obsolete
--          tnDigitalWrapperRawCountStatsScalarsGroup,
--          tnDigitalWrapperRawCountStatsGroup,
--          tnL1ProtRawCountStatsScalarsGroup,
--          tnL1ProtRawCountStatsGroup,
          tnOptStatsScalarsGroup,
          tnOptStatsGroup,
          tnOprStatsScalarsGroup,
          tnOprStatsGroup,
          tnOptRawCountStatsScalarsGroup,
          tnOptRawCountStatsGroup,
          tnOprRawCountStatsScalarsGroup,
          tnOprRawCountStatsGroup,
          tnOpOutStatsScalarsGroup,
          tnOpOutStatsGroup,
          tnOpInStatsScalarsGroup,
          tnOpInStatsGroup,
          tnOpOutRawCountStatsScalarsGroup,
          tnOpOutRawCountStatsGroup,
          tnOpInRawCountStatsScalarsGroup,
          tnOpInRawCountStatsGroup,
--          obsolete
--          tnStatsTCAItuGroup,
          tnOpOchOutStatsScalarsGroup,
          tnOpOchOutStatsGroup,
          tnOpOchInStatsScalarsGroup,
          tnOpOchInStatsGroup,
          tnOpOchOutRawCountStatsScalarsGroup,
          tnOpOchOutRawCountStatsGroup,
          tnOpOchInRawCountStatsScalarsGroup,
          tnOpOchInRawCountStatsGroup,
          tnStatsPortClearAllGroup,
          tnStatsTCAScalarsGroup,
          tnSdhStatsScalarsGroup,
          tnSdhStatsGroup,
          tnSdhRawCountStatsScalarsGroup,
          tnSdhRawCountStatsGroup,
--          obsolete
--          tnPathSummaryStatsScalarsGroup,
--          tnPathSummaryStatsGroup,
--          tnPathSummaryRawCountStatsScalarsGroup,
--          tnPathSummaryRawCountStatsGroup,
--          tnFibreChannelStatsScalarsGroup,
--          tnFibreChannelStatsGroup,
--          tnFibreChannelRawCountStatsScalarsGroup,
--          tnFibreChannelRawCountStatsGroup,
          tnPhyCodeSublayerStatsScalarsGroup,
          tnPhyCodeSublayerStatsGroup,
          tnPhyCodeSublayerRawCountStatsScalarsGroup,
          tnPhyCodeSublayerRawCountStatsGroup,
          tnDigitalWrapper64BitStatsScalarsGroup,
          tnDigitalWrapper64BitStatsGroup,
          tnDigitalWrapper64BitRawCountStatsScalarsGroup,
          tnDigitalWrapper64BitRawCountStatsGroup,
          tnStatsBaselineGroup,
          tnCdrStatsScalarsGroup,
          tnCdrStatsGroup,
          tnCdrRawCountStatsScalarsGroup,
          tnCdrRawCountStatsGroup,
          tnDgdrStatsScalarsGroup,
          tnDgdrStatsGroup,
          tnDgdrRawCountStatsScalarsGroup,
          tnDgdrRawCountStatsGroup,
          tnFoffrStatsScalarsGroup,
          tnFoffrStatsGroup,
          tnFoffrRawCountStatsScalarsGroup,
          tnFoffrRawCountStatsGroup,
          tnE1StatsScalarsGroup,
          tnE1StatsGroup,
          tnE1RawCountStatsScalarsGroup,
          tnE1RawCountStatsGroup,
          tnPreFECBitsStatsScalarsGroup,
          tnPreFECBitsStatsGroup,
          tnPreFECBitsRawCountStatsScalarsGroup,
          tnPreFECBitsRawCountStatsGroup,
--          obsolete
--          tnStatsTcmTCAGroup,
--          tnStatsTcmTCAProfileGroup,
--          tnStatsTcmPortGroup,
--          tnTcm64BitStatsScalarsGroup,
--          tnTcm64BitStatsGroup,
--          tnTcm64BitRawCountStatsScalarsGroup,
--          tnTcm64BitRawCountStatsGroup,
          tnEncrypt64BitStatsScalarsGroup,
          tnEncrypt64BitStatsGroup,
          tnEncrypt64BitRawCountStatsScalarsGroup,
          tnEncrypt64BitRawCountStatsGroup,
          tnOthOdukStatsRxConfigScalarsGroup,
          tnOthOdukStatsRxConfigGroup,
          tnOthOdukStatsTxConfigScalarsGroup,
          tnOthOdukStatsTxConfigGroup,
          tnOthOdukStatsControlScalarsGroup,
          tnOthOdukStatsControlGroup,
          tnOthOdukStatsRxScalarsGroup,
          tnOthOdukStatsRxGroup,
          tnOthOdukStatsTxScalarsGroup,
          tnOthOdukStatsTxGroup,
          tnOthOtukStatsScalarsGroup,
          tnOthOtukStatsGroup,
          tnOthOdukStatsRxThresholdScalarsGroup,
          tnOthOdukStatsTxThresholdScalarsGroup,
          tnOthOtukStatsThresholdScalarsGroup,
          tnOthOdukRawCountStatsRxScalarsGroup,
          tnOthOdukRawCountStatsRxGroup,
          tnOthOdukRawCountStatsTxScalarsGroup,
          tnOthOdukRawCountStatsTxGroup,
          tnOthOtukRawCountStatsScalarsGroup,
          tnOthOtukRawCountStatsGroup,
          tnOsnrStatsScalarsGroup,
          tnOsnrStatsGroup,
          tnOsnrRawCountStatsScalarsGroup,
          tnOsnrRawCountStatsGroup,
          tnSonetStatsThresholdScalarsGroup,
          tnSdhStatsThresholdScalarsGroup,
          tnDwStatsThresholdScalarsGroup,
          tnPcsStatsThresholdScalarsGroup,
          tnOthOdukStatsDMConfigScalarsGroup,
          tnOthOdukStatsDMConfigGroup,
          tnOthOdukStatsDMScalarsGroup,
          tnOthOdukStatsDMGroup,
          tnOthOdukRawCountStatsDMScalarsGroup,
          tnOthOdukRawCountStatsDMGroup,
          tnOthOdukStatsTcmConfigScalarsGroup,
          tnOthOdukStatsTcmConfigGroup,
          tnOthOdukStatsTcmEnableScalarsGroup,
          tnOthOdukStatsTcmEnableGroup,
          tnStatsLanePwrsConfigScalarsGroup,
          tnStatsLanePwrsConfigGroup,
          tnOthOdukStatsTcmScalarsGroup,
          tnOthOdukStatsTcmGroup,
          tnTcmStatsThresholdScalarsGroup,
          tnOpticalLaneStatPowerScalarsGroup,
          tnTcmRawCountStatsScalarsGroup,
          tnTcmRawCountStatsGroup,
          tnEncryptionFailToDecryptScalarsGroup,
          tnFECPMStatsScalarsGroup,
          tnFECPMStatsGroup,
          tnFECPMStatsThresholdScalarsGroup,
          tnFECPMRawCountStatsScalarsGroup,
          tnFECPMRawCountStatsGroup,
          tnOtuStatsPortIntervalGroup,
          tnOtuStatsPortGroup,
          tnpreFECBERStatsScalarsGroup,
          tnpreFECBERStatsGroup,
          tnStatisticspreFECBERScalarsGroup,
          tnpreFECBERRawCountStatsScalarsGroup,
          tnpreFECBERRawCountStatsGroup,
          tnStatisticsStreamingPMScalarsGroup,
          tnStreamingPmThresholdScalarsGroup,
          tnStreamingPmThresholdGroup,
          tnOpOutCStatsScalarsGroup,
          tnOpOutCStatsGroup,
          tnOpInCStatsScalarsGroup,
          tnOpInCStatsGroup,
          tnOpOutCRawCountStatsScalarsGroup,
          tnOpOutCRawCountStatsGroup,
          tnOpInCRawCountStatsScalarsGroup,
          tnOpInCRawCountStatsGroup,
          tnOpOutLStatsScalarsGroup,
          tnOpOutLStatsGroup,
          tnOpInLStatsScalarsGroup,
          tnOpInLStatsGroup,
          tnOpOutLRawCountStatsScalarsGroup,
          tnOpOutLRawCountStatsGroup,
          tnOpInLRawCountStatsScalarsGroup,
          tnOpInLRawCountStatsGroup,
          tnETHFECPMStatsScalarsGroup,
          tnETHFECPMStatsGroup,
          tnETHFECPMRawCountStatsScalarsGroup,
          tnETHFECPMRawCountStatsGroup,
          tnSyncEStatsScalarsGroup,
          tnSyncEStatsGroup,
          tnSyncERawCountStatsScalarsGroup,
          tnSyncERawCountStatsGroup,
          tnSyncEStatsConfigScalarsGroup,
          tnSyncEStatsConfigGroup,
          tnSyncEStatsOffsetScalarsGroup,
          tnSyncStatsScalarsGroup,
          tnSyncStatsGroup,
          tnSyncRawCountStatsScalarsGroup,
          tnSyncRawCountStatsGroup,
          tnSyncStatsConfigScalarsGroup,
          tnSyncStatsConfigGroup,
          tnPTOFFScalarsGroup,
          tnPTOFFGroup,
          tnPTOFFRawCountScalarsGroup,
          tnPTOFFRawCountGroup,
          tnPTOFFStatsConfigScalarsGroup,
          tnPTOFFStatsConfigGroup,
          tnPTMSDLYScalarsGroup,
          tnPTMSDLYGroup,
          tnPTMSDLYRawCountScalarsGroup,
          tnPTMSDLYRawCountGroup,
          tnPTMSDLYStatsConfigScalarsGroup,
          tnPTMSDLYStatsConfigGroup,
          tnPTSMDLYScalarsGroup,
          tnPTSMDLYGroup,
          tnPTSMDLYRawCountScalarsGroup,
          tnPTSMDLYRawCountGroup,
          tnPTSMDLYStatsConfigScalarsGroup,
          tnPTSMDLYStatsConfigGroup,
          tnPTMPDLYScalarsGroup,
          tnPTMPDLYGroup,
          tnPTMPDLYRawCountScalarsGroup,
          tnPTMPDLYRawCountGroup,
          tnPTMPDLYStatsConfigScalarsGroup,
          tnPTMPDLYStatsConfigGroup,
          tnPTERREFScalarsGroup,
          tnPTERREFGroup,
          tnPTERREFRawCountScalarsGroup,
          tnPTERREFRawCountGroup,
          tnPTERREFStatsConfigScalarsGroup,
          tnPTERREFStatsConfigGroup,
          tnPTOFFACUMScalarsGroup,
          tnPTOFFACUMGroup,
          tnPTOFFACUMRawCountScalarsGroup,
          tnPTOFFACUMRawCountGroup,
          tnPTOFFACUMStatsConfigScalarsGroup,
          tnPTOFFACUMStatsConfigGroup,
          tnStatsPTPClearAllScalarsGroup,
          tnStatsPTPClearAllGroup,
          tnPktWanifStatsControlScalarsGroup,
          tnPktWanifStatsControlGroup,
          tnCsrStatsScalarsGroup,
          tnCsrStatsGroup,
          tnCsrRawCountStatsScalarsGroup,
          tnCsrRawCountStatsGroup,
          tnQmarginStatsScalarsGroup,
          tnQmarginStatsGroup,
          tnQmarginRawCountStatsScalarsGroup,
          tnQmarginRawCountStatsGroup,
          tnPdlStatsScalarsGroup,
          tnPdlStatsGroup,
          tnPdlRawCountStatsScalarsGroup,
          tnPdlRawCountStatsGroup,
          tnSoprStatsScalarsGroup,
          tnSoprStatsGroup,
          tnSoprRawCountStatsScalarsGroup,
          tnSoprRawCountStatsGroup,
          tnEsnrStatsScalarsGroup,
          tnEsnrStatsGroup,
          tnEsnrRawCountStatsScalarsGroup,
          tnEsnrRawCountStatsGroup,
          tnOpSupChInStatsScalarsGroup,
          tnOpSupChInStatsGroup,
          tnOpSupChInRawCountStatsScalarsGroup,
          tnOpSupChInRawCountStatsGroup,
          tnOpSupChOutStatsScalarsGroup,
          tnOpSupChOutStatsGroup,
          tnOpSupChOutRawCountStatsScalarsGroup,
          tnOpSupChOutRawCountStatsGroup,
          tnEvmStatsScalarsGroup,
          tnEvmStatsGroup,
          tnEvmRawCountStatsScalarsGroup,
          tnEvmRawCountStatsGroup,
          tnOsnrRxStatsScalarsGroup,
          tnOsnrRxStatsGroup,
          tnOsnrRxRawCountStatsScalarsGroup,
          tnOsnrRxRawCountStatsGroup,
          tnQfactorStatsScalarsGroup,
          tnQfactorStatsGroup,
          tnQfactorRawCountStatsScalarsGroup,
          tnQfactorRawCountStatsGroup,
          tnOchOprStatsScalarsGroup,
          tnOchOprStatsGroup,
          tnOchOprRawCountStatsScalarsGroup,
          tnOchOprRawCountStatsGroup,
          tnFcPktStatsScalarsGroup,
          tnFcPktStatsGroup,
          tnFcPktRawCountStatsScalarsGroup,
          tnFcPktRawCountStatsGroup,
          tnFcPktStatsThresholdScalarsGroup
        }
        ::= { tnStatisticsCompliances 1 }

END -- DEFINITION OF TROPIC-STATISTICS-MIB
