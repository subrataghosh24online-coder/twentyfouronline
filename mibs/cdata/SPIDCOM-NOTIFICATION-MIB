--
-- ALARM-MIB.my
-- MIB generated by MG-SOFT Visual MIB Builder Version 4.0 Build 349
-- Friday, November 21, 2003 at 15:00:38
--

	SPIDCOM-NOTIFICATION-MIB DEFINITIONS ::= BEGIN

		IMPORTS
			spidcom       FROM SPIDCOM-MIB;


--
-- Node definitions
--

		-- 1.3.6.1.4.1.22764.4
		specificSpidcomTrap OBJECT IDENTIFIER 	::= { spidcom 4 }




	END

--
-- SPIDCOM-NOTIFICATION-MIB.my
--
