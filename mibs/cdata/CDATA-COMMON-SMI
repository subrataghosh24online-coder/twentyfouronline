--
-- CDATA-COMMON-SMI.my
-- MIB generated by MG-SOFT Visual MIB Builder Version 3.0 Build 253
-- Wednesday, March 02, 2016 at 16:10:01
--

	CDATA-COMMON-SMI DEFINITIONS ::= BEGIN
 
		IMPORTS
			enterprises, MODULE-IDENTITY, OBJECT-IDENTITY			
				FROM SNMPv2-SMI			
			TEXTUAL-CONVENTION			
				FROM SNMPv2-TC;
	
	
--  May 27, 2010 at 10:56 GMT
		vendor MODULE-IDENTITY 
			LAST-UPDATED "201603021453Z"		-- March 02, 2016 at 14:53 GMT
			ORGANIZATION 
				"vendor"
			CONTACT-INFO 
				"Contact info"
			DESCRIPTION 
				"common mib smi"
			REVISION "201603021447Z"		-- March 02, 2016 at 14:47 GMT
			DESCRIPTION
				"add gpon node"
			::= { enterprises 34592 }
		
	
--
-- Textual conventions
--
	
		DataDirection ::= TEXTUAL-CONVENTION
			STATUS current
			DESCRIPTION 
				"A data channel normally have two direction, up and down"
			SYNTAX INTEGER
				{
				upstream(1),
				downstream(2)
				}
			
		DeviceOperation ::= TEXTUAL-CONVENTION
			STATUS current
			DESCRIPTION 
				"This type defines an operate action aggregate"
			SYNTAX INTEGER
				{
				reset(2),
				default(3),
				saveConfig(4),
				restore(5),
				delete(6)
				}
			
		DeviceStatus ::= TEXTUAL-CONVENTION
			STATUS current
			DESCRIPTION 
				"Device work status type. One device or dummy device may
				have following five work status:
				notPresent(1): the device is not present (not installed)
				offline(2):the device is present,but can not be communicated (or failed to get its info)
				online(3):the device is present and can be communicated
				normal(4):the device is online and work well
				abnormal(5): the device is online but work abnormal for some reason"
			SYNTAX INTEGER
				{
				notPresent(1),
				offline(2),
				online(3),
				normal(4),
				abnormal(5)
				}
			
		DeviceType ::= TEXTUAL-CONVENTION
			STATUS current
			DESCRIPTION 
				"Device type convention. Define all PBB device type value.
				
				----------------------------------
				| family | series | class | type |
				----------------------------------
				   8b        8b      8b      8b
				
				refer to document <pducuct type defines>"
			SYNTAX INTEGER { fd1508gs(67174657) }
			
		LedStatus ::= TEXTUAL-CONVENTION
			STATUS current
			DESCRIPTION 
				"Led status"
			SYNTAX INTEGER
				{
				on(1),
				off(2),
				blink(3)
				}
			
--  Textual conventions
-- 
		OperSwitch ::= TEXTUAL-CONVENTION
			STATUS current
			DESCRIPTION 
				"Device function operation switch type"
			SYNTAX INTEGER
				{
				enable(1),
				disable(2)
				}
			
	
--
-- Node definitions
--
	
--  Node definitions
-- 
-- 1.3.6.1.4.1.34592.1
		-- 1.3.6.1.4.1.34592.1
		ipProduct OBJECT-IDENTITY
			STATUS current
			DESCRIPTION 
				"ip products line.
				"
			::= { vendor 1 }
		
--  1.3.6.1.4.1.34592.1.1
		-- 1.3.6.1.4.1.34592.1.1
		mediaConverter OBJECT-IDENTITY
			STATUS current
			DESCRIPTION 
				"supported by media converter line products.
				"
			::= { ipProduct 1 }
		
--  1.3.6.1.4.1.34592.1.2
		-- 1.3.6.1.4.1.34592.1.2
		switch OBJECT-IDENTITY
			STATUS current
			DESCRIPTION 
				"supported by smartCPE Switch line products.
				"
			::= { ipProduct 2 }
		
--  1.3.6.1.4.1.34592.1.3
		-- 1.3.6.1.4.1.34592.1.3
		epon OBJECT-IDENTITY
			STATUS current
			DESCRIPTION 
				"supported by epon line products."
			::= { ipProduct 3 }
		
--  1.3.6.1.4.1.34592.1.4
		-- 1.3.6.1.4.1.34592.1.4
		eoc OBJECT-IDENTITY
			STATUS current
			DESCRIPTION 
				"supported by eoc line products."
			::= { ipProduct 4 }
		
		-- 1.3.6.1.4.1.34592.1.5
		gpon OBJECT-IDENTITY
			STATUS current
			DESCRIPTION 
				"supported by gpon line products."
			::= { ipProduct 5 }
		
	
	END

--
-- CDATA-COMMON-SMI.my
--
