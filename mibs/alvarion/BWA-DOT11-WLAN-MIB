-- Title:      BWA  Private MIB
--             This Private MIB supports BWA-PtMP and BWA-PtP product lines.
--
--
-- Version:    4.5.16
-- Date:       Tuesday August 14 2007
-- Comments:   BWA agents also support the following Public MIBs:
  
-- This MIB supports BWA VL products (AU and SU),
-- BWA 4900 (AU and SU) and
-- BWA-PtP products (BU and RB). 

-- Some MIB compilers require that the following lines 
-- for proper compilation

--#include "rfc1155.smi"
--#include "rfc1212.smi"


-- mgmt           OBJECT IDENTIFIER ::= { iso org(3) dod(6) internet(1)  mgmt(2) }
-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }

-- End of lines which might be needed to other MIB browsers 
-- for proper compilation


BWA-DOT11-WLAN-MIB DEFINITIONS ::= BEGIN


  IMPORTS
       MODULE-IDENTITY, NOTIFICATION-TYPE, enterprises, IpAddress,Counter32,OBJECT-TYPE
               FROM SNMPv2-SMI;

bwa        		OBJECT IDENTIFIER ::= { enterprises 12394 }
products		OBJECT IDENTIFIER ::= { bwa 1 }

bwaVLMib	MODULE-IDENTITY
		LAST-UPDATED	"0708141146Z"
		ORGANIZATION	"BWA Products"
		CONTACT-INFO	"Contact Man
                         Postal: BWA Products
			             Street Number ZipCode
			             Country
		                 Tel:    000-0-0000000
		                 Fax:    000-0-0000000
		                 E-mail: E-mail"
		DESCRIPTION		
		      "BWA VL products, BWA 4900, BWA-PtP"
		REVISION 	     "0708141146Z"
		DESCRIPTION		
		      "Version 4.5"
		::=  {  products 1 }
  
  		 
  MacAddress ::= OCTET STRING (SIZE(6))
  DisplayString ::= OCTET STRING 

bwaOID     OBJECT IDENTIFIER ::= { bwa      4 }
bwaVLOID  OBJECT IDENTIFIER ::= { bwaOID   1 }


bwaVLAU     OBJECT IDENTIFIER ::= { bwaVLOID 1 }
bwaVLSU     OBJECT IDENTIFIER ::= { bwaVLOID 2 }

bwaVLAU-BS     OBJECT IDENTIFIER ::= { bwaVLOID 4 }
bwaVLAU-SA     OBJECT IDENTIFIER ::= { bwaVLOID 5 }

bwaVLAUS-BS     OBJECT IDENTIFIER ::= { bwaVLOID 6 }
bwaVLAUS-SA     OBJECT IDENTIFIER ::= { bwaVLOID 7 }
bwaVLAU-EZ	    OBJECT IDENTIFIER ::= { bwaVLOID 8 }


bwaVLSU-6-1D   OBJECT IDENTIFIER ::= { bwaVLOID 11 }
bwaVLSU-6-BD   OBJECT IDENTIFIER ::= { bwaVLOID 12 }
bwaVLSU-24-BD  OBJECT IDENTIFIER ::= { bwaVLOID 13 }
bwaVLSU-BD     OBJECT IDENTIFIER ::= { bwaVLOID 14 }
bwaVLSU-54-BD  OBJECT IDENTIFIER ::= { bwaVLOID 15 }

bwaVLSU-3-1D  OBJECT IDENTIFIER ::= { bwaVLOID 16 }
bwaVLSU-3-4D  OBJECT IDENTIFIER ::= { bwaVLOID 17 }
bwaVLSU-I	  OBJECT IDENTIFIER ::= { bwaVLOID 18 }


ptp-BU-B14     OBJECT IDENTIFIER ::= { bwaVLOID 21 }
ptp-BU-B28     OBJECT IDENTIFIER ::= { bwaVLOID 22 }
ptp-BU-B100    OBJECT IDENTIFIER ::= { bwaVLOID 23 }

ptp-RB-B14     OBJECT IDENTIFIER ::= { bwaVLOID 31 }
ptp-RB-B28     OBJECT IDENTIFIER ::= { bwaVLOID 32 }
ptp-RB-B100    OBJECT IDENTIFIER ::= { bwaVLOID 33 }

bwa4900-AU-BS OBJECT IDENTIFIER ::= { bwaVLOID 41 }
bwa4900-AU-SA OBJECT IDENTIFIER ::= { bwaVLOID 42 }
bwa4900-SU-BD OBJECT IDENTIFIER ::= { bwaVLOID 51 }

bwaVLProducts		OBJECT IDENTIFIER ::= {	bwaVLOID 3 }

-- ****************************************************************************************
-- ****************************************************************************************
-- General System Info
-- ===================
bwaVLSysInfo       OBJECT IDENTIFIER ::= {bwaVLMib 1}


    bwaVLUnitHwVersion OBJECT-TYPE
            SYNTAX DisplayString (SIZE(0..32))
            MAX-ACCESS read-only
            STATUS current
            DESCRIPTION  
            "Applicable to all units.  
             Hardware platform version."
            ::= { bwaVLSysInfo 1 }

    bwaVLRunningSoftwareVersion OBJECT-TYPE
            SYNTAX DisplayString (SIZE(0..32))
            MAX-ACCESS read-only
            STATUS current
            DESCRIPTION  
            "Applicable to all units.  
             Running software version."
            ::= { bwaVLSysInfo 2 }

    bwaVLRunningFrom OBJECT-TYPE
            SYNTAX INTEGER { mainVersion(1) , shadowVersion(2)}
            MAX-ACCESS read-only
            STATUS current
            DESCRIPTION  
            "Applicable to all units.  
             The memory (main or shadow) from which the current version is 
             running from." 
            ::= { bwaVLSysInfo 3 }

    bwaVLMainVersionNumber OBJECT-TYPE
            SYNTAX DisplayString (SIZE(0..32))
            MAX-ACCESS read-only
            STATUS current
            DESCRIPTION  
            "Applicable to all units.  
             Main software version number."
            ::= { bwaVLSysInfo 4 }

    bwaVLMainVersionFileName OBJECT-TYPE
            SYNTAX DisplayString (SIZE(0..32))
            MAX-ACCESS read-only
            STATUS current
            DESCRIPTION  
            "Applicable to all units.  
             Main software version file name."
            ::= { bwaVLSysInfo 5 }


    bwaVLShadowVersionNumber OBJECT-TYPE
            SYNTAX DisplayString (SIZE(0..32))
            MAX-ACCESS read-only
            STATUS current
            DESCRIPTION  
            "Applicable to all units.  
             Shadow software version number."
            ::= { bwaVLSysInfo 6 }

    bwaVLShadowVersionFileName OBJECT-TYPE
            SYNTAX DisplayString (SIZE(0..32))
            MAX-ACCESS read-only
            STATUS current
            DESCRIPTION  
            "Applicable to all units.  
             Shadow software version file name."
            ::= { bwaVLSysInfo 7 }

    bwaVLUnitMacAddress OBJECT-TYPE
            SYNTAX  MacAddress
            MAX-ACCESS  read-only    
            STATUS  current
            DESCRIPTION
            "Applicable to all units.  
             Unit hardware MAC address."
            ::= { bwaVLSysInfo 8 }

    bwaVLUnitType OBJECT-TYPE
            SYNTAX INTEGER {auBS (1), auSA(2) , su-6-1D(3),su-6-BD(4),su-24-BD(5),
                            bu-B14(6),bu-B28(7),rb-B14(8),rb-B28(9),su-BD(10),su-54-BD (11),
                            su-3-1D(12),su-3-4D(13),ausBS(14),ausSA(15),
                            auBS4900(16),auSA4900(17),su4900(18), bu-B100(19), rb-B100(20), su-I(21), 
                            au-E(22) }
            MAX-ACCESS read-only
            STATUS current
            DESCRIPTION  
            "Applicable to all units.  
             auBS     (1) : AU-BS (modular access unit). 
             auSA     (2) : AU-SA (stand-alone access unit).
             su-6-1D  (3) : SU-6-1D (subscriber unit supporting 6 Mbps)
             su-6-BD  (4) : SU-6-BD (subscriber unit supporting 6 Mbps).
             su-24-BD (5) : SU-24-BD (subscriber unit supporting 24 Mbps).
			 bu-B14   (6) : BU-B14 (PtP Base Unit supporting 14 Mbps).
			 bu-B28   (7) : BU-B28 (PtP Base Unit supporting 28 Mbps).
			 rb-B14   (8) : RB-B14 (PtP Remote Bridge supporting 14 Mbps).
			 rb-B28   (9) : RB-B28 (PtP Remote Bridge supporting 28 Mbps).
			 su-BD   (10) : SU-BD (subscriber unit).
			 su-54-BD(11) : SU-54-BD (subscriber unit supporting 54 Mbps).
             su-3-1D (12) : SU-3-1D (subscriber unit supporting 3 Mbps).
             su-3-4D (13) : SU-3-4D (subscriber unit supporting 3 Mbps).
             ausBS   (14) : AUS-BS (modular access unit supporting maxim 8 or 25 
                            (via licensing) subscribers and allowing association 
                            only with SU-3 or SU-6).
             ausSA   (15) : AUS-SA (stand-alone access unit supporting maxim 8 or 25 
                            (via licensing)subscribers and allowing association only 
                            with SU-3 or SU-6 ).
             auBS4900(16) : AU-BS-4900 (BWA 4900 modular access unit)
             auSA4900(17) : AU-SA-4900 (BWA 4900 stand alone access unit)
             suBD4900(18) : SU-BD-4900 (BWA 4900 subscriber unit)
             bu-B100 (19) : BU-B100 (PtP Base Unit unlimited throughput)
             rb-B100 (20) : BU-B100 (PtP Remote Bridge unlimited throughput) 
             su-I    (21) : SU-I
             au-E    (22) : AU-E"
             ::= { bwaVLSysInfo 9 }

    bwaVLAssociatedAU OBJECT-TYPE
            SYNTAX  MacAddress
            MAX-ACCESS read-only
            STATUS current
            DESCRIPTION  
            "Applicable to SU/RB only.  
             Associated AU/BU MAC address."
            ::= { bwaVLSysInfo 10 }

    bwaVLNumOfAssociationsSinceLastReset OBJECT-TYPE
            SYNTAX  INTEGER
            MAX-ACCESS read-only
            STATUS current
            DESCRIPTION  
            "Applicable to all units.  
             The number of associations since last reset, including 
             duplicate associations (re-associations)."
            ::= { bwaVLSysInfo 11 }

    bwaVLCurrentNumOfAssociations OBJECT-TYPE
            SYNTAX  INTEGER	
            MAX-ACCESS read-only
            STATUS current
            DESCRIPTION  
            "Applicable to AU only.  
             Not applicable to BWA-PtP products.
             The number of SUs currently associated with the AU.
             BWA-PtP products return 65535."
            ::= { bwaVLSysInfo 13 }

    bwaVLUnitBootVersion OBJECT-TYPE
            SYNTAX DisplayString (SIZE(0..32))
            MAX-ACCESS read-only
            STATUS current
            DESCRIPTION  
            "Applicable to all units.  
             Boot version."
            ::= { bwaVLSysInfo 14 }

    bwaVLRadioBand OBJECT-TYPE
			SYNTAX INTEGER {band-5-8GHz (1), band-5-4GHz (2) , band-4-9GHz (3),band-5-2GHz (4),band-2-4GHz (5),band-5-3GHz (6),band-4-9GHzJapan (7)}
            MAX-ACCESS read-only
            STATUS current
            DESCRIPTION  
            "Applicable to all units.  
             The unit's radio band."
            ::= { bwaVLSysInfo 15 }

    bwaVLCurrentEthernetPortState  OBJECT-TYPE
            SYNTAX  INTEGER	{ halfDuplexAnd10Mbps  (1),
            				  fullDuplexAnd10Mbps  (2),
							  halfDuplexAnd100Mbps (3),
							  fullDuplexAnd100Mbps (4),
							  linkDown             (5) }

            MAX-ACCESS read-only
            STATUS current
            DESCRIPTION  
            "Applicable to all units.  
             The current Ethernet port state."
            ::= { bwaVLSysInfo 16 }



    bwaVLTimeSinceLastReset OBJECT-TYPE
            SYNTAX DisplayString (SIZE(0..32))
            MAX-ACCESS read-only
            STATUS current
            DESCRIPTION  
            "Applicable to all units.  
             The elapsed time since last reset."
            ::= { bwaVLSysInfo 17 }

bwaVLCountryDependentParameters   OBJECT IDENTIFIER ::= {bwaVLSysInfo 18}
	
    bwaVLCountryCode OBJECT-TYPE
            SYNTAX DisplayString (SIZE(0..32))
            MAX-ACCESS read-only
            STATUS current
            DESCRIPTION  
            "Applicable to all units.
             The country code and country name or country group name 
             that is supported by the unit."
            ::= { bwaVLCountryDependentParameters 1 }

    bwaVLCountryDependentParamsTable  OBJECT-TYPE
            SYNTAX SEQUENCE OF BwaVLCountryDependentParameterEntry
            MAX-ACCESS not-accessible
            STATUS current
            DESCRIPTION
            "Applicable to all units. A table of country dependent parameters."
            ::= {bwaVLCountryDependentParameters 2}

    bwaVLCountryDependentParameterEntry OBJECT-TYPE
            SYNTAX BwaVLCountryDependentParameterEntry
            MAX-ACCESS not-accessible
            STATUS current
            DESCRIPTION
            "Applicable to all units. 
             An entry in the Country Dependent Parameters table."  
             INDEX { bwaVLCountryDependentParameterTableIdx }
            ::= { bwaVLCountryDependentParamsTable 1 }

    BwaVLCountryDependentParameterEntry ::= SEQUENCE {
            bwaVLCountryDependentParameterTableIdx     INTEGER,
            bwaVLCountryDependentParameterFrequencies  DisplayString,
			bwaVLAllowedBandwidth                      INTEGER,
			bwaVLRegulationMaxTxPowerAtAntennaPort	  INTEGER,
			bwaVLRegulationMaxEIRP					  INTEGER,
			bwaVLMinModulationLevel                    INTEGER,
			bwaVLMaxModulationLevel                    INTEGER,
			bwaVLBurstModeSupport                      INTEGER,
			bwaVLMaximumBurstDuration                  INTEGER,
			bwaVLDfsSupport							  INTEGER,
			bwaVLMinimumHwRevision                     INTEGER
            }
               
    bwaVLCountryDependentParameterTableIdx  OBJECT-TYPE
            SYNTAX INTEGER  (1..5)
            MAX-ACCESS read-only
            STATUS current
            DESCRIPTION 
            "Applicable to all units. 
             The sub-band ID of the entry in the Country Dependent 
             Parameters table. Serves also as index for the table entry."
           ::= { bwaVLCountryDependentParameterEntry 1 }

    bwaVLCountryDependentParameterFrequencies   OBJECT-TYPE
            SYNTAX DisplayString  
            MAX-ACCESS read-only
            STATUS current
            DESCRIPTION 
            "Applicable to all units. 
             The frequencies included in the applicable sub-band entry."
           ::= { bwaVLCountryDependentParameterEntry 2 }
	
    bwaVLAllowedBandwidth   OBJECT-TYPE
            SYNTAX INTEGER  
            MAX-ACCESS read-only
            STATUS current
            DESCRIPTION 
            "Applicable to all units. 
             The bandwidth when using the applicable the sub-band."
           ::= { bwaVLCountryDependentParameterEntry 3 }

    bwaVLRegulationMaxTxPowerAtAntennaPort  OBJECT-TYPE
            SYNTAX INTEGER  
            MAX-ACCESS read-only
            STATUS current
            DESCRIPTION 
            "Applicable to all units. 
             The maximum allowed Tx power when using the applicable sub-band.
             A RegulationMaxTxPowerAtAntennaPort of 255, means no limit"
           ::= { bwaVLCountryDependentParameterEntry 4 }
 
    bwaVLRegulationMaxEIRP   OBJECT-TYPE
            SYNTAX INTEGER  
            MAX-ACCESS read-only
            STATUS current
            DESCRIPTION 
            "Applicable to all units.
             The maximum Tx EIRP 
             when using the applicable sub-band.
             A Regulation Max EIRP of 0, means no limit."
           ::= { bwaVLCountryDependentParameterEntry 5 }


    bwaVLMinModulationLevel  OBJECT-TYPE
            SYNTAX INTEGER {  level1 (1), 
                              level2 (2), 
                              level3 (3), 
                              level4 (4), 
                              level5 (5), 
                              level6 (6), 
                              level7 (7),
                              level8 (8)
                            } 
            MAX-ACCESS read-only
            STATUS current
            DESCRIPTION 
            "Applicable to all units. 
             The minimum supported modulation level."
           ::= { bwaVLCountryDependentParameterEntry 6 }

    bwaVLMaxModulationLevel  OBJECT-TYPE
            SYNTAX INTEGER {  level1 (1), 
                              level2 (2), 
                              level3 (3), 
                              level4 (4), 
                              level5 (5), 
                              level6 (6), 
                              level7 (7),
                              level8 (8)
                            } 
            MAX-ACCESS read-only
            STATUS current
            DESCRIPTION 
            "Applicable to all units. 
             The maximum supported modulation level."
           ::= { bwaVLCountryDependentParameterEntry 7 }
	
    bwaVLBurstModeSupport  OBJECT-TYPE
            SYNTAX INTEGER  {supported(1), notSupported(2)}
            MAX-ACCESS read-only
            STATUS current
            DESCRIPTION 
            "Applicable to all units. 
             The supported Burst Mode Option."
           ::= { bwaVLCountryDependentParameterEntry 8}

    bwaVLMaximumBurstDuration   OBJECT-TYPE
            SYNTAX INTEGER 
            MAX-ACCESS read-only
            STATUS current
            DESCRIPTION 
            "Applicable to all units. 
             Applicable only if Burst Mode Option is supported. 
             The maximum supported burst duration."
           ::= { bwaVLCountryDependentParameterEntry 9}

	 
    bwaVLDfsSupport  OBJECT-TYPE
            SYNTAX INTEGER  {supported(1), notSupported(2)}
            MAX-ACCESS read-only
            STATUS current
            DESCRIPTION 
            "Applicable to AU/BU only. 
             The supported Dfs Option."
           ::= { bwaVLCountryDependentParameterEntry 10}
	
    bwaVLMinimumHwRevision  OBJECT-TYPE
            SYNTAX INTEGER {hwRevisionA (1), hwRevisionB (2), 
                            hwRevisionC (3), hwRevisionD (4), 
                            hwRevisionE (5), na (255)}
            MAX-ACCESS read-only
            STATUS current
            DESCRIPTION 
            "Applicable to all units. 
             The Minimum HW Revision needed to support the country code."
           ::= { bwaVLCountryDependentParameterEntry 11}
 

    bwaVLAuthenticationEncryptionSupport OBJECT-TYPE
            SYNTAX INTEGER  {supported(1), notSupported(2)}
            MAX-ACCESS read-only
            STATUS current
            DESCRIPTION  
            "Applicable to all units.
             The supported Authentication Encryption Option."
            ::= { bwaVLCountryDependentParameters 3 }

    bwaVLDataEncryptionSupport OBJECT-TYPE
            SYNTAX INTEGER  {supported(1), notSupported(2)}
            MAX-ACCESS read-only
            STATUS current
            DESCRIPTION  
            "Applicable to all units.
             The supported Data Encryption Option."
            ::= { bwaVLCountryDependentParameters 4 }

    bwaVLAESEncryptionSupport OBJECT-TYPE
            SYNTAX INTEGER  {supported(1), notSupported(2)}
            MAX-ACCESS read-only
            STATUS current
            DESCRIPTION  
            "Applicable to all units.
             The supported AES Encryption Option."
            ::= { bwaVLCountryDependentParameters 5 }

    bwaVLAntennaGainChange OBJECT-TYPE
            SYNTAX INTEGER {supported(1), notSupported(2)}
            MAX-ACCESS read-only
            STATUS current
            DESCRIPTION  
            "Applicable to all units.  
             Indicates whether the Antenna Gain parameter is changeable or fixed." 
            ::= { bwaVLSysInfo 19 }

    bwaVLAteTestResults OBJECT-TYPE
            SYNTAX INTEGER { none(0), pass(1), fail(2) }
            MAX-ACCESS read-only
            STATUS current
            DESCRIPTION  
            "Applicable to all units.  
            Results of ATE Test " 
            ::= { bwaVLSysInfo 20 }

    bwaVLSerialNumber OBJECT-TYPE
            SYNTAX DisplayString (SIZE(0..35))
            MAX-ACCESS read-only
            STATUS current
            DESCRIPTION  
            "Applicable to all units.  
            Serial Number of the unit" 
            ::= { bwaVLSysInfo 21 }

-- Unit Control
-- ============
bwaVLUnitControl       OBJECT IDENTIFIER ::= {bwaVLMib 2}

    bwaVLResetUnit OBJECT-TYPE
            SYNTAX  INTEGER { cancel (1), resetSystemNow (2) }  
            MAX-ACCESS read-write
            STATUS current
            DESCRIPTION  
            "Applicable to all units.  
             Resets the unit and applies new parameter values."
            ::= { bwaVLUnitControl 1 }


    bwaVLSetDefaults OBJECT-TYPE
            SYNTAX  INTEGER {  noDefaultSettingRequested (0),
                               completeFactory  (1), 
                               partialFactory   (2), 
                               completeOperator (3), 
                               partialOperator  (4), 
                               cancelCurrentPendingRequest(5) }  
            MAX-ACCESS read-write
            STATUS current
            DESCRIPTION  
            "Applicable to all units.  
             Sets unit configuration to Defaults values after the 
             next reset.    
             noDefaultSettingRequested : Read-Only Option, no Default setting was Issued.
             completeFactory : All parameters revert to Factory 
                               Defaults values.
             partialFactory  : All parameters revert to Factory 
                               Defaults values, except the parameters 
                               required for maintaining wireless 
                               connectivity.    
             completeOperator: All parameters revert to Operator 
                               Defaults values. 
             partialOperator : All parameters revert to Operator 
                               Defaults values, except the parameters 
                               required for maintaining wireless 
                               connectivity.
             cancelCurrentPendingRequest : Default Setting request is cancelled."
            ::= { bwaVLUnitControl 2 }

    bwaVLUnitName OBJECT-TYPE
            SYNTAX DisplayString (SIZE(0..32))
            MAX-ACCESS read-write
            STATUS current
            DESCRIPTION  
            "Applicable to all units.  
             The unit name. 
             A string of up to 32 printable ASCII characters."
            ::= { bwaVLUnitControl 3 }

    bwaVLFlashMemoryControl OBJECT-TYPE
            SYNTAX  INTEGER { resetAndBootFromShadowVersion (1), 
                              useRunningVersionAfterReset (2),cancel(3) }  
            MAX-ACCESS read-write
            STATUS current
            DESCRIPTION  
            "Applicable to all units.  
             resetAndBootFromShadowVersion : Activates the backup 
                                             version.   
             useRunningVersionAfterReset   : The currently active 
                                             version will become the main 
                                             version and will be activated 
                                             after next reset."
            ::= { bwaVLUnitControl 4 }


    bwaVLTelnetLogoutTimer  OBJECT-TYPE
            SYNTAX  INTEGER   
            MAX-ACCESS read-write
            STATUS current
            DESCRIPTION  
            "Applicable to all units.  
             Time-out of management via Telnet program. 
             Automatic exit if the program is inactive for the 
             defined time.
             Range: 1 to 999 (minutes)."
            ::= { bwaVLUnitControl 5 }

    bwaVLSaveCurrentConfigurationAsOperatorDefaults OBJECT-TYPE
            SYNTAX  INTEGER { saveAsDefaults (1),cancel(2) }  
            MAX-ACCESS read-write
            STATUS current
            DESCRIPTION  
            "Applicable to all units.  
             Saves the current configuration as Operator Defaults.
             Cannot be executed after requesting set defaults 
             and the unit was not reset."
            ::= { bwaVLUnitControl 6 }

    bwaVLExitTelnet OBJECT-TYPE
            SYNTAX  INTEGER { cancelOperation (1), exit (2)}  
            MAX-ACCESS read-write
            STATUS current
            DESCRIPTION  
            "Applicable to all units.  
             Exit the management via Telnet program."
            ::= { bwaVLUnitControl 7 }

bwaVLUnitPasswords     OBJECT IDENTIFIER ::= {bwaVLUnitControl 8}

    bwaVLReadOnlyPassword OBJECT-TYPE
            SYNTAX DisplayString (SIZE(1..8))
            MAX-ACCESS read-write
            STATUS current
            DESCRIPTION  
            "Applicable to all units. 
             The User (read only) password.
             This is also the Read Community String.
             Up to 8 printable ASCII characters."
            ::= { bwaVLUnitPasswords 1 }

    bwaVLInstallerPassword OBJECT-TYPE
            SYNTAX DisplayString (SIZE(1..8))
            MAX-ACCESS read-write
            STATUS current
            DESCRIPTION  
            "Applicable to all units. 
             The Installer password.
             Up to 8 printable ASCII characters."
            ::= { bwaVLUnitPasswords 2 }

    bwaVLAdminPassword OBJECT-TYPE
            SYNTAX DisplayString (SIZE(1..8))
            MAX-ACCESS read-write
            STATUS current
            DESCRIPTION  
            "Applicable to all units. 
            The Administrator password. Accessible only with SNMP Write 
            Community String (administrator password). 
            Up to 8 printable ASCII characters."
            ::= { bwaVLUnitPasswords 3 }


    bwaVLEthernetNegotiationMode  OBJECT-TYPE
            SYNTAX INTEGER { force10MbpsAndHalfDuplex   (1),
            				 force10MbpsAndFullDuplex   (2),
							 force100MbpsAndHalfDuplex  (3),
							 force100MbpsAndFullDuplex  (4),
							 autoNegotiationMode        (5) }
            MAX-ACCESS read-write
            STATUS current
            DESCRIPTION  
            "Applicable to all units.  
             The speed/duplex mode of the Ethernet port." 
            ::= { bwaVLUnitControl 9 }

bwaVLFTPParameters      OBJECT IDENTIFIER ::= {bwaVLUnitControl 10}

bwaVLFTPServerParams      OBJECT IDENTIFIER ::= {bwaVLFTPParameters 1}

    bwaVLFTPServerUserName OBJECT-TYPE
            SYNTAX  DisplayString (SIZE(0..18))  
            MAX-ACCESS read-write
            STATUS current
            DESCRIPTION  
            "Applicable to all units. 
             The user name to be used for access to the FTP server. 
             Accessible only with SNMP Write Community String 
             (administrator password)." 
            ::= { bwaVLFTPServerParams 1 }

    bwaVLFTPServerPassword OBJECT-TYPE
            SYNTAX  DisplayString (SIZE(0..18))  
            MAX-ACCESS read-write
            STATUS current
            DESCRIPTION  
            "Applicable to all units. 
             The password to be used for access to the FTP server. 
             Accessible only with SNMP Write Community String 
             (administrator password)." 
            ::= { bwaVLFTPServerParams 2 }

    bwaVLFTPClientIPAddress OBJECT-TYPE
            SYNTAX  IpAddress  
            MAX-ACCESS read-write
            STATUS current
            DESCRIPTION  
            "Applicable to all units.  
             For SW version higher than 4.0 this is read-only. 
             The IP address of the FTP stack in the unit." 
            ::= { bwaVLFTPServerParams 3 }  

    bwaVLFTPServerIpAddress OBJECT-TYPE
            SYNTAX  IpAddress  
            MAX-ACCESS read-write
            STATUS current
            DESCRIPTION  
            "Applicable to all units.  
             The IP address of the FTP server." 
            ::= { bwaVLFTPServerParams 4 }  

    bwaVLFTPClientMask OBJECT-TYPE
            SYNTAX  IpAddress  
            MAX-ACCESS read-write
            STATUS current
            DESCRIPTION  
            "Applicable to all units.  
             The Mask of the FTP stack in the unit." 
            ::= { bwaVLFTPServerParams 5 }  


    bwaVLFTPGatewayIpAddress OBJECT-TYPE
            SYNTAX  IpAddress  
            MAX-ACCESS read-write
            STATUS current
            DESCRIPTION  
            "Applicable to all units.  
             The FTP Gateway address"
            ::= { bwaVLFTPServerParams 6 }  


bwaVLFTPSwDownload      OBJECT IDENTIFIER ::= {bwaVLFTPParameters 2}

   bwaVLFTPSwFileName  OBJECT-TYPE
            SYNTAX DisplayString (SIZE(1..20))
            MAX-ACCESS read-write
            STATUS current
            DESCRIPTION  
            "Applicable to all units.  
             The name of the SW file to be downloaded."
            ::= { bwaVLFTPSwDownload 1 }

   bwaVLFTPSwSourceDir  OBJECT-TYPE
            SYNTAX DisplayString (SIZE(0..80))
            MAX-ACCESS read-write
            STATUS current
            DESCRIPTION  
            "Applicable to all units.  
             The source directory of the required file in the FTP server.
             Up to 80 printable ASCII characters.
             Use dot (.) To clear field"
            ::= { bwaVLFTPSwDownload 2 }

    bwaVLFTPDownloadSwFile OBJECT-TYPE
            SYNTAX  INTEGER { downloadFile (1) , cancel (2)}  
            MAX-ACCESS read-write
            STATUS current
            DESCRIPTION  
            "Applicable to all units.  
             Execution  of the SW download operation" 
            ::= { bwaVLFTPSwDownload 3 }

bwaVLConfigurationFileLoading      OBJECT IDENTIFIER ::= {bwaVLFTPParameters 3}

   bwaVLConfigurationFileName  OBJECT-TYPE
            SYNTAX DisplayString (SIZE(1..20))
            MAX-ACCESS read-write
            STATUS current
            DESCRIPTION  
            "Applicable to all units.  
             The name of the configuration file to be downloaded/uploaded."
            ::= { bwaVLConfigurationFileLoading 1 }

   bwaVLOperatorDefaultsFileName  OBJECT-TYPE
            SYNTAX DisplayString (SIZE(1..20))
            MAX-ACCESS read-write
            STATUS current
            DESCRIPTION  
            "Applicable to all units.  
             The name of the Operator Defaults file to be downloaded/uploaded"
            ::= { bwaVLConfigurationFileLoading 2 }

   bwaVLFTPConfigurationFileSourceDir  OBJECT-TYPE
            SYNTAX DisplayString (SIZE(0..80))
            MAX-ACCESS read-write
            STATUS current
            DESCRIPTION  
            "Applicable to all units.  
             The source directory of the required file in the FTP server.
             Up to 80 printable ASCII characters.
             Use dot (.) To clear field"
            ::= { bwaVLConfigurationFileLoading 3 }

    bwaVLExecuteFTPConfigurationFileLoading OBJECT-TYPE
            SYNTAX  INTEGER {executeFTPGetConfigurationFile (1), executeFTPPutConfigurationFile (2),
							 executeFTPGetOperatorDefaults  (3) , executeFTPPutOperatorDefaults (4), cancel (5) }  
            MAX-ACCESS read-write
            STATUS current
            DESCRIPTION  
            "Applicable to all units.  
             Execution of the file download/upload operation." 
            ::= { bwaVLConfigurationFileLoading 4 }



bwaVLEventLogFileUploading   OBJECT IDENTIFIER ::= {bwaVLFTPParameters 4}

   bwaVLEventLogFileName  OBJECT-TYPE
            SYNTAX DisplayString (SIZE(1..20))
            MAX-ACCESS read-write
            STATUS current
            DESCRIPTION  
            "Applicable to all units.  
             The name of the Event Log file to be uploaded."
            ::= { bwaVLEventLogFileUploading 1 }

   bwaVLEventLogDestinationDir  OBJECT-TYPE
            SYNTAX DisplayString (SIZE(0..80))
            MAX-ACCESS read-write
            STATUS current
            DESCRIPTION  
            "Applicable to all units.  
             The destination directory of the event log file.
             Up to 80 printable ASCII characters.
             Use dot (.) To clear field."
            ::= { bwaVLEventLogFileUploading 2 }

    bwaVLUploadEventLogFile OBJECT-TYPE
            SYNTAX  INTEGER { uploadFile (1) , cancel (2)}  
            MAX-ACCESS read-write
            STATUS current
            DESCRIPTION  
            "Applicable to all units.  
             Execution  of the event log upload operation." 
            ::= { bwaVLEventLogFileUploading 3 }

    bwaVLLoadingStatus OBJECT-TYPE
            SYNTAX  INTEGER {inProcess (1), successful (2), failed (3)}  
            MAX-ACCESS read-only
            STATUS current
            DESCRIPTION  
            "Applicable to all units.  
             The status of the last loading operation."
            ::= { bwaVLUnitControl 11 }

bwaVLEventLogFileParams   OBJECT IDENTIFIER ::= {bwaVLUnitControl 12}

   bwaVLEventLogPolicy  OBJECT-TYPE
            SYNTAX INTEGER {message (1), warning (2), error (3),fatal(4), logNone(5)}
            MAX-ACCESS read-write
            STATUS current
            DESCRIPTION  
            "Applicable to all units.  
              The lowest level event to be registered in the event log."
            ::= { bwaVLEventLogFileParams 1 }

   bwaVLEraseEventLog  OBJECT-TYPE
            SYNTAX INTEGER { eraseEventLog (1),cancel(2) }
            MAX-ACCESS read-write
            STATUS current
            DESCRIPTION  
            "Applicable to all units.  
              Erase the event log."
            ::= { bwaVLEventLogFileParams 2 }

    bwaVLSystemLocation OBJECT-TYPE
            SYNTAX DisplayString (SIZE(0..34))
            MAX-ACCESS read-write
            STATUS current
            DESCRIPTION  
            "Applicable to all units.  
             The unit location."
            ::= { bwaVLUnitControl 13 }

bwaVLFeatureUpgrade   OBJECT IDENTIFIER ::= {bwaVLUnitControl 14}
   
    bwaVLFeatureUpgradeManually OBJECT-TYPE
            SYNTAX DisplayString (SIZE(32..64))
            MAX-ACCESS read-write
            STATUS current
            DESCRIPTION  
            "Applicable to all units.  
             Upgrade unit to support new feature. Enter your license number 
             (32 to 64 hex digits)."
            ::= { bwaVLFeatureUpgrade 1 }

bwaVLChangeUnitType  OBJECT-TYPE
            SYNTAX INTEGER { bu(1), rb(2), cancel(3) }
            MAX-ACCESS read-write
            STATUS current
            DESCRIPTION  
            "Applicable RB/BU only.  
             Change the unit type between BU and RB."
            ::= { bwaVLUnitControl 15 }

   bwaLighteAPWorkingMode OBJECT-TYPE
        	SYNTAX  INTEGER  
        	MAX-ACCESS read-write
        	STATUS current
        	DESCRIPTION 
        	"Applicable to AU only. 
         	Change unit running mode: 0 - VL mode 1 - Mixed cell mode" 
			::= { bwaVLUnitControl 16 }


-- Network Management Params
-- =========================
   bwaVLNwMngParameters   OBJECT IDENTIFIER ::= {bwaVLMib 3}

    bwaVLAccessToNwMng OBJECT-TYPE
           SYNTAX   INTEGER { fromWirelessOnly  (1), 
                              fromEthernetOnly (2), 
                              fromBothWirelessAndEthernet  (3), 
                              na (255) } 
            MAX-ACCESS read-write
            STATUS current
            DESCRIPTION 
            "Applicable to all units.  
             The port to be used for remote management."
            ::= { bwaVLNwMngParameters 1 }


    bwaVLNwMngFilter OBJECT-TYPE
             SYNTAX INTEGER { disable (1),
                              activateOnEthernetPort (2), 
                              activateOnWirelessPort  (3), 
                              activateOnBothWirelessAndEthernet  (4), 
                              na (255) } 
            MAX-ACCESS read-write
            STATUS current
            DESCRIPTION 
            "Applicable to all units.  
             Disables or enable on one of the ports, or on both 
             ports, IP address based filtering of management messages 
             (e.g. SNMP , Telnet , TFTP , DHCP)."
           ::= { bwaVLNwMngParameters 2 }




    mngIpFilterTable OBJECT-TYPE
            SYNTAX SEQUENCE OF MngIpFilterEntry
            MAX-ACCESS not-accessible
            STATUS current
            DESCRIPTION
            "Applicable to all units.  
             A Management IP Filter Table of up to 3 IP addresses 
             of devices that are authorized to access the unit 
             for management purposes." 
            ::= { bwaVLNwMngParameters 3 }

    mngIpFilterEntry  OBJECT-TYPE
            SYNTAX MngIpFilterEntry
            MAX-ACCESS not-accessible
            STATUS current
            DESCRIPTION
            "Applicable to all units.  
             A Management IP Filter Table entry."
            INDEX { bwaVLNwMngIpTableIdx }
            ::= { mngIpFilterTable 1 }

    MngIpFilterEntry ::= SEQUENCE { bwaVLNwMngIpAddress   IpAddress,
                                    bwaVLNwMngIpTableIdx  INTEGER }
   
    bwaVLNwMngIpAddress   OBJECT-TYPE
            SYNTAX IpAddress  
            MAX-ACCESS read-write
            STATUS current
            DESCRIPTION 
            "Applicable to all units.  
             An IP address in the Management IP Filter Table."
          ::= { mngIpFilterEntry 1 }

    bwaVLNwMngIpTableIdx   OBJECT-TYPE
            SYNTAX INTEGER (1..10) 
            MAX-ACCESS read-only
            STATUS current
            DESCRIPTION 
            "Applicable to all units.  
             A table index for an entry in the Management IP Filter 
             Table."
         ::= { mngIpFilterEntry 2 }


    bwaVLDeleteOneNwIpAddr OBJECT-TYPE
            SYNTAX  INTEGER (0 | 1..10 | 255) 
            MAX-ACCESS read-write
            STATUS current
            DESCRIPTION 
            "Applicable to all units.  
             0 - cancel operation.
             1..10 - Deletes a single selected entry from the Management IP 
             Filter Table."
            ::= { bwaVLNwMngParameters 4 }

    bwaVLDeleteAllNwIpAddrs OBJECT-TYPE
            SYNTAX INTEGER { deleteAll (1), cancelOperation (2), na (255) } 
            MAX-ACCESS read-write
            STATUS current
            DESCRIPTION 
            "Applicable to all units.  
             Deletes all entries from the Management IP Filter Table."
            ::= { bwaVLNwMngParameters 5 }

    bwaVLAccessToNwTrap OBJECT-TYPE
            SYNTAX INTEGER { disable(1), enable(2) } 
            MAX-ACCESS read-write
            STATUS current
            DESCRIPTION 
            "Applicable to all units.  
             Enables or disables sending of traps."
            ::= { bwaVLNwMngParameters 6 }

    mngTrapTable OBJECT-TYPE
            SYNTAX SEQUENCE OF MngTrapEntry
            MAX-ACCESS not-accessible
            STATUS current
            DESCRIPTION
            "Applicable to all units.  
             A Management Trap Table of up to 10 IP addresses of 
             stations to send traps to." 
            ::= { bwaVLNwMngParameters 7 }

    mngTrapEntry  OBJECT-TYPE
            SYNTAX MngTrapEntry
            MAX-ACCESS not-accessible
            STATUS current
            DESCRIPTION
            "Applicable to all units.  
             A Management Trap Table entry." 
            INDEX { bwaVLNwTrapTableIdx }
            ::= { mngTrapTable 1 }
                                
    MngTrapEntry ::= SEQUENCE { bwaVLNwMngTrapCommunity DisplayString,
                                bwaVLNwMngTrapAddress   IpAddress,
                                bwaVLNwTrapTableIdx     INTEGER }
                                
    bwaVLNwMngTrapCommunity OBJECT-TYPE
            SYNTAX DisplayString (SIZE(0..14))
            MAX-ACCESS read-write
            STATUS current
            DESCRIPTION  
            "Applicable to all units.  
             The trap community associated with the applicable 
             entry in the Management Trap Table.
             Up to 14 printable case sensitive ASCII characters."
            ::= { mngTrapEntry 1 }

    bwaVLNwMngTrapAddress   OBJECT-TYPE
            SYNTAX  IpAddress  
            MAX-ACCESS read-write
            STATUS current
            DESCRIPTION  
            "Applicable to all units.  
             An IP address in the Management Trap Table entry." 
        ::= { mngTrapEntry 2 }

    bwaVLNwTrapTableIdx   OBJECT-TYPE
            SYNTAX  INTEGER (1..10) 
            MAX-ACCESS read-only
            STATUS current
            DESCRIPTION  
            "Applicable to all units.  
             Tables Index for an entry in the Management Trap Table."
        ::= { mngTrapEntry 3 }


    bwaVLDeleteOneTrapAddr OBJECT-TYPE
            SYNTAX  INTEGER (0 | 1..10 | 255)
            MAX-ACCESS read-write
            STATUS current
            DESCRIPTION  
            "Applicable to all units.  
             0 - cancel operation.
             1..10 - Deletes a single selected entry from the Management 
             Trap Table."
            ::= { bwaVLNwMngParameters 8 }


    bwaVLDeleteAllTrapAddrs OBJECT-TYPE
            SYNTAX  INTEGER { deleteAll (1),cancelOperation (2),  na (255) } 
            MAX-ACCESS read-write
            STATUS current
            DESCRIPTION  
            "Applicable to all units.  
             Deletes all entries from the Management Trap Table."
            ::= { bwaVLNwMngParameters 9 }

	bwaVLMngIpRangesTable OBJECT-TYPE
            SYNTAX SEQUENCE OF BwaVLMngIpRangeEntry
            MAX-ACCESS not-accessible
            STATUS current
            DESCRIPTION
            "Applicable to all units.  
             Table of Management IP Address Ranges" 
            ::= { bwaVLNwMngParameters 10 }

    bwaVLMngIpRangeEntry  OBJECT-TYPE
            SYNTAX BwaVLMngIpRangeEntry
            MAX-ACCESS not-accessible
            STATUS current
            DESCRIPTION
            "Applicable to all units.  
             A Management IP Address Ranges Table entry" 
            INDEX { bwaVLMngIpRangeIdx }
            ::= { bwaVLMngIpRangesTable 1 }
                                
    BwaVLMngIpRangeEntry ::= SEQUENCE { 
								bwaVLMngIpRangeIdx		INTEGER,
								bwaVLMngIpRangeFlag		INTEGER,					
                                bwaVLMngIpRangeStart     IpAddress,
                                bwaVLMngIpRangeEnd		IpAddress,
                                bwaVLMngIpRangeMask		IpAddress
                                }
               
 
    bwaVLMngIpRangeIdx OBJECT-TYPE
            SYNTAX  INTEGER (1..10)  
            MAX-ACCESS read-only
            STATUS current
            DESCRIPTION  
            "Applicable to all units.  
             Index of an entry in the Management IP Address Ranges Table"
            ::= { bwaVLMngIpRangeEntry 1 }

    bwaVLMngIpRangeFlag OBJECT-TYPE
            SYNTAX  INTEGER { rangeDefinedByStartEndAddr(1), rangeDefinedByStartAddrMask(2)}  
            MAX-ACCESS read-write
            STATUS current
            DESCRIPTION  
            "Applicable to all units.  
             Defines the method of defining the range:
             Using Start & End Address( rangeDefinedByStartEndAddr ),
             or using Start Address and Mask ( rangeDefinedByStartAddrSubNetMask )."
            ::= { bwaVLMngIpRangeEntry 2 }

    
    bwaVLMngIpRangeStart OBJECT-TYPE
            SYNTAX  IpAddress
            MAX-ACCESS read-write
            STATUS current
            DESCRIPTION  
            "Applicable to all units.  
             Start Address of the range"
            ::= { bwaVLMngIpRangeEntry 3 }
    
    bwaVLMngIpRangeEnd OBJECT-TYPE
            SYNTAX  IpAddress
            MAX-ACCESS read-write
            STATUS current
            DESCRIPTION  
            "Applicable to all units.  
             End Address of the range. 
             Used only if bwaVLMngIpRangeFlag is  rangeDefinedByStartEndAddr"
            ::= { bwaVLMngIpRangeEntry 4 }
            
	bwaVLMngIpRangeMask OBJECT-TYPE
            SYNTAX  IpAddress
            MAX-ACCESS read-write
            STATUS current
            DESCRIPTION  
			"Applicable to all units.  
             End Address of the range. 
             Used only if bwaVLMngIpRangeFlag is  rangeDefinedByStartAddrMask"
            ::= { bwaVLMngIpRangeEntry 5 } 
            
	bwaVLDeleteOneNwIpRange OBJECT-TYPE
            SYNTAX  INTEGER (0 | 1..10 | 255) 
            MAX-ACCESS read-write
            STATUS current
            DESCRIPTION 
            "Applicable to all units.  
             0 - cancel operation.
             1..10 - Deletes a single selected entry from the Management IP 
             Ranges Table."
            ::= { bwaVLNwMngParameters 11 }
            
    
	bwaVLDeleteAllNwIpRanges OBJECT-TYPE
            SYNTAX INTEGER { deleteAll (1), cancelOperation (2), na (255) } 
            MAX-ACCESS read-write
            STATUS current
            DESCRIPTION 
            "Applicable to all units.  
             Deletes all entries from the Management IP Ranges Table."
            ::= { bwaVLNwMngParameters 12 }

	bwaVLApClientIpAddress    OBJECT-TYPE
            SYNTAX  IpAddress
            MAX-ACCESS read-write
            STATUS current
            DESCRIPTION 
            "Applicable to SU/RB unit only.  
             The IP Address of the WIFI WIMAX unit"
            ::= { bwaVLNwMngParameters 13 }

-- IP Params:
-- ===========
bwaVLIpParams      OBJECT IDENTIFIER ::= {bwaVLMib 4}

    bwaVLUnitIpAddress OBJECT-TYPE
            SYNTAX  IpAddress  
            MAX-ACCESS read-write
            STATUS current
            DESCRIPTION  
            "Applicable to all units.  
             IP address of the unit."
            ::= { bwaVLIpParams 1 }

    bwaVLSubNetMask OBJECT-TYPE
            SYNTAX  IpAddress  
            MAX-ACCESS read-write
            STATUS current
            DESCRIPTION  
            "Applicable to all units.  
             Subnet mask of the unit."
            ::= { bwaVLIpParams 2 }

    bwaVLDefaultGWAddress OBJECT-TYPE
            SYNTAX  IpAddress  
            MAX-ACCESS read-write
            STATUS current
            DESCRIPTION  
            "Applicable to all units.  
             Default gateway IP address of the unit."
            ::= { bwaVLIpParams 3 }

    bwaVLUseDhcp OBJECT-TYPE
            SYNTAX  INTEGER{ disable (1), 
                             dhcpOnly (2), 
                             automatic (3) }
            MAX-ACCESS  read-write    
            STATUS  current
            DESCRIPTION
            "Applicable to all units.  
             DHCP client mode of operation. 
             disabled : Use regular (manual) methods to configure IP 
                        parameters. 
             dHCP Only: Use DHCP server to configure IP parameters. 
             automatic: Use DHCP server to configure IP parameters. 
                        If a DHCP server is not available, use 
                        manually configured values."
            ::= { bwaVLIpParams 4 }

    bwaVLAccessToDHCP OBJECT-TYPE
            SYNTAX  INTEGER{ fromWirelessOnly    (1),
                             fromEthernetOnly (2),
                             fromBothWirelessAndEthernet (3) }
            MAX-ACCESS  read-write    
            STATUS  current
            DESCRIPTION
            "Applicable to all units.  
             The port to be used for communicating with a DHCP server."
            ::= { bwaVLIpParams 5 }

    bwaVLRunTimeIPaddr OBJECT-TYPE
            SYNTAX  IpAddress
            MAX-ACCESS  read-only
            STATUS  current
            DESCRIPTION
            "Applicable to all units.  
             The run-time IP address. If DHCP is used the Run Time 
             IP Address is the address given to the unit by the 
             server. Otherwise it is the manually configured address."
            ::= { bwaVLIpParams 6 }

    bwaVLRunTimeSubNetMask OBJECT-TYPE
            SYNTAX  IpAddress
            MAX-ACCESS  read-only
            STATUS  current
            DESCRIPTION
            "Applicable to all units.  
             The run-time Subnet Mask. If DHCP is used the Run Time 
             Subnet Mask is the mask given to the unit by the server. 
             Otherwise it is the manually configured mask."
            ::= { bwaVLIpParams 7 }

    bwaVLRunTimeDefaultIPGateway OBJECT-TYPE
            SYNTAX  IpAddress
            MAX-ACCESS  read-only
            STATUS  current
            DESCRIPTION
            "Applicable to all units.  
             The run-time Gateway IP address. If DHCP is used the 
             Run Time Gateway IP Address is the address given to the 
             unit by the server. Otherwise it is the manually 
             configured address."
            ::= { bwaVLIpParams 8 }


-- Bridge Params
-- ==============
bwaVLBridgeParameters      OBJECT IDENTIFIER ::= {bwaVLMib 5}


bwaVLVLANSupport       OBJECT IDENTIFIER ::= {bwaVLBridgeParameters 1}

    bwaVLVlanID OBJECT-TYPE
            SYNTAX  INTEGER 
            MAX-ACCESS read-write
            STATUS current
            DESCRIPTION  
            "Applicable to SU/RB only.
             VLAN ID for data frame tagging. 
             Applicable to Access Link only. 
             Range: 1 to 4094. 0 - not applicable."
            ::= { bwaVLVLANSupport 1 }

    bwaVLEthernetLinkType OBJECT-TYPE
            SYNTAX  INTEGER { accessLink (1), 
                              trunkLink (2), 
                              hybridLink (3),
                              serviceProviderLink (4) }
            MAX-ACCESS read-write
            STATUS current
            DESCRIPTION  
            "Applicable to all units.  
             VLAN support mode (Link Type). 
             The Access Link option is not available for AU/BU.
             Service Provider Link is not available for BU/RB."
            ::= { bwaVLVLANSupport 2 }
 
    bwaVLManagementVlanID OBJECT-TYPE
            SYNTAX  INTEGER 
            MAX-ACCESS read-write
            STATUS current
            DESCRIPTION  
            "Applicable to all units.  
             VLAN ID for management frame tagging.
             Range: 1 to 4094, 65535 for No VLAN tagging."
            ::= { bwaVLVLANSupport 3 }

bwaVLVLANForwarding        OBJECT IDENTIFIER ::= {bwaVLVLANSupport 4}

     bwaVLVlanForwardingSupport OBJECT-TYPE
            SYNTAX  INTEGER { disable (1) , enable (2), na(255) } 
            MAX-ACCESS read-write
            STATUS current
            DESCRIPTION  
            "Applicable to all units.  
             Enables or disables the VLAN forwarding feature. 
             (applicable in Trunk and Service Provider links only)."
            ::= { bwaVLVLANForwarding 1 }

    bwaVLVlanForwardingTable OBJECT-TYPE
            SYNTAX SEQUENCE OF BwaVLVlanForwardingEntry
            MAX-ACCESS not-accessible
            STATUS current
            DESCRIPTION
            "Applicable to all units.  
             A VLAN Forwarding Table of up to 20 VLAN IDs of devices 
             to which data frames are forwarded when VLAN Forwarding 
             is Enabled. (applicable in Trunk and Service Provider links only)."
            ::= { bwaVLVLANForwarding 2 }

    bwaVLVlanForwardingEntry  OBJECT-TYPE
            SYNTAX BwaVLVlanForwardingEntry
            MAX-ACCESS not-accessible
            STATUS current
            DESCRIPTION
            "Applicable to all units.  
             A VLAN Forwarding Table entry. (applicable in Trunk and Service Provider 
             links only)."
            INDEX { bwaVLVlanForwardingTableIdx }
            ::= { bwaVLVlanForwardingTable 1 }

    BwaVLVlanForwardingEntry ::= SEQUENCE {
            bwaVLVlanForwardingTableIdx  INTEGER,
            bwaVLVlanIdForwarding  INTEGER
            }

         
    bwaVLVlanForwardingTableIdx   OBJECT-TYPE
            SYNTAX  INTEGER  (1..20)
            MAX-ACCESS read-only
            STATUS current
            DESCRIPTION  
            "Applicable to all units.  
             A read only table index for a VLAN entry in the VLAN 
             Forwarding Table."
        ::= { bwaVLVlanForwardingEntry 1 }

    bwaVLVlanIdForwarding   OBJECT-TYPE
            SYNTAX  INTEGER  
            MAX-ACCESS read-write
            STATUS current
            DESCRIPTION  
            "Applicable to all units.  
             The list of VLAN ID's in the VLAN ID Forwarding Table. 
             To Remove a VLAN ID - SET the corresponding entry to 0. 
             To Add a new VLAN ID SET an entry which is currently 0.
             Range : 0 to 4094"
        ::= { bwaVLVlanForwardingEntry 2 }
 
bwaVLVlanRelaying    OBJECT IDENTIFIER ::= {bwaVLVLANSupport 5}

    bwaVLVlanRelayingSupport OBJECT-TYPE
            SYNTAX  INTEGER { disable (1) , enable (2), na(255) } 
            MAX-ACCESS read-write
            STATUS current
            DESCRIPTION  
            "Applicable to AU only. 
             Not applicable to BWA-PtP products. 
             Enables or disables VLAN Relaying (applicable in 
             Trunk and Service Provider links only)."
            ::= { bwaVLVlanRelaying 1 }

    bwaVLVlanRelayingTable OBJECT-TYPE
            SYNTAX SEQUENCE OF BwaVLVlanRelayingEntry
            MAX-ACCESS not-accessible
            STATUS current
            DESCRIPTION
            "Applicable to AU only. 
			 Not applicable to BWA-PtP products.
             A VLAN Relaying Table of up to 20 VLAN IDs of devices 
             to which data frames are relayed when VLAN Relaying is 
             Enabled. (applicable in Trunk and Service Provider links only)."
            ::= { bwaVLVlanRelaying 2 }

    bwaVLVlanRelayingEntry  OBJECT-TYPE
            SYNTAX BwaVLVlanRelayingEntry
            MAX-ACCESS not-accessible
            STATUS current
            DESCRIPTION
            "Applicable to AU only.
             Not applicable to BWA-PtP products. 
             A VLAN Relaying Table entry. (applicable in Trunk and Service 
             Provider links only)."
            INDEX { bwaVLVlanRelayingTableIdx }
            ::= { bwaVLVlanRelayingTable 1 }

    BwaVLVlanRelayingEntry ::= SEQUENCE {
            bwaVLVlanRelayingTableIdx  INTEGER,
            bwaVLVlanIdRelaying  INTEGER
            }
   
    bwaVLVlanRelayingTableIdx   OBJECT-TYPE
            SYNTAX  INTEGER  (1..20)
            MAX-ACCESS read-only
            STATUS current
            DESCRIPTION  
            "Applicable to AU only. 
             Not applicable to BWA-PtP products.
             A table index for a VLAN entry in the VLAN 
             Relaying Table."
        ::= { bwaVLVlanRelayingEntry 1 }


    bwaVLVlanIdRelaying   OBJECT-TYPE
            SYNTAX  INTEGER  
            MAX-ACCESS read-write
            STATUS current
            DESCRIPTION  
            "Applicable to AU only. 
             Not applicable to BWA-PtP products.
             The list of VLAN ID's in the VLAN ID Relaying Table. 
             To Remove a VLAN ID - SET the corresponding entry to 0. 
             To Add a new VLAN ID SET an entry which is currently 0.
             Range: 0 to 4094 , 0 - remove entry."
        ::= { bwaVLVlanRelayingEntry 2 }


bwaVLVLANTrafficPriority       OBJECT IDENTIFIER ::= {bwaVLVLANSupport 6}

    bwaVLVlanDataPriority OBJECT-TYPE
            SYNTAX  INTEGER  { na(255) }
            MAX-ACCESS read-write
            STATUS current
            DESCRIPTION  
            "Applicable to SU/RB only. 
             Priority tagging for data frames. Applicable to Access 
             Link only.
             Range: 0 to 7."
            ::= { bwaVLVLANTrafficPriority 1 }
  
    bwaVLVlanManagementPriority OBJECT-TYPE
            SYNTAX  INTEGER  { na(255) }
            MAX-ACCESS read-write
            STATUS current
            DESCRIPTION  
            "Applicable to all units.  
             Priority tagging for management frames. Applicable to 
             Access Link and Trunk Link only.
             Range: 0 to 7."
            ::= { bwaVLVLANTrafficPriority 2 }

 
    bwaVLVlanPriorityThreshold OBJECT-TYPE
            SYNTAX  INTEGER  { na(255) }
            MAX-ACCESS read-write
            STATUS current
            DESCRIPTION  
            "Applicable to all units. Not applicable to units with SW 
             version 3.1 or higher. 
             Priority threshold for tagged frames received from 
             Ethernet port. Applicable to Hybrid Link and Trunk Link 
             only.
             Valid values: 0-7."
            ::= { bwaVLVLANTrafficPriority 3 }

	bwaVLVLANQinQ	OBJECT IDENTIFIER ::= {bwaVLVLANSupport 7}
	
	bwaVLQinQEthertype   OBJECT-TYPE
            SYNTAX	INTEGER  (33025 .. 36864|37120|37376)
            MAX-ACCESS read-write
            STATUS current
            DESCRIPTION  
            "Applicable to AU and SU. Not applicable to PtP units. 
            The Ethernet type of the Service Provider Tag.
            The range is  0x8101(33025) - 0x9000(36864), 0x9100(37120), 0x9200(37376)."
        ::= { bwaVLVLANQinQ 1 }
        
	bwaVLQinQProviderVlanID   OBJECT-TYPE
            SYNTAX	INTEGER (1..4094)
            MAX-ACCESS read-write
            STATUS current
            DESCRIPTION  
            "Applicable to SU only.
            VLAN ID of the Service Provider Tag."
        ::= { bwaVLVLANQinQ 2 }

    bwaVLBridgeAgingTime OBJECT-TYPE
            SYNTAX  INTEGER  
            MAX-ACCESS read-write
            STATUS current
            DESCRIPTION  
            "Applicable to all units.  
             Bridge aging time for devices on both the Ethernet and 
             wireless link sides. 
             Range: 20 to 2000 seconds."
            ::= { bwaVLBridgeParameters 2 }

    bwaVLBroadcastRelaying OBJECT-TYPE
            SYNTAX  INTEGER  {	disable (1),
								broadcastMulticastEnable (2),
								broadcastEnable (3),
								multicastEnable (4),
								na (255) }
            MAX-ACCESS read-write
            STATUS current
            DESCRIPTION  
            "Applicable to AU only. 
             Not applicable to BWA-PtP products.
             Enables/disables the relaying of broadcast messages to 
             the wireless link."
            ::= { bwaVLBridgeParameters 4 }

    bwaVLUnicastRelaying OBJECT-TYPE
            SYNTAX  INTEGER  { disable(1), enable(2), na (255) }
            MAX-ACCESS read-write
            STATUS current
            DESCRIPTION  
            "Applicable to AU only. 
             Not applicable to BWA-PtP products.
             Enables/disables the relaying of unicast messages to 
             the wireless link."
            ::= { bwaVLBridgeParameters 5 }

    bwaVLEthBroadcastFiltering OBJECT-TYPE
            SYNTAX  INTEGER { disable (1), 
                              onEthernetOnly (2), 
                              onWirelessOnly  (3),
                              onBothWirelessAndEthernet (4), 
                              na (255) } 
            MAX-ACCESS read-write
            STATUS current
            DESCRIPTION  
            "Applicable to SU/RB only. 
             Enables/disables the filtering of Ethernet (layer2) 
             broadcasts.    
             disable             : No filtering.    
             onEthernetOnly      : Filters broadcasts received on the Ethernet port only.    
             onWirelessOnly      : Filters broadcasts received on the Wlan port only.    
             onBothWirelessAndEth: Filters broadcasts received on both ports."
            ::= { bwaVLBridgeParameters 6 }                                                                        

bwaVLEthBroadcastingParameters     OBJECT IDENTIFIER ::= {bwaVLBridgeParameters 7}

    bwaVLDHCPBroadcastOverrideFilter OBJECT-TYPE
            SYNTAX  INTEGER { disable (1), enable (2), na (255) } 
            MAX-ACCESS read-write
            STATUS current
            DESCRIPTION  
            "Applicable to SU/RB only. 
             Enables or disables the broadcasting of DHCP messages, 
             overriding the general *bwaVLEthBroadcastFiltering Ethernet 
             broadcast filtering option." 
            ::= { bwaVLEthBroadcastingParameters 1 }

    bwaVLPPPoEBroadcastOverrideFilter OBJECT-TYPE
            SYNTAX  INTEGER { disable (1), enable (2), na (255) } 
            MAX-ACCESS read-write
            STATUS current
            DESCRIPTION  
            "Applicable to SU/RB only. 
             Enables or disables the broadcasting of PPPoE messages, 
             overriding the general *bwaVLEthBroadcastFiltering Ethernet 
             broadcast filtering option."
            ::= { bwaVLEthBroadcastingParameters 2 }

    bwaVLARPBroadcastOverrideFilter OBJECT-TYPE
            SYNTAX  INTEGER { disable (1), enable (2), na (255) } 
            MAX-ACCESS read-write
            STATUS current
            DESCRIPTION  
            "Applicable to SU/RB only. 
             Enables or disables the broadcasting of ARP messages, 
             overriding the general *bwaVLEthBroadcastFiltering Ethernet 
             broadcast filtering option."
            ::= { bwaVLEthBroadcastingParameters 3 }

    bwaVLEthBroadcastMulticastLimiterOption OBJECT-TYPE
            SYNTAX  INTEGER { disable (1),
							  limitOnlyBroadcasts(2),
							  limitMulticastsExceptBroadcasts(3),
							  limitAllMulticasts(4) } 
            MAX-ACCESS read-write
            STATUS current
            DESCRIPTION  
            "Applicable to all units.
            Enable/disable the limiter for multicast and broadcast packets." 
            ::= { bwaVLEthBroadcastingParameters 4 }
       
   bwaVLEthBroadcastMulticastLimiterThreshold OBJECT-TYPE
            SYNTAX  INTEGER
            MAX-ACCESS read-write
            STATUS current
            DESCRIPTION  
            "Applicable to all units.
            The limit on the number of multicast and broadcast packets when the 
            Ethernet Broadcast/Multicast Limiter Option is enabled.
            Range: 0 to 204800" 
            ::= { bwaVLEthBroadcastingParameters 5 }
            
   bwaVLEthBroadcastMulticastLimiterSendTrapInterval OBJECT-TYPE
            SYNTAX  INTEGER
            MAX-ACCESS read-write
            STATUS current
            DESCRIPTION  
            "Applicable to all units.
            The minimum time between two successive traps that are sent indicating the 
            number of packets that were dropped by the Ethernet Broadcast/Multicast 
            Limiter since the last trap was sent.
            Range: 1 to 60 minutes" 
            ::= { bwaVLEthBroadcastingParameters 6 }

bwaVLToSPriorityParameters     OBJECT IDENTIFIER ::= {bwaVLBridgeParameters 8}

    bwaVLToSPrecedenceThreshold OBJECT-TYPE
            SYNTAX  INTEGER  
            MAX-ACCESS read-write
            STATUS current
            DESCRIPTION  
            "Applicable to all units. Not applicable to units with SW version 3.1 or higher.
             Priority threshold (based on the ToS) for frames received 
             from the Ethernet port.
             Range: 0 to 7."
            ::= { bwaVLToSPriorityParameters 1 }

    bwaVLRoamingOption OBJECT-TYPE
            SYNTAX  INTEGER  { disable (1), enable (2), na(255) }
            MAX-ACCESS read-write      
            STATUS current       
            DESCRIPTION  
            "Applicable to SU/RB only.
             Disable/enable the roaming feature. When enabled, the SU/RB will start 
             scanning for an AU/BU after about one second of not receiving beacons or data 
             from current AU/BU. Once it found a new AU/BU, it will also send through 
             the wireless network a roaming SNAP on behalf of its clients informing 
             other devices in the network of their new location. When disabled, it 
             will wait for about seven seconds before starting scanning, and it will not 
             send a roaming SNAP."
            ::= { bwaVLBridgeParameters 9 }

bwaVLMacAddressDenyList  OBJECT IDENTIFIER ::= {bwaVLBridgeParameters 10}

    bwaVLMacAddressDenyListTable OBJECT-TYPE
            SYNTAX SEQUENCE OF BwaVLMacAddressDenyListEntry
            MAX-ACCESS not-accessible
            STATUS current
            DESCRIPTION
            "Applicable to AU only. 
			 Not applicable to BWA-PtP units.                                   
             A list of up to 100 MAC Addresses of SUs.
             If bwaVLMacAddressDenyListAction is set to denyList, 
             these are SUs that are not allowed to transfer data 
             to the AU. 
             If bwaVLMacAddressDenyListAction is set to allowList, 
             only these SUs are allowed to transfer data to the AU."
            ::= { bwaVLMacAddressDenyList 1 }

    bwaVLMacAddressDenyListEntry  OBJECT-TYPE
            SYNTAX BwaVLMacAddressDenyListEntry
            MAX-ACCESS not-accessible
            STATUS current
            DESCRIPTION
            "Applicable to AU only.
			 Not applicable to BWA-PtP units.                                   
             An entry in the Mac Address Deny List Table."
            INDEX { bwaVLMacAddressDenyListTableIdx }
            ::= { bwaVLMacAddressDenyListTable 1 }

    BwaVLMacAddressDenyListEntry ::= SEQUENCE {
            bwaVLMacAddressDenyListTableIdx  INTEGER,
            bwaVLMacAddressDenyListId  MacAddress
            }
        
    bwaVLMacAddressDenyListTableIdx   OBJECT-TYPE
            SYNTAX  INTEGER (1..100) 
            MAX-ACCESS read-only
            STATUS current
            DESCRIPTION  
            "Applicable to AU only. 
			 Not applicable to BWA-PtP units.                                   
             A read only table index for a MAC Address entry 
             in the Mac Address Deny List Table. Range: 1 to 100."
        ::= { bwaVLMacAddressDenyListEntry 1 }

    bwaVLMacAddressDenyListId   OBJECT-TYPE
            SYNTAX  MacAddress  
            MAX-ACCESS read-write
            STATUS current
            DESCRIPTION  
            "Applicable to AU only.
			 Not applicable to BWA-PtP units.                                   
             The list of MAC Addresses in the Mac Address Deny 
             List Table. 
             To Remove a MAC Address - SET the corresponding entry 
             to 0. 
             To Add a new MAC Address - SET an entry which is 
             currently 0."
        ::= { bwaVLMacAddressDenyListEntry 2 }

    bwaVLMacAddressDenyListAdd OBJECT-TYPE
            SYNTAX MacAddress
            MAX-ACCESS read-write
            STATUS current
            DESCRIPTION  
            "Applicable to AU only. 
			 Not applicable to BWA-PtP units.                                   
             Add a MAC address to the MAC Address Deny List Table"
            ::= { bwaVLMacAddressDenyList 2 }

    bwaVLMacAddressDenyListRemove OBJECT-TYPE
            SYNTAX MacAddress
            MAX-ACCESS read-write
            STATUS current
            DESCRIPTION  
            "Applicable to AU only. 
			 Not applicable to BWA-PtP units.                                   
             Delete a MAC address from the MAC Address Deny List Table"
            ::= { bwaVLMacAddressDenyList 3 }

    bwaVLNumberOfMacAddressesInDenyList OBJECT-TYPE
            SYNTAX INTEGER { na(255) }
            MAX-ACCESS read-only
            STATUS current
            DESCRIPTION  
            "Applicable to AU only. 
			 Not applicable to BWA-PtP units.                                   
             Number of MAC addresses in the MAC Address Deny List Table."
            ::= { bwaVLMacAddressDenyList 4 }

bwaVLMacAddressDenyListAction OBJECT-TYPE
            SYNTAX  INTEGER  { denyList(1), allowedList(2), na(255) }
            MAX-ACCESS read-write      
            STATUS current       
            DESCRIPTION  
            "Applicable to AU only.        
            Define the action to be used by the Mac Address Deny List.
            allowedList(2) means that the list becomes Allow list."
            ::= { bwaVLMacAddressDenyList 5 }


bwaVLPortsControl  OBJECT IDENTIFIER ::= {bwaVLBridgeParameters 11}

    bwaVLEthernetPortControl OBJECT-TYPE
            SYNTAX  INTEGER   { disable(1), enable(2), na(255) }  
            MAX-ACCESS read-write
            STATUS current
            DESCRIPTION  
            "Applicable to SU/RB only.
             Enable/disable the Ethernet port. When disabled, only 
             data frames are blocked. Management frames are accepted."
            ::= { bwaVLPortsControl 1 }


-- Air Interface Params
-- =====================
bwaVLAirInterface      OBJECT IDENTIFIER ::= {bwaVLMib 6}

bwaVLESSIDParameters      OBJECT IDENTIFIER ::= {bwaVLAirInterface 1}

    bwaVLESSID OBJECT-TYPE
            SYNTAX DisplayString (SIZE(0..31))
            MAX-ACCESS read-write
            STATUS current
            DESCRIPTION  
            "Applicable to all units. 
             The Extended Service Set ID (ESSID) used to prevent 
             the merging of collocated systems.
             The ESSID is accessible only with the write community 
             string (administrator password).
             Up to 31 printable case sensitive ASCII characters." 
            ::= { bwaVLESSIDParameters 1 }


    bwaVLOperatorESSIDOption  OBJECT-TYPE
            SYNTAX INTEGER {disable (1) , enable (2), na (255) }
            MAX-ACCESS read-write
            STATUS current
            DESCRIPTION  
            "Applicable to AU/BU only. 
             Enabling/disabling the use of the Operator ESSID."
            ::= { bwaVLESSIDParameters 2 }


    bwaVLOperatorESSID OBJECT-TYPE
            SYNTAX DisplayString (SIZE(0..31))
            MAX-ACCESS read-write
            STATUS current
            DESCRIPTION  
            "Applicable to AU/BU only.
             A secondary ESSID to support easy installation of SUs as well as
             the use of the Best AU/BU feature.
             Accessible only with SNMP Write Community 
             Up to 31 printable case sensitive ASCII characters." 
            ::= { bwaVLESSIDParameters 3}

	bwaVLRunTimeESSID OBJECT-TYPE
		    SYNTAX DisplayString (SIZE(31))
		    MAX-ACCESS read-only
		    STATUS current
		    DESCRIPTION  
		    "Applicable to SU/RB only. 
		     The ESSID of the associated AU/BU.
		     Accessible only with SNMP Write Community.
		     Up to 31 printable ASCII characters, case sensitive."
		    ::= { bwaVLESSIDParameters 4 }


    bwaVLMaximumCellRadius  OBJECT-TYPE
            SYNTAX  INTEGER  
            MAX-ACCESS read-write      
            STATUS current       
            DESCRIPTION  
            "Applicable to all units.  
             For AU/BU: read-write. In units with SW version 2.0 and up -
             applicable only when the Cell Distance Mode is set to Manual. 
             The highest distance from the AU/BU of any SU/RB served by it. 
             Affects the maximum time the units wait for a response message 
             and the slot size by taking into account the round trip propagation delay. 
             For SU/RB: read-only. The distance is learned from the AU/BU. 
             Range: For units below version 2.0 the range is 0 - 50000 Meters. 
             Otherwise - the range is 0 to 54 Kilometers.
             0 means no compensation (minimum slot size, maximal delay timeout)."
            ::= { bwaVLAirInterface 2 }

    bwaVLAIFS  OBJECT-TYPE
            SYNTAX  INTEGER { oneSlot (1), twoSlots (2) } 
            MAX-ACCESS read-write      
            STATUS current       
            DESCRIPTION  
            "Applicable to AU and SU. Not applicable to BWA-PtP products.
             Not applicable if Wireless Link Prioritization is enabled.
             Arbitration Inter-Frame Spacing (AIFS) value, in slots. 
             This is the number of time slots that define the DIFS. (DIFS=SIFS+AIFS). 
             A value of 1 should be used only in point-to-point applications to 
             allow one unit to have advantage over the other unit."
            ::= { bwaVLAirInterface 3 }


	bwaVLWirelessTrapThreshold OBJECT-TYPE
	    SYNTAX INTEGER     
	    MAX-ACCESS read-write
	    STATUS current
	    DESCRIPTION
	    "Applicable to AU/BU only.
	     A wireless link quality threshold, expressed in % of retransmissions,
	     for sending the bwaVLAUWirelessQualityTRAP.   
	     This trap indicate whether the quality has gone below or 
	     above the specified threshold.
	     The Threshold Range: 1 to 100 (%  retransmissions)."
	     ::= {  bwaVLAirInterface 4 }



    bwaVLTransmitPowerTable OBJECT-TYPE
            SYNTAX SEQUENCE OF BwaVLTransmitPowerEntry
            MAX-ACCESS not-accessible
            STATUS current
            DESCRIPTION
            "Applicable to all units.
             A table of transmit power parameters. " 
            ::= { bwaVLAirInterface 5}

    bwaVLTransmitPowerEntry  OBJECT-TYPE
            SYNTAX BwaVLTransmitPowerEntry
            MAX-ACCESS not-accessible
            STATUS current
            DESCRIPTION
            "Applicable to all units. 
             An entry in the Transmit Power Table." 
            INDEX { bwaVLTransmitPowerIdx }
            ::= { bwaVLTransmitPowerTable 1 }
                                
    BwaVLTransmitPowerEntry ::= SEQUENCE {   bwaVLTransmitPowerIdx          INTEGER,
                                				bwaVLApplicableModulationLevel INTEGER,
                                				bwaVLMaximumTxPowerRange       DisplayString,
                                				bwaVLTxPower     	          DisplayString,
												bwaVLCurrentTxPower		      DisplayString
                                			  }

    bwaVLTransmitPowerIdx OBJECT-TYPE
            SYNTAX INTEGER	(1..4)
            MAX-ACCESS read-only
            STATUS current
            DESCRIPTION  
            "Applicable to all units.
             An index of an entry in the Transmit Power Table." 
            ::= { bwaVLTransmitPowerEntry 1 }
								

    bwaVLApplicableModulationLevel       OBJECT-TYPE
            SYNTAX INTEGER {level1to5 (1), level6  (2), level7  (3),level8  (4)}
            MAX-ACCESS read-only
            STATUS current
            DESCRIPTION  
            "Applicable to all units.
             The applicable modulation level for an entry in the Transmit Power Table.
              Level 8 is not applicable to units with HW revision A." 
            ::= { bwaVLTransmitPowerEntry 2 }

    bwaVLMaximumTxPowerRange  OBJECT-TYPE
            SYNTAX DisplayString
            MAX-ACCESS read-only
            STATUS current
            DESCRIPTION  
            "Applicable to all units.
             The allowed range for the bwaVLTxPower parameter at the 
             applicable modulation level . Range: -10 to the maximum allowed 
             power level at the applicable modulation level , in dBm." 
            ::= { bwaVLTransmitPowerEntry 3 }


    bwaVLTxPower OBJECT-TYPE
            SYNTAX DisplayString
            MAX-ACCESS read-write
            STATUS current
            DESCRIPTION  
            "Applicable to all units.
             Read-only for units with SW version 4.0 and higher.
			 In AU/BU: The transmit power in dBm defined for the applicable rate.
			 In SU/RB: If ATPC is disabled, this is the transmit power in dBm 
			 defined for the applicable rate.
			 If ATPC is enabled, it serves as the initial transmit power in dBm 
			 for the ATPC algorithm. 
			 In SU/RB: The range is -10 dBm to the power value defined by 
			           bwaVLMaximumTxPower for the applicable modulation level.
			 In AU/BU: The range is -10 dBm to the power value defined by 
			           bwaVLMaximumTxPowerRange for the applicable modulation level."
            ::= { bwaVLTransmitPowerEntry 4 }



    bwaVLCurrentTxPower OBJECT-TYPE
            SYNTAX DisplayString
            MAX-ACCESS read-only
            STATUS current
            DESCRIPTION 
            "Applicable to SU/RB.
             The actual transmit power in dBm for the applicable rate.
             Range: -17 to the maximum value defined by bwaVLMaximumTxPowerRange 
             for the applicable modulation level."
            ::= { bwaVLTransmitPowerEntry 5 }

    bwaVLMaximumTransmitPowerTable OBJECT-TYPE
            SYNTAX SEQUENCE OF BwaVLMaximumTransmitPowerEntry
            MAX-ACCESS not-accessible
            STATUS current
            DESCRIPTION
            "Applicable to SU/RB only.
             A table of maximum transmit power parameters. " 
            ::= { bwaVLAirInterface 6}

    bwaVLMaximumTransmitPowerEntry  OBJECT-TYPE
            SYNTAX BwaVLMaximumTransmitPowerEntry
            MAX-ACCESS not-accessible
            STATUS current
            DESCRIPTION
            "Applicable to SU/RB only. 
             An entry in the Maximum Transmit Power Table." 
            INDEX { bwaVLMaximumTransmitPowerIdx }
            ::= { bwaVLMaximumTransmitPowerTable 1 }
                                
    BwaVLMaximumTransmitPowerEntry ::= SEQUENCE {   bwaVLMaximumTransmitPowerIdx        INTEGER,
                                				       bwaVLMaxTxApplicableModulationLevel INTEGER,
                                				       bwaVLDefinedMaximumTxPowerRange     DisplayString,
                                				       bwaVLMaxTxPower     	              DisplayString
                                			  }

    bwaVLMaximumTransmitPowerIdx OBJECT-TYPE
            SYNTAX INTEGER	(1..4)
            MAX-ACCESS read-only
            STATUS current
            DESCRIPTION  
            "Applicable to SU/RB only.
             An index of an entry in the Maximum Transmit Power Table." 
            ::= { bwaVLMaximumTransmitPowerEntry 1 }
								

    bwaVLMaxTxApplicableModulationLevel       OBJECT-TYPE
            SYNTAX INTEGER {level1to5 (1), level6  (2), level7  (3),level8  (4)}
            MAX-ACCESS read-only
            STATUS current
            DESCRIPTION  
            "Applicable to SU/RB only.
             The applicable modulation level for an entry in the Maximum 
              Transmit Power Table.
              Level 8 is not applicable to units with HW revision A." 
            ::= { bwaVLMaximumTransmitPowerEntry 2 }

    bwaVLDefinedMaximumTxPowerRange  OBJECT-TYPE
            SYNTAX DisplayString
            MAX-ACCESS read-only
            STATUS current
            DESCRIPTION  
            "Applicable to SU/RB only.
             The allowed range for the bwaVLMaxTxPower parameter at the 
             applicable modulation level .
             Range: -10 to the maximum allowed power level at the applicable 
             modulation level , in dBm." 
            ::= { bwaVLMaximumTransmitPowerEntry 3 }


    bwaVLMaxTxPower OBJECT-TYPE
            SYNTAX DisplayString
            MAX-ACCESS read-write
            STATUS current
            DESCRIPTION  
            "Applicable to SU/RB only.
            Read-only for units with SW version 4.0 and higher.
			The maximum value that can be configured for the bwaVLTxPower 
			parameter. This is also the maximum power level that can be reached 
			by the ATPC algorithm.
			The range is -10 dBm to the maximum value defined by 
			bwaVLDefinedMaximumTxPowerRange for the applicable modulation level."
            ::= { bwaVLMaximumTransmitPowerEntry 4 }

    bwaVLMaxNumOfAssociations OBJECT-TYPE
            SYNTAX  INTEGER  
            MAX-ACCESS read-write      
            STATUS current       
            DESCRIPTION  
            "Applicable to AU only. 
             Not applicable to BWA-PtP products.
             Sets the upper limit for the number of SUs 
             that can be associated with the AU.
             Range: For regular AUs (AU-BS, AU-SA) 
             the range is from 0 to 512 if encryption is disabled
             the range id form 0 to 124 if encryption is enabled
             For AUS-BS and AUS-SA with SW version 4.0 and higher 
             the range is between 0 to 8 or 25 (via licensing).
             For AUS-BS and AUS-SA with SW version below 4.0             the range 
             is between 0 to 5.  
             BWA-PtP products return 65535."
            ::= { bwaVLAirInterface 10 }


bwaVLBestAu   OBJECT IDENTIFIER ::= {bwaVLAirInterface 11}

    bwaVLBestAuSupport OBJECT-TYPE
            SYNTAX  INTEGER  { disable (1), enable (2), na (255) }
            MAX-ACCESS read-write      
            STATUS current       
            DESCRIPTION  
            "Applicable to SU/RB only. 
             Disable/enable the Best AU/BU selection mechanism."
            ::= { bwaVLBestAu  1 }

    bwaVLBestAuNoOfScanningAttempts OBJECT-TYPE
            SYNTAX  INTEGER
            MAX-ACCESS read-write      
            STATUS current       
            DESCRIPTION  
            "Applicable to SU/RB only. 
             The number of scanning attempts to collect information 
             for the Best AU/BU decision.
             Range: 1 to 255."
            ::= { bwaVLBestAu  2 }

    bwaVLPreferredAuMacAddress OBJECT-TYPE
            SYNTAX MacAddress 
            MAX-ACCESS read-write      
            STATUS current       
            DESCRIPTION  
            "Applicable to SU/RB only.
             The MAC address of the preferred AU/BU (overriding the 
             Best AU/BU selection process). 
             000000000000 means no preferred AU/BU."
            ::= { bwaVLBestAu 3 }

    bwaVLNeighborAuTable OBJECT-TYPE
            SYNTAX SEQUENCE OF BwaVLNeighborAuEntry
            MAX-ACCESS not-accessible
            STATUS current
            DESCRIPTION
            "Applicable to SU/RB only. 
             A table of data on neighboring AUs/BUs."
            ::= { bwaVLBestAu 4}

    bwaVLNeighborAuEntry  OBJECT-TYPE
            SYNTAX BwaVLNeighborAuEntry
            MAX-ACCESS not-accessible
            STATUS current
            DESCRIPTION
            "Applicable to SU/RB only. 
             An entry in the Neighbor AU/BU Table." 
            INDEX { bwaVLNeighborAuIdx }
            ::= { bwaVLNeighborAuTable 1 }
                                
    BwaVLNeighborAuEntry ::= SEQUENCE { bwaVLNeighborAuIdx        INTEGER,
    							bwaVLNeighborAuMacAdd                MacAddress,
                                bwaVLNeighborAuESSID                 DisplayString,
                                bwaVLNeighborAuSNR                   INTEGER,
                                bwaVLNeighborAuAssocLoadStatus       INTEGER,
                                bwaVLNeighborAuMark                  INTEGER,
	                            bwaVLNeighborAuHwRevision	        INTEGER,
	                            bwaVLNeighborAuCountryCode           INTEGER,
	                            bwaVLNeighborAuSwVer			        DisplayString,
	                            bwaVLNeighborAuAtpcOption	        INTEGER,
	                            bwaVLNeighborAuAdapModOption	        INTEGER,
	                            bwaVLNeighborAuBurstModeOption       INTEGER,
	                         	bwaVLNeighborAuDfsOption	            INTEGER,
	                            bwaVLNeighborAuConcatenationOption   INTEGER,
	                            bwaVLNeighborAuLearnCountryCodeBySU  INTEGER,
	                            bwaVLNeighborAuSecurityMode	        INTEGER,
	                            bwaVLNeighborAuAuthOption	        INTEGER,
	                            bwaVLNeighborAuDataEncyptOption      INTEGER,
	                            bwaVLNeighborAuPerSuDistanceLearning INTEGER
                                }

    bwaVLNeighborAuIdx OBJECT-TYPE
            SYNTAX INTEGER	(1..20)
            MAX-ACCESS read-only
            STATUS current
            DESCRIPTION  
            "Applicable to SU/RB only. 
             An index of an entry in the Neighbor AU/BU Table."
            ::= { bwaVLNeighborAuEntry 1 }
								
    bwaVLNeighborAuMacAdd OBJECT-TYPE
            SYNTAX MacAddress
            MAX-ACCESS read-only
            STATUS current
            DESCRIPTION  
            "Applicable to SU/RB only. 
             A MAC address of an AU/BU in the Neighbor AU/BU Table."
            ::= { bwaVLNeighborAuEntry 2 }

    bwaVLNeighborAuESSID OBJECT-TYPE
            SYNTAX DisplayString
            MAX-ACCESS read-only
            STATUS current
            DESCRIPTION  
            "Applicable to SU/RB only.  
             The ESSID of an AU/BU in the Neighbor AU/BU Table.
             Accessible only with SNMP Write Community."
            ::= { bwaVLNeighborAuEntry 3 }

    bwaVLNeighborAuSNR OBJECT-TYPE
            SYNTAX INTEGER { na (255) }
            MAX-ACCESS read-only
            STATUS current
            DESCRIPTION  
            "Applicable to SU/RB only. 
             The received signal quality (SNR) in dB of an AU/BU 
             in the Neighbor AU/BU Table."
            ::= { bwaVLNeighborAuEntry 4 }

    bwaVLNeighborAuAssocLoadStatus OBJECT-TYPE
            SYNTAX INTEGER {  full (1),notFull (2), na (255) }
            MAX-ACCESS read-only
            STATUS current
            DESCRIPTION  
            "Applicable to SU/RB only. 
             Neighbor AU/BU association load status in the Neighbor 
             AU/BU Table."
            ::= { bwaVLNeighborAuEntry 5 }
    
    bwaVLNeighborAuMark OBJECT-TYPE
            SYNTAX INTEGER
            MAX-ACCESS read-only
            STATUS current
            DESCRIPTION  
            "Applicable to SU/RB only.
             Neighbor AU/BU mark in the Neighbor AU/BU Table."
            ::= { bwaVLNeighborAuEntry 6 }

    bwaVLNeighborAuHwRevision OBJECT-TYPE
            SYNTAX INTEGER {hwRevisionA (1), hwRevisionB (2), hwRevisionC (3),
							hwRevisionD (4), hwRevisionE (5),na (255)}
            MAX-ACCESS read-only
            STATUS current
            DESCRIPTION  
            "Applicable to SU/RB only.
             Neighbor AU/BU HW revision in the Neighbor AU/BU Table."
            ::= { bwaVLNeighborAuEntry 7 }

    bwaVLNeighborAuCountryCode OBJECT-TYPE
            SYNTAX INTEGER 	
            MAX-ACCESS read-only
            STATUS current
            DESCRIPTION  
            "Applicable to SU/RB only.
             Neighbor AU/BU supported country code in the Neighbor 
             AU/BU Table."
            ::= { bwaVLNeighborAuEntry 8 }

    bwaVLNeighborAuSwVer OBJECT-TYPE
            SYNTAX DisplayString 
            MAX-ACCESS read-only
            STATUS current
            DESCRIPTION  
            "Applicable to SU/RB only.
             Neighbor AU/BU SW version in the Neighbor 
             AU/BU Table."
            ::= { bwaVLNeighborAuEntry 9 }

    bwaVLNeighborAuAtpcOption OBJECT-TYPE
            SYNTAX INTEGER { disable (1), enable (2), na (255)}
            MAX-ACCESS read-only
            STATUS current
            DESCRIPTION  
            "Applicable to SU/RB only.
             Neighbor AU/BU ATPC option configuration in the Neighbor 
             AU/BU Table."
            ::= { bwaVLNeighborAuEntry 10 }

    bwaVLNeighborAuAdapModOption OBJECT-TYPE
            SYNTAX INTEGER { disable (1), enable (2), na (255)}
            MAX-ACCESS read-only
            STATUS current
            DESCRIPTION  
            "Applicable to SU/RB only.
             Neighbor AU/BU adaptive modulation option configuration 
             in the Neighbor AU/BU Table."
            ::= { bwaVLNeighborAuEntry 11 }

    bwaVLNeighborAuBurstModeOption OBJECT-TYPE
            SYNTAX INTEGER { disable (1), enable (2), na (255)}
            MAX-ACCESS read-only
            STATUS current
            DESCRIPTION  
            "Applicable to SU/RB only.
             Neighbor AU/BU burst mode option configuration 
             in the Neighbor AU/BU Table."
            ::= { bwaVLNeighborAuEntry 12 }

    bwaVLNeighborAuDfsOption OBJECT-TYPE
            SYNTAX INTEGER { disable (1), enable (2), na(255)}
            MAX-ACCESS read-only
            STATUS current
            DESCRIPTION  
            "Applicable to SU/RB only.
             Neighbor AU/BU DFS option configuration 
             in the Neighbor AU/BU Table."
            ::= { bwaVLNeighborAuEntry 14 }

    bwaVLNeighborAuConcatenationOption OBJECT-TYPE
            SYNTAX INTEGER { disable (1), enable (2), na (255)}
            MAX-ACCESS read-only
            STATUS current
            DESCRIPTION  
            "Applicable to SU/RB only.
             Neighbor AU/BU concatenation option configuration 
             in the Neighbor AU/BU Table."
            ::= { bwaVLNeighborAuEntry 15 }

    bwaVLNeighborAuLearnCountryCodeBySU OBJECT-TYPE
            SYNTAX INTEGER { disable (1), enable (2), na (255)}
            MAX-ACCESS read-only
            STATUS current
            DESCRIPTION  
            "Applicable to SU only.
             Starting with 4.0 is not applicable for BWA 4900 and BWA PtP products.
             Neighbor AU Learn Country Code by SU configuration 
             in the Neighbor AU Table."
            ::= { bwaVLNeighborAuEntry 17 }

   bwaVLNeighborAuSecurityMode     OBJECT-TYPE
            SYNTAX INTEGER  {wep(1), aesOCB(2), fips197(3), na(255)}
            MAX-ACCESS read-only
            STATUS current
            DESCRIPTION  
            "Applicable to SU/RB only.
             Neighbor AU/BU security mode configuration 
             in the Neighbor AU/BU Table."
            ::= { bwaVLNeighborAuEntry 18 }

   bwaVLNeighborAuAuthOption     OBJECT-TYPE
            SYNTAX INTEGER  {openSystem (1), sharedKey (2), na (255)}
            MAX-ACCESS read-only
            STATUS current
            DESCRIPTION  
            "Applicable to SU/RB only.
             Neighbor AU/BU authentication option configuration 
             in the Neighbor AU/BU Table."
            ::= { bwaVLNeighborAuEntry 19 }

   bwaVLNeighborAuDataEncyptOption     OBJECT-TYPE
            SYNTAX INTEGER  {disable (1), enable (2), na (255)}
            MAX-ACCESS read-only
            STATUS current
            DESCRIPTION  
            "Applicable to SU/RB only.
             Neighbor AU/BU data encryption option configuration 
             in the Neighbor AU/BU Table."
            ::= { bwaVLNeighborAuEntry 20 }

	bwaVLNeighborAuPerSuDistanceLearning		OBJECT-TYPE
            SYNTAX INTEGER  {disable (1), enable (2), na (255)}
            MAX-ACCESS read-only
            STATUS current
            DESCRIPTION  
            "Applicable to SU only.
             Neighbor AU per SU distance learning option configuration 
             in the Neighbor AU Table."
            ::= { bwaVLNeighborAuEntry 21 }

bwaVLFrequencyDefinition	   OBJECT IDENTIFIER ::= {bwaVLAirInterface 12}
   

    bwaVLSubBandLowerFrequency OBJECT-TYPE
            SYNTAX INTEGER
            MAX-ACCESS read-write
            STATUS obsolete
            DESCRIPTION  
		    "Applicable to SU only. 
		     Not applicable to units with SW version 2.0 or higher. 
             The lowest frequency in the subset to be used for scanning.
             For 5.8GHz products the range is 5740 to 5830 MHz using 10MHz resolution.
             For 4.9GHz products the range is 4920 to 5080 MHz using 10MHz resolution.
             For HW Revision C and above this leaf is not relevant - shall return 0."
            ::= { bwaVLFrequencyDefinition 1 }

    bwaVLSubBandUpperFrequency OBJECT-TYPE
            SYNTAX INTEGER
            MAX-ACCESS read-write
            STATUS obsolete
            DESCRIPTION  
            "Applicable to SU only. 
             Not applicable to units with SW version 2.0 or higher. 
             The highest frequency in the subset to be used for scanning.
             For 5.8GHz products the range is 5740 to 5830 MHz using 10MHz resolution.
             For 4.9GHz products the range is 4920 to 5080 MHz using 10MHz resolution.
             For HW Revision C and above this leaf is not relevant - shall return 0."
            ::= { bwaVLFrequencyDefinition 2 }

    bwaVLScanningStep  OBJECT-TYPE
            SYNTAX INTEGER	{ mhz-5(1), mhz-10(2) , mhz-20(3), na(255) }
            MAX-ACCESS read-write
            STATUS current
            DESCRIPTION  
            "Applicable to all units - For flexible Sub-Bands only.		
             For units with version 2.0 and above this is a read-only parameter.
             The scanning step to be used for generating the frequency subset."
            ::= { bwaVLFrequencyDefinition 3 }


    bwaVLFrequencySubsetTable OBJECT-TYPE
            SYNTAX SEQUENCE OF BwaVLFrequencySubsetEntry
            MAX-ACCESS not-accessible
            STATUS current
            DESCRIPTION
            "Applicable to SU/RB and to AU/BU.
             Not applicable to SU/RB with SW version 4.0 and higher.
			 The Frequency Subset Table that includes all frequencies from 
			 the selected Sub-band."
                ::= { bwaVLFrequencyDefinition 4 }

    bwaVLFrequencySubsetEntry  OBJECT-TYPE
            SYNTAX BwaVLFrequencySubsetEntry
            MAX-ACCESS not-accessible
            STATUS current
            DESCRIPTION
            "Applicable to SU/RB and to AU/BU.
             Not applicable to SU/RB with SW version 4.0 and higher.
             An entry in the Frequency Subset Table. "  
             INDEX { bwaVLFrequencySubsetTableIdx }
            ::= { bwaVLFrequencySubsetTable 1 }

    BwaVLFrequencySubsetEntry ::= SEQUENCE {
            bwaVLFrequencySubsetTableIdx       INTEGER,
            bwaVLFrequencySubsetFrequency      INTEGER,
            bwaVLFrequencySubsetActive         INTEGER,
            bwaVLFrequencySubsetFrequencyNew   DisplayString
            }
               
    bwaVLFrequencySubsetTableIdx   OBJECT-TYPE
            SYNTAX INTEGER  (1..40)
            MAX-ACCESS read-only
            STATUS current
            DESCRIPTION 
            "Applicable to SU/RB and to AU/BU.
             Not applicable to SU/RB with SW version 4.0 and higher.
			 An index of an entry in the Frequency subset Table."
           ::= { bwaVLFrequencySubsetEntry 1 }


    bwaVLFrequencySubsetFrequency   OBJECT-TYPE
            SYNTAX INTEGER  
            MAX-ACCESS read-only
            STATUS current
            DESCRIPTION 
            "Applicable to SU/RB and to AU/BU. 
             Not applicable to SU/RB with SW version 4.0 and higher.
             Applicable to all units with HW revision B and lower 
             (for units with HW revision C and higher replaced by 
             bwaVLFrequencySubsetFrequencyNew to support a 
             resolution of 0.5 MHz).  
             The frequency in MHz of an entry in the Frequency Subset table."
           ::= { bwaVLFrequencySubsetEntry 2 }

    bwaVLFrequencySubsetActive   OBJECT-TYPE
            SYNTAX INTEGER  {active (1) , notActive (2)}
            MAX-ACCESS read-write
            STATUS current
            DESCRIPTION 
            "Applicable to SU/RB and to AU/BU.
             Not applicable to SU/RB with SW version 4.0 and higher.
			 The status of an entry in the Frequency subset Table.
			 The frequency of an active entry will be included in the 
			 final list of frequencies to be used for scanning."
           ::= { bwaVLFrequencySubsetEntry 3 }

    bwaVLFrequencySubsetFrequencyNew   OBJECT-TYPE
            SYNTAX DisplayString
            MAX-ACCESS read-write
            STATUS current
            DESCRIPTION 
            "Applicable to all units. 
             Not applicable to SU/RB with SW version 4.0 and higher.
             The frequency in MHz of an entry in the Frequency Subset table. 
             (Replaces bwaVLFrequencySubsetFrequency to support a resolution 
             of 0.5 MHz for units with HW revision C and higher)."
           ::= { bwaVLFrequencySubsetEntry 4 }

    bwaVLSetSelectedFreqSubset  OBJECT-TYPE
            SYNTAX INTEGER	 {setSelectedFreqsSubset(1) ,cancel (2)}
            MAX-ACCESS read-write
            STATUS current
            DESCRIPTION  
            "Applicable to SU/RB and to AU/BU.
             Not applicable to SU/RB with SW version 4.0 and higher.
			 Apply the selected subset.
			 After the next reset the new subset will be used."
            ::= { bwaVLFrequencyDefinition 5 }




    bwaVLCurrentFrequencySubsetTable OBJECT-TYPE
            SYNTAX SEQUENCE OF BwaVLCurrentFrequencySubsetEntry
            MAX-ACCESS not-accessible
            STATUS current
            DESCRIPTION
            "Applicable to SU/RB and to AU/BU.
			 Not applicable to SU/RB with SW version 4.0 and higher.
			 The Current Frequency Subset table. In SU/RB it includes all 
			 frequencies that are currently used for scanning.
			 In AU/BU it includes all frequencies that can be used by the 
			 DFS mechanism (if applicable)"
                ::= { bwaVLFrequencyDefinition 6 }

    bwaVLCurrentFrequencySubsetEntry  OBJECT-TYPE
            SYNTAX BwaVLCurrentFrequencySubsetEntry
            MAX-ACCESS not-accessible
            STATUS current
            DESCRIPTION
            "Applicable to SU/RB and to AU/BU.
             An entry in the Current Frequency Subset Table. "  
             INDEX { bwaVLCurrentFrequencySubsetTableIdx }
            ::= { bwaVLCurrentFrequencySubsetTable 1 }

    BwaVLCurrentFrequencySubsetEntry ::= SEQUENCE {
            bwaVLCurrentFrequencySubsetTableIdx      INTEGER,
            bwaVLCurrentFrequencySubsetFrequency     INTEGER,
            bwaVLCurrentFrequencySubsetFrequencyNew  DisplayString
            }
               
    bwaVLCurrentFrequencySubsetTableIdx   OBJECT-TYPE
            SYNTAX INTEGER  (1..40)
            MAX-ACCESS read-only
            STATUS current
            DESCRIPTION 
            "Applicable to SU/RB and to AU/BU.
			 An index of an entry in the Current Frequency subset Table.
			 Not applicable to SU/RB with SW version 4.0 and higher."
           ::= { bwaVLCurrentFrequencySubsetEntry 1 }


    bwaVLCurrentFrequencySubsetFrequency   OBJECT-TYPE
            SYNTAX INTEGER  
            MAX-ACCESS read-only
            STATUS current
            DESCRIPTION 
			"Applicable to all units. 
			 Not applicable to SU/RB with SW version 4.0 and higher.
			 Applicable to all units with HW revision B and lower 
			 (for units with HW revision C and higher replaced by 
			 bwaVLCurrentFrequencySubsetFrequencyNew to support 
			 a resolution of 0.5 MHz). 
			 The frequency in MHz of an entry in the Current Frequency Subset table."
           ::= { bwaVLCurrentFrequencySubsetEntry 2 }

    bwaVLCurrentFrequencySubsetFrequencyNew   OBJECT-TYPE
            SYNTAX DisplayString  
            MAX-ACCESS read-only
            STATUS current
            DESCRIPTION 
            "Applicable to all units. Not applicable to SU/RB with SW version 4.0 and higher. 
             The frequency in MHz of an entry in the Current Frequency Subset table. 
             (Replaces bwaVLCurrentFrequencySubsetFrequency to support a 
             resolution of 0.5 MHz for units with HW revision C and higher)."
            ::= { bwaVLCurrentFrequencySubsetEntry 3 }
	
    bwaVLCurrentAUOperatingFrequency  OBJECT-TYPE
            SYNTAX INTEGER	
            MAX-ACCESS read-only
            STATUS current
            DESCRIPTION  
		    "Applicable to AU/BU with HW revision B and lower 
		     (for units with HW revision C and higher replaced by 
		     bwaVLCurrentUOperatingFrequencyNew to support a resolution 
		     of 0.5 MHz). 
		     The operating frequency in MHz. 
		     For 5.8GHz products with SW version below 2.0 the range is 
		     5740 to 5830 MHz using 10MHz resolution. 
		     For units with SW version 2.0 and up the range is as defined 
		     in the selected Sub Band."
            ::= { bwaVLFrequencyDefinition 7 }

    bwaVLCurrentAUOperatingFrequencyNew  OBJECT-TYPE
            SYNTAX DisplayString	
            MAX-ACCESS read-only
            STATUS current
            DESCRIPTION  
            "Applicable to AU/BU. The operating frequency in MHz. 
             (Replaces bwaVLCurrentAUOperatingFrequency to support 
             a resolution of 0.5 MHz for units with HW revision C and higher). 
             For 5.8GHz products with SW version below 2.0 the range is 
             5740 to 5830 MHz using 10MHz resolution. 
             For units with SW version 2.0 and up the range is as defined 
             in the selected Sub Band."
            ::= { bwaVLFrequencyDefinition 13 }

    bwaVLAUDefinedFrequency  OBJECT-TYPE
            SYNTAX INTEGER	
            MAX-ACCESS read-write
            STATUS current
            DESCRIPTION  
            "Applicable to AU/BU with HW revision B and lower 
             (for units with HW revision C and higher replaced by 
             bwaVLAUDefinedFrequencyNew to support a resolution of 0.5 MHz). 
             For 5.8GHz products with SW version below 2.0 this is the frequency 
             in MHz of the AU/BU after the next reset. 
             For units with SW version 2.0 and up this is the frequency in MHz 
             to use when the DFS Option is disabled. 
             For 5.8GHz products with SW version below 2.0 the range is 
             5740 to 5830 MHz using 10MHz resolution. 
             For units with SW version 2.0 and up the range is as defined 
             in the selected Sub Band."            
            ::= { bwaVLFrequencyDefinition 8 }

    bwaVLAUDefinedFrequencyNew  OBJECT-TYPE
            SYNTAX DisplayString	
            MAX-ACCESS read-write
            STATUS current
            DESCRIPTION  
            "Applicable to AU/BU. 
             For 5.8GHz products with SW version below 2.0 this is the 
             frequency in MHz of the AU/BU after the next reset. 
             For units with SW version 2.0 and up this is the 
             frequency in MHz to use when the DFS Option is disabled. 
             (Replaces bwaVLAUDefinedFrequency to support a resolution 
             of 0.5 MHz for units with HW revision C and higher). 
             For 5.8GHz products with SW version below 2.0 the range 
             is 5740 to 5830 MHz using 10MHz resolution. 
             For units with SW version 2.0 and up the range is as 
             defined in the selected Sub Band."
            ::= { bwaVLFrequencyDefinition 14 }

    bwaVLCurrentSUOperatingFrequency  OBJECT-TYPE
            SYNTAX DisplayString	
            MAX-ACCESS read-only
            STATUS current
            DESCRIPTION  
            "Applicable to SU/RB only.
			 The frequency used currently by the unit.
			 For 5.8GHz products with SW version below 2.0 the range is 
			 5740 to 5830 MHz using 10MHz resolution.
             For units with SW version 2.0 and up the range is as defined 
             in the selected Sub Band."
            ::= { bwaVLFrequencyDefinition 9 }

bwaVLSubBandSelect   OBJECT IDENTIFIER ::= {bwaVLFrequencyDefinition 10}


    bwaVLSelectSubBandIndex OBJECT-TYPE
            SYNTAX INTEGER	
            MAX-ACCESS read-write
            STATUS current
            DESCRIPTION
            "Applicable to all units with SW version below 4.0 
            For units with SW version 4.0 and up it is applicable 
            only for AU/BU. For SU/RB it defines only the sub-band 
            for the Spectrum Analyzer.
             The ID of the sub-band used by the unit."  
            ::= { bwaVLSubBandSelect 1 }



bwaVLDFSParameters   OBJECT IDENTIFIER ::= {bwaVLFrequencyDefinition 11}

    bwaVLDFSOption  OBJECT-TYPE
            SYNTAX INTEGER	{ disable (1) , enable (2), na (255) } 
            MAX-ACCESS read-write
            STATUS current
            DESCRIPTION  
            "Applicable to AU/BU only.
             Enabling/disabling the DFS Algorithm. 
             Not applicable if DFS Option is not supported by the current Sub Band."
            ::= { bwaVLDFSParameters 1 }

    bwaVLDFSChannelCheckTime  OBJECT-TYPE
            SYNTAX INTEGER	 
            MAX-ACCESS read-write
            STATUS current
            DESCRIPTION  
            "Applicable to AU/BU only. 
             Defines the time the unit checks the channel for presence of 
             radar signals and does not transmit after power up or association 
             or after moving to a new channel due to detecting radar in the used 
             channel. Range: 1 to 3600 (seconds)."
            ::= { bwaVLDFSParameters 3 }


    bwaVLDFSChannelAvoidancePeriod  OBJECT-TYPE
            SYNTAX INTEGER	 
            MAX-ACCESS read-write
            STATUS current
            DESCRIPTION  
            "Applicable to AU/BU only. 
             Defines the time after detecting radar signals in a channel of 
             avoiding using the channel or adjacent channels in 
             accordance with the bandwidth. Range: 1 to 60 (minutes)."
            ::= { bwaVLDFSParameters 4 }


    bwaVLDFSSuWaitingOption  OBJECT-TYPE
            SYNTAX INTEGER	{ disable (1) , enable (2), na(255) }	 
            MAX-ACCESS read-write
            STATUS current
            DESCRIPTION  
            "Applicable to AU/BU only. 
            Defines whether the associated SUs should wait for this AU/BU 
            after it stopped transmitting due to radar detection, before 
            they starts scanning for other AUs/BUs."
            ::= { bwaVLDFSParameters 5 }


    bwaVLDFSClearRadarDetectedChannelsAfterReset OBJECT-TYPE
            SYNTAX  INTEGER { cancel (1), clearRadarChannels (2), na(255) }  
            MAX-ACCESS read-write
            STATUS current
            DESCRIPTION  
            "Applicable to AU/BU only. 
             Clear Radar Detected and Adjacent to Radar channels after unit reset.
             Returns the unit to operate in default frequency."
            ::= { bwaVLDFSParameters 6 }

	bwaVLDFSRadarDetectionChannelsTable OBJECT-TYPE	  
			SYNTAX SEQUENCE OF BwaVLDFSRadarDetectionChannelsEntry
			MAX-ACCESS not-accessible
			STATUS current
			DESCRIPTION
            "Applicable to AU/BU only. 
             Applicable only when DFS option is on.
             Displays the current channels defined in the sub-band and their radar 
             detection status."
			::= { bwaVLDFSParameters 7 }

	bwaVLDFSRadarDetectionChannelsEntry OBJECT-TYPE	
			SYNTAX BwaVLDFSRadarDetectionChannelsEntry
			MAX-ACCESS not-accessible
			STATUS current
	        DESCRIPTION
	        "Applicable to AU/BU only. 
	         An entry in the bwaVLDFSRadarDetectionChannelsTable."
			INDEX { bwaVLDFSChannelIdx }
			::= { bwaVLDFSRadarDetectionChannelsTable 1 }
								
	BwaVLDFSRadarDetectionChannelsEntry ::= SEQUENCE { 
	        bwaVLDFSChannelIdx	                    INTEGER, 
			bwaVLDFSChannelFrequency                 INTEGER,	 
			bwaVLDFSChannelRadarStatus               INTEGER,
			bwaVLDFSChannelFrequencyNew              DisplayString }

	bwaVLDFSChannelIdx   OBJECT-TYPE			 
			SYNTAX INTEGER  (1..40)
			MAX-ACCESS read-only
			STATUS current
			DESCRIPTION	 
            "Applicable to AU/BU only. Read-only. 
             The index of the entry in the 
             bwaVLDFSRadarDetectionChannelsTable."
	    ::= { bwaVLDFSRadarDetectionChannelsEntry 1 }
		   							
	bwaVLDFSChannelFrequency   OBJECT-TYPE			 
			SYNTAX INTEGER  
			MAX-ACCESS read-only
			STATUS current
			DESCRIPTION	 
			"Applicable to AU/BU with HW revision B and lower 
			 (for units with HW revision C and higher replaced by 
			 bwaVLDFSChannelFrequency New to support a resolution 
			 of 0.5 MHz). 
			 The frequency in MHz of a channel in the DFS Radar 
			 Detection Channels Table."
	    ::= { bwaVLDFSRadarDetectionChannelsEntry 2 }

    bwaVLDFSChannelRadarStatus   OBJECT-TYPE			 
			SYNTAX INTEGER  { radarFree       (1),
			                  adjacentToRadar (2),
			                  radarDetected   (3) }
			MAX-ACCESS read-only
			STATUS current
			DESCRIPTION	 
            "Applicable to AU/BU only.  
             The radar detection status of a channel in 
             bwaVLDFSRadarDetectionChannelTable."
	    ::= { bwaVLDFSRadarDetectionChannelsEntry 3 }

	bwaVLDFSChannelFrequencyNew   OBJECT-TYPE			 
			SYNTAX DisplayString  
			MAX-ACCESS read-only
			STATUS current
			DESCRIPTION	 
			"Applicable to AU/BU. The frequency of a channel in the 
			 DFS Radar Detection Channels Table. 
			 (Replaces bwaVLDFSChannelFrequency to support a 
			 resolution of 0.5 MHz for units with HW revision C and higher)."
	    ::= { bwaVLDFSRadarDetectionChannelsEntry 4 }

    bwaVLDFSMinimumPulsesToDetect  OBJECT-TYPE
            SYNTAX INTEGER	 
            MAX-ACCESS read-write
            STATUS current
            DESCRIPTION  
            "Applicable to AU/BU only. 
             Defines the minimum number of pulses to detect a radar. 
             Range: 1 - 100."
            ::= { bwaVLDFSParameters 8 }


bwaVLDFSChannelReuseParameters OBJECT IDENTIFIER ::= {bwaVLDFSParameters 9}

    bwaVLDFSChannelReuseOption  OBJECT-TYPE
            SYNTAX INTEGER	{ disable (1) , enable (2), na (255) } 
            MAX-ACCESS read-write
            STATUS current
            DESCRIPTION  
            "Applicable to AU/BU only.
             Enabling/disabling the DFS Channel Reuse Algorithm. 
             Not applicable if DFS Option is not supported by the current Sub Band."
            ::= { bwaVLDFSChannelReuseParameters 1 }

    bwaVLDFSRadarActivityAssessmentPeriod  OBJECT-TYPE
            SYNTAX INTEGER	 
            MAX-ACCESS read-write
            STATUS current
            DESCRIPTION  
            "Applicable to AU/BU only. 
             Range: 1 to 12 (Houres)."
            ::= { bwaVLDFSChannelReuseParameters 2 }

    bwaVLDFSMaximumNumberOfDetectionsInAssessmentPeriod  OBJECT-TYPE
            SYNTAX INTEGER	 
            MAX-ACCESS read-write
            STATUS current
            DESCRIPTION  
            "Applicable to AU/BU only. 
             Range: 1 to 10 (Times)."
            ::= { bwaVLDFSChannelReuseParameters 3 }

   bwaVLCountryCodeLearningBySU OBJECT-TYPE
            SYNTAX  INTEGER  { disable(1), enable(2), na(255) }
            MAX-ACCESS read-write      
            STATUS current       
            DESCRIPTION  
            "Applicable to AU only. 
             Starting with 4.0 it is nor applicable for BWA 4900 and BWA PtP.
             Defines whether the SUs learn the country code of the AU."
            ::= { bwaVLFrequencyDefinition 12 }


-- AUTOMATIC SUB BAND SELECT BEGIN

	bwaVLAutoSubBandSelect	OBJECT IDENTIFIER ::= { bwaVLFrequencyDefinition 15 }
	
	bwaVLAutoSubBandSelectedFreqSubset  OBJECT-TYPE
            SYNTAX INTEGER	 { setAllSelectedFreqsSubset(1), cancel (2) }
            MAX-ACCESS read-write
            STATUS current
            DESCRIPTION  
            "Applicable to SU/RB with SW version 4.0 and higher.        
			 Apply the selected subset. After the next reset the new 
			 subset will be used for scanning."
            ::= { bwaVLAutoSubBandSelect 1 }
            
	bwaVLAutoSubBandFrequencySubsetTable OBJECT-TYPE
            SYNTAX SEQUENCE OF BwaVLAutoSubBandFrequencySubsetEntry
            MAX-ACCESS not-accessible
            STATUS current
            DESCRIPTION
            "Applicable to SU/RB with SW version 4.0 and higher. 
            The Frequency Subset Table that includes all available 
            sub-bands and all the frequencies in these sub-bands."
            ::= { bwaVLAutoSubBandSelect 2 }

    bwaVLAutoSubBandFrequencySubsetEntry  OBJECT-TYPE
            SYNTAX BwaVLAutoSubBandFrequencySubsetEntry
            MAX-ACCESS not-accessible
            STATUS current
            DESCRIPTION
            "Applicable to SU/RB with SW version 4.0 and higher.
             An entry in the Frequency Subset Table. "  
             INDEX { bwaVLAutoSubBandFrequencySubsetBandIdx, bwaVLAutoSubBandFrequencySubsetFrequencyIdx }
            ::= { bwaVLAutoSubBandFrequencySubsetTable 1 }

    BwaVLAutoSubBandFrequencySubsetEntry ::= SEQUENCE {
            bwaVLAutoSubBandFrequencySubsetBandIdx		INTEGER,
            bwaVLAutoSubBandFrequencySubsetFrequencyIdx  INTEGER,
            bwaVLAutoSubBandFrequencySubsetActive        INTEGER,
            bwaVLAutoSubBandFrequencySubsetFrequency     DisplayString
            }
               
    bwaVLAutoSubBandFrequencySubsetBandIdx   OBJECT-TYPE
            SYNTAX INTEGER  (1..5)
            MAX-ACCESS read-only
            STATUS current
            DESCRIPTION 
            "Applicable to SU/RB with SW version 4.0 and higher.
			 The index of the applicable Sub Band. 
			 This is the Sub Band ID of the relevant entry in 
			 the Country Dependent Parameters table.
			 Serves also as an index of the entry in the 
			 Frequency subset Table."
           ::= { bwaVLAutoSubBandFrequencySubsetEntry 1 }
           
	bwaVLAutoSubBandFrequencySubsetFrequencyIdx   OBJECT-TYPE
            SYNTAX INTEGER  (1..40)
            MAX-ACCESS read-only
            STATUS current
            DESCRIPTION 
            "Applicable to SU/RB with SW version 4.0 and higher.
			 The index of the applicable frequency in the 
			 applicable Sub Band.  
			 Serves also as an index of the entry in the 
			 Frequency subset Table."
           ::= { bwaVLAutoSubBandFrequencySubsetEntry 2 }


    bwaVLAutoSubBandFrequencySubsetActive   OBJECT-TYPE
            SYNTAX INTEGER  {active (1) , notActive (2)}
            MAX-ACCESS read-write
            STATUS current
            DESCRIPTION 
            "Applicable to SU/RB with SW version 4.0 and higher.
			 The status of an entry in the Auto Sub Band Frequency subset Table.
			 The frequency of an active entry will be included in the 
			 final list of frequencies to be used for scanning."
           ::= { bwaVLAutoSubBandFrequencySubsetEntry 3 }

    bwaVLAutoSubBandFrequencySubsetFrequency   OBJECT-TYPE
            SYNTAX DisplayString
            MAX-ACCESS read-only
            STATUS current
            DESCRIPTION 
            "Applicable to SU/RB with SW version 4.0 and higher. 
             The frequency in MHz of the entry in the Auto Sub Band Frequency Subset table."
           ::= { bwaVLAutoSubBandFrequencySubsetEntry 4 }


-- AUTOMATIC SUB BAND SELECT END


bwaVLATPC   OBJECT IDENTIFIER ::= {bwaVLAirInterface 13}

    bwaVLAtpcOption  OBJECT-TYPE
            SYNTAX INTEGER	{ disable (1) , enable (2) , na (255) } 
            MAX-ACCESS read-write
            STATUS current
            DESCRIPTION  
            "Applicable all units.
             Enabling/disabling the ATPC Algorithm."
            ::= { bwaVLATPC 1 }

    bwaVLDeltaFromMinSNRLevel  OBJECT-TYPE
            SYNTAX INTEGER	 
            MAX-ACCESS read-write
            STATUS current
            DESCRIPTION  
            "Applicable AU/BU only.
			 The Minimum SNR Level plus the value of this parameter define the 
			 maximum desired level of the average SNR at the AU/BU. 
			 If the ATPC Option is enabled,	than if the received SNR is above 
			 the maximum desired level, the AU/BU will transmit Power-Down 
			 messages to the applicable SU/RB.
             Range: 4 to 20 (dB)."
            ::= { bwaVLATPC 2 }

    bwaVLMinimumSNRLevel  OBJECT-TYPE
            SYNTAX INTEGER	 
            MAX-ACCESS read-write
            STATUS current
            DESCRIPTION  
            "Applicable AU/BU only.
             Defines the minimum desired level of the average SNR at the AU/BU.
             Below this level, if *AtpcOption is enabled, the AU/BU will transmit
             ATPC Power-Up messages to the applicable SU/RB.
             The *MinimumSNRLevel cannot be higher  than *MaximumSNRLevel.
             Range: 4 to 60 (dB)."
            ::= { bwaVLATPC 3 }


    bwaVLMinimumIntervalBetweenATPCMessages  OBJECT-TYPE
            SYNTAX INTEGER	 
            MAX-ACCESS read-write
            STATUS current
            DESCRIPTION  
            "Applicable AU/BU only.
			 The minimum interval between two consecutive AU/BU to SU/RB messages.
             Range: 1 to 3600 (Sec)."
            ::= { bwaVLATPC 4 }



    bwaVLPowerLevelSteps  OBJECT-TYPE
            SYNTAX INTEGER	 
            MAX-ACCESS read-write
            STATUS current
            DESCRIPTION  
            "Applicable AU/BU only.
			 The step in dB that the SU/RB will use when receiving an ATPC 
			 Power-Up/Power-Down message.
             Range: 1 to 20  (dB)."
            ::= { bwaVLATPC 6 }

bwaVLCellDistanceParameters   OBJECT IDENTIFIER ::= {bwaVLAirInterface 15}

    bwaVLCellDistanceMode  OBJECT-TYPE
            SYNTAX INTEGER	{ automatic (1) , manual (2), na (255) } 
            MAX-ACCESS read-write
            STATUS current
            DESCRIPTION  
            "Applicable AU/BU only. 
             The selected mode of deciding on Cell Distance."
            ::= { bwaVLCellDistanceParameters 1 }

    bwaVLFairnessFactor  OBJECT-TYPE
            SYNTAX INTEGER { na (255)}	 
            MAX-ACCESS read-write
            STATUS current
            DESCRIPTION  
            "Applicable AU/BU only.
             Not applicable to BWA-PtP products for SW version below 4.0.. 
             The percentage of the maximum distance that is taken into 
             account in the time slot calculation. Range: 0 to 100 
             (Percent). A value of 0 means the minimal slot size 
             (9 microseconds).
             BWA-PtP products with SW version below 4.0 return na."
            ::= { bwaVLCellDistanceParameters 2 }

    bwaVLMeasuredCellDistance  OBJECT-TYPE
            SYNTAX INTEGER {below-2-Km(1)}
            MAX-ACCESS read-only
            STATUS current
            DESCRIPTION  
            "Applicable AU/BU only.
			 The Maximum Cell Distance as calculated by the AU/BU.
             Range: 0 to 54 (Kilometers)."
            ::= { bwaVLCellDistanceParameters 3 }

    bwaVLUnitWithMaxDistance  OBJECT-TYPE
            SYNTAX MacAddress	 
            MAX-ACCESS read-only
            STATUS current
            DESCRIPTION  
            "Applicable AU only.
			 Not applicable to BWA-PtP units.
			 The MAC address of the unit with the maximum distance
			 from the AU."
            ::= { bwaVLCellDistanceParameters 4 }

	bwaVLPerSuDistanceLearning	OBJECT-TYPE
            SYNTAX INTEGER	{ disable (1) , enable (2) } 
            MAX-ACCESS read-write
            STATUS current
            DESCRIPTION  
            "Aplicable to AU only. Applicable only if Cell Distance Mode is 
			set to Automatic. When disabled, all SUs in the cell will use 
			for the ACK Timeout the computed distance of the farthest SU. 
			When enabled, each SU will use its own computed distance"
            ::= { bwaVLCellDistanceParameters 5 }

   bwaVLScanningMode OBJECT-TYPE
            SYNTAX  INTEGER  { passive (1), active (2)}
            MAX-ACCESS read-write      
            STATUS current       
            DESCRIPTION  
            "Applicable to SU/RB only. 
             The scanning mode. In cells where the DFS Option is enabled 
             Scanning Mode is forced to Passive."
            ::= { bwaVLAirInterface 16 }

   bwaVLAntennaGain OBJECT-TYPE
            SYNTAX  DisplayString
            MAX-ACCESS read-write      
            STATUS current       
            DESCRIPTION  
            "Applicable to all units. Read-write in units where 
             bwaVLAntennaGainChange  is supported. 
             Read-only in units where bwaVLAntennaGainChange is not supported. 
             The net gain (including cable attenuation for detached antennas) of 
             the antenna. 
             Range: 0  - to Maximum EIRP defined by country code + 10 (dBi). 
             A value of -2 (this value is configurable only in factory) 
             means don't care.
             A value of -1 (this value is configurable only in factory) 
             means that the unit will not transmit until the actual value 
             is configured."
            ::= { bwaVLAirInterface 17 }

bwaVLSpectrumAnalysisParameters       OBJECT IDENTIFIER ::= {bwaVLAirInterface 18}

    bwaVLSpectrumAnalysisChannelScanPeriod OBJECT-TYPE
            SYNTAX  INTEGER  
            MAX-ACCESS read-write
            STATUS current
            DESCRIPTION 
            "Applicable to all units. 
             The period of staying on each channel for information gathering 
             when performing Spectrum analysis. 
             Range: 2-30 seconds."
            ::= { bwaVLSpectrumAnalysisParameters 1 }

    bwaVLSpectrumAnalysisScanCycles OBJECT-TYPE
            SYNTAX  INTEGER  
            MAX-ACCESS read-write
            STATUS current
            DESCRIPTION 
            "Applicable to all units.  
             The number of scanning cycles when performing Spectrum Analysis. 
             Range: 1-100."
            ::= { bwaVLSpectrumAnalysisParameters 2 }

    bwaVLAutomaticChannelSelection OBJECT-TYPE
            SYNTAX  INTEGER  { disable (1), enable (2), na (255)}
            MAX-ACCESS read-write
            STATUS current
            DESCRIPTION 
            "Applicable to AU/BU only.  
             Defines weather the AU/BU shall choose the most noise free channel
             upon startup after spectrum analysis."
            ::= { bwaVLSpectrumAnalysisParameters 3 }

    bwaVLSpectrumAnalysisActivation OBJECT-TYPE
            SYNTAX  INTEGER  { cancelOperation (1), activateNow (2)}
            MAX-ACCESS read-write
            STATUS current
            DESCRIPTION 
            "Applicable to all units.  
             Activates spectrum analysis, the unit is automatically reset upon 
             activation."
            ::= { bwaVLSpectrumAnalysisParameters 4 }

    bwaVLSpectrumAnalysisStatus OBJECT-TYPE
            SYNTAX  INTEGER  { inactive (1), currentlyActive (2)}
            MAX-ACCESS read-only
            STATUS current
            DESCRIPTION 
            "Applicable to all units.  
             Defines weather the unit is currently under performing 
             a spectrum analysis process."
            ::= { bwaVLSpectrumAnalysisParameters 5 }

    bwaVLResetSpectrumCounters OBJECT-TYPE
            SYNTAX  INTEGER  { cancelOperation (1), resetCounters (2)}
            MAX-ACCESS read-write
            STATUS current
            DESCRIPTION 
            "Applicable to all units.  
             Resets the spectrum analysis counters."
            ::= { bwaVLSpectrumAnalysisParameters 6 }

    bwaVLSpectrumAnalysisInformationTable OBJECT-TYPE
            SYNTAX SEQUENCE OF BwaVLSpectrumAnalysisInformationEntry
            MAX-ACCESS not-accessible
            STATUS current
            DESCRIPTION
            "Applicable to all units.  
             The spectrum analysis information table."
            ::= { bwaVLSpectrumAnalysisParameters 7 }

    bwaVLSpectrumAnalysisInformationEntry  OBJECT-TYPE
            SYNTAX BwaVLSpectrumAnalysisInformationEntry
            MAX-ACCESS not-accessible
            STATUS current
            DESCRIPTION
            "Applicable to all units.  
             The spectrum analysis information table entry."
            INDEX { bwaVLSpectrumAnalysisInformationTableIdx }
            ::= { bwaVLSpectrumAnalysisInformationTable 1 }

    BwaVLSpectrumAnalysisInformationEntry ::= SEQUENCE {
            bwaVLSpectrumAnalysisInformationTableIdx           INTEGER,
            bwaVLSpectrumAnalysisInformationChannel            DisplayString,
            bwaVLSpectrumAnalysisInformationSignalCount        INTEGER,
            bwaVLSpectrumAnalysisInformationSignalSNR          INTEGER,
            bwaVLSpectrumAnalysisInformationSignalWidth        INTEGER,
            bwaVLSpectrumAnalysisInformationOFDMFrames         INTEGER
            }

         
    bwaVLSpectrumAnalysisInformationTableIdx   OBJECT-TYPE
            SYNTAX INTEGER (1..60)
            MAX-ACCESS read-only
            STATUS current
            DESCRIPTION  
            "Applicable to all units.  
             A read only table index for a Spectrum Analysis Information entry in the  
             Spectrum Analysis Information Table."
        ::= { bwaVLSpectrumAnalysisInformationEntry 1 }

    bwaVLSpectrumAnalysisInformationChannel   OBJECT-TYPE
            SYNTAX DisplayString 
            MAX-ACCESS read-only
            STATUS current
            DESCRIPTION  
            "Applicable to all units.  
             The channels in the Spectrum Analysis Information Table.
             If the unit is currently under spectrum analysis the channels would 
             be those on which the analysis is currently performed.
             If the unit is in normal mode the channels would be the those on 
             which the last analysis was performed."
        ::= { bwaVLSpectrumAnalysisInformationEntry 2 }

    bwaVLSpectrumAnalysisInformationSignalCount    OBJECT-TYPE
            SYNTAX INTEGER 
            MAX-ACCESS read-only
            STATUS current
            DESCRIPTION  
            "Applicable to all units.
             The number of signals (excluding OFDM frames) detected in the channel. 
             If the unit is currently under spectrum analysis the count would 
             be of the analysis that is currently performed. 
             If the unit is in normal mode the count would be of the last 
             analysis performed."
        ::= { bwaVLSpectrumAnalysisInformationEntry 3 }

    bwaVLSpectrumAnalysisInformationSignalSNR   OBJECT-TYPE
            SYNTAX INTEGER 
            MAX-ACCESS read-only
            STATUS current
            DESCRIPTION  
            "Applicable to all units.
			 The approximate SNR of the signals (excluding OFDM frames)
			 detected in the channel.
			 If the unit is currently under spectrum analysis the SNR would
			 be of the analysis that is currently performed.
			 If the unit is in normal mode the SNR would be of the last
			 analysis performed."
        ::= { bwaVLSpectrumAnalysisInformationEntry 4 }

    bwaVLSpectrumAnalysisInformationSignalWidth   OBJECT-TYPE
            SYNTAX INTEGER 
            MAX-ACCESS read-only
            STATUS current
            DESCRIPTION  
            "Applicable to all units. 
             The average width of the signals (excluding OFDM frames) 
             detected in the channel. 
             If the unit is currently under spectrum analysis the width would 
             be of the analysis that is currently performed. 
             If the unit is in normal mode the width would be of the last 
             analysis performed."
        ::= { bwaVLSpectrumAnalysisInformationEntry 5 }

    bwaVLSpectrumAnalysisInformationOFDMFrames   OBJECT-TYPE
            SYNTAX INTEGER 
            MAX-ACCESS read-only
            STATUS current
            DESCRIPTION  
            "Applicable to all units. 
             The number of OFDM frames detected in the channel. 
             If the unit is currently under spectrum analysis the count would 
             be of the analysis that is currently performed. 
             If the unit is in normal mode the count would be of the last 
             analysis performed."
        ::= { bwaVLSpectrumAnalysisInformationEntry 6 }

    bwaVLMaxNumOfAssociationsLimit OBJECT-TYPE
            SYNTAX  INTEGER  
            MAX-ACCESS read-only      
            STATUS current       
            DESCRIPTION  
            "Applicable to AU only. 
             Not applicable to BWA-PtP products. 
             Shows the limit for the number of SUs that can be associated 
             with the AU. 
             For AU-BS, AU-SA if Data Encryption is enabled, the upper 
             limit is 124, otherwise it is 512. 
             For AUS-BS, AUS-SA with SW version 4.0 and higher the upper limit 
             is 8 or 25 (via licensing).
             For AUS-BS, AUS-SA with SW version below 4.0 the upper limit is 5.
             BWA-PtP products return 65535."
            ::= { bwaVLAirInterface 19 }

bwaVLDisassociate   OBJECT IDENTIFIER ::= {bwaVLAirInterface 20}

    bwaVLDisassociateAllSUs OBJECT-TYPE
            SYNTAX  INTEGER  { cancelOperation (1), disassociateAllSUs(2)}
            MAX-ACCESS read-write
            STATUS current
            DESCRIPTION 
            "Applicable to AU only.  
             The AU shall disassociate all its associated units."
            ::= { bwaVLDisassociate 1 }

    bwaVLDisassociateSuByMacAddress OBJECT-TYPE
            SYNTAX  MacAddress 
            MAX-ACCESS read-write
            STATUS current
            DESCRIPTION 
            "Applicable to AU only.  
             The AU shall disassociate the SU with the configured MAC address."
            ::= { bwaVLDisassociate 2 }

    bwaVLTxControl OBJECT-TYPE
            SYNTAX  INTEGER  { on (1), off(2)}
            MAX-ACCESS read-write
            STATUS current
            DESCRIPTION 
            "Applicable to AU/BU only.  
             Tx Control of the AU/BU.
             Starting with version 4.0 it is run-time.
             For SW version below 4.0 the unit reset itself.
			 If set to ethernetStatusControl, the unit will not transmit 
             if the Ethernet link is down.
             This parameter can be configured only via the ethernet port."
            ::= { bwaVLAirInterface 21 }

    bwaVLLostBeaconsWatchdogThreshold OBJECT-TYPE
            SYNTAX  INTEGER  ( 0 | 100..1000 )
            MAX-ACCESS read-write
            STATUS current
            DESCRIPTION 
            "Applicable to AU/BU only.  
            The number of unsuccessful consecutive transmissions beacons 
            before Internal refresh is performed. 
			0 means that the lost beacons watchdog is not 
			used and internal refresh is not performed."
			::= { bwaVLAirInterface 22}     

    bwaVLTransmitPower       OBJECT-TYPE
            SYNTAX INTEGER
            MAX-ACCESS read-write
            STATUS current
            DESCRIPTION  
            "Applicable to all units with SW version 4.0 and higher.
             The uniform transmit power for all modulation levels. For a specific
             modulation level the effective transmit power (bwaVLTxPower) is 
             the minimum between the uniform transmit power and the maximum 
             transmit power for that modulation level." 
            ::= { bwaVLAirInterface 23 }
    
    bwaVLMaximumTxPower       OBJECT-TYPE
            SYNTAX INTEGER
            MAX-ACCESS read-write
            STATUS current
            DESCRIPTION  
            "Applicable to only SU/RB with SW version 4.0 and higher.
            The Maximum Transmit Power for all modulation levels.
            The Maximum Transmit Power for a specific modulation level is the 
            minimum between this parameter and the hardware limitation for 
            that modulation level" 
            ::= { bwaVLAirInterface 24 }        
            
   bwaVLCountryCodeParameters   OBJECT IDENTIFIER ::= {bwaVLAirInterface 25}            
   
   bwaLCountryCodeReApply OBJECT-TYPE
	     	SYNTAX	INTEGER { reapply(1),cancel(2), na(255) }  
		    MAX-ACCESS read-write
	     	STATUS current
		    DESCRIPTION	 
            "Applicable to all units.
             Re-apply country code parameters."
			::= { bwaVLCountryCodeParameters 1 }


-- Service Params
-- ==============
   bwaVLServiceParameters       OBJECT IDENTIFIER ::= {bwaVLMib 7}

--    bwaVLMirCirOption OBJECT-TYPE
--    SYNTAX  INTEGER {disable (1),
--                     enable (2), 
--                     na (255)} 
--        MAX-ACCESS read-write
--        STATUS current
--        DESCRIPTION 
--        "Applicable to AU and SU. Read-only in SU. 
--         The setting in the AU enables/disables the MIR/CIR support 
--         feature for all SUs served by the AU."
--    ::= { bwaVLServiceParameters 1 }

    bwaVLMirDownlink OBJECT-TYPE
        SYNTAX  INTEGER  
        MAX-ACCESS read-write
        STATUS current
        DESCRIPTION 
        "Applicable to SU/RB only. 
         The Maximum Information Rate (MIR) from AU/BU to SU/RB.
         MIR must be above bwaVLCirDownlink value.
         Range for set: 128 to 2,048 (Kbps) for SU-3 with SW version below 4.0,
						128 to 3,072 (Kbps) for SU-3 with SW version 4.0 and higher,				
                        128 to 3,968 (Kbps) for SU-6 with SW version less than 4.0,
                        128 to 6,016 (Kbps) for SU-6 with SW version greater than 4.0,
         	            128 to 14,976 (Kbps) for SU-24, 
         	            128 to 53,888 (Kbps) for SU-BD and SU-54,
         	            128 to 6,912  (Kbps) for RB-14, 
         	            128 to 22,016 (Kbps) for RB-28,
         	            128 to 107,904 (Kbps) for RB-100.
         	            128 to 6,016 (Kbps) for SU-I.
         The actual value (Get) will be the entered value rounded to the nearest 
         multiple of 128 (N*128)." 
    ::= { bwaVLServiceParameters 2 }
   
    bwaVLMirUplink OBJECT-TYPE
        SYNTAX INTEGER  
        MAX-ACCESS read-write
        STATUS current
        DESCRIPTION 
        "Applicable to SU/RB only. 
         The Maximum Information Rate (MIR) from SU/RB to AU/BU.
         MIR must be above bwaVLCirUplink value.
         Range for set: 128 to 2,048 (Kbps) for SU-3,
                        128 to 3,968  (Kbps) for SU-6 with SW version less than 4.0,
                        128 to 4,096  (Kbps) for SU-6 with SW version greater than 4.0,
         	            128 to 14,976 (Kbps) for SU-24, 
         	            128 to 53,888 (Kbps) for SU-BD and SU-54,
         	            128 to 6,912  (Kbps) for RB-14, 
         	            128 to 22,016 (Kbps) for RB-28, 
         	            128 to 107,904 (Kbps) for RB-100.
         	            128 to 2,048 (Kbps) for SU-I.
		 The actual value (Get) will be the entered value rounded to the nearest 
		 multiple of 128 (N*128)." 
    ::= { bwaVLServiceParameters 3 }

   
    bwaVLCirDownlink OBJECT-TYPE
        SYNTAX INTEGER  
        MAX-ACCESS read-write
        STATUS current
        DESCRIPTION 
        "Applicable to SU only. 
         Not applicable to BWA-PtP products. 
         The Committed Information Rate (CIR) from AU to SU.
         CIR must be below bwaVLMirDownlink value.
         Range for Set: 
         0 to 2,048 (Kbps) for SU-3 with SW version below 4.0,
		 0 to 3,072 (Kbps) for SU-3 with SW version 4.0 and higher,				
         0 to 3,968 (Kbps) for SU-6 with SW version less than 4.0,
         0 to 6,016 (Kbps) for SU-6 with SW version greater than 4.0
         0 to 14,976 (Kbps) for SU-24, 
         0 to 45,056 (Kbps) for SU-BD and SU-54. 
         0 to 6,016 (Kbps) for SU-I.
         The actual value (Get) will be the entered value rounded to the 
         nearest multiple of 128 (N*128).
		 BWA-PtP products will return 65535."
    ::= { bwaVLServiceParameters 4 }

   
    bwaVLCirUplink OBJECT-TYPE	  
         SYNTAX INTEGER  
         MAX-ACCESS read-write
         STATUS current
         DESCRIPTION  
         "Applicable to SU only. 
          Not applicable to BWA-PtP products. 
          The Committed Information Rate (CIR) from SU to AU.
          CIR must be below bwaVLMirUplink value.
          Range for Set: 
          0 to 2,048 (Kbps) for SU-3,
          0 to 3,968  (Kbps) for SU-6 with SW version less than 4.0,
          0 to 4,096  (Kbps) for SU-6 with SW version greater than 4.0,
          0 to 14,976 (Kbps) for SU-24, 
          0 to 45,056 (Kbps) for SU-BD and SU-54. 
          0 to 2,048 (Kbps) for SU-I.
          The actual value (Get) will be the entered value rounded to the nearest 
          multiple of 128 (N*128).
          BWA-PtP products will return 65535."
    ::= { bwaVLServiceParameters 5 }


    bwaVLMaxDelay OBJECT-TYPE
        SYNTAX INTEGER  
        MAX-ACCESS read-write
        STATUS current
        DESCRIPTION 
        "Applicable to SU only. 
         Not applicable to BWA-PtP products.
         The maximal time packets may be delayed by the 
         CIR\MIR mechanism. Above the configured maximal period 
         the packets are discarded.
         Range: 300 to 10000 milliseconds.
         BWA-PtP products return 65535."
    ::= { bwaVLServiceParameters 6 }

    bwaVLMaxBurstDuration OBJECT-TYPE
        SYNTAX INTEGER  
        MAX-ACCESS read-write
        STATUS current
        DESCRIPTION 
        "Applicable to AU and SU. 
         Not applicable to BWA-PtP products.
         The maximum time during which inactivity bonus time 
         can be accumulated for future burst transmissions.
         Range: 0 to 2000 milliseconds.
         BWA-PtP products return 65535"
    ::= { bwaVLServiceParameters 7 }

    bwaVLGracefulDegradationLimit OBJECT-TYPE
        SYNTAX INTEGER  
        MAX-ACCESS read-write
        STATUS current
        DESCRIPTION 
        "Applicable to AU only. 
         Not applicable to BWA-PtP products.
         The maximum limit for activating the graceful 
         degradation algorithm.
         Range: 0 to 70% rate of the CIR.
         BWA-PtP products return 255."
    ::= { bwaVLServiceParameters 8 }

    bwaVLMirOnlyOption OBJECT-TYPE
        SYNTAX  INTEGER {disable (1), enable (2), na (255)} 
        MAX-ACCESS read-write
        STATUS current
        DESCRIPTION 
        "Applicable to AU only. 
         Not applicable to BWA-PtP products. 
         When bwaMirOnly is enabled, it overrides the CIR/MIR 
         algorithm for determining actual information rate and 
         forces the algorithm to operate with MIR parameter 
         settings only. When enabled, the Graceful Degradation 
         algorithm is disabled."
    ::= { bwaVLServiceParameters 9 }


bwaVLTrafficPrioritization OBJECT IDENTIFIER ::= {bwaVLServiceParameters 10}

bwaVLTrafficPriVLAN OBJECT IDENTIFIER ::= {bwaVLTrafficPrioritization 1}

bwaVLVLANPriorityThreshold OBJECT-TYPE
        SYNTAX  INTEGER (1..7)
        MAX-ACCESS read-write
        STATUS current
        DESCRIPTION 
        "Applicable to all units. 
        If the VLAN Priority's value of the frame is less than or equal to this
        threshold the frame will get LOW priority, otherwise the frame will get 
        HIGH priority.
        Untagged frames will get LOW priority"
    ::= { bwaVLTrafficPriVLAN 1 }


bwaVLTrafficPriIPToS OBJECT IDENTIFIER ::= {bwaVLTrafficPrioritization 2}

bwaVLToSPrioritizationOption OBJECT-TYPE
        SYNTAX  INTEGER {disable(1), ipPrecedence(2), dSCP(3) } 
        MAX-ACCESS read-write
        STATUS current
        DESCRIPTION 
		"Applicable to all units. Disable/Enable IP ToS prioritization and 
		choose the interpretation of the IP ToS field from IP header.
		ipPrecedence(2): The IP ToS field is defined by RFC791. In this 
                         case the prioritization will be done using the 
                         Precedence sub-field of IP ToS. This sub-field 
                         has 3 bits, so it can be between 0 and 7.
		dSCP(3):         The IP ToS field is defined by RFC2474. In this
                         case the prioritization will be done using the 
                         DSCP sub-field. The size of the sub-field is 6 bits, 
                         so the range is 0 to 63."
    ::= { bwaVLTrafficPriIPToS 1 }

bwaVLIPPrecedenceThreshold OBJECT-TYPE
        SYNTAX  INTEGER (0..7)
        MAX-ACCESS read-write
        STATUS current
        DESCRIPTION 
		"Applicable to all units. The threshold of Precedence sub-field of IP ToS 
		field from IP Header (RFC791) to be used when the ToS Prioritization 
		Option is set to IP Precedence.
		If the Precedence sub-field of a frame is less than or equal to this 
		threshold the frame will have LOW priority, otherwise it will get HIGH 
		priority."
    ::= { bwaVLTrafficPriIPToS 2 }

bwaVLIPDSCPThreshold OBJECT-TYPE
        SYNTAX  INTEGER (0..63)
        MAX-ACCESS read-write
        STATUS current
        DESCRIPTION 
		"Applicable to all units. The threshold of DSCP sub-field of IP ToS 
		field from IP Header (RFC2474) to be used when ToS Prioritization 
		Option is set to DSCP.
		If the DSCP sub-field of a frame is less than or equal to this 
		threshold the frame will have LOW priority, otherwise it will get 
		HIGH priority."
    ::= { bwaVLTrafficPriIPToS 3 }
 
        
bwaVLTrafficPriUdpTcpPortRange OBJECT IDENTIFIER ::= {bwaVLTrafficPrioritization 3}

bwaVLUdpTcpPortRangePrioritizationOption OBJECT-TYPE
        SYNTAX  INTEGER {disable(1), udpOnly(2), tcpOnly(3), udpANDtcp(4) } 
        MAX-ACCESS read-write
        STATUS current
        DESCRIPTION 
        "Applicable to all units. Disable/Enable Prioritization using UDP and/or
        TCP Port Ranges. 
		udpOnly(2)  : prioritization will be done only for UDP packets
		tcpOnly(3)  : prioritization will be done only for TCP packets
		udpANDtcp(4): prioritization will be done for UDP and TCP packets"
    ::= { bwaVLTrafficPriUdpTcpPortRange 1 }

bwaVLUdpPortRangeConfig OBJECT IDENTIFIER ::= {bwaVLTrafficPriUdpTcpPortRange 2}

bwaVLUdpPortPriRTPRTCP OBJECT-TYPE
        SYNTAX  INTEGER {rtpANDrtcp(1),rtpOnly(2) } 
        MAX-ACCESS read-write
        STATUS current
        DESCRIPTION 
        "Applicale to all units.
        RTP/RTCP ports prioritization option for UDP packets. 
        rtpANDrtcp(1): the possible RTP and RTCP packet with destination port in the
                       defined port ranges will get HIGH priority
		rtpOnly(2): only possible RTP packet (packet with even destination port ) 
		            with destination port in the defined port ranges will get HIGH 
		            priority."
    ::= { bwaVLUdpPortRangeConfig 1 }

bwaVLUdpPortRangeNum OBJECT-TYPE
        SYNTAX  INTEGER 
        MAX-ACCESS read-only
        STATUS current
        DESCRIPTION 
        "Applicable to all units. The number of entries in the UDP Port Range Table"
    ::= { bwaVLUdpPortRangeConfig 2 }
    
bwaVLUdpPortRangeTable OBJECT-TYPE
        SYNTAX SEQUENCE OF BwaVLUdpPortRangeEntry
        MAX-ACCESS not-accessible
        STATUS current
        DESCRIPTION
		"Applicable to all units. A table of UDP port ranges use for prioritization. 
		The user can define up to 64 ranges.
        An entry is empty if start is 65535 and end is 0"
        ::= { bwaVLUdpPortRangeConfig 3 }

bwaVLUdpPortRangeEntry  OBJECT-TYPE
        SYNTAX BwaVLUdpPortRangeEntry
        MAX-ACCESS not-accessible
        STATUS current
        DESCRIPTION
        "Applicable to all units. A UDP Port Ranges Table entry." 
        INDEX { bwaVLUdpPortRangeIdx }
        ::= { bwaVLUdpPortRangeTable 1 }

BwaVLUdpPortRangeEntry ::= SEQUENCE {
        bwaVLUdpPortRangeStart INTEGER,
        bwaVLUdpPortRangeEnd INTEGER,
        bwaVLUdpPortRangeIdx INTEGER
        }
            
bwaVLUdpPortRangeStart OBJECT-TYPE
        SYNTAX INTEGER(0..65535)  
        MAX-ACCESS read-only
        STATUS current
        DESCRIPTION 
        "Applicable to all units. Start port of an UDP Port Range"
        ::= { bwaVLUdpPortRangeEntry 1 }

bwaVLUdpPortRangeEnd OBJECT-TYPE
        SYNTAX INTEGER(0..65535)  
        MAX-ACCESS read-only
        STATUS current
        DESCRIPTION 
        "Applicable to all units. End port of an UDP Port Range"
        ::= { bwaVLUdpPortRangeEntry 2 }
           
bwaVLUdpPortRangeIdx OBJECT-TYPE
        SYNTAX INTEGER(1..64)  
        MAX-ACCESS read-only
        STATUS current
        DESCRIPTION 
        "Applicable to all units. UDP Port Range Entry's index "
        ::= { bwaVLUdpPortRangeEntry 3 }


bwaVLUdpPortRangeAdd OBJECT-TYPE
        SYNTAX DisplayString (SIZE(0..250)) 
        MAX-ACCESS read-write
        STATUS current
        DESCRIPTION 
        "Applicable to all units. Add port range(s) to UDP Port Ranges Table. 
        Get operation will return the empty string. 
		A range is defined <start>-<end> or <start> where <start> is the Start 
		Port of the range and <end> is the End Port. If only <start> is 
		specified the range is <start>-<start>.
        The value of  <start> and <end> are between 0..65535.
        The user can add several ranges using a comma to separate between ranges. 
        Example: 10-256,99,987-900"
    ::= { bwaVLUdpPortRangeConfig 4 }
    
bwaVLUdpPortRangeDelete OBJECT-TYPE
        SYNTAX DisplayString (SIZE(0..250)) 
        MAX-ACCESS read-write
        STATUS current
        DESCRIPTION 
        "Applicable to all units. Delete port range(s) from UDP Port Ranges Table. 
        Get operation will return the empty string.
        A range is defined <start>-<end> or <start> where <start> is the Start 
        Port of the range and <end> is the End Port. If only <start> is 
        specified the range is <start>-<start>.
        The value of  <start> and <end> are between 0..65535.
        The user can delete several ranges using a comma to separate between 
        ranges.
        Example: 10-256,99,987-900"
    ::= { bwaVLUdpPortRangeConfig 5 }

bwaVLUdpPortRangeDeleteAll OBJECT-TYPE
        SYNTAX INTEGER { deleteAll(1), cancelOperation(2) }
        MAX-ACCESS read-write
        STATUS current
        DESCRIPTION 
		"Applicable to all units. Delete all entries form UDP Port Ranges Table. 
		Get operation will return 1"
    ::= { bwaVLUdpPortRangeConfig 6 }



bwaVLTcpPortRangeConfig OBJECT IDENTIFIER ::= {bwaVLTrafficPriUdpTcpPortRange 3}

bwaVLTcpPortPriRTPRTCP OBJECT-TYPE
        SYNTAX  INTEGER {rtpANDrtcp(1),rtpOnly(2) } 
        MAX-ACCESS read-write
        STATUS current
        DESCRIPTION 
        "Applicable to all units. RTP/RTCP ports prioritization option for TCP packets. 
		rtpANDrtcp(1): the possible RTP and RTCP packet with destination port 
		in the defined port ranges will get HIGH priority
		rtpOnly(2): only possible RTP packet (packet with even destination port )"
    ::= { bwaVLTcpPortRangeConfig 1 }

bwaVLTcpPortRangeNum OBJECT-TYPE
        SYNTAX  INTEGER 
        MAX-ACCESS read-only
        STATUS current
        DESCRIPTION 
        "Applicable to all units. The number of entries in the TCP Port Range Table"
    ::= { bwaVLTcpPortRangeConfig 2 }
    
bwaVLTcpPortRangeTable OBJECT-TYPE
        SYNTAX SEQUENCE OF BwaVLTcpPortRangeEntry
        MAX-ACCESS not-accessible
        STATUS current
        DESCRIPTION
        "Table of TCP Port Ranges use for prioritization.
        The user can define up to 64 ranges.
        An entry is empty if start is 65535 and end is 0"
        ::= { bwaVLTcpPortRangeConfig 3 }

bwaVLTcpPortRangeEntry  OBJECT-TYPE
        SYNTAX BwaVLTcpPortRangeEntry
        MAX-ACCESS not-accessible
        STATUS current
        DESCRIPTION
        "Applicable to all units. A TCP Port Ranges Table entry." 
        INDEX { bwaVLTcpPortRangeIdx }
        ::= { bwaVLTcpPortRangeTable 1 }

BwaVLTcpPortRangeEntry ::= SEQUENCE {
        bwaVLTcpPortRangeStart INTEGER,
        bwaVLTcpPortRangeEnd INTEGER,
        bwaVLTcpPortRangeIdx INTEGER
        }
            
bwaVLTcpPortRangeStart OBJECT-TYPE
        SYNTAX INTEGER(0..65535)  
        MAX-ACCESS read-only
        STATUS current
        DESCRIPTION 
        "Applicable to all units. Start port of a TCP Port Range"
        ::= { bwaVLTcpPortRangeEntry 1 }

bwaVLTcpPortRangeEnd OBJECT-TYPE
        SYNTAX INTEGER(0..65535)  
        MAX-ACCESS read-only
        STATUS current
        DESCRIPTION 
        "Applicable to all units. End port of a TCP Port Range"
        ::= { bwaVLTcpPortRangeEntry 2 }
           
bwaVLTcpPortRangeIdx OBJECT-TYPE
        SYNTAX INTEGER(1..64)  
        MAX-ACCESS read-only
        STATUS current
        DESCRIPTION 
        "Applicable to all units. TCP Port Range Entry's index"
        ::= { bwaVLTcpPortRangeEntry 3 }


bwaVLTcpPortRangeAdd OBJECT-TYPE
        SYNTAX DisplayString (SIZE(0..250)) 
        MAX-ACCESS read-write
        STATUS current
        DESCRIPTION 
        "Applicable to all units. Add port range(s) to TCP Port Ranges Table. 
        Get operation will return the empty string. 
		A range is defined <start>-<end> or <start> where <start> is the Start 
		Port of the range and <end> is the End Port. If only <start> is specified 
		the range is <start>-<start>.
        The value of  <start> and <end> are between 0..65535.
        The user can add several ranges using comma to separate between ranges.
        Example: 10-256,99,987-900"
    ::= { bwaVLTcpPortRangeConfig 4 }
    
bwaVLTcpPortRangeDelete OBJECT-TYPE
        SYNTAX DisplayString (SIZE(0..250)) 
        MAX-ACCESS read-write
        STATUS current
        DESCRIPTION 
		"Applicable to all units. Delete port range(s) from TCP Port Ranges Table. 
		Get operation will return the empty string.
        A range is defined <start>-<end> or <start> where <start> is the Start 
        Port of the range and <end> is the End Port. If only <start> is specified 
        the range is <start>-<start>.
        The value of  <start> and <end> are between 0..65535.
        The user can delete several ranges using comma to separate between ranges.
        Example: 10-256,99,987-900"
    ::= { bwaVLTcpPortRangeConfig 5 }

bwaVLTcpPortRangeDeleteAll OBJECT-TYPE
        SYNTAX INTEGER { deleteAll(1), cancelOperation(2) }
        MAX-ACCESS read-write
        STATUS current
        DESCRIPTION 
        "Applicable to all units. Delete all entries form TCP Port Ranges Table
        Get operation will return 1"
    ::= { bwaVLTcpPortRangeConfig 6 }

bwaVLWirelessLinkPrioritization OBJECT IDENTIFIER ::= {bwaVLTrafficPrioritization 4}

bwaVLWirelessLinkPrioritizationOption OBJECT-TYPE
            SYNTAX  INTEGER  { disable(1), enable(2), na(255) }
            MAX-ACCESS read-write      
            STATUS current       
            DESCRIPTION  
            "Applicable only to AU with a license for the Wireless Link Prioritization feature and to BU-100. 
             Enable/disable the traffic prioritization over the 
             Wireless Link"
            ::= { bwaVLWirelessLinkPrioritization  1}

bwaVLlowPriorityAIFS OBJECT-TYPE
            SYNTAX  INTEGER  (3..254)
            MAX-ACCESS read-write      
            STATUS current       
            DESCRIPTION  
            "Applicable only to AU with a license for the Wireless Link Prioritization feature and to BU-100. 
            Applicable only if the Wireless Link Prioritization Option is enabled.
            Define the AIFS (Arbitration Inter-frame Space) that will be used   
            for transmitting Low Priority Traffic"
            ::= { bwaVLWirelessLinkPrioritization  2}

bwaVLHWRetriesHighPriority OBJECT-TYPE
            SYNTAX  INTEGER (0..14)
            MAX-ACCESS read-write      
            STATUS current       
            DESCRIPTION  
            "Applicable only to AU with a license for the Wireless Link Prioritization feature and to BU-100.
            Applicable only if the Wireless Link Prioritization Option is enabled. 
            Defines the Maximum number of HW Retries for a unicast data packet 
            that has High Priority"
            ::= { bwaVLWirelessLinkPrioritization  3}
            
bwaVLHWRetriesLowPriority OBJECT-TYPE
            SYNTAX  INTEGER (0..14)
            MAX-ACCESS read-write      
            STATUS current       
            DESCRIPTION  
            "Applicable only to AU with a license for the Wireless Link Prioritization feature and to BU-100.
            Applicable only if the Wireless Link Prioritization Option is enabled. 
            Defines the Maximum number of HW Retries for a unicast data packet 
            that has Low Priority"
            ::= { bwaVLWirelessLinkPrioritization 4}
            
bwaVLAUBurstDurationHighPriority OBJECT-TYPE
            SYNTAX  INTEGER  (0..40)
            MAX-ACCESS read-write      
            STATUS current       
            DESCRIPTION  
            "Applicable only to AU with a license for the Wireless Link Prioritization feature and to BU-100. 
            Applicable only if the Wireless Link Prioritization Option is enabled.
             Defines the Maximum duration of burst that can be done by AU with 
             High Priority packets.
             The time is given in 250 microseconds units"
            ::= { bwaVLWirelessLinkPrioritization  5}
            
bwaVLAUBurstDurationLowPriority OBJECT-TYPE
            SYNTAX  INTEGER  (0..40)
            MAX-ACCESS read-write      
            STATUS current       
            DESCRIPTION  
            "Applicable only to AU with a license for the Wireless Link Prioritization feature and to BU-100. 
            Applicable only if the Wireless Link Prioritization Option is enabled.
             Defines the Maximum duration of burst that can be done by AU 
             with Low Priority packets.
             The time is given in 250 microseconds units"
            ::= { bwaVLWirelessLinkPrioritization  6}
            
bwaVLSUBurstDurationHighPriority OBJECT-TYPE
            SYNTAX  INTEGER (0..40)
            MAX-ACCESS read-write      
            STATUS current       
            DESCRIPTION  
            "Applicable only to AU with a license for the Wireless Link Prioritization feature and to BU-100. 
            Applicable only if the Wireless Link Prioritization Option is enabled.
            Defines the Maximum duration of burst that can be done by SU/RB 
            with High Priority packets.
            The parameter is configurable in AU and the SUs/RB will learn it 
            form AU/BU.
            The time is given in 250 microseconds units"
            ::= { bwaVLWirelessLinkPrioritization  7}

bwaVLSUBurstDurationLowPriority OBJECT-TYPE
            SYNTAX  INTEGER (0..40)
            MAX-ACCESS read-write      
            STATUS current       
            DESCRIPTION  
            "Applicable only to AU with a license for the Wireless Link Prioritization feature and to BU-100. 
            Applicable only if the Wireless Link Prioritization Option is enabled.
            Defines the Maximum duration of burst that can be done by SU/RB 
            with High Priority packets.
            The parameter is configurable in AU/BU and the SUs/RB will learn it 
            from AU/BU.
            The time is given in 250 microseconds units"
            ::= { bwaVLWirelessLinkPrioritization  8}

    
--DRAP BEGIN

bwaVLDrap OBJECT IDENTIFIER ::= { bwaVLServiceParameters 11 }

bwaVLDrapSupport OBJECT-TYPE
		SYNTAX INTEGER {disable(1), enable(2), na(255)}
		MAX-ACCESS read-write
		STATUS current
		DESCRIPTION
		"Applicable to AU. Not applicable to BWA PtP products.
		Disable/Enable the DRAP feature" 
		::= { bwaVLDrap 1 }

bwaVLDrapUdpPort OBJECT-TYPE
		SYNTAX INTEGER (8000..8200)
		MAX-ACCESS read-write
		STATUS current
		DESCRIPTION
		"Applicable to AU when DRAP support is enabled. 
		Not applicable to BWA PtP products. 
		The UDP port used for the DRAP server"
		::= { bwaVLDrap 2 }

bwaVLDrapMaxNumberOfVoiceCalls OBJECT-TYPE
		SYNTAX INTEGER (0..255)
		MAX-ACCESS read-write
		STATUS current
		DESCRIPTION
		"Applicable to AU when DRAP support is enabled. 
		Not applicable to BWA PtP products. 
		The maximum number of voice calls that can be supported by the AU"
		::= { bwaVLDrap 3 }

bwaVLDrapTTL OBJECT-TYPE
		SYNTAX INTEGER (1..255)
		MAX-ACCESS read-write
		STATUS current
		DESCRIPTION
		"Applicable to AU when DRAP support is enabled. 
		Not applicable to BWA PtP products. 
		The maximum time between two allocation requests"
		::= { bwaVLDrap 4 }

bwaVLDrapNoOfActiveVoiceCalls OBJECT-TYPE
        SYNTAX INTEGER
        MAX-ACCESS read-only
        STATUS current
        DESCRIPTION 
		"Applicable to AU when DRAP support is enabled. 
		Not applicable to BWA PtP products. 
		The current total number of  active voice calls."
        ::= { bwaVLDrap 5 }


--DRAP END

bwaVLLowPriorityTrafficMinimumPercent OBJECT-TYPE
		SYNTAX INTEGER (0..100)
		MAX-ACCESS read-write
		STATUS current
		DESCRIPTION 
		"The minimum percent of the traffic rate that is allocated to the low priority traffic"
		::= { bwaVLServiceParameters 12 }

bwaVLSUPMirDownlink OBJECT-TYPE
        SYNTAX  INTEGER  
        MAX-ACCESS read-write
        STATUS current
        DESCRIPTION 
        "Applicable to AU only. 
         The Maximum Information Rate (MIR) from AU to SUP.
            Range for set: 128 to 12,032 (Kbps).
         The actual value (Get) will be the entered value rounded to the nearest 
         multiple of 128 (N*128)." 
    ::= { bwaVLServiceParameters 13 }

bwaVLMIRThresholdPercent OBJECT-TYPE
        SYNTAX  INTEGER (0..100) 
        MAX-ACCESS read-write
        STATUS current
        DESCRIPTION 
        "Applicable to AU only.  
		MIR Threshold Percent" 
    ::= { bwaVLServiceParameters 14 }		


-- User Filtering Params
-- =====================
   bwaVLUserFilterParams   OBJECT IDENTIFIER ::= {bwaVLMib 8}

    bwaVLUserFilterOption OBJECT-TYPE
            SYNTAX INTEGER { disable (1), 
                             ipOnly (2), 
                             userDefinedAddrOnly (3), 
                             pPPoEOnly (4), 
                             na (255) } 
            MAX-ACCESS read-write
            STATUS current
            DESCRIPTION 
            "Applicable to SU/RB only. 
             Defines user-filtering options.
             disable: No filtering.
             iPOnly: Only IP protocol frames pass. 
             userDefinedAddrOnly: Only ip frames to/from user defined IP 
                                  addresses pass.
             pPPoE Only: Only PPPoE frames pass."
             ::= { bwaVLUserFilterParams 1 }

    bwaVLIpFilterTable OBJECT-TYPE
            SYNTAX SEQUENCE OF BwaVLIpFilterEntry
            MAX-ACCESS not-accessible
            STATUS current
            DESCRIPTION
            "Applicable to SU/RB only. 
             An IP Filter Table of up to 8 user defined addresses, 
             or address groups, to be used if the selected User 
             Filtering option is userDefinedAddrOnly." 
            ::= { bwaVLUserFilterParams 2 }

    bwaVLIpFilterEntry  OBJECT-TYPE
            SYNTAX BwaVLIpFilterEntry
            MAX-ACCESS not-accessible
            STATUS current
            DESCRIPTION
            "Applicable to SU/RB only. 
             An IP Filter Table entry." 
            INDEX { bwaVLIpFilterIdx }
            ::= { bwaVLIpFilterTable 1 }

   BwaVLIpFilterEntry ::= SEQUENCE {
            bwaVLIpID   IpAddress,
            bwaVLMaskID IpAddress,
            bwaVLIpFilterRange INTEGER,
            bwaVLIpFilterIdx INTEGER
            }
               
    bwaVLIpID   OBJECT-TYPE
            SYNTAX IpAddress  
            MAX-ACCESS read-write
            STATUS current
            DESCRIPTION 
            "Applicable to SU/RB only. 
             An IP address of an IP Filter Table entry."
           ::= { bwaVLIpFilterEntry 1 }

    bwaVLMaskID OBJECT-TYPE
            SYNTAX IpAddress  
            MAX-ACCESS read-write
            STATUS current
            DESCRIPTION 
            "Applicable to SU/RB only. 
             An IP Mask of an IP Filter Table entry. Either a mask 
             or a range, but not both can be used to define an 
             address group. If the range is other than 0, than the mask is 
             ignored and only the range value is used to define the address group."
           ::= { bwaVLIpFilterEntry 2 }
   
    bwaVLIpFilterRange OBJECT-TYPE
            SYNTAX INTEGER 
            MAX-ACCESS read-write
            STATUS current
            DESCRIPTION 
            "Applicable to SU/RB only. 
             An addresses range for the IP Filter Table entry. The 
             first address in the range is the IP address.
             O means that the range is not used.  
             Either a mask or a range, but not both can be used to 
             define an address group.
			 If the range is other than 0, than the mask is ignored and 
			 only the range value is used to define the address group.
             Range: 0 to 255."
            ::= { bwaVLIpFilterEntry 3 }

    bwaVLIpFilterIdx   OBJECT-TYPE
            SYNTAX INTEGER  (1..8)
            MAX-ACCESS read-only
            STATUS current
            DESCRIPTION 
            "Applicable to SU/RB only. 
             A table index for the IP Filter Table entry." 
         ::= { bwaVLIpFilterEntry 4 }

    bwaVLDeleteOneUserFilter OBJECT-TYPE
            SYNTAX  INTEGER { deletefirstEntry  (1), deletesecondEntry (2), 
                              deletethirdEntry  (3), deletefourthEntry (4), 
                              deletefifthEntry  (5), deletesixthEntry (6), 
                              deleteseventhEntry(7), deleteeighthEntry (8), 
                              cancelOperation   (9), na (255) } 
 
            MAX-ACCESS read-write
            STATUS current
            DESCRIPTION 
            "Applicable to SU/RB only. 
             Deletes a single selected entry from the IP Filter 
             Table."
            ::= { bwaVLUserFilterParams 3 }

    bwaVLDeleteAllUserFilters OBJECT-TYPE
            SYNTAX  INTEGER { deleteAll (1), cancelOperation (2),  
                              na (255) } 
            MAX-ACCESS read-write
            STATUS current
            DESCRIPTION 
            "Applicable to SU/RB only. 
             Deletes all entries from the IP Filter Table."
            ::= { bwaVLUserFilterParams 4 }

    bwaVLDHCPUnicastOverrideFilter OBJECT-TYPE
            SYNTAX  INTEGER { disable (1), enable (2), na (255) } 
            MAX-ACCESS read-write
            STATUS current
            DESCRIPTION  
            "Applicable to SU/RB only. 
             Enables or disables the unicast DHCP messages, 
             overriding the IP Filtering option." 
            ::= { bwaVLUserFilterParams 5 }


 
-- Security Params
-- ==================
bwaVLSecurityParameters     OBJECT IDENTIFIER ::= {bwaVLMib 9}

    bwaVLAuthenticationAlgorithm OBJECT-TYPE
            SYNTAX  INTEGER  {openSystem(1) , sharedKey(2)}
            MAX-ACCESS read-write
            STATUS current
            DESCRIPTION  
            "Applicable to all units.
            Enables/disables the authentication encryption option.
            openSystem: Authentication messages are not encrypted.
            sharedKey : Authentication messages are encrypted "
            ::= { bwaVLSecurityParameters 1 }

    bwaVLSUDefaultKeyID OBJECT-TYPE
            SYNTAX  INTEGER  
            MAX-ACCESS read-write
            STATUS current
            DESCRIPTION  
            "Applicable to SU/RB only.
			 The key to be used for encryption of authentication messages 
			 and/or data.
             Range: 1 to 4. "
            ::= { bwaVLSecurityParameters 2 }

    bwaVLDataEncryptionOption OBJECT-TYPE
            SYNTAX  INTEGER  {disable(1) , enable(2)}
            MAX-ACCESS read-write
            STATUS current
            DESCRIPTION  
            "Applicable to all units.
             Enables/disables the data encryption option. "
            ::= { bwaVLSecurityParameters 3 }

    bwaVLAUDefaultMulticastKeyID OBJECT-TYPE
            SYNTAX  INTEGER  
            MAX-ACCESS read-write
            STATUS current
            DESCRIPTION  
            "Applicable to AU/BU only.
             The key to be used for encryption of multicasts and broadcasts."
            ::= { bwaVLSecurityParameters 4 }

    bwaVLSecurityMode OBJECT-TYPE
            SYNTAX  INTEGER   {wep(1) , aesOCB(2), fips197(3)}
            MAX-ACCESS read-write
            STATUS current
            DESCRIPTION  
            "Applicable to all units. The fips197 option is applicable only to units with a license to
             use FIPS 197 algorithm.
             The encryption algorithm to be used for authentication messages 
             and/or data encryption."
            ::= { bwaVLSecurityParameters 5 }


    bwaVLAuthenticationPromiscuousMode OBJECT-TYPE
            SYNTAX  INTEGER   {disable(1) , enable(2)}
            MAX-ACCESS read-write
            STATUS current
            DESCRIPTION  
            "Applicable to AU/BU only.
             Enables/disable the promiscuous mode allowing authentication of 
             and communication with all SUs/RB regardless of their security 
             parameters."
            ::= { bwaVLSecurityParameters 6 }


    bwaVLKey1 OBJECT-TYPE
            SYNTAX  DisplayString (SIZE(32))
            MAX-ACCESS read-write
            STATUS current
            DESCRIPTION  
            "Applicable to all units.
             Key number 1. Accessible only with SNMP Write Community String 
             (administrator password).
             Valid values: 32 hexadecimal digits."
            ::= { bwaVLSecurityParameters 7 }

    bwaVLKey2 OBJECT-TYPE
            SYNTAX  DisplayString (SIZE(32))
            MAX-ACCESS read-write
            STATUS current
            DESCRIPTION  
            "Applicable to all units.
             Key number 2. Accessible only with SNMP Write Community String 
             (administrator password).
             Valid values: 32 hexadecimal digits."
            ::= { bwaVLSecurityParameters 8 }

    bwaVLKey3 OBJECT-TYPE
            SYNTAX  DisplayString (SIZE(32))
            MAX-ACCESS read-write
            STATUS current
            DESCRIPTION  
            "Applicable to all units.
             Key number 3. Accessible only with SNMP Write Community String 
             (administrator password).
             Valid values: 32 hexadecimal digits."
            ::= { bwaVLSecurityParameters 9 }

    bwaVLKey4 OBJECT-TYPE
            SYNTAX  DisplayString (SIZE(32))
            MAX-ACCESS read-write
            STATUS current
            DESCRIPTION  
            "Applicable to all units.
             Key number 4. Accessible only with SNMP Write Community String 
             (administrator password).
             Valid values: 32 hexadecimal digits."
            ::= { bwaVLSecurityParameters 10 }

bwaVLSecurityModeSupport OBJECT-TYPE
            SYNTAX  INTEGER (0..7)
            MAX-ACCESS read-only
            STATUS current
            DESCRIPTION  
            "Applicable to all units. Returns types of encryption that are supported.
            0 - no encryption
            1 - WEP
            2 - AES OCB
            3 - WEP and AES OCB
            4 - FIPS-197
            5 - FIPS-197 and WEP
            6 - FIPS-197 and AES OCB
            7 - FIPS-197, AES OCB and WEP"
            ::= { bwaVLSecurityParameters 12 }


-- Performance Params
-- ==================
bwaVLPerformanceParams     OBJECT IDENTIFIER ::= {bwaVLMib 10}

    bwaVLRTSThreshold OBJECT-TYPE
            SYNTAX  INTEGER  
            MAX-ACCESS read-write
            STATUS current
            DESCRIPTION  
            "Applicable to SU and AU. 
             Not applicable to BWA-PtP products. 
             The minimum frame size that requires an RTS/CTS handshake.            
             Range: For units bearing SW version 3.0 and above: 20 to 3400 bytes,
			 for previous SW versions 20 to 1600 bytes.
             BWA-PtP products return 65535."
            ::= { bwaVLPerformanceParams 1 }

    bwaVLMinContentionWindow OBJECT-TYPE
            SYNTAX  INTEGER  
            MAX-ACCESS read-write
            STATUS current
            DESCRIPTION  
            "Applicable to SU and AU. 
             For units bearing SW version 4.0 and above applicable to 
             BWA PtP products, for previous SW versions not applicable 
             to BWA PtP products. 
             The initial value to be used by the contention window calculation 
             algorithm.
             Value must be 0 or power of 2 minus 1 (7,15,31...).
             Range: 0 to 1023, excluding 1 and 3.
             BWA-PtP products with SW version below 4.0 return 65535."
            ::= { bwaVLPerformanceParams 3 }

    bwaVLMaxContentionWindow OBJECT-TYPE
            SYNTAX  INTEGER  
            MAX-ACCESS read-write
            STATUS current
            DESCRIPTION  
            "Applicable to SU and AU. 
             For units bearing SW version 4.0 and above applicable to 
             BWA PtP products, for previous SW versions not applicable 
             to BWA PtP products. 
             The maximum value to be used by the contention window calculation 
             algorithm.
             Value must be power of 2 minus 1 (7,15,31...)
             Range: 7 to 1023."
            ::= { bwaVLPerformanceParams 4 }

    bwaVLMaximumModulationLevel OBJECT-TYPE
            SYNTAX  INTEGER { level1 (1), 
                              level2 (2), 
                              level3 (3), 
                              level4 (4), 
                              level5 (5), 
                              level6 (6), 
                              level7 (7),
                              level8 (8)
                            } 
            MAX-ACCESS read-write
            STATUS current
            DESCRIPTION  
            "Applicable to all units.
             If the Adaptive Modulation algorithm is enabled, it sets the 
             Maximum Modulation Level to be used.
             If The Modulation algorithm is disabled, it sets the Fixed 
             Modulation Level to be used.
			 The range is 1 to 8. 8 is not applicable for units with HW revision A." 
            ::= { bwaVLPerformanceParams 5 }

    bwaVLMulticastModulationLevel OBJECT-TYPE
            SYNTAX  INTEGER { level1 (1), 
                              level2 (2), 
                              level3 (3), 
                              level4 (4), 
                              level5 (5), 
                              level6 (6), 
                              level7 (7),
                              level8 (8) 
                            } 
 
            MAX-ACCESS read-write
            STATUS current
            DESCRIPTION  
            "Applicable to AU/BU only.
             The modulation level for multicast and broadcast data frames.
			 The range is 1 to 8.
			 8 is not applicable for units with HW revision A." 
            ::= { bwaVLPerformanceParams 6 }

    bwaVLAvgSNRMemoryFactor  OBJECT-TYPE
            SYNTAX DisplayString	 
            MAX-ACCESS read-write
            STATUS current
            DESCRIPTION  
            "Applicable to all units.
			 The weight of history in average SNR calculation.
			 The higher is the value, the higher is the weight of history.
             Range: -1 (Disregard History) to 32."
            ::= { bwaVLPerformanceParams 7 }

    bwaVLHardwareRetries OBJECT-TYPE
            SYNTAX  INTEGER  
            MAX-ACCESS read-write
            STATUS current
            DESCRIPTION  
            "Applicable to all units.
             Not applicable if Wireless Link Prioritization is enabled.
             The maximum number of trials to transmit an unacknowledged 
             frame in each Hardware Retrial phase.
             Range : 1 to 14." 
            ::= { bwaVLPerformanceParams 8 }


bwaVLAdaptiveModulationParams     OBJECT IDENTIFIER ::= {bwaVLPerformanceParams 9}

    bwaVLAdaptiveModulationAlgorithmOption OBJECT-TYPE
            SYNTAX  INTEGER  {   disable (1) , enable (2), na (255) }
            MAX-ACCESS read-write      
            STATUS current       
            DESCRIPTION  
            "Applicable to all units. 
             Enables/disables the adaptive modulation level decision mechanism."
            ::= { bwaVLAdaptiveModulationParams  1 }


    bwaVLSoftwareRetrySupport OBJECT-TYPE
            SYNTAX  INTEGER  {   disable (1) , enable (2), na (255) }
            MAX-ACCESS read-write      
            STATUS current       
            DESCRIPTION  
            "Applicable to all units. 
             Read-only for units with version 2.0. 
             Not applicable for units with SW version 3.0 and higher. 
             The status of the Software Retry mechanism. 
             Enabled when the Adaptive Modulation algorithm is enabled and 
             the Burst Mode Option is disabled. Otherwise it is disabled." 
            ::= { bwaVLAdaptiveModulationParams  2 }


    bwaVLNumOfSoftwareRetries OBJECT-TYPE
            SYNTAX  INTEGER { na (255) }
            MAX-ACCESS read-write 
            STATUS current
            DESCRIPTION  
            "Applicable to all units. 
             Read-only for units with version 2.0. 
             Not applicable for units with SW version 3.0 and higher. 
             The maximum number of times to use the Software Retry mechanism 
             when it is enabled."
            ::= { bwaVLAdaptiveModulationParams 3 }



    bwaVLMinIntervalBetweenAdaptiveModulationAlgorithmMessages  OBJECT-TYPE
            SYNTAX INTEGER	 
            MAX-ACCESS read-write
            STATUS current
            DESCRIPTION  
            "Applicable all units.
			 The minimum interval between two consecutive AU/BU to SU/RB messages.
             Range: 1 to 3600 (Sec)."
            ::= { bwaVLAdaptiveModulationParams 4 }

    bwaVLAdaptiveModulationDecisionThresholds OBJECT-TYPE
            SYNTAX  INTEGER  { normal (1) , high (2), na (255) }
            MAX-ACCESS read-write      
            STATUS current       
            DESCRIPTION  
            "Applicable to all units. 
             Defines the setting of thresholds for the rate decision algorithm. 
             high (2) should typically be used when the SNR is lower than 13dB."
            ::= { bwaVLAdaptiveModulationParams  5 }

bwaVLBurstMode     OBJECT IDENTIFIER ::= {bwaVLPerformanceParams 10}

    bwaVLBurstModeOption OBJECT-TYPE
            SYNTAX  INTEGER  {   disable (1) , enable (2), blocked(3), na (255) }
            MAX-ACCESS read-write      
            STATUS current       
            DESCRIPTION  
            "Applicable to all units.
             Applicable only if Burst Mode Option is supported by country 
             specific parameters of the Sub Band.  
             Not applicable if Wireless Link Prioritization is enabled.
             Enables/disable burst mode operation.
             In SU/RB with HW Revision B or lower blocked(3) value is returned
             when Security Mode is Wep , Data Encryption Option
			 is Enabled and Burst option is Enabled.
			 In AU/BU with HW Revision B or lower blocked(3) value is returned
			 when Dfs Option is Enabled and Burst mode is enabled."
            ::= { bwaVLBurstMode  1 }

    bwaVLBurstInterval OBJECT-TYPE
            SYNTAX  INTEGER
            MAX-ACCESS read-write      
            STATUS current       
            DESCRIPTION  
            "Applicable to all units.
             Not applicable if Wireless Link Prioritization is enabled.
             Burst mode interval in milliseconds.
             Range: 1 to the maximum value as defined in the country 
             specific parameters of the Sub Band (milliseconds)."
            ::= { bwaVLBurstMode  2 }

bwaVLConcatenationParameters     OBJECT IDENTIFIER ::= {bwaVLPerformanceParams 11}
  
   bwaVLConcatenationOption OBJECT-TYPE
            SYNTAX  INTEGER  { disable (1), enable (2), na (255)}
            MAX-ACCESS read-write      
            STATUS current       
            DESCRIPTION  
            "Applicable to all units. 
             Defines the Concatenation option."
            ::= { bwaVLConcatenationParameters 1 }

   bwaVLConcatenationMaximumNumberOfFrames OBJECT-TYPE
            SYNTAX  INTEGER (2..8)
            MAX-ACCESS read-write      
            STATUS current       
            DESCRIPTION  
            "Applicable to all units with SW version 3.X . 
             Not applicable for version 4.0 and higher.
             Defines the maximum numbers of frames that can be concatenated.
             Range:2 to 8 (frames)."
            ::= { bwaVLConcatenationParameters 2 }
    
   bwaVLConcatenationMaxFrameSize OBJECT-TYPE
            SYNTAX  INTEGER
            MAX-ACCESS read-write      
            STATUS current       
            DESCRIPTION  
            "Applicable to all units. 
			 Defines the maximum size of a concatenated frame.
			 Range:
			 256 to 2200 (bytes) for BWA PtP products BU/RB14 BU/RB28, 
			 or for AU/SU with HW revision A or B.
			 256 to 4032 (bytes) for AU/SU with HW Revision 
			 C or higher and BWA PtP products BU/RB100."
            ::= { bwaVLConcatenationParameters 3 }


-- Site Survey Params
-- ==================
bwaVLSiteSurvey        OBJECT IDENTIFIER ::= {bwaVLMib 11}

    bwaVLAverageReceiveSNR  OBJECT-TYPE
            SYNTAX INTEGER
            MAX-ACCESS read-only
            STATUS current
            DESCRIPTION 
            "Applicable to SU/RB only. 
             The average Signal to Noise Ratio of received frames."
            ::= { bwaVLSiteSurvey 1 }

-- Traffic Counters
-- ================
bwaVLTrafficStatistics	    OBJECT IDENTIFIER ::= {bwaVLSiteSurvey 2}


    bwaVLResetTrafficCounters OBJECT-TYPE
	     	SYNTAX	INTEGER { reset (1),cancel(2) }  
		    MAX-ACCESS read-write
	     	STATUS current
		    DESCRIPTION	 
            "Applicable to all units.
             Resets the traffic counters."
			::= { bwaVLTrafficStatistics 1 }

bwaVLEthCounters	         OBJECT IDENTIFIER ::= {bwaVLTrafficStatistics 2}
bwaVLWirelessLinkCounters OBJECT IDENTIFIER ::= {bwaVLTrafficStatistics 3}
bwaVLWirelessLinkEvents	 OBJECT IDENTIFIER ::= {bwaVLTrafficStatistics 4}

bwaVLPerModulationLevelCounters	     OBJECT IDENTIFIER ::= {bwaVLTrafficStatistics 5}


	bwaVLResetPerModulationLevelCounters OBJECT-TYPE
	     	SYNTAX	INTEGER { resetCounters(1) , cancel (2) } 
		    MAX-ACCESS read-write
	     	STATUS current
		    DESCRIPTION	 
            "Applicable to all units.
             Resets the per-Modulation Level counters ." 
			::= { bwaVLPerModulationLevelCounters 1 }



    bwaVLSUPerModulationLevelCountersTable OBJECT-TYPE
            SYNTAX SEQUENCE OF BwaVLSUPerModulationLevelCountersEntry
            MAX-ACCESS not-accessible
            STATUS current
            DESCRIPTION
            "Applicable to SU/RB. 
             Per Rate Counters table." 
            ::= { bwaVLPerModulationLevelCounters 2 }

    bwaVLSUPerModulationLevelCountersEntry  OBJECT-TYPE
            SYNTAX BwaVLSUPerModulationLevelCountersEntry
            MAX-ACCESS not-accessible
            STATUS current
            DESCRIPTION
            "Applicable to SU/RB. 
             An entry in the Per modulation  Counters table." 
            INDEX { bwaVLSUPerModulationLevelCountersTableIdx }
            ::= { bwaVLSUPerModulationLevelCountersTable 1 }

    BwaVLSUPerModulationLevelCountersEntry ::= SEQUENCE {
            bwaVLSUPerModulationLevelCountersTableIdx       INTEGER,
            bwaVLSUPerModulationLevelCountersApplicableModLevel INTEGER,
            bwaVLSUPerModulationLevelCountersTxSuccess      Counter32,
            bwaVLSUPerModulationLevelCountersTxFailed   Counter32
            }

         
    bwaVLSUPerModulationLevelCountersTableIdx   OBJECT-TYPE
            SYNTAX  INTEGER  (1..8)
            MAX-ACCESS read-only
            STATUS current
            DESCRIPTION  
            "Applicable to SU/RB.
             An index of an entry in the Per modulation level Counters table." 
        ::= { bwaVLSUPerModulationLevelCountersEntry 1 }

    bwaVLSUPerModulationLevelCountersApplicableModLevel   OBJECT-TYPE
            SYNTAX  INTEGER    { 
            					 modLevel-1  (1), 
							     modLevel-2  (2), 
							     modLevel-3  (3), 
							     modLevel-4  (4), 
							     modLevel-5  (5), 
							     modLevel-6  (6), 
							     modLevel-7  (7), 
							     modLevel-8  (8) 
							   } 
            MAX-ACCESS read-only
            STATUS current
            DESCRIPTION  
            "Applicable to SU/RB.
             The applicable modulation level of the entry in the Per 
             modulation level Counters table.
             Modulation Level 8 is not applicable for units with HW revision A." 
        ::= { bwaVLSUPerModulationLevelCountersEntry 2 }


    bwaVLSUPerModulationLevelCountersTxSuccess      OBJECT-TYPE
            SYNTAX  Counter32  
            MAX-ACCESS read-only
            STATUS current
            DESCRIPTION  
            "Applicable to SU/RB.
             The total number of successfully transmitted unicasts at the 
             applicable modulation level." 
        ::= { bwaVLSUPerModulationLevelCountersEntry 3 }


    bwaVLSUPerModulationLevelCountersTxFailed   OBJECT-TYPE
            SYNTAX  Counter32  
            MAX-ACCESS read-only
            STATUS current
            DESCRIPTION  
            "Applicable to SU/RB.
             The total number of dropped frames at the applicable 
             Modulation Level." 
        ::= { bwaVLSUPerModulationLevelCountersEntry 4 }


   bwaVLAverageModulationLevel	 OBJECT-TYPE
	        SYNTAX INTEGER 
	        MAX-ACCESS read-only
	        STATUS current
	        DESCRIPTION	
	        "Applicable to SU/RB. 
	         The average modulation level for successful transmission 
	         (rounded to nearest integer) since last reset of the 
	         Per Modulation Level counters. 
	         Range: 1 to 8."  
	        ::= { bwaVLPerModulationLevelCounters 3 }

    bwaVLTotalRxFramesViaEthernet OBJECT-TYPE
      		SYNTAX  Counter32
		    MAX-ACCESS read-only
	     	STATUS current
		    DESCRIPTION	 
            "Applicable to all units. 
             Total number of frames received via the Ethernet port."
			::= { bwaVLEthCounters 1 }

    bwaVLTxWirelessToEthernet OBJECT-TYPE
      		SYNTAX  Counter32
		    MAX-ACCESS read-only
	     	STATUS current
		    DESCRIPTION	 
            "Applicable to all units. 
             Total number of frames transmitted to the Ethernet port."
			::= { bwaVLEthCounters 2 }

bwaVLTxFramesToWireless	 OBJECT IDENTIFIER ::= {bwaVLWirelessLinkCounters 1}

    bwaVLAUBeaconsToWireless OBJECT-TYPE
      		SYNTAX  Counter32
		    MAX-ACCESS read-only
	     	STATUS current
		    DESCRIPTION	 
            "Applicable to AU/BU only.
             The number of beacons transmitted to the wireless media."
			::= { bwaVLTxFramesToWireless 1 }

--    bwaVLOtherMngFramesToWireless OBJECT-TYPE
--      		SYNTAX  Counter32
--		    MAX-ACCESS read-only
--	     	STATUS current
--		    DESCRIPTION	 
--            "Applicable to AU and SU.
--             The number of management frames transmitted to the wireless media.
--             In AU, this count does not include Beacons."
--			::= { bwaVLTxFramesToWireless 2 }

    bwaVLDataAndOtherMngFramesToWireless OBJECT-TYPE
      		SYNTAX  Counter32
		    MAX-ACCESS read-only
	     	STATUS current
		    DESCRIPTION	 
            "Applicable to AU/BU only.
             The number of data and management frames transmitted to the 
             wireless media. The count includes one count for each data 
             frame transmitted successfully (excluding retransmissions)."
			::= { bwaVLTxFramesToWireless 3 }

    bwaVLTotalTxFramesToWireless OBJECT-TYPE
      		SYNTAX  Counter32
		    MAX-ACCESS read-only
	     	STATUS current
		    DESCRIPTION	 
            "Applicable to all units. 
             The number of frames transmitted to the wireless media.
             The count includes one count for each data frame
             that was transmitted successfully (excluding retransmissions),
             and also the number of transmitted control and management frames, 
             including beacons."
			::= { bwaVLTxFramesToWireless 4 }
   
    bwaVLTotalTransmittedUnicasts OBJECT-TYPE
      		SYNTAX  Counter32
		    MAX-ACCESS read-only
	     	STATUS current
		    DESCRIPTION	 
            "Applicable to AU/BU only.	 
             The total number of unicast frames successfully transmitted 
             to the wireless media, excluding retransmissions."
			::= { bwaVLTxFramesToWireless 5 }

    bwaVLTotalTransmittedConcatenatedFramesDouble OBJECT-TYPE
      		SYNTAX  Counter32
		    MAX-ACCESS read-only
	     	STATUS current
		    DESCRIPTION	 
            "Applicable to all products.	 
             The total number of double concatenated frames successfully transmitted 
             to the wireless media, excluding retransmissions."
			::= { bwaVLTxFramesToWireless 6 }

    bwaVLTotalTransmittedConcatenatedFramesSingle OBJECT-TYPE
      		SYNTAX  Counter32
		    MAX-ACCESS read-only
	     	STATUS current
		    DESCRIPTION	 
            "Applicable to all products.	 
             The total number of double concatenated frames successfully transmitted 
             to the wireless media, excluding retransmissions."
			::= { bwaVLTxFramesToWireless 7 }

    bwaVLTotalTransmittedConcatenatedFramesMore OBJECT-TYPE
      		SYNTAX  Counter32
		    MAX-ACCESS read-only
	     	STATUS current
		    DESCRIPTION	 
            "Applicable to all products.	 
             The total number of concatenated frames with more then two frames successfully 
             transmitted to the wireless media, excluding retransmissions."
			::= { bwaVLTxFramesToWireless 8 }

    bwaVLTotalRxFramesFromWireless OBJECT-TYPE
      		SYNTAX  Counter32
		    MAX-ACCESS read-only
	     	STATUS current
		    DESCRIPTION	 
            "Applicable to all units. 
             The total number of frames that were received
             from the wireless media.
             The count includes data and control and management
             frames, including beacons received from the AU/BU.
             The count does not include frames that were discarded
             internally, bad frames and duplicate frames."
			::= { bwaVLWirelessLinkCounters 2 }

    bwaVLTotalRetransmittedFrames OBJECT-TYPE
      		SYNTAX  Counter32
		    MAX-ACCESS read-only
	     	STATUS current
		    DESCRIPTION	 
            "Applicable to all units. 
             The total number of retransmissions of data frames 
             (counts all unsuccessful transmissions/retransmissions)."
			::= { bwaVLWirelessLinkCounters 3 }

    bwaVLFramesDropped OBJECT-TYPE
      		SYNTAX  Counter32
		    MAX-ACCESS read-only
	     	STATUS current
		    DESCRIPTION	 
            "Applicable to all units. 
             The number of dropped frames.
             The frames that were retransmitted to the extent
             of the maximum allowed number of retransmissions
             without being acknowledged.."
			::= { bwaVLWirelessLinkCounters 4 }


bwaVLDataFramesSubmittedToBridge	 OBJECT IDENTIFIER ::= {bwaVLWirelessLinkCounters 5}

	bwaVLFramesSubmittedViaHighQueue OBJECT-TYPE
      		SYNTAX  Counter32
		    MAX-ACCESS read-only
	     	STATUS current
		    DESCRIPTION	 
            "Applicable to all units. 
             Frames submitted to the internal bridge via the High priority queue. 
             for transmission to the wireless media."
			::= { bwaVLDataFramesSubmittedToBridge 1 }

	bwaVLFramesSubmittedViaMidQueue OBJECT-TYPE
      		SYNTAX  Counter32
		    MAX-ACCESS read-only
	     	STATUS current
		    DESCRIPTION	 
            "Applicable to all units. 
             Frames submitted to the internal bridge via the Mid priority queue 
             for transmission to the wireless media."
			::= { bwaVLDataFramesSubmittedToBridge 2 }

	bwaVLFramesSubmittedViaLowQueue OBJECT-TYPE
      		SYNTAX  Counter32
		    MAX-ACCESS read-only
	     	STATUS current
		    DESCRIPTION	 
            "Applicable to all units. 
             Frames submitted to the internal bridge via the Low priority queue 
             for transmission to the wireless media."
			::= { bwaVLDataFramesSubmittedToBridge 3 }

	bwaVLTotalNoOfDataFramesSubmitted OBJECT-TYPE
      		SYNTAX  Counter32
		    MAX-ACCESS read-only
	     	STATUS current
		    DESCRIPTION	 
            "Applicable to all units. 
             The total number of data frames submitted to the internal bridge 
             for transmission to the wireless media."
			::= { bwaVLDataFramesSubmittedToBridge 4 }


    bwaVLTotalRecievedDataFrames OBJECT-TYPE
      		SYNTAX  Counter32
		    MAX-ACCESS read-only
	     	STATUS current
		    DESCRIPTION	 
            "Applicable to all units. 
             The total number of data frames received from the
             wireless media, including duplicate frames."
			::= { bwaVLWirelessLinkCounters 6 }

    bwaVLRecievedBadFrames OBJECT-TYPE
      		SYNTAX  Counter32
		    MAX-ACCESS read-only
	     	STATUS current
		    DESCRIPTION	 
            "Applicable to all units. 
             The number of frames received from the wireless
             media with errors (CRC errors)."
			::= { bwaVLWirelessLinkCounters 7 }

    bwaVLNoOfDuplicateFramesDiscarded OBJECT-TYPE
      		SYNTAX  Counter32
		    MAX-ACCESS read-only
	     	STATUS current
		    DESCRIPTION	 
            "Applicable to all units. 
             The number of frames discarded due to receiving multiple copies."
			::= { bwaVLWirelessLinkCounters 8 }

    bwaVLNoOfInternallyDiscardedMirCir OBJECT-TYPE
      		SYNTAX  Counter32
		    MAX-ACCESS read-only
	     	STATUS current
		    DESCRIPTION	 
            "Applicable to all units. 
            The number of data frames received from the Ethernet port that were 
            discarded by the MIR/CIR mechanism either to avoid exceeding the 
            maximum allowed information rate, or when the wireless link conditions 
            do not enable reaching the allowed rate."
			::= { bwaVLWirelessLinkCounters 9 }

    bwaVLTotalRxConcatenatedFramesDouble OBJECT-TYPE
      		SYNTAX  Counter32
		    MAX-ACCESS read-only
	     	STATUS current
		    DESCRIPTION	 
            "Applicable to all units.
            The total number of double concatenated frames received 
            from the wireless media, including duplicate frames."
			::= { bwaVLWirelessLinkCounters 10 }

    bwaVLTotalRxConcatenatedFramesSingle OBJECT-TYPE
      		SYNTAX  Counter32
		    MAX-ACCESS read-only
	     	STATUS current
		    DESCRIPTION	 
            "Applicable to all units. 
             The total number of data fast frames single concatenated 
             frames received from the wireless media, including duplicate frames."
			::= { bwaVLWirelessLinkCounters 11 }

    bwaVLTotalRxConcatenatedFramesMore OBJECT-TYPE
      		SYNTAX  Counter32
		    MAX-ACCESS read-only
	     	STATUS current
		    DESCRIPTION	 
            "Applicable to all units. 
             The total number of data fast frames concatenated with more then two 
             frames received from the wireless media, including duplicate frames."
			::= { bwaVLWirelessLinkCounters 12 }

--	bwaVLInternallyGeneratedFramesSubmittedToBridge OBJECT-TYPE
--      		SYNTAX  Counter32
--		    MAX-ACCESS read-only
--	     	STATUS current
--		    DESCRIPTION	 
--            "Applicable to SU and AU. Read-only.
--             The number of internally generated frames(wireless management and control frames)
--             submitted to the bridge for transmission to the wireless media."
--			::= { bwaVLWirelessLinkCounters 10 }


bwaVLTxEvents	 OBJECT IDENTIFIER ::= {bwaVLWirelessLinkEvents 1}

    bwaVLDroppedFrameEvents OBJECT-TYPE
      		SYNTAX  Counter32
		    MAX-ACCESS read-only
	     	STATUS current
		    DESCRIPTION	 
            "Applicable to all units. 
			 The number of frames that were dropped because they were retransmitted
			 to the maximum allowed number of retransmissions without being 
			 acknowledged."
			::= { bwaVLTxEvents 1 }

    bwaVLFramesDelayedDueToSwRetry OBJECT-TYPE
      		SYNTAX  Counter32
		    MAX-ACCESS read-only
	     	STATUS current
		    DESCRIPTION	 
            "Applicable to all units. 
             Not applicable for units with SW Version 3.0 and higher.
             The number of frames that were delayed because the SW retry 
             algorithm was activated on a previous frame designated for the 
             same recipient."
			::= { bwaVLTxEvents 2 }

    bwaVLUnderrunEvents OBJECT-TYPE
      		SYNTAX  Counter32
		    MAX-ACCESS read-only
	     	STATUS current
		    DESCRIPTION	 
            "Applicable to all units. 
             The number of frames whose transmission was aborted because the rate
             of submitting frames for transmission exceeded the available 
             transmission capability."
			::= { bwaVLTxEvents 3 }

    bwaVLOthersTxEvents  OBJECT-TYPE
      		SYNTAX  Counter32
		    MAX-ACCESS read-only
	     	STATUS current
		    DESCRIPTION	 
            "Applicable to all units. 
             The number of Tx events due to problems other than those of 
             the other Tx Events counters."
			::= { bwaVLTxEvents 4 }

    bwaVLTotalTxEvents OBJECT-TYPE
      		SYNTAX  Counter32
		    MAX-ACCESS read-only
	     	STATUS current
		    DESCRIPTION	 
            "Applicable to all units. 
             The total number of Tx special events."
			::= { bwaVLTxEvents 5 }

bwaVLRxEvents	 OBJECT IDENTIFIER ::= {bwaVLWirelessLinkEvents 2}

    bwaVLPhyErrors OBJECT-TYPE
      		SYNTAX  Counter32
		    MAX-ACCESS read-only
	     	STATUS current
		    DESCRIPTION	 
            "Applicable to all units, only when DFS is enabled. 
             The number of unidentified signals."
			::= { bwaVLRxEvents 1 }

    bwaVLCRCErrors OBJECT-TYPE
      		SYNTAX  Counter32
		    MAX-ACCESS read-only
	     	STATUS current
		    DESCRIPTION	 
            "Applicable to all units. 
             The number of frames received from the wireless media containing 
             CRC errors."
			::= { bwaVLRxEvents 2 }

    bwaVLOverrunEvents OBJECT-TYPE
      		SYNTAX  Counter32
		    MAX-ACCESS read-only
	     	STATUS current
		    DESCRIPTION	 
            "Applicable to all units. 
             The number of frames that were discarded because the receive 
             rate exceeded the processing capability or the capacity of the 
             Ethernet port."
			::= { bwaVLRxEvents 3 }

    bwaVLRxDecryptEvents OBJECT-TYPE
      		SYNTAX  Counter32
		    MAX-ACCESS read-only
	     	STATUS current
		    DESCRIPTION	 
            "Applicable to all units. 
             The number of frames that were not received properly due to a 
             problem in the data decryption mechanism."
			::= { bwaVLRxEvents 4 }

    bwaVLTotalRxEvents OBJECT-TYPE
      		SYNTAX  Counter32
		    MAX-ACCESS read-only
	     	STATUS current
		    DESCRIPTION	 
            "Applicable to all units. 
             The total number of Rx special events."
			::= { bwaVLRxEvents 5 }


-- Associations Database
-- 
bwaVLMacAddressDatabase   OBJECT IDENTIFIER ::= {bwaVLSiteSurvey 5}

bwaVLAUMacAddressDatabase   OBJECT IDENTIFIER ::= {bwaVLMacAddressDatabase 1}

bwaVLAUAdbResetAllModulationLevelCounters OBJECT-TYPE
	  SYNTAX  INTEGER { reset (1), cancel (2) }  
      MAX-ACCESS  read-write    
      STATUS  current
      DESCRIPTION
      "Applicable to AU/BU only. 
	   To reset all the counters for all SUs/RB in the MAC Address Database."
      ::= { bwaVLAUMacAddressDatabase 1 }

bwaVLAUAdbTable OBJECT-TYPE
	  SYNTAX SEQUENCE OF BwaVLAUAdbEntry
	  MAX-ACCESS not-accessible
	  STATUS current
	  DESCRIPTION
      "Applicable to AU/BU only. 
       AU/BU MAC Address Database table."
	  ::= { bwaVLAUMacAddressDatabase 2 }

bwaVLAUAdbEntry  OBJECT-TYPE
	  SYNTAX BwaVLAUAdbEntry
	  MAX-ACCESS not-accessible
	  STATUS current
      DESCRIPTION
      "Applicable to AU/BU only. 
       An entry in the AU/BU MAC Address Database table."
	  INDEX { bwaVLAdbIndex }
	  ::= { bwaVLAUAdbTable 1 }

			   
BwaVLAUAdbEntry ::= SEQUENCE {
 	  bwaVLAdbIndex			    INTEGER,
 	  bwaVLAdbMacAddress		    MacAddress,
	  bwaVLAdbStatus			    INTEGER,
	  bwaVLAdbSwVersion			DisplayString,
	  bwaVLAdbSNR                INTEGER,
 	  bwaVLAdbMaxModulationLevel INTEGER,
	  bwaVLAdbTxFramesTotal	    Counter32,
	  bwaVLAdbDroppedFramesTotal	Counter32,
	  bwaVLAdbTxSuccessModLevel1	Counter32,
	  bwaVLAdbTxSuccessModLevel2	Counter32,
	  bwaVLAdbTxSuccessModLevel3	Counter32,
	  bwaVLAdbTxSuccessModLevel4	Counter32,
	  bwaVLAdbTxSuccessModLevel5	Counter32,
	  bwaVLAdbTxSuccessModLevel6	Counter32,
	  bwaVLAdbTxSuccessModLevel7	Counter32,
	  bwaVLAdbTxSuccessModLevel8	Counter32,
	  bwaVLAdbTxFailedModLevel1	Counter32,
	  bwaVLAdbTxFailedModLevel2	Counter32,
	  bwaVLAdbTxFailedModLevel3	Counter32,
	  bwaVLAdbTxFailedModLevel4	Counter32,
	  bwaVLAdbTxFailedModLevel5	Counter32,
	  bwaVLAdbTxFailedModLevel6	Counter32,
	  bwaVLAdbTxFailedModLevel7	Counter32,
	  bwaVLAdbTxFailedModLevel8	Counter32,
   	  bwaVLAdbCirTx              INTEGER,
      bwaVLAdbMirTx              INTEGER,
      bwaVLAdbCirRx              INTEGER,
      bwaVLAdbMirRx              INTEGER,
      bwaVLAdbCirMaxDelay        INTEGER,
	  bwaVLAdbDistance			INTEGER,
	  bwaVLAdbHwRevision			INTEGER,
	  bwaVLAdbCpldVer			DisplayString,
	  bwaVLAdbCountryCode    	INTEGER,
	  bwaVLAdbBootVer			DisplayString,
	  bwaVLAdbAtpcOption			INTEGER,
	  bwaVLAdbAdapModOption		INTEGER,
	  bwaVLAdbBurstModeOption	INTEGER,
	  bwaVLAdbConcatenationOption	INTEGER,
	  bwaVLAdbSecurityMode		INTEGER,
	  bwaVLAdbAuthOption			INTEGER,
	  bwaVLAdbDataEncyptOption	INTEGER,
	  bwaVLAdbAge               INTEGER,
	  bwaVLAdbUnitName           DisplayString
	  }

bwaVLAdbIndex OBJECT-TYPE
	  SYNTAX INTEGER  (1..512)
	  MAX-ACCESS read-only
	  STATUS current
	  DESCRIPTION	
      "Applicable to AU/BU only. 
	   The index of an entry in the AU/BU MAC Address Database table."
	  ::= { bwaVLAUAdbEntry 1 }

bwaVLAdbMacAddress  OBJECT-TYPE
	  SYNTAX MacAddress  
	  MAX-ACCESS read-only
	  STATUS current
	  DESCRIPTION
      "Applicable to AU/BU only. 
	   The MAC Address of an SU/RB entry in the MAC Address Database 
	   table."
	  ::= { bwaVLAUAdbEntry 2 }

bwaVLAdbStatus	 OBJECT-TYPE
	  SYNTAX INTEGER { associated       (1), 
	                   authenticated    (2),
	                   notAuthenticated (3) }
	  MAX-ACCESS read-only
	  STATUS current
	  DESCRIPTION	
      "Applicable to AU/BU only. 
	   The status of the relevant SU/RB."
	  ::= { bwaVLAUAdbEntry 3 }

bwaVLAdbSwVersion OBJECT-TYPE
	  SYNTAX DisplayString  
	  MAX-ACCESS read-only
	  STATUS current
	  DESCRIPTION	
      "Applicable to AU/BU only. 
	   The SW version of the relevant SU/RB."
	  ::= { bwaVLAUAdbEntry 4 }

bwaVLAdbSNR	OBJECT-TYPE
	  SYNTAX INTEGER  
	  MAX-ACCESS read-only
	  STATUS current
	  DESCRIPTION	
      "Applicable to AU/BU only. 
	   The average Signal to Noise Ratio in dB of frames received by 
	   the AU/BU from the relevant SU/RB."
	  ::= { bwaVLAUAdbEntry 5 }

bwaVLAdbMaxModulationLevel  OBJECT-TYPE
	  SYNTAX INTEGER  { modLevel-1 (1), 
	                    modLevel-2 (2), 
                        modLevel-3 (3), 
                        modLevel-4 (4), 
                        modLevel-5 (5), 
                        modLevel-6 (6), 
                        modLevel-7 (7), 
                        modLevel-8 (8) 
                      }  
	  MAX-ACCESS read-only
	  STATUS current
	  DESCRIPTION	
      "Applicable to AU/BU only. 
	   The value configured in the relevant SU/RB for the Maximum Modulation 
	   Level parameter.
	   Modulation Level 8 is not applicable for units with HW revision A."
	  ::= { bwaVLAUAdbEntry 6 }

bwaVLAdbTxFramesTotal	OBJECT-TYPE
	  SYNTAX Counter32 
	  MAX-ACCESS read-only
	  STATUS current
	  DESCRIPTION	
      "Applicable to AU/BU only. 
	   Counts the total number of unicast  frames (excluding retransmissions) 
	   that were successfully transmitted to the SU/RB over the wireless link."
	  ::= { bwaVLAUAdbEntry 7 }

bwaVLAdbDroppedFramesTotal  OBJECT-TYPE
	  SYNTAX Counter32 
	  MAX-ACCESS read-only
	  STATUS current
	  DESCRIPTION	
      "Applicable to AU/BU only. 
	   Counts the total number of frames intended to the SU/RB that 
	   were dropped because they were retransmitted to the extent 
	   of the maximum allowed number of retransmissions without 
	   being acknowledged."
	  ::= { bwaVLAUAdbEntry 8 }

bwaVLAdbTxSuccessModLevel1	OBJECT-TYPE
	  SYNTAX Counter32 
	  MAX-ACCESS read-only
	  STATUS current
	  DESCRIPTION	
      "Applicable to AU/BU only. 
	   Counts the total number of unicast frames (excluding retransmissions) 
	   that were successfully transmitted to the SU/RB over the wireless link 
	   using modulation level 1."
	  ::= { bwaVLAUAdbEntry 9 }

bwaVLAdbTxSuccessModLevel2	OBJECT-TYPE
	  SYNTAX Counter32 
	  MAX-ACCESS read-only
	  STATUS current
	  DESCRIPTION	
      "Applicable to AU/BU only. 
	   Counts the total number of unicast frames (excluding retransmissions) 
	   that were successfully transmitted to the SU/RB over the wireless link 
	   using modulation level 2."
	  ::= { bwaVLAUAdbEntry 10 }

bwaVLAdbTxSuccessModLevel3	OBJECT-TYPE
	  SYNTAX Counter32 
	  MAX-ACCESS read-only
	  STATUS current
	  DESCRIPTION	
      "Applicable to AU/BU only. 
	   Counts the total number of unicast frames (excluding retransmissions) 
	   that were successfully transmitted to the SU/BU over the wireless link 
	   using modulation level 3."
	  ::= { bwaVLAUAdbEntry 11 }

bwaVLAdbTxSuccessModLevel4	OBJECT-TYPE
	  SYNTAX Counter32 
	  MAX-ACCESS read-only
	  STATUS current
	  DESCRIPTION	
      "Applicable to AU/BU only. 
	   Counts the total number of unicast frames (excluding retransmissions) 
	   that were successfully transmitted to the SU/RB over the wireless link 
	   using modulation level 4."
	  ::= { bwaVLAUAdbEntry 12 }

bwaVLAdbTxSuccessModLevel5	OBJECT-TYPE
	  SYNTAX Counter32 
	  MAX-ACCESS read-only
	  STATUS current
	  DESCRIPTION	
      "Applicable to AU/BU only. 
	   Counts the total number of unicast frames (excluding retransmissions) 
	   that were successfully transmitted to the SU/RB over the wireless link 
	   using modulation level 5."
	  ::= { bwaVLAUAdbEntry 13 }

bwaVLAdbTxSuccessModLevel6	OBJECT-TYPE
	  SYNTAX Counter32 
	  MAX-ACCESS read-only
	  STATUS current
	  DESCRIPTION	
      "Applicable to AU/BU only. 
	   Counts the total number of unicast frames (excluding retransmissions) 
	   that were successfully transmitted to the SU/BU over the wireless link 
	   using modulation level 6."
	  ::= { bwaVLAUAdbEntry 14 }

bwaVLAdbTxSuccessModLevel7	OBJECT-TYPE
	  SYNTAX Counter32 
	  MAX-ACCESS read-only
	  STATUS current
	  DESCRIPTION	
      "Applicable to AU/BU only. 
	   Counts the total number of unicast frames (excluding retransmissions) 
	   that were successfully transmitted to the SU/RB over the wireless link 
	   using modulation level 7."
	  ::= { bwaVLAUAdbEntry 15 }

bwaVLAdbTxSuccessModLevel8	OBJECT-TYPE
	  SYNTAX Counter32 
	  MAX-ACCESS read-only
	  STATUS current
	  DESCRIPTION	
      "Applicable to AU/BU only. 
	   Counts the total number of unicast frames (excluding retransmissions) 
	   that were successfully transmitted to the SU/RB over the wireless link 
	   using modulation level 8.
	   Not applicable for units with HW revision A."
	  ::= { bwaVLAUAdbEntry 16 }

bwaVLAdbTxFailedModLevel1	OBJECT-TYPE
	  SYNTAX Counter32 
	  MAX-ACCESS read-only
	  STATUS current
	  DESCRIPTION	
      "Applicable to AU/BU only. 
	   Counts the total number of failures to successfully
	   transmit unicast frames intended to the SU/RB using modulation level 1."
	  ::= { bwaVLAUAdbEntry 17 }

bwaVLAdbTxFailedModLevel2	OBJECT-TYPE
	  SYNTAX Counter32 
	  MAX-ACCESS read-only
	  STATUS current
	  DESCRIPTION	
      "Applicable to AU/BU only. 
	   Counts the total number of failures to successfully
	   transmit unicast frames intended to the SU/RB using modulation level 2."
	  ::= { bwaVLAUAdbEntry 18 }

bwaVLAdbTxFailedModLevel3	OBJECT-TYPE
	  SYNTAX Counter32 
	  MAX-ACCESS read-only
	  STATUS current
	  DESCRIPTION	
      "Applicable to AU/BU only. 
	   Counts the total number of failures to successfully
	   transmit unicast frames intended to the SU/RB using modulation level 3."
	  ::= { bwaVLAUAdbEntry 19 }

bwaVLAdbTxFailedModLevel4	OBJECT-TYPE
	  SYNTAX Counter32 
	  MAX-ACCESS read-only
	  STATUS current
	  DESCRIPTION	
      "Applicable to AU/BU only. 
	   Counts the total number of failures to successfully
	   transmit unicast frames intended to the SU/RB using modulation level 4."
	  ::= { bwaVLAUAdbEntry 20 }

bwaVLAdbTxFailedModLevel5	OBJECT-TYPE
	  SYNTAX Counter32 
	  MAX-ACCESS read-only
	  STATUS current
	  DESCRIPTION	
      "Applicable to AU/BU only. 
	   Counts the total number of failures to successfully
	   transmit unicast frames intended to the SU/RB using modulation level 5."
	  ::= { bwaVLAUAdbEntry 21 }

bwaVLAdbTxFailedModLevel6	OBJECT-TYPE
	  SYNTAX Counter32 
	  MAX-ACCESS read-only
	  STATUS current
	  DESCRIPTION	
      "Applicable to AU/BU only. 
	   Counts the total number of failures to successfully
	   transmit unicast frames intended to the SU/RB using modulation level 6."
	  ::= { bwaVLAUAdbEntry 22 }

bwaVLAdbTxFailedModLevel7	OBJECT-TYPE
	  SYNTAX Counter32 
	  MAX-ACCESS read-only
	  STATUS current
	  DESCRIPTION	
      "Applicable to AU/BU only. 
	   Counts the total number of failures to successfully
	   transmit unicast frames intended to the SU/RB using modulation level 7."
	  ::= { bwaVLAUAdbEntry 23 }

bwaVLAdbTxFailedModLevel8	OBJECT-TYPE
	  SYNTAX Counter32 
	  MAX-ACCESS read-only
	  STATUS current
	  DESCRIPTION	
      "Applicable to AU/BU only. 
	   Counts the total number of failures to successfully
	   transmit unicast frames intended to the SU/RB using modulation level 8.
	   Not applicable for units with HW revision A."
	  ::= { bwaVLAUAdbEntry 24 }

bwaVLAdbCirTx  OBJECT-TYPE
   SYNTAX INTEGER 
   MAX-ACCESS read-only
   STATUS current
   DESCRIPTION 
   "Applicable to AU Only. 
    Not applicable to BWA-PtP products. Read-only. 
    The value configured in the relevant SU for the CIR: 
    SU to AU parameter."
   ::= { bwaVLAUAdbEntry 25 }

bwaVLAdbMirTx  OBJECT-TYPE
   SYNTAX INTEGER 
   MAX-ACCESS read-only
   STATUS current
   DESCRIPTION 
   "Applicable to AU/BU only. 
    The value configured in the relevant SU/RB for the MIR: 
    SU/RB to AU/BU parameter."
   ::= { bwaVLAUAdbEntry 26 }

bwaVLAdbCirRx  OBJECT-TYPE
   SYNTAX INTEGER 
   MAX-ACCESS read-only
   STATUS current
   DESCRIPTION 
   "Applicable to AU Only.
    Not applicable to BWA-PtP products.
    The value configured in the relevant SU for the CIR: 
    AU to SU parameter."
   ::= { bwaVLAUAdbEntry 27 }

bwaVLAdbMirRx  OBJECT-TYPE
   SYNTAX INTEGER 
   MAX-ACCESS read-only
   STATUS current
   DESCRIPTION 
   "Applicable to AU/BU only. 
    The value configured in the relevant SU/RB for the MIR: 
    AU/BU to SU/RB parameter."
   ::= { bwaVLAUAdbEntry 28 }

bwaVLAdbCirMaxDelay   OBJECT-TYPE
   SYNTAX INTEGER 
   MAX-ACCESS read-only
   STATUS current
   DESCRIPTION 
   "Applicable to AU Only. 
    Not applicable to BWA-PtP products.
    The value configured in the relevant SU for the CIR Maximum 
    Delay parameter."
   ::= { bwaVLAUAdbEntry 29 }

bwaVLAdbDistance     OBJECT-TYPE
   SYNTAX INTEGER  {below-2-Km(1)}
   MAX-ACCESS read-only
   STATUS current
   DESCRIPTION 
   "Applicable to AU/BU Only.  
    The distance between the SU/RB and the AU/BU (In Kilometers)."
   ::= { bwaVLAUAdbEntry 30 }

bwaVLAdbHwRevision     OBJECT-TYPE
  SYNTAX INTEGER  {hwRevisionA(1), hwRevisionB(2), hwRevisionC(3), 
                    hwRevisionD(4), hwRevisionE(5), na(255)}
   MAX-ACCESS read-only
   STATUS current
   DESCRIPTION 
   "Applicable to AU/BU Only.  
    The SU/RB HW Revision."
   ::= { bwaVLAUAdbEntry 31 }

bwaVLAdbCpldVer     OBJECT-TYPE
   SYNTAX DisplayString
   MAX-ACCESS read-only
   STATUS current
   DESCRIPTION 
   "Applicable to AU/BU Only.  
    The SU/RB CPLD Version."
   ::= { bwaVLAUAdbEntry 32 }

bwaVLAdbCountryCode     OBJECT-TYPE
   SYNTAX INTEGER  
   MAX-ACCESS read-only
   STATUS current
   DESCRIPTION 
   "Applicable to AU/BU Only.  
    The SU/RB supported country code."
   ::= { bwaVLAUAdbEntry 33 }

bwaVLAdbBootVer     OBJECT-TYPE
   SYNTAX DisplayString
   MAX-ACCESS read-only
   STATUS current
   DESCRIPTION 
   "Applicable to AU/BU Only.  
    The SU/RB Boot Version."
   ::= { bwaVLAUAdbEntry 34 }

bwaVLAdbAtpcOption     OBJECT-TYPE
   SYNTAX INTEGER  {disable (1), enable (2), na (255)}
   MAX-ACCESS read-only
   STATUS current
   DESCRIPTION 
   "Applicable to AU/BU Only.  
    The SU/RB ATPC option configuration."
   ::= { bwaVLAUAdbEntry 35 }

bwaVLAdbAdapModOption     OBJECT-TYPE
   SYNTAX INTEGER  {disable (1), enable (2), na (255)}
   MAX-ACCESS read-only
   STATUS current
   DESCRIPTION 
   "Applicable to AU/BU Only.  
    The SU/RB adaptive modulation option configuration."
   ::= { bwaVLAUAdbEntry 36 }

bwaVLAdbBurstModeOption     OBJECT-TYPE
   SYNTAX INTEGER  {disable (1), enable (2), na (255)}
   MAX-ACCESS read-only
   STATUS current
   DESCRIPTION 
   "Applicable to AU/BU Only.  
    The SU/RB burst mode option configuration."
   ::= { bwaVLAUAdbEntry 37 }

bwaVLAdbConcatenationOption     OBJECT-TYPE
   SYNTAX INTEGER  {disable (1), enable (2), na(255)}
   MAX-ACCESS read-only
   STATUS current
   DESCRIPTION 
   "Applicable to AU/BU Only.  
    The SU/RB concatenation option configuration."
   ::= { bwaVLAUAdbEntry 39 }

bwaVLAdbSecurityMode     OBJECT-TYPE
   SYNTAX INTEGER  {wep(1), aes(2), fips197(3), na(255)}
   MAX-ACCESS read-only
   STATUS current
   DESCRIPTION 
   "Applicable to AU/BU Only.  
    The SU/RB security mode configuration."
   ::= { bwaVLAUAdbEntry 41 }

bwaVLAdbAuthOption     OBJECT-TYPE
   SYNTAX INTEGER  {openSystem (1), sharedKey (2), na (255)}
   MAX-ACCESS read-only
   STATUS current
   DESCRIPTION 
   "Applicable to AU/BU Only.  
    The SU/RB authentication algorithm configuration."
   ::= { bwaVLAUAdbEntry 42 }

bwaVLAdbDataEncyptOption     OBJECT-TYPE
   SYNTAX INTEGER  {disable (1), enable (2), na (255)}
   MAX-ACCESS read-only
   STATUS current
   DESCRIPTION 
   "Applicable to AU/BU Only.  
    The SU/RB data encryption option configuration."
   ::= { bwaVLAUAdbEntry 43 }

bwaVLAdbAge	OBJECT-TYPE
	  SYNTAX INTEGER  
	  MAX-ACCESS read-only
	  STATUS current
	  DESCRIPTION	
      "Applicable to AU/BU only. 
	   The time since any packet was received from the relevant SU/RB."
	  ::= { bwaVLAUAdbEntry 44 }

bwaVLAdbUnitName	OBJECT-TYPE
	  SYNTAX DisplayString 
	  MAX-ACCESS read-only
	  STATUS current
	  DESCRIPTION	
      "Applicable to AU/BU only. 
	   The unit name of the relevant SU/RB."
	  ::= { bwaVLAUAdbEntry 45 }

bwaVLUpLinkQualityIndicator  OBJECT IDENTIFIER ::= { bwaVLSiteSurvey 6}

bwaVLMeasureUpLinkQualityIndicator	 OBJECT-TYPE
	  SYNTAX INTEGER { start (1) , cancel (2)}
	  MAX-ACCESS read-write
	  STATUS current
	  DESCRIPTION	
	  "Applicable to SU/RB. 
	   Starts calculation of LQI. 
	   The calculation will be for a period of 10 seconds."  
	  ::= { bwaVLUpLinkQualityIndicator 1 }


bwaVLReadUpLinkQualityIndicator	 OBJECT-TYPE
	  SYNTAX INTEGER 
	  MAX-ACCESS read-only
	  STATUS current
	  DESCRIPTION	
	  "Applicable to SU/RB. 
	   The results of the last LQI calculation. 
	   Range: 1 to 8."  
	  ::= { bwaVLUpLinkQualityIndicator 2 }
 

bwaVLUpLinkQualityIndicatorStatus	 OBJECT-TYPE
	  SYNTAX INTEGER  {fullTest(1) , limitedTest(2)}
	  MAX-ACCESS read-only
	  STATUS current
	  DESCRIPTION	
	  "Applicable to SU/RB Only. 
	   Indicates the test conditions. 
	   fullTest means that there are no limitations 
	   on the range of available modulation levels, and that all modulation levels 
	   from 1 to 8 can be used. 
	   limitedTest indicates that the results may not indicate the true quality since 
	   the available range is limited - by HW (HW Revision A), 
	   or by the applicable parameters in the country code, 
	   or by the configurable Maximum Modulation Level parameter."  
	  ::= { bwaVLUpLinkQualityIndicator 3 }

-- AC pinpoint table end
	  
bwaVLMacPinpoint   OBJECT IDENTIFIER ::= {bwaVLSiteSurvey 7}

          bwaVLMacPinpointTable OBJECT-TYPE
              SYNTAX  SEQUENCE OF BwaVLMacPinpointEntry
              MAX-ACCESS  not-accessible
              STATUS  current
              DESCRIPTION
                      "Applicable to AU/BU only.
                      A table that contains information about wireless device
                      used by a certain Ethernet station in order to
                      connect to the wireless network"
              ::= { bwaVLMacPinpoint 1 }

          bwaVLMacPinpointEntry OBJECT-TYPE
              SYNTAX  BwaVLMacPinpointEntry
              MAX-ACCESS  not-accessible
              STATUS  current
              DESCRIPTION
                      "Applicable to AU/BU only. An entry in the MAC Pinpoint Table.
                      Each entry contains an Ethernet station MAC address and the MAC
                      address of the wireless device used to connect it to the wireless 
                      network"
              INDEX   { mptEthernetStationMACAddress }
              ::= { bwaVLMacPinpointTable 1 }

          BwaVLMacPinpointEntry ::=
              SEQUENCE {
                  mptEthernetStationMACAddress
                      MacAddress,
                  mptUnitMACAddress
                      MacAddress
              }

          mptEthernetStationMACAddress OBJECT-TYPE
              SYNTAX  MacAddress
              MAX-ACCESS  read-only
              STATUS  current
              DESCRIPTION
                      "Applicable to AU/BU only.
                      The MAC address of the Ethernet station. It is used as an 
                      index in the MAC Pinpoint Table."
              ::= { bwaVLMacPinpointEntry 1 }
              
          mptUnitMACAddress OBJECT-TYPE
              SYNTAX  MacAddress
              MAX-ACCESS  read-only
              STATUS  current
              DESCRIPTION
                      "Applicable to AU/BU only. The MAC address of the wireless 
                      device used by the station with the MAC Address from the 
                      index in order to access the wireless network."
              ::= { bwaVLMacPinpointEntry 2 }
-- AC pinpoint table end

-- GATEWAY TABLE BEGIN

bwaVLDrapGatewaysTable OBJECT-TYPE
        SYNTAX SEQUENCE OF BwaVLDrapGatewayEntry
        MAX-ACCESS not-accessible
        STATUS current
        DESCRIPTION
		"This table provides information about Gateways supporting DRAP that are
		registered at the AU"
        ::= { bwaVLSiteSurvey 8  }

bwaVLDrapGatewayEntry  OBJECT-TYPE
        SYNTAX BwaVLDrapGatewayEntry
        MAX-ACCESS not-accessible
        STATUS current
        DESCRIPTION
        "A Drap Gateway Entry." 
        INDEX { bwaVLDrapGatewayIndex }
        ::= { bwaVLDrapGatewaysTable 1 }

BwaVLDrapGatewayEntry ::= SEQUENCE {
		bwaVLDrapGatewayIndex					    INTEGER,
		bwaVLDrapGatewayIP 					        IpAddress,
       	bwaVLDrapGatewayType					    INTEGER,
        bwaVLDrapGatewayNoOfActiveVoiceCalls		INTEGER
        }
            
bwaVLDrapGatewayIndex OBJECT-TYPE
        SYNTAX INTEGER	(1..512)  
        MAX-ACCESS read-only
        STATUS current
        DESCRIPTION 
        "Gateway Entry's Index"
        ::= { bwaVLDrapGatewayEntry 1 }
        
bwaVLDrapGatewayIP OBJECT-TYPE
        SYNTAX IpAddress  
        MAX-ACCESS read-only
        STATUS current
        DESCRIPTION 
        "The IP address of the Gateway"
        ::= { bwaVLDrapGatewayEntry 2 }

bwaVLDrapGatewayType OBJECT-TYPE
        SYNTAX INTEGER  { vgDataVoice (4), vgData1Voice1 (5), 
                          vgData4Voice2 (6), vgDataVoice2(7), 
                          ngData4Wireless (11),
                          vgUnknown(255)
                         }
        MAX-ACCESS read-only
        STATUS current
        DESCRIPTION 
        "The Gateway type"
        ::= { bwaVLDrapGatewayEntry 3 }

bwaVLDrapGatewayNoOfActiveVoiceCalls OBJECT-TYPE
        SYNTAX INTEGER  
        MAX-ACCESS read-only
        STATUS current
        DESCRIPTION 
        "The current number of active voice calls handled by the Gateway"
        ::= { bwaVLDrapGatewayEntry 4 }

-- GATEWAY TABLE END 

-- ****************************************************************************************
--  TRAP defenitions: 
-- ****************************************************************************************

bwaVLTraps OBJECT IDENTIFIER ::= { bwaVLMib 14 }

bwaVLTrapSUMacAddr OBJECT-TYPE
    SYNTAX  MacAddress
    MAX-ACCESS  read-only  
    STATUS current
    DESCRIPTION
    "Applicable to AU/BU only.
     SU/RB MAC Address."
    ::= { bwaVLTraps 1 }

--bwaVLTrapSNRQuality   OBJECT-TYPE
--    SYNTAX INTEGER
--    MAX-ACCESS read-only  
--    STATUS current
--    DESCRIPTION
--    "Applicable to SU only.
--     SNR of received signal."
--    ::= { bwaVLTraps 2 }

bwaVLTrapText  OBJECT-TYPE
    SYNTAX DisplayString
    MAX-ACCESS read-only
    STATUS current
    DESCRIPTION
    "Textual string for future use."
    ::= { bwaVLTraps 3 }

bwaVLTrapToggle    OBJECT-TYPE
    SYNTAX INTEGER{
        on (1),
        off (2)
        }
    MAX-ACCESS read-only
    STATUS current
    DESCRIPTION
    "Applicable to all units.
     An On/Off toggle status." 
    ::= { bwaVLTraps 4 }

bwaVLTrapParameterChanged  OBJECT-TYPE
    SYNTAX INTEGER{ cirOrMir (1),
                    ipFilter (2), 
                    vlan (4)}
    MAX-ACCESS read-only
    STATUS current
    DESCRIPTION
    "Applicable to all units.
     A modification to one of the parameters related to CIR/MIR,  
     IP Filtering or VLAN."
    ::= { bwaVLTraps 5 }

bwaVLTrapAccessRights  OBJECT-TYPE
    SYNTAX INTEGER{ notLoggedIn   (1), 
                    readOnly      (2), 
                    installer     (3), 
                    administrator (4),  
                    factory       (5) }
    MAX-ACCESS read-only
    STATUS current
    DESCRIPTION
    "Applicable to all units.
     The access rights used for login."
    ::= { bwaVLTraps 6 }

bwaVLTrapLog   OBJECT-TYPE
    SYNTAX INTEGER{ telnetLogin  (3), 
                    telnetLogout (4) }
    MAX-ACCESS read-only
    STATUS current
    DESCRIPTION
    "Applicable to all units.
     Login or logout to the Monitor program via Telnet."
    ::= { bwaVLTraps 7 }

bwaVLTrapTelnetUserIpAddress   OBJECT-TYPE
    SYNTAX  IpAddress  
    MAX-ACCESS read-only
    STATUS current
    DESCRIPTION
    "Applicable to all units.
     The IP address of a Telnet user."
    ::= { bwaVLTraps 8 }

bwaVLTrapRTx   OBJECT-TYPE
    SYNTAX INTEGER
    MAX-ACCESS read-only  
    STATUS current
    DESCRIPTION
    "Applicable to AU/BU only. 
     Retransmissions as a percentage of total transmissions."
    ::= { bwaVLTraps 9 }

bwaVLTrapFtpOrTftpStatus    OBJECT-TYPE
    SYNTAX INTEGER{
        successful (1),
        failed (2)
        }
    MAX-ACCESS read-only
    STATUS current
    DESCRIPTION
    "Applicable to all units.
     The status of the last FTP/TFTP loading procedure." 
    ::= { bwaVLTraps 10 }
 
bwaVLDFSMoveFreq    OBJECT-TYPE
    SYNTAX INTEGER
    MAX-ACCESS read-only
    STATUS current
    DESCRIPTION
    "Applicable to AU/BU with HW revision B and lower 
     (for units with HW revision C and higher replaced by 
     bwaVLTrapDFSMoveFreq New to support a resolution of 0.5 MHz). 
     The new frequency in MHz after detecting radar on a previous channel."    
    ::= { bwaVLTraps 11 }
 
bwaVLDFSMoveFreqNew    OBJECT-TYPE
    SYNTAX DisplayString
    MAX-ACCESS read-only
    STATUS current
    DESCRIPTION
    "Applicable to AU/BU. 
     The new frequency in MHz after detecting radar on a previous channel. 
     (Replaces bwaVLDFSMoveFreq to support a resolution of 0.5 MHz for 
     units with HW revision C and higher)."
    ::= { bwaVLTraps 12 }

    
bwaVLEthBroadcastThresholdExceeded    OBJECT-TYPE
    SYNTAX INTEGER
    MAX-ACCESS read-only
    STATUS current
    DESCRIPTION
    "Applicable to all units. 
    The number of packets that are dropped by the ethernet broadcast/multicast limiter."
    ::= { bwaVLTraps 13 }
 
 
bwaVLTrapSubscriberType    OBJECT-TYPE
    SYNTAX INTEGER{ unknownSubscriberType(0), 
                    su-3(3)  , su-6(6)  , rb-14(14), 
                    su-24(24), rb-28(28), su-54(54), 
                    rb-100(100) }
    MAX-ACCESS read-only
    STATUS current
    DESCRIPTION
    "Applicable to AUS only.
    The type of subscriber that was rejected by AUS" 
    ::= { bwaVLTraps 14 }


bwaVLTrapMACAddress   OBJECT-TYPE
    SYNTAX MacAddress
    MAX-ACCESS read-only
    STATUS current
    DESCRIPTION
    "Applicable to BU/RB only.
    The MAC address of the BWA PtP unit whose type has been changed" 
    ::= { bwaVLTraps 15 }
    
bwaVLNewUnitTypeTrap  OBJECT-TYPE
    SYNTAX INTEGER { bu(1), rb(2) }
    MAX-ACCESS read-only
    STATUS current
    DESCRIPTION
    "Applicable to BU/RB only.
    The new type of the BWA PtP unit." 
    ::= { bwaVLTraps 16 }
            
bwaVLTrapSWVersion  OBJECT-TYPE
    SYNTAX DisplayString
    MAX-ACCESS read-only
    STATUS current
    DESCRIPTION
    "The SW version of the SU that tries to associate 
    with a station that has Wireless Link Prioritization Enabled"
    ::= { bwaVLTraps 17 }    
            
--
-- Private Traps for BWA-PtMP
--

bwaVLSUassociatedAUTRAP NOTIFICATION-TYPE
        OBJECTS
        {
           bwaVLTrapSUMacAddr     -- SU MAC address
        }
        STATUS current
        DESCRIPTION
        "An AU/BU trap indicating a new association with an SU/RB."
    ::= { bwaVLProducts 2 }

bwaVLAUdisassociatedTRAP NOTIFICATION-TYPE
        OBJECTS
        {
           bwaVLTrapSUMacAddr      --Unit MAC address
        }
        STATUS current
        DESCRIPTION
        "An AU/BU trap indicating that an SU/RB has been disassociated 
         from the AU.
         The AU/BU decides that an SU/RB has been disassociated from it and remove it
         from the ADB after receiving from another AU/BU a SNAP frame with the SU/RB 
         MAC address.
         The SNAP frame indicating a network topology change where the SU/RB has 
         associated with another AU/BU will be received if both AUs/BUs are 
         connected to the same Ethernet backbone."
    ::= { bwaVLProducts 3 }

bwaVLAUagingTRAP NOTIFICATION-TYPE
        OBJECTS
        {
     	  bwaVLTrapSUMacAddr  	-- Unit MAC address
        }
        STATUS current
        DESCRIPTION
	    "An AU/BU trap indicating that the unit association was aged out
	     and removed from the Association database following its failure
	     to acknowledge a specified number of consecutive frames."
    ::= { bwaVLProducts 4 }

bwaVLSUassociatedTRAP NOTIFICATION-TYPE
        OBJECTS
        {
--         bwaVLLastAUMacAddress,          Old AU mac address
           bwaVLAssociatedAU              -- New AU mac address
--         bwaVLTrapLastSNRQuality,          Average SNR with old AU
        }
        STATUS current
        DESCRIPTION
        "An SU/RB trap indicating association with an AU/BU. 
         In addition to the MAC address information of the AU/BU, the 
         trap also includes information on the average SNR of frames 
         received from the AU/BU."
    ::= { bwaVLProducts 6 }

bwaVLAUwirelessQualityTRAP NOTIFICATION-TYPE
        OBJECTS
        {
          bwaVLTrapToggle,
          bwaVLTrapRTx
        }
        STATUS current
        DESCRIPTION
        "An AU/BU trap, indicating that the quality of the wireless 
         link (retransmissions rate) has changed and dropped below (Off) or increased  
         above (On) a threshold , defined by the *bwaVLWirelessTrapThreshold. 
         The threshold for AU/BU is a percentage of retransmissions."
    ::= { bwaVLProducts 20 }

bwaVLPowerUpFromReset NOTIFICATION-TYPE
        OBJECTS
        {
           bwaVLUnitMacAddress    -- Unit MAC address
        }
        STATUS current
        DESCRIPTION
        "An AU/BU trap indicating power up after Reset."
    ::= { bwaVLProducts 101 }

bwaVLTelnetStatusTRAP NOTIFICATION-TYPE
        OBJECTS
        {
          bwaVLTrapLog,
          bwaVLTrapAccessRights,
          bwaVLTrapTelnetUserIpAddress
        }
        STATUS current
        DESCRIPTION
        "Applicable to all units.
         A trap indicating that a log-in or log-out has been performed 
         via Telnet. Includes the log-in access 
         right and the IP address of the PC performing Telnet."
    ::= { bwaVLProducts 102 }

bwaVLParameterChangedTRAP NOTIFICATION-TYPE
        OBJECTS
        {
           bwaVLTrapParameterChanged
        }
        STATUS current
        DESCRIPTION
        "Applicable to all units. A trap indicating a change in a CIR/MIR, IP Filter 
         or VLAN parameter."
    ::= { bwaVLProducts 103 }

bwaVLLoadingStatusTRAP NOTIFICATION-TYPE
        OBJECTS
        {
          bwaVLTrapFtpOrTftpStatus,
		  bwaVLUnitMacAddress
        }
        STATUS current
        DESCRIPTION
        "Applicable to all units.
         A trap indicating that last FTP/TFTP loading process has been 
         finished successfully or failed. "
    ::= { bwaVLProducts 104 }

bwaVLPromiscuousModeTRAP NOTIFICATION-TYPE
        OBJECTS
        {
          bwaVLTrapToggle,
		  bwaVLUnitMacAddress
        }
        STATUS current
        DESCRIPTION
        "An AU/BU trap, indicating that the AU/BU In (On) Promiscuous Mode or 
         out (Off) Promiscuous Mode." 
    ::= { bwaVLProducts 105 }

bwaVLDFSRadarDetecetedTRAP NOTIFICATION-TYPE
        STATUS current
        DESCRIPTION
        "DFS: Applicable to AU/BU only.
         A trap indicating that a radar was detected. "
    ::= { bwaVLProducts 106 }

bwaVLDFSFrequcnyTRAP NOTIFICATION-TYPE
        OBJECTS
        {
          bwaVLDFSMoveFreq, 
          bwaVLDFSMoveFreqNew        
        }
        STATUS current
        DESCRIPTION
        "Applicable to AU/BU only.
         A trap indicating that the unit moved to a new frequency. "
    ::= { bwaVLProducts 107 }

bwaVLDFSNoFreeChannelsExistsTRAP NOTIFICATION-TYPE
        STATUS current
        DESCRIPTION
        "Applicable to AU/BU only.
         A trap indicating that a radar was detected and there is no 
         free channel. "
    ::= { bwaVLProducts 108 }

bwaVLEthBroadcastMulticatLimiterTRAP NOTIFICATION-TYPE
        OBJECTS
        {
			bwaVLEthBroadcastThresholdExceeded
		}
        STATUS current
        DESCRIPTION
		"Applicable to all units. The trap is send if the 
		ethernet broadcast filter threshold is exceeded
		and it contains the number of dropped packets."
    ::= { bwaVLProducts 109 }

bwaVLAUSUnsupportedSubscriberTypeTRAP NOTIFICATION-TYPE
        OBJECTS
        {
			bwaVLTrapSUMacAddr,
			bwaVLTrapSubscriberType
		}
        STATUS current
        DESCRIPTION
		"Applicable to AUS only.
		This trap is generated when a subscriber with unsupported type tries to associate to AUS.
		The AUS supports only SU-3 and SU-6.
		The first variable of the trap is the subscriber MAC Address.
		The second variable is the type of subscriber"
    ::= { bwaVLProducts 110 }


bwaVLUnitTypeChangedTRAP NOTIFICATION-TYPE
        OBJECTS
        {
			bwaVLTrapMACAddress,
			bwaVLNewUnitTypeTrap
		}
        STATUS current
        DESCRIPTION
		"Applicable to BU/RB only.
		This trap is generated when the user change the type of the BWA PtP unit.
		The RB can be converted in BU or vice versa.
		The first variable of the trap is the unit MAC Address.
		The second variable is the new type of the unit"
    ::= { bwaVLProducts 111 }

bwaVLWLPrioritizationNotSupportedBySUTRAP NOTIFICATION-TYPE
        OBJECTS
        {
			bwaVLTrapSUMacAddr,
			bwaVLTrapSWVersion
		}
        STATUS current
        DESCRIPTION
		"Applicable to AU/BU only.
         This trap is generated when an SU/RB with a SW version below 4.0 
         that does not support Wireless Link Prioritization is associated 
         with an AU/BU with thw Wireless Link Prioritization Option enabled. 
		 The first variable of the trap is the SU/RB MAC Address.
		 The second variable is the SW version of the SU/RB"
    ::= { bwaVLProducts 112 }

END
