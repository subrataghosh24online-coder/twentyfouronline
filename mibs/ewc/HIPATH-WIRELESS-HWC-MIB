HIPATH-WIRELESS-HWC-MIB DEFINITIONS ::= BEGIN
 
        IMPORTS
            hiPathWirelessMgmt, hiPathWirelessModules
                FROM HIPATH-WIRELESS-SMI
            WEPKeytype
                FROM IEEE802dot11-MIB
            Ipv6Address
                FROM IPV6-TC
            ifIndex, InterfaceIndex
                FROM IF-MIB
            OBJECT-GROUP, MODULE-COMPLIANCE, NOTIFICATION-GROUP
                FROM SNMPv2-CONF
            TimeTicks, IpAddress, Integer32, Unsigned32, Gauge32, 
            Counter32, Counter64, OBJECT-TYPE, MODULE-IDENTITY, NOTIFICATION-TYPE
                FROM SNMPv2-SMI
            DisplayString, TruthValue, RowStatus, MacAddress, TEXTUAL-CONVENTION
                FROM SNMPv2-TC;

        -- 1.3.6.1.4.1.4329.15.5.2
        hiPathWirelessControllerMib MODULE-IDENTITY 
            LAST-UPDATED "201604131355Z"  -- Wednesday April 13 13:55 UTC 2016
            ORGANIZATION 
                "Chantry Networks Inc."
            CONTACT-INFO 
                "Chantry Networks, Inc.
                
                55 Commerce Valley Drive (W), Suite 400
                Thornhill, Ontario L3T 7V9, Canada

                Phone:   1-289-695-3182
                Fax:     1 289-695-3299"
            DESCRIPTION 
                "The access controller MIB"



            REVISION "201604131355Z"  -- Wednesday April 13 13:55 UTC 2016
            DESCRIPTION 
            "
            - Added wlanAppVisibility to wlanTable."

            REVISION "201603091641Z"  -- Wednesday March 09 16:41 UTC 2016
            DESCRIPTION 
            "
            - Added stationIPv6Address1, stationIPv6Address2, and  stationIPv6Address3
               to stationEventAlarm.
            - Added apTotalStationsAInOctets, apTotalStationsAOutOctets, apTotalStationsBInOctets,
               apTotalStationsBOutOctets, apTotalStationsGInOctets, apTotalStationsGOutOctets,
               apTotalStationsN50InOctets, apTotalStationsN50OutOctets, apTotalStationsN24InOctets,
               apTotalStationsN24OutOctets, apTotalStationsACInOctets, and apTotalStationsACOutOctets
               to apStatsTable."



            REVISION "201510061731Z"  -- Tuesday October 06 17:31 UTC 2015
            DESCRIPTION 
            "
            - Modified the description of stationEventTimeStamp.
            - Added more access points (APs) to apPlatforms.
            - Deprecated topoWireStatTable.
            - Added topoCompleteStatTable.
            - Added applyMacAddressFormat  to authenticationAdvanced.
            - Added radiusMacAddressFormatOption to vnsGlobalSetting."


            REVISION "201506121205Z"  -- Friday Jun 12 12:05 UTC 2015
            DESCRIPTION 
            "
            - Modified the description of topoStatTable.
            - Modified the description of apPerformanceReportByRadioTable."


            REVISION "201503171031Z"  -- Tuesday March 17 10:31 UTC 2015
            DESCRIPTION 
            "
            - Added wlanRadioManagement11k, wlanBeaconReport, QuietIE, 
               wlanMirrorN, and wlanNetFlow to wlanTable.
            - Added wlanPrivfastTransition, and wlanPrivManagementFrameProtection to wlanPrivTable.
            - Added topologyIsGroup, topologyGroupMembers, and topologyMemberId to topologyTable.
            - Added netflowAndMirrorN Object. It contains netflowDestinationIP, netflowInterval,
               mirrorFirstN, and mirrorL2Ports.
            - Added fastTransition(13) to muDot11ConnectionCapability.
            - Added clearAccessRejectMsg and accessRejectMsgTable.
            - Added vnsQoSWirelessUseAdmControlBestEffort, and 
               vnsQoSWirelessUseAdmControlBackground to vnsQoSTable.
            - Added maxBestEffortBWforReassociation, maxBestEffortBWforAssociation,
               maxBackgroundBWforReassociation, and maxBackgroundBWforAssociation
               to wirelessQoS.
            - Added radacctStartOnIPAddr and clientServiceTypeLogin to authenticationAdvanced.
            - Added apPerformanceReportByRadioTable.
            - Added apPerformanceReportbyRadioAndWlanTable.
            - Added apChannelUtilizationTable.
            - Added apAccessibilityTable.
            - Added apNeighboursTable."


            REVISION "201411281731Z"  -- Friday  November 28 17:31 UTC 2014
            DESCRIPTION 
            "- Added topoWireStatTable."

            REVISION "201406171529Z"  -- Tuesday  June 17 15:29 UTC 2014
            DESCRIPTION 
                "- Added firewallFriendlyExCP(7) to wlanAuthType.
                 - Added firewallFriendlyExCP(7) to wlanCPAuthType.
                 - Added wlanCPIdentity, wlanCPCustomSpecificURL and 
                    wlanCPSelectionOption to  wlanCPTable.
                 - Added wlanAuthRadiusOperatorNameSpace, wlanAuthRadiusOperatorName and
                     wlanAuthMACBasedAuthReAuthOnAreaRoam to wlanAuthTable.
                 - Added radiusExtnsSettingTable.
                 - Added authenticationAdvanced.
                 - Added areaChange(12) to stationEventType."



            REVISION "201404161429Z"  -- Wednesday  April 16 14:29 UTC 2014
            DESCRIPTION 
                "- Added apLogManagement Objects.
                 - Added apMaintenanceCycle Objects.
                 - Deprecated wlanCPExtTosValue from wlanCPTable.
                 - Deprecated apSSHAccess from apTable.
                 - Added apSSHConnection to apTable.
                 - Added na(3) to apTelnetAccess."



            REVISION "201401271429Z"  -- Monday  January 27 14:29 UTC 2014
            DESCRIPTION 
                "- Added apRadioAttenuation  to apRadioAntennaTable.
                 - Added apRadioStatusTable.
                 - Added apRadioProtocol  to apRadioTable.
                 - Deprecated apRadioType from apRadioTable."



            REVISION "201311181029Z"  -- Monday  November 18 10:29 UTC 2013
            DESCRIPTION 
                "- stationsByProtocol was modified to add stationsByProtocolUnavailable, stationsByProtocolError and stationsByProtocolAC.
                 - Added muDot11ConnectionCapability to  muTable.
                 - deprecated muConnectionCapability from muTable. 
                 - Added ac(6) to muConnectionProtoco.
                 - Added apInterfaceMTU, apEffectiveTunnelMTU and apTotalStationsAC to apStatsTable.
                 - Added dot11ac(11) and dot11cStrict(12) to apRadioType.
                 - Added wlanAuthRadiusAcctAfterMacBaseAuthorization and wlanAuthRadiusTimeoutRole to wlanAuthTable.
                 - Added wlanPrivWPAversion to wlanPrivTable.
                 - Added jumboFrames to physicalPortObjects.
                 - Added apRegister to apEventId."

            REVISION "201308281117Z"  -- Wednesday  August 28 11:17 UTC 2013
            DESCRIPTION 
                "- apTable was modified to add apIPMulticastAssembly."



            REVISION "201308011555Z"  -- Thu August 1 15:55 UTC 2013
            DESCRIPTION 
                "
                 - Added wlanCPUseHTTPSforConnection to wlanCPTable.
                 - Added wlanRadiusServerTable.
                 - Added inSrvScanGrpDetectRogueAP and  inSrvScanGrpListeningPort to inServiceScanGroupTable.
                 - Added dedicatedScanGrpDetectRogueAP and dedicatedScanGrpListeningPort to dedicatedScanGroupTable.
                 - Added clientAutologinOption to vnsGlobalSetting.
                 - Added licenseMode, licenseLocalAP, licenseForeignAP, licenseLocalRadarAP and licenseForeignRadarAP to licensingInformation.
                 - Added sysCPUType to systemObjects.
                 - Added adHocModeDevice(6) and  rogueAP(7) to dedicatedScanGrpCounterMeasures and inServiceScanGroupTable ."



            REVISION "201307121650Z"  -- Friday  July 12 16:50 UTC 2013
            DESCRIPTION 
                "- Added AccessPoint reigisteration event notification."

            REVISION "201304181555Z"  -- Thu Apr 18 15:55 UTC 2013
            DESCRIPTION 
                "- Added radiusFastFailoverEventsTable.
                 - Addes dhcpRelayListenersTable.
                 - topologyTable was modified to add new topologyDynamicEgress value..
                 - Added apRadioAntennaTable.
                 - Added stationSessionNotifications trap.
                 - scanGroupAPAssignmentTable was modified to add 
                    scanGroupAPAssignControllerIPAddress and scanGroupAPAssignFordwardingService.
                 - scanAPTable was modified to add scanAPProfileName and scanAPProfileType.
                 - Added dedicatedScanGroupTable. 
                 - apStatsTable was modified to add apInvalidPolicyCount.
                 - apTable was modified to add apSecureDataTunnelType
                 - uncategorizedAPTable was modified to add uncategorizedAPSSID 
                    and deprecate uncategorizedAPDescption."


            REVISION "201210181150Z"        -- October 18, 2012 at 11:50 GMT
            DESCRIPTION 
                "Description changes for object groups:
                 uncategorizedAPGroup, authorizedAPGroup and prohibitedAPGroup."
            REVISION "201209271110Z"        -- September 27, 2012 at 11:10 GMT
            DESCRIPTION 
                "- Added radiusStrictMode
                - Enhance description field of a few variables"
            REVISION "201209101410Z"        -- September 10, 2012 at 14:10 GMT
            DESCRIPTION 
                "Added support:
                - widsWips: Configuration and statistic infromation about intrusion detection and prevention.
                - Controller dashboard information was added under  'dashboard', that includes 
                  some controler statistics and lincensing information
                - wlanSecurityReportTable was created to report on the status of weak WLAN configuration
                - apAntennaTable was added to provide AP antenna information
                - MU access list: creating MU access list using set of MAC addresses.
                - muACLTable is deprecated and replaced by muAccessListTable.
                - apTable was modified with added new field: apMICErrorWarning"
                
            REVISION "201202131933Z"        -- February 13, 2012 at 19:33 GMT
            DESCRIPTION 
                "Added support:
                - siteTable:  main table to create any site.
                - sitePolicyTable: The table for assigning policies to a site.
                - siteCosTable:  The table for retrieving assigned CoS to a site.
                - siteAPTable: Table for assinging APs to a site.
                - siteWlanTable:  Table for assinging WLANs to a site.
                All tables above can collectively be used to configure a site or retrieve its configuration values.
                apTable was modified with new value for show its site membership.
                - WlanAuthTable::wlanAuthReplaceCalledStationIDWithZone was added.
                - WlanCpTable::wlanCPGuestMaxConcurrentSession was added.
                - TopologyTable was modified with additional new elements.
                - apTable was modified with new AP attributes.
                - muTable::muBSSIDMac was added.
                - loadGroupTable: more elements were added to this table.
                - loadGroupTable::loadGroupLoadControl was deprecated and was replaced with two new fields 
                  each representing one radio."
                  
            REVISION "201108171418Z"        -- August 17, 2011 at 14:18 GMT
            DESCRIPTION 
                "muTable was modified to show its association to WLAN by including WLAN ID into muTable."
            REVISION "201106131310Z"        -- June 13, 2011 at 13:10 GMT
            DESCRIPTION 
                "secureConnection: This object was added to support weak cipher configuration.
                VSN related fields were modified: 
                   -- vnsFilterRuleDirection, vnsFilterRuleProtocol, vnsFilterRuleEtherType.
                muTable was modified with added fields: 
                   -- muTopologyName, muPolicyName, muDefaultCoS, muConnectionProtocol, muConnectionCapability.
                More added for configuration of MU Access List:
                  - muACLType, muACLTable.
                apStatsTable was modified with more new elements:
                  - apTotalStationsA, apTotalStationsB, apTotalStationsG,apTotalStationsN50, apTotalStationsN24."
            REVISION "201104291606Z"        -- April 29, 2011 at 16:06 GMT
            DESCRIPTION 
                "Added layer two physical tables:
                - layerTwoPortTable   
                
                Following tables are deprecated due to changes in EWC:
                - physicalPortsTable
                - phyDHCPRangeTable


                HWC (HiPath Wireless Controller) has been replaced with EWC (Enterasys
                Wireless Controller)."
                
            REVISION "201101131325Z"        -- January 13, 2011 at 13:25 GMT
            DESCRIPTION 
                "Added more tables to reflect WLAN configuration. Detailed WLAN configuration
                are reflected in new tables:
                - wlanPrivTable  (WLAN privacy configuration)
                - wlanAuthTable  (WLAN authentication configuration)
                - wlanRadiusTable  (RADIUS assignment for each WLAN)
                - wlanCPTable   (WLAN captive portal configuration)
                - wlanServiceType field was modifed to support mesh.

                Acess point related changes are:
                - apStaticMTUSize to apTable   
                - apRadioNumber   to apRadioTable  
                - apRadioType     to apRadioTable 

                Global advanced filtering mode were added:  advancedFilteringMode

                Following item were not applicable to HWC captive portal anymore and are deprecated:
                - cpLoginLabel
                - cpPasswordLabel 
                - cpHeaderURL 
                - cpFooterURL 
                - cpMessage 

                Access point load balancing group are reflected in new tables:
                - loadGroupTable  (load group configuration)
                - loadGrpRadiosTable  (radio assignment to loadGroupTable)
                - loadGrpWlanTable    (WLAN assignment to loadGroupTable) "
                
            REVISION "201004291744Z"        -- April 29, 2010 at 17:44 GMT
            DESCRIPTION 
                "HWC release 7.31:  Enhancement are in the area of:
                - availability:  HWC availability support 
                - vnManagerObjects: Mobility enhancement related to MU counters
                - tunnelStatsTable: Mobility tunnel stats enhancement such as MU counters
                - AP stats enhancement in apStatsTable
                - apRegistration: AP registration and administration configuration fields
                - topologyTable:  Advanced topology configuration fields are added to this table.
                - topoStatTable: topoStatFrameChkSeqErrors and topoStatFrameTooLongErrors added
                - WLAN scalars added: wlanMaxEntries, wlanNumEntries, wlanTableNextAvailableIndex
                - wlanTable: Table of WLAN configuration
                - wlanStatsTable: WLAN statistics such as  clients counts, RADIUS
                  request counts, RAIDUS failed or rejected counters. "
                  
            REVISION "201004081645Z"        -- April 08, 2010 at 16:45 GMT
            DESCRIPTION 
                "Obsoleted following items:
                - vnsAssignmentMode
                - vnsParentIfIndex
                - vnsRateControlProfTable 
                - vnsWDSStatTable
                - vnsStatTable.  These stats are reflected under topology
                - vnsExceptionStatTable. These stats are reflected under topology."
                
            REVISION "201002231517Z"        -- February 23, 2010 at 15:17 GMT
            DESCRIPTION 
                "New changes include:
                - Topology configuratioin
                - Statistics about topoloy
                - Exception stat about topology."
            REVISION "200908181200Z"        -- August 18, 2009 at 12:00 GMT
            DESCRIPTION 
                "Added version of the image for sensors."
            REVISION "200907231247Z"        -- July 23, 2009 at 12:47 GMT
            DESCRIPTION 
                "Added SLP status field to VNS configuration table (vnsConfigTable)."
            REVISION "200904231714Z"        -- April 23, 2009 at 17:14 GMT
            DESCRIPTION 
                "Added information about sensor management."
            REVISION "200901191349Z"        -- January 19, 2009 at 13:49 GMT
            DESCRIPTION 
                "Added new fields for VNS such as vnsEabled.
                Added AP filter for ACL list for Access Points"
            REVISION "200808131431Z"        -- August 13, 2008 at 14:31 GMT
            DESCRIPTION 
                "Added DNS entries.
                Aded DAS values
                Added RADIUS server information"
            REVISION "200711261615Z"        -- November 26, 2007 at 16:15 GMT
            DESCRIPTION 
                "DHCP information related to the Controller was added to the MIB."
            REVISION "200708111615Z"        -- August 11, 2007 at 16:15 GMT
            DESCRIPTION 
                "Modified apTable with additional fields."
            REVISION "200701151338Z"        -- January 15, 2007 at 13:38 GMT
            DESCRIPTION 
                "Added WDS VNS."
            REVISION "200510281312Z"        -- October 28, 2005 at 13:12 GMT
            DESCRIPTION 
                "Initial version."
            ::= { hiPathWirelessModules 2 }


--
-- Textual conventions
--

        LogEventSeverity ::= TEXTUAL-CONVENTION
            STATUS current
            DESCRIPTION 
                "The log event severities used in the access controller."
            SYNTAX INTEGER
                {
                critical(1),
                major(2),
                minor(3),
                information(4),
                trace(5)
                }



HundredthOfGauge64 ::= TEXTUAL-CONVENTION
    DISPLAY-HINT    "d-2"
    STATUS          current
    DESCRIPTION
        "This textual convention represents a hundredth of a 64-bit gauge number."
    SYNTAX          Counter64


HundredthOfGauge32 ::= TEXTUAL-CONVENTION
    DISPLAY-HINT    "d-2"
    STATUS          current
    DESCRIPTION
        "This textual convention represents a hundredth of a gauge number."
    SYNTAX          Gauge32 

HundredthOfInt32 ::= TEXTUAL-CONVENTION
    DISPLAY-HINT    "d-2"
    STATUS          current
    DESCRIPTION
        "This textual convention represents a hundredth of an integer number."
    SYNTAX          Integer32 


--
-- Node definitions
--
    
        -- 1.3.6.1.4.1.4329.15.3.2
        hiPathWirelessController OBJECT IDENTIFIER ::= { hiPathWirelessMgmt 2 }


        -- 1.3.6.1.4.1.4329.15.3.2.1
        systemObjects OBJECT IDENTIFIER ::= { hiPathWirelessController 1 }


        -- 1.3.6.1.4.1.4329.15.3.2.1.1
        sysSoftwareVersion OBJECT-TYPE
            SYNTAX DisplayString
            MAX-ACCESS read-only
            STATUS current
            DESCRIPTION
                "System software version."
            ::= { systemObjects 1 }


        -- 1.3.6.1.4.1.4329.15.3.2.1.2
        sysLogLevel OBJECT-TYPE
            SYNTAX LogEventSeverity
            MAX-ACCESS read-write
            STATUS current
            DESCRIPTION
                "Sets the level of events which are written to the system
                log."
            ::= { systemObjects 2 }


        -- 1.3.6.1.4.1.4329.15.3.2.1.3
        sysSerialNo OBJECT-TYPE
            SYNTAX OCTET STRING (SIZE (0..64))
            MAX-ACCESS read-only
            STATUS current
            DESCRIPTION
                "System serial number."
            ::= { systemObjects 3 }


        -- 1.3.6.1.4.1.4329.15.3.2.1.4
        sysLogSupport OBJECT IDENTIFIER ::= { systemObjects 4 }


        -- 1.3.6.1.4.1.4329.15.3.2.1.4.1
        hiPathWirelessAppLogFacility OBJECT-TYPE
            SYNTAX INTEGER
                {
                local0(0),
                local1(1),
                local2(2),
                local3(3),
                local4(4),
                local5(5),
                local6(6)
                }
            MAX-ACCESS read-write
            STATUS current
            DESCRIPTION
                "The application log facility level for syslog."
            ::= { sysLogSupport 1 }


        -- 1.3.6.1.4.1.4329.15.3.2.1.4.2
        serviceLogFacility OBJECT-TYPE
            SYNTAX INTEGER
                {
                local0(0),
                local1(1),
                local2(2),
                local3(3),
                local4(4),
                local5(5),
                local6(6)
                }
            MAX-ACCESS read-write
            STATUS current
            DESCRIPTION
                "The service log facility level for syslog."
            ::= { sysLogSupport 2 }


        -- 1.3.6.1.4.1.4329.15.3.2.1.4.3
        includeAllServiceMessages OBJECT-TYPE
            SYNTAX TruthValue
            MAX-ACCESS read-write
            STATUS current
            DESCRIPTION
                "Indicates if DHCP messages should also be forwarded to syslog."
            ::= { sysLogSupport 3 }


        -- 1.3.6.1.4.1.4329.15.3.2.1.4.4
        sysLogServersTable OBJECT-TYPE
            SYNTAX SEQUENCE OF SysLogServersEntry
            MAX-ACCESS not-accessible
            STATUS current
            DESCRIPTION
                "Table of syslog servers to forward logging messages."
            ::= { sysLogSupport 4 }


        -- 1.3.6.1.4.1.4329.15.3.2.1.4.4.1
        sysLogServersEntry OBJECT-TYPE
            SYNTAX SysLogServersEntry
            MAX-ACCESS not-accessible
            STATUS current
            DESCRIPTION
                "Configuration information for an external syslog server."
            INDEX { sysLogServerIndex }
            ::= { sysLogServersTable 1 }


        SysLogServersEntry ::=
            SEQUENCE { 
                sysLogServerIndex
                    Integer32,
                sysLogServerEnabled
                    TruthValue,
                sysLogServerIP
                    IpAddress,
                sysLogServerPort
                    Integer32,
                sysLogServerRowStatus
                    RowStatus
             }

        -- 1.3.6.1.4.1.4329.15.3.2.1.4.4.1.1
        sysLogServerIndex OBJECT-TYPE
            SYNTAX Integer32 (1..2147483647)
            MAX-ACCESS read-write
            STATUS current
            DESCRIPTION
                "Table index for the syslog server."
            ::= { sysLogServersEntry 1 }


        -- 1.3.6.1.4.1.4329.15.3.2.1.4.4.1.2
        sysLogServerEnabled OBJECT-TYPE
            SYNTAX TruthValue
            MAX-ACCESS read-write
            STATUS current
            DESCRIPTION
                "Indicates if messages are to be sent to the syslog server."
            ::= { sysLogServersEntry 2 }


        -- 1.3.6.1.4.1.4329.15.3.2.1.4.4.1.3
        sysLogServerIP OBJECT-TYPE
            SYNTAX IpAddress
            MAX-ACCESS read-write
            STATUS current
            DESCRIPTION
                "syslog server IP address."
            ::= { sysLogServersEntry 3 }


        -- 1.3.6.1.4.1.4329.15.3.2.1.4.4.1.4
        sysLogServerPort OBJECT-TYPE
            SYNTAX Integer32
            MAX-ACCESS read-write
            STATUS current
            DESCRIPTION
                "syslog server port number."
            ::= { sysLogServersEntry 4 }


        -- 1.3.6.1.4.1.4329.15.3.2.1.4.4.1.5
        sysLogServerRowStatus OBJECT-TYPE
            SYNTAX RowStatus
            MAX-ACCESS read-write
            STATUS current
            DESCRIPTION
                "RowStatus for operating on syslogServersTable."
            ::= { sysLogServersEntry 5 }

        -- 1.3.6.1.4.1.4329.15.3.2.1.5
        sysCPUType OBJECT-TYPE
            SYNTAX DisplayString
            MAX-ACCESS read-only
            STATUS current
            DESCRIPTION
                "Wireless controller's CPU type"
            ::= { systemObjects 5 }




        -- 1.3.6.1.4.1.4329.15.3.2.1.6
        apLogManagement OBJECT IDENTIFIER ::= { systemObjects 6 }


        -- 1.3.6.1.4.1.4329.15.3.2.1.6.1
        apLogCollectionEnable OBJECT-TYPE
            SYNTAX TruthValue
            MAX-ACCESS read-write
            STATUS current
            DESCRIPTION
                "If this field is set to true, then the AP log collection feature is enabled."
            ::= { apLogManagement 1 }


        -- 1.3.6.1.4.1.4329.15.3.2.1.6.2
        apLogFrequency OBJECT-TYPE
            SYNTAX Integer32 
            MAX-ACCESS read-write
            STATUS current
            DESCRIPTION
                "Number of  log collections performed daily. The number must be one of the following 1, 2, 4, 6."
            ::= { apLogManagement 2 }

        -- 1.3.6.1.4.1.4329.15.3.2.1.6.3
        apLogDestination OBJECT-TYPE
            SYNTAX INTEGER
                {
                local(0),
                flash(1),
                remote(2)
                }
            MAX-ACCESS read-write
            STATUS current
            DESCRIPTION
                "Destination where the log file will be stored. If the  
                  local flash is not mounted, then you can not select 1.
                0 : local memory.
                1 : flash.
                2 : remote location.
                "
            ::= { apLogManagement 3 }


        -- 1.3.6.1.4.1.4329.15.3.2.1.6.4
        apLogFTProtocol OBJECT-TYPE
            SYNTAX INTEGER
                {
                ftp(0),
                scp(1)
                }
            MAX-ACCESS read-write
            STATUS current
            DESCRIPTION
                "File transfer protocol. This field has meaning only when apLogDestination is set to remote(2).
                0 : ftp.
                1 : scp."
            ::= { apLogManagement 4 }

        -- 1.3.6.1.4.1.4329.15.3.2.1.6.5
        apLogServerIP OBJECT-TYPE
            SYNTAX IpAddress
            MAX-ACCESS read-write
            STATUS current
            DESCRIPTION
                "The IP address of the remote server. This field has meaning only when apLogDestination is set to remote(2)."
            ::= { apLogManagement 5 }


        -- 1.3.6.1.4.1.4329.15.3.2.1.6.6
        apLogUserId OBJECT-TYPE
            SYNTAX DisplayString
            MAX-ACCESS read-write
            STATUS current
            DESCRIPTION
                "The user ID that is used for access to the remote server.
                  This field has meaning only when apLogDestination is set to remote(2)."
            ::= { apLogManagement 6 }

        -- 1.3.6.1.4.1.4329.15.3.2.1.6.7
        apLogPassword OBJECT-TYPE
            SYNTAX DisplayString
            MAX-ACCESS read-write
            STATUS current
            DESCRIPTION
                "The user password that is used for access to the remote server.
                  This field has meaning only when apLogDestination is set to remote(2).
                  This field can only be viewed in SNMPv3 mode with privacy."
                
            ::= { apLogManagement 7 }



        -- 1.3.6.1.4.1.4329.15.3.2.1.6.8
        apLogDirectory OBJECT-TYPE
            SYNTAX DisplayString
            MAX-ACCESS read-write
            STATUS current
            DESCRIPTION
                "The directory of the remote server.
                  This field has meaning only when apLogDestination is set to remote(2)."
            ::= { apLogManagement 8 }



        -- 1.3.6.1.4.1.4329.15.3.2.1.6.9
        apLogSelectedAPsTable OBJECT-TYPE
            SYNTAX SEQUENCE OF APLogSelectedAPsEntry
            MAX-ACCESS not-accessible
            STATUS current
            DESCRIPTION
                "Table containing a list of APs for which log collection is supported."
            ::= { apLogManagement 9 }



        -- 1.3.6.1.4.1.4329.15.3.2.1.6.9.1
        apLogSelectedAPsEntry OBJECT-TYPE
            SYNTAX APLogSelectedAPsEntry
            MAX-ACCESS not-accessible
            STATUS current
            DESCRIPTION
                "Configuration information of an AP which supports the AP log feature."
            INDEX { apSerialNo }
            ::= { apLogSelectedAPsTable 1 }

        APLogSelectedAPsEntry ::=
            SEQUENCE { 
                apSerialNo
                    OCTET STRING,
                select
                    TruthValue
                    }


        -- 1.3.6.1.4.1.4329.15.3.2.1.6.9.1.1
        apSerialNo OBJECT-TYPE
            SYNTAX OCTET STRING (SIZE (16))
            MAX-ACCESS not-accessible
            STATUS current
            DESCRIPTION
                "Table index for the apLogSelectedAPs. The AP's serial number serves as the index."
            ::= { apLogSelectedAPsEntry 1 }


        -- 1.3.6.1.4.1.4329.15.3.2.1.6.9.1.1
        select OBJECT-TYPE
            SYNTAX TruthValue
            MAX-ACCESS read-write
            STATUS current
            DESCRIPTION
                "Indicates whether logs are collected from the AP."
            ::= { apLogSelectedAPsEntry 2 }



        -- 1.3.6.1.4.1.4329.15.3.2.1.6.10
        apLogQuickSelectedOption OBJECT-TYPE
            SYNTAX INTEGER
                {
                unknown(0),
                addAll(1),
                addAllLocal(2),
                addAllForeign(3),
                removeAll(4),
                removeAllLocal(5),
                removeAllForeign(6)
                }

            MAX-ACCESS read-write
            STATUS current
            DESCRIPTION
                "This is a quick select option for the user to perform the AP's bulk selection.
                  This field is write-only and read access returns unknown(0) value.
                 0 : unknown.
                 1 : add all APs.
                 2 : add all local APs.
                 3 : add all foreign APs.
                 4 : remove all APs.
                 5 : remove all local APs.
                 6 : remove all foreign APs."
            ::= { apLogManagement 10 }




        -- 1.3.6.1.4.1.4329.15.3.2.1.7
        apLogFileUtility OBJECT IDENTIFIER ::= { systemObjects 7 }

        -- 1.3.6.1.4.1.4329.15.3.2.1.7.1
            apLogFileUtilityLimit OBJECT-TYPE
            SYNTAX      Unsigned32 (0..4294967295) 
            MAX-ACCESS  read-only
            STATUS      current
            DESCRIPTION 
                "The maximum number of AP log file copy  requests that can be
                held in the apLogFileCopyTable. A value of 0 indicates no 
                configured limit." 
        ::= { apLogFileUtility 1 }

        -- 1.3.6.1.4.1.4329.15.3.2.1.7.2
            apLogFileUtilityCurrent OBJECT-TYPE 
            SYNTAX      Gauge32
            MAX-ACCESS  read-only
            STATUS      current
            DESCRIPTION 
                "The number of AP log file copy requests currently in the apLogFileCopyTable." 
            ::= { apLogFileUtility 2 } 

        -- 1.3.6.1.4.1.4329.15.3.2.1.7.5
            apLogFileCopyTable OBJECT-TYPE 
            SYNTAX      SEQUENCE OF ApLogFileCopyEntry
            MAX-ACCESS  not-accessible
            STATUS      current
            DESCRIPTION 
                "List of AP log file copy requests." 
            ::= { apLogFileUtility 5 } 


            apLogFileCopyEntry OBJECT-TYPE 
            SYNTAX      ApLogFileCopyEntry
            MAX-ACCESS  not-accessible
            STATUS      current
            DESCRIPTION 
                "An entry describing the AP log file copy request." 
            INDEX { apLogFileCopyIndex }
            ::= { apLogFileCopyTable 1 } 

            ApLogFileCopyEntry ::= 
                SEQUENCE { 
                    apLogFileCopyIndex 
                        Unsigned32, 
                    apLogFileCopyDestination
                        INTEGER, 
                    apLogFileCopyProtocol
                        INTEGER, 
                    apLogFileCopyServerIP 
                        IpAddress,
                    apLogFileCopyUserID
                        DisplayString,
                    apLogFileCopyPassword
                        DisplayString,
                    apLogFileCopyServerDirectory
                        DisplayString,
                    apLogFileCopyOperation
                        INTEGER,  
                    apLogFileCopyOperationStatus 
                        INTEGER,
                     apLogFileCopyRowStatus 
                        RowStatus 
                        }

        -- 1.3.6.1.4.1.4329.15.3.2.1.7.5.1
        apLogFileCopyIndex       OBJECT-TYPE 
        SYNTAX      Unsigned32 (1..4294967295)
        MAX-ACCESS  not-accessible
        STATUS      current
        DESCRIPTION 
            "The index for this AP log file copy request." 
        ::= { apLogFileCopyEntry 1 } 

        -- 1.3.6.1.4.1.4329.15.3.2.1.7.5.2
        apLogFileCopyDestination OBJECT-TYPE
           SYNTAX INTEGER
                {
                flash(1),
                remoteServer(2)
                }
            MAX-ACCESS read-write
            STATUS current
            DESCRIPTION
                "Destination where the log file will be copied. If the local flash is
                  not mounted, then you can not select 1.
                 1 : copy the local AP log file to flash.
                 2 : copy the local AP log file to remote server. "
            ::= { apLogFileCopyEntry 2 }


        -- 1.3.6.1.4.1.4329.15.3.2.1.7.5.3
        apLogFileCopyProtocol OBJECT-TYPE
           SYNTAX INTEGER
                {
                ftp(0),
                scp(1)
                }
            MAX-ACCESS read-write
            STATUS current
            DESCRIPTION
                "File transfer protocol to be used to copy the log file.
                0 : ftp.
                1 : scp."
            ::= { apLogFileCopyEntry 3 }


        -- 1.3.6.1.4.1.4329.15.3.2.1.7.5.4
        apLogFileCopyServerIP OBJECT-TYPE
            SYNTAX IpAddress
            MAX-ACCESS read-write
            STATUS current
            DESCRIPTION
                "The IP address of the remote server."
            ::= { apLogFileCopyEntry 4 }

        -- 1.3.6.1.4.1.4329.15.3.2.1.7.5.5
        apLogFileCopyUserID OBJECT-TYPE
            SYNTAX DisplayString
            MAX-ACCESS read-write
            STATUS current
            DESCRIPTION
                "The user ID that is used for access to the remote server."
            ::= { apLogFileCopyEntry 5 }

        -- 1.3.6.1.4.1.4329.15.3.2.1.7.5.6
        apLogFileCopyPassword OBJECT-TYPE
            SYNTAX DisplayString
            MAX-ACCESS read-write
            STATUS current
            DESCRIPTION
                "The user password that is used for access to the remote server.
                 This field can only be viewed in SNMPv3 mode with privacy."
            ::= { apLogFileCopyEntry 6 }


        -- 1.3.6.1.4.1.4329.15.3.2.1.7.5.7
        apLogFileCopyServerDirectory OBJECT-TYPE
            SYNTAX DisplayString
            MAX-ACCESS read-write
            STATUS current
            DESCRIPTION
                "The directory on the remote server."
            ::= { apLogFileCopyEntry 7 }

        -- 1.3.6.1.4.1.4329.15.3.2.1.7.5.8
        apLogFileCopyOperation OBJECT-TYPE
            SYNTAX INTEGER
                {
                start(1)
                }
            MAX-ACCESS read-create
            STATUS current
            DESCRIPTION
                "If this field is set to 1, then the controller will start to perform the copy action."
            ::= { apLogFileCopyEntry 8 }

        -- 1.3.6.1.4.1.4329.15.3.2.1.7.5.9
        apLogFileCopyOperationStatus OBJECT-TYPE
            SYNTAX INTEGER
                {
                  inactive(1),
                  pending(2),
                  running(3),
                  success(4),
                  failure(5)
                  }
            MAX-ACCESS read-only
            STATUS current
            DESCRIPTION
                "The operational state of the AP log file copy request.
                 inactive - Indicates that the RowStatus of this conceptual row is not in the `active` state.
                 pending  - Indicates that the AP log file copy described by this row is ready to run and waiting in a queue.
                 running  - Indicates that the AP log file copy described by this row is running.
                 success  - Indicates that the AP log file copy described by this row has successfully run to completion.
                 failure  - Indicates that the AP log file copy described by this row has failed to run to completion."
            ::= { apLogFileCopyEntry 9 }

        apLogFileCopyRowStatus OBJECT-TYPE 
            SYNTAX      RowStatus
            MAX-ACCESS  read-create
            STATUS      current
            DESCRIPTION 
                "Row status variable for row operations on the apLogFileCopyTable." 
         ::= { apLogFileCopyEntry 10 } 




        -- 1.3.6.1.4.1.4329.15.3.2.2
        dnsObjects OBJECT IDENTIFIER ::= { hiPathWirelessController 2 }


        -- 1.3.6.1.4.1.4329.15.3.2.2.1
        primaryDNS OBJECT-TYPE
            SYNTAX IpAddress
            MAX-ACCESS read-write
            STATUS current
            DESCRIPTION
                "Primary DNS address configured in the Controller."
            ::= { dnsObjects 1 }


        -- 1.3.6.1.4.1.4329.15.3.2.2.2
        secondaryDNS OBJECT-TYPE
            SYNTAX IpAddress
            MAX-ACCESS read-write
            STATUS current
            DESCRIPTION
                "Secondary DNS address configured in the Controller."
            ::= { dnsObjects 2 }


        -- 1.3.6.1.4.1.4329.15.3.2.2.3
        tertiaryDNS OBJECT-TYPE
            SYNTAX IpAddress
            MAX-ACCESS read-write
            STATUS current
            DESCRIPTION
                "Third DNS address configured in the Controller."
            ::= { dnsObjects 3 }


        -- 1.3.6.1.4.1.4329.15.3.2.3
        mgmtPortObjects OBJECT IDENTIFIER ::= { hiPathWirelessController 3 }


        -- 1.3.6.1.4.1.4329.15.3.2.3.1
        mgmtPortIfIndex OBJECT-TYPE
            SYNTAX Integer32
            MAX-ACCESS read-only
            STATUS current
            DESCRIPTION
                "ifIndex of the management port."
            ::= { mgmtPortObjects 1 }


        -- 1.3.6.1.4.1.4329.15.3.2.3.2
        mgmtPortHostname OBJECT-TYPE
            SYNTAX DisplayString
            MAX-ACCESS read-write
            STATUS current
            DESCRIPTION
                "Hostname of the management port."
            ::= { mgmtPortObjects 2 }


        -- 1.3.6.1.4.1.4329.15.3.2.3.5
        mgmtPortDomain OBJECT-TYPE
            SYNTAX DisplayString
            MAX-ACCESS read-write
            STATUS current
            DESCRIPTION
                "Domain of the management port."
            ::= { mgmtPortObjects 5 }


        -- 1.3.6.1.4.1.4329.15.3.2.4
        physicalPortObjects OBJECT IDENTIFIER ::= { hiPathWirelessController 4 }


        -- 1.3.6.1.4.1.4329.15.3.2.4.1
        physicalPortCount OBJECT-TYPE
            SYNTAX Integer32
            MAX-ACCESS read-only
            STATUS current
            DESCRIPTION
                "Number of rows in routerPortsTable."
            ::= { physicalPortObjects 1 }


        -- 1.3.6.1.4.1.4329.15.3.2.4.2
        physicalPortsTable OBJECT-TYPE
            SYNTAX SEQUENCE OF PhysicalPortsEntry
            MAX-ACCESS not-accessible
            STATUS deprecated
            DESCRIPTION
                "Table of router ports on the controller."
            ::= { physicalPortObjects 2 }


        -- 1.3.6.1.4.1.4329.15.3.2.4.2.1
        physicalPortsEntry OBJECT-TYPE
            SYNTAX PhysicalPortsEntry
            MAX-ACCESS not-accessible
            STATUS deprecated
            DESCRIPTION
                "An entry in routerPortsTable."
            INDEX { ifIndex }
            ::= { physicalPortsTable 1 }


        PhysicalPortsEntry ::=
            SEQUENCE { 
                portMgmtTrafficEnable
                    TruthValue,
                portDuplexMode
                    INTEGER,
                portFunction
                    INTEGER,
                portEnabled
                    INTEGER,
                portName
                    OCTET STRING,
                portIpAddress
                    IpAddress,
                portMask
                    IpAddress,
                portMacAddress
                    MacAddress,
                portVlanID
                    Integer32,
                portDHCPEnable
                    TruthValue,
                portDHCPGateway
                    DisplayString,
                portDHCPDomain
                    DisplayString,
                portDHCPDefaultLease
                    Integer32,
                portDHCPMaxLease
                    Integer32,
                portDHCPDnsServers
                    DisplayString,
                portDHCPWins
                    DisplayString
             }

        -- 1.3.6.1.4.1.4329.15.3.2.4.2.1.1
        portMgmtTrafficEnable OBJECT-TYPE
            SYNTAX TruthValue
            MAX-ACCESS read-write
            STATUS deprecated
            DESCRIPTION
                "Determines whether controller management 
                network traffic is allowed over this interface."
            ::= { physicalPortsEntry 1 }


        -- 1.3.6.1.4.1.4329.15.3.2.4.2.1.2
        portDuplexMode OBJECT-TYPE
            SYNTAX INTEGER
                {
                full(1),
                half(2),
                auto(3)
                }
            MAX-ACCESS read-write
            STATUS deprecated
            DESCRIPTION
                "Duplex mode for the esa ports."
            ::= { physicalPortsEntry 2 }


        -- 1.3.6.1.4.1.4329.15.3.2.4.2.1.3
        portFunction OBJECT-TYPE
            SYNTAX INTEGER
                {
                router(1),
                host(2),
                thirdPartyAP(3)
                }
            MAX-ACCESS read-write
            STATUS deprecated
            DESCRIPTION
                "Specifies the behavior of the EWC physical ports."
            ::= { physicalPortsEntry 3 }


        -- 1.3.6.1.4.1.4329.15.3.2.4.2.1.4
        portEnabled OBJECT-TYPE
            SYNTAX INTEGER
                {
                enabled(1),
                disabled(2)
                }
            MAX-ACCESS read-write
            STATUS deprecated
            DESCRIPTION
                "If enabled, the interface administratively is enabled."
            ::= { physicalPortsEntry 4 }


        -- 1.3.6.1.4.1.4329.15.3.2.4.2.1.5
        portName OBJECT-TYPE
            SYNTAX OCTET STRING
            MAX-ACCESS read-only
            STATUS deprecated
            DESCRIPTION
                "A textual string containing information about the port."
            ::= { physicalPortsEntry 5 }


        -- 1.3.6.1.4.1.4329.15.3.2.4.2.1.6
        portIpAddress OBJECT-TYPE
            SYNTAX IpAddress
            MAX-ACCESS read-write
            STATUS deprecated
            DESCRIPTION
                "The IP address of this port."
            ::= { physicalPortsEntry 6 }


        -- 1.3.6.1.4.1.4329.15.3.2.4.2.1.7
        portMask OBJECT-TYPE
            SYNTAX IpAddress
            MAX-ACCESS read-write
            STATUS deprecated
            DESCRIPTION
                "The subnet mask associated with the IP address of this port."
            ::= { physicalPortsEntry 7 }


        -- 1.3.6.1.4.1.4329.15.3.2.4.2.1.8
        portMacAddress OBJECT-TYPE
            SYNTAX MacAddress
            MAX-ACCESS read-only
            STATUS deprecated
            DESCRIPTION
                "Port's MAC address."
            ::= { physicalPortsEntry 8 }


        -- 1.3.6.1.4.1.4329.15.3.2.4.2.1.9
        portVlanID OBJECT-TYPE
            SYNTAX Integer32 (-1..4094)
            MAX-ACCESS read-write
            STATUS deprecated
            DESCRIPTION
                "External VLAN tag for the physical port for trasmitted and received packets.
                Value ranges: (-1) it is not tagged, zero(0) means reserved, 1-4094 tag value."
            DEFVAL { -1 }
            ::= { physicalPortsEntry 9 }


        -- 1.3.6.1.4.1.4329.15.3.2.4.2.1.10
        portDHCPEnable OBJECT-TYPE
            SYNTAX TruthValue
            MAX-ACCESS read-write
            STATUS deprecated
            DESCRIPTION
                "If enabled, the controller is configured as default DHCP server for AP."
            ::= { physicalPortsEntry 10 }


        -- 1.3.6.1.4.1.4329.15.3.2.4.2.1.11
        portDHCPGateway OBJECT-TYPE
            SYNTAX DisplayString
            MAX-ACCESS read-write
            STATUS deprecated
            DESCRIPTION
                "Gateway address to be supplied to the wireless clients if controller is
                configured as default DHCP server for AP."
            ::= { physicalPortsEntry 11 }


        -- 1.3.6.1.4.1.4329.15.3.2.4.2.1.12
        portDHCPDomain OBJECT-TYPE
            SYNTAX DisplayString
            MAX-ACCESS read-write
            STATUS deprecated
            DESCRIPTION
                "Domain name to be supplied to the wireless clients if controller is
                configured as default DHCP server for AP."
            ::= { physicalPortsEntry 12 }


        -- 1.3.6.1.4.1.4329.15.3.2.4.2.1.13
        portDHCPDefaultLease OBJECT-TYPE
            SYNTAX Integer32
            MAX-ACCESS read-write
            STATUS deprecated
            DESCRIPTION
                "Default DHCP lease time in seconds to be supplied to the wireless
                clients if controller is configured as default DHCP server for AP."
            ::= { physicalPortsEntry 13 }


        -- 1.3.6.1.4.1.4329.15.3.2.4.2.1.14
        portDHCPMaxLease OBJECT-TYPE
            SYNTAX Integer32
            MAX-ACCESS read-write
            STATUS deprecated
            DESCRIPTION
                "Maximum DHCP lease time in seconds to be supplied to the wireless
                clients if controller is configured as default DHCP server for AP."
            ::= { physicalPortsEntry 14 }


        -- 1.3.6.1.4.1.4329.15.3.2.4.2.1.15
        portDHCPDnsServers OBJECT-TYPE
            SYNTAX DisplayString
            MAX-ACCESS read-write
            STATUS deprecated
            DESCRIPTION
                "List of DNSs to be supplied to the wireless clients if controller is
                configured as default DHCP server for AP."
            ::= { physicalPortsEntry 15 }


        -- 1.3.6.1.4.1.4329.15.3.2.4.2.1.16
        portDHCPWins OBJECT-TYPE
            SYNTAX DisplayString
            MAX-ACCESS read-write
            STATUS deprecated
            DESCRIPTION
                "List of WINSs to be supplied to the wireless clients if controller is
                configured as default DHCP server for AP."
            ::= { physicalPortsEntry 16 }


        -- 1.3.6.1.4.1.4329.15.3.2.4.3
        physicalPortsInternalVlanID OBJECT-TYPE
            SYNTAX Integer32 (-1..4094)
            MAX-ACCESS read-write
            STATUS current
            DESCRIPTION
                "Internal VLAN tag to be used for physical ports for which the exernal 
                VLAN tag have not been configured.
                Value ranges: (-1) it is not tagged, zero(0) means reserved, 1-4094 tag value."
            DEFVAL { 1 }
            ::= { physicalPortObjects 3 }


        -- 1.3.6.1.4.1.4329.15.3.2.4.4
        physicalFlash OBJECT-TYPE
            SYNTAX INTEGER
                {
                mounted(1),
                unmounted(2)
                }
            MAX-ACCESS read-only
            STATUS current
            DESCRIPTION
                "Flash drive status."
            ::= { physicalPortObjects 4 }


        -- 1.3.6.1.4.1.4329.15.3.2.4.5
        phyDHCPRangeTable OBJECT-TYPE
            SYNTAX SEQUENCE OF PhyDHCPRangeEntry
            MAX-ACCESS not-accessible
            STATUS deprecated
            DESCRIPTION
                "phyDHCPRangeTable contains the IP address ranges that DHCP
                will serve to clients associated with physical ports."
            ::= { physicalPortObjects 5 }


        -- 1.3.6.1.4.1.4329.15.3.2.4.5.1
        phyDHCPRangeEntry OBJECT-TYPE
            SYNTAX PhyDHCPRangeEntry
            MAX-ACCESS not-accessible
            STATUS deprecated
            DESCRIPTION
                "Configuration information for a DHCP range."
            INDEX { ifIndex, phyDHCPRangeIndex }
            ::= { phyDHCPRangeTable 1 }


        PhyDHCPRangeEntry ::=
            SEQUENCE { 
                phyDHCPRangeIndex
                    Integer32,
                phyDHCPRangeStart
                    IpAddress,
                phyDHCPRangeEnd
                    IpAddress,
                phyDHCPRangeType
                    INTEGER,
                phyDHCPRangeStatus
                    RowStatus
             }

        -- 1.3.6.1.4.1.4329.15.3.2.4.5.1.1
        phyDHCPRangeIndex OBJECT-TYPE
            SYNTAX Integer32 (1..2147483647)
            MAX-ACCESS read-write
            STATUS deprecated
            DESCRIPTION
                "Index for the DHCP row element."
            ::= { phyDHCPRangeEntry 1 }


        -- 1.3.6.1.4.1.4329.15.3.2.4.5.1.2
        phyDHCPRangeStart OBJECT-TYPE
            SYNTAX IpAddress
            MAX-ACCESS read-write
            STATUS deprecated
            DESCRIPTION
                "First IP address in the range."
            ::= { phyDHCPRangeEntry 2 }


        -- 1.3.6.1.4.1.4329.15.3.2.4.5.1.3
        phyDHCPRangeEnd OBJECT-TYPE
            SYNTAX IpAddress
            MAX-ACCESS read-write
            STATUS deprecated
            DESCRIPTION
                "Last IP address in the range."
            ::= { phyDHCPRangeEntry 3 }


        -- 1.3.6.1.4.1.4329.15.3.2.4.5.1.4
        phyDHCPRangeType OBJECT-TYPE
            SYNTAX INTEGER
                {
                inclusion(1),
                exclusion(2)
                }
            MAX-ACCESS read-write
            STATUS deprecated
            DESCRIPTION
                "Determines whether addresses in the specified range will 
                be included, or excluded by the DHCP server."
            ::= { phyDHCPRangeEntry 4 }


        -- 1.3.6.1.4.1.4329.15.3.2.4.5.1.5
        phyDHCPRangeStatus OBJECT-TYPE
            SYNTAX RowStatus
            MAX-ACCESS read-write
            STATUS deprecated
            DESCRIPTION
                "Row status variable for row operations on the phyDHCPRangeTable"
            ::= { phyDHCPRangeEntry 5 }


        -- 1.3.6.1.4.1.4329.15.3.2.4.6
        layerTwoPortTable OBJECT-TYPE
            SYNTAX SEQUENCE OF LayerTwoPortEntry
            MAX-ACCESS not-accessible
            STATUS current
            DESCRIPTION
                "This table contains all layer two ports."
            ::= { physicalPortObjects 6 }


        -- 1.3.6.1.4.1.4329.15.3.2.4.6.1
        layerTwoPortEntry OBJECT-TYPE
            SYNTAX LayerTwoPortEntry
            MAX-ACCESS not-accessible
            STATUS current
            DESCRIPTION
                "Entry for a layer two port."
            INDEX { ifIndex }
            ::= { layerTwoPortTable 1 }


        LayerTwoPortEntry ::=
            SEQUENCE { 
                layerTwoPortName
                    DisplayString,
                layerTwoPortMgmtState
                    INTEGER,
                layerTwoPortMacAddress
                    MacAddress
             }

        -- 1.3.6.1.4.1.4329.15.3.2.4.6.1.1
        layerTwoPortName OBJECT-TYPE
            SYNTAX DisplayString (SIZE (1..32))
            MAX-ACCESS read-only
            STATUS current
            DESCRIPTION
                "Text string identifying the port within the controller."
            ::= { layerTwoPortEntry 1 }


        -- 1.3.6.1.4.1.4329.15.3.2.4.6.1.2
        layerTwoPortMgmtState OBJECT-TYPE
            SYNTAX INTEGER
                {
                disabled(0),
                enabled(1)
                }
            MAX-ACCESS read-write
            STATUS current
            DESCRIPTION
                "This value indicates administrator state of the port. "
            DEFVAL { enabled }
            ::= { layerTwoPortEntry 2 }


        -- 1.3.6.1.4.1.4329.15.3.2.4.6.1.3
        layerTwoPortMacAddress OBJECT-TYPE
            SYNTAX MacAddress
            MAX-ACCESS read-only
            STATUS current
            DESCRIPTION
                "Port's MAC address."
            ::= { layerTwoPortEntry 3 }

        -- 1.3.6.1.4.1.4329.15.3.2.4.7
        jumboFrames OBJECT-TYPE
            SYNTAX INTEGER
                {
                disabled(0),
                enabled(1)
                }
            MAX-ACCESS read-write
            STATUS current
            DESCRIPTION
                "Enables support for frames up to 1800 bytes long. jumboFrames support only 
                 applies to the controller and compatible APs."
            ::= { physicalPortObjects 7 }



        -- 1.3.6.1.4.1.4329.15.3.2.5
        vnManagerObjects OBJECT IDENTIFIER ::= { hiPathWirelessController 5 }


        -- 1.3.6.1.4.1.4329.15.3.2.5.1
        vnRole OBJECT-TYPE
            SYNTAX INTEGER
                {
                none(1),
                vnMgr(2),
                vnAgent(3)
                }
            MAX-ACCESS read-write
            STATUS current
            DESCRIPTION
                "Specifies the role of this EWC in inter-EWC mobility.  
                None indicates that mobile units cannot roam to or 
                from this EWC.  In any EWC cluster, only one EWC should
                be specified as vnMgr, all others should be have 
                vnRole = vnAgent."
            ::= { vnManagerObjects 1 }


        -- 1.3.6.1.4.1.4329.15.3.2.5.2
        vnIfIndex OBJECT-TYPE
            SYNTAX Integer32
            MAX-ACCESS read-write
            STATUS current
            DESCRIPTION
                "ifIndex of the physical port where inter-EWC tunnels terminate.
                This field has meaning if vnRole is not none(1)"
            ::= { vnManagerObjects 2 }


        -- 1.3.6.1.4.1.4329.15.3.2.5.3
        vnHeartbeatInterval OBJECT-TYPE
            SYNTAX Integer32
            MAX-ACCESS read-write
            STATUS current
            DESCRIPTION
                "The time interval between inter-EWC polling messages.
                This field has meaning if vnRole is not none(1)"
            ::= { vnManagerObjects 3 }


        -- 1.3.6.1.4.1.4329.15.3.2.5.4
        vnLocalClients OBJECT-TYPE
            SYNTAX Counter32
            MAX-ACCESS read-only
            STATUS current
            DESCRIPTION
                "Number of locally associated clients to this controller that is considered to be 
                their home controller in the mobility zone, which this controller is part of."
            ::= { vnManagerObjects 4 }


        -- 1.3.6.1.4.1.4329.15.3.2.5.5
        vnForeignClients OBJECT-TYPE
            SYNTAX Counter32
            MAX-ACCESS read-only
            STATUS current
            DESCRIPTION
                "Number of clients that have registered with another controller in the mobility zone,
                which this controller is part of, and currently have roamed to this controller."
            ::= { vnManagerObjects 5 }


        -- 1.3.6.1.4.1.4329.15.3.2.5.6
        vnTotalClients OBJECT-TYPE
            SYNTAX Counter32
            MAX-ACCESS read-only
            STATUS current
            DESCRIPTION
                "Number of local and foreign clients on this controller in the Mobility zone."
            ::= { vnManagerObjects 6 }


        -- 1.3.6.1.4.1.4329.15.3.2.6
        ntpObjects OBJECT IDENTIFIER ::= { hiPathWirelessController 6 }


        -- 1.3.6.1.4.1.4329.15.3.2.6.1
        ntpEnabled OBJECT-TYPE
            SYNTAX TruthValue
            MAX-ACCESS read-write
            STATUS current
            DESCRIPTION
                "Enable or disables support for the Network Time Protocol (NTP)."
            ::= { ntpObjects 1 }


        -- 1.3.6.1.4.1.4329.15.3.2.6.2
        ntpTimezone OBJECT-TYPE
            SYNTAX DisplayString
            MAX-ACCESS read-write
            STATUS current
            DESCRIPTION
                "Specifies the time zone where this EWC resides."
            ::= { ntpObjects 2 }


        -- 1.3.6.1.4.1.4329.15.3.2.6.3
        ntpTimeServer1 OBJECT-TYPE
            SYNTAX DisplayString
            MAX-ACCESS read-write
            STATUS current
            DESCRIPTION
                "Primary NTP server."
            ::= { ntpObjects 3 }


        -- 1.3.6.1.4.1.4329.15.3.2.6.4
        ntpTimeServer2 OBJECT-TYPE
            SYNTAX DisplayString
            MAX-ACCESS read-write
            STATUS current
            DESCRIPTION
                "Secondary NTP server."
            ::= { ntpObjects 4 }


        -- 1.3.6.1.4.1.4329.15.3.2.6.5
        ntpTimeServer3 OBJECT-TYPE
            SYNTAX DisplayString
            MAX-ACCESS read-write
            STATUS current
            DESCRIPTION
                "Tertiary NTP server."
            ::= { ntpObjects 5 }


        -- 1.3.6.1.4.1.4329.15.3.2.6.6
        ntpServerEnabled OBJECT-TYPE
            SYNTAX TruthValue
            MAX-ACCESS read-write
            STATUS current
            DESCRIPTION
                "Enable or disables support for controller as NTP server."
            ::= { ntpObjects 6 }


        -- 1.3.6.1.4.1.4329.15.3.2.7
        controllerStats OBJECT IDENTIFIER ::= { hiPathWirelessController 7 }


        -- 1.3.6.1.4.1.4329.15.3.2.7.1
        tunnelsTxRxBytes OBJECT-TYPE
            SYNTAX Counter64
            MAX-ACCESS read-only
            STATUS current
            DESCRIPTION
                "Sum of transmitted and received bytes over all existing tunnels."
            ::= { controllerStats 1 }


        -- 1.3.6.1.4.1.4329.15.3.2.7.6
        tunnelCount OBJECT-TYPE
            SYNTAX Integer32
            MAX-ACCESS read-only
            STATUS current
            DESCRIPTION
                "Number of connections to other WirelessController controllers."
            ::= { controllerStats 6 }


        -- 1.3.6.1.4.1.4329.15.3.2.7.7
        tunnelStatsTable OBJECT-TYPE
            SYNTAX SEQUENCE OF TunnelStatsEntry
            MAX-ACCESS not-accessible
            STATUS current
            DESCRIPTION
                "tunnelStatsTable contains a list of the IP tunnels connected 
                to this EWC for use in inter-EWC mobility."
            ::= { controllerStats 7 }


        -- 1.3.6.1.4.1.4329.15.3.2.7.7.1
        tunnelStatsEntry OBJECT-TYPE
            SYNTAX TunnelStatsEntry
            MAX-ACCESS not-accessible
            STATUS current
            DESCRIPTION
                "Statistics for a mobility tunnel."
            INDEX { tunnelStartIP, tunnelEndIP }
            ::= { tunnelStatsTable 1 }


        TunnelStatsEntry ::=
            SEQUENCE { 
                tunnelStartIP
                    IpAddress,
                tunnelStartHWC
                    OCTET STRING,
                tunnelEndIP
                    IpAddress,
                tunnelEndHWC
                    OCTET STRING,
                tunnelStatus
                    INTEGER,
                tunnelStatsTxBytes
                    Counter32,
                tunnelStatsRxBytes
                    Counter32,
                tunnelStatsTxRxBytes
                    Counter32
             }

        -- 1.3.6.1.4.1.4329.15.3.2.7.7.1.1
        tunnelStartIP OBJECT-TYPE
            SYNTAX IpAddress
            MAX-ACCESS read-write
            STATUS current
            DESCRIPTION
                "IP address for the start of the tunnel."
            ::= { tunnelStatsEntry 1 }


        -- 1.3.6.1.4.1.4329.15.3.2.7.7.1.2
        tunnelStartHWC OBJECT-TYPE
            SYNTAX OCTET STRING
            MAX-ACCESS read-write
            STATUS current
            DESCRIPTION
                "Name of the access controller for the start of the tunnel."
            ::= { tunnelStatsEntry 2 }


        -- 1.3.6.1.4.1.4329.15.3.2.7.7.1.3
        tunnelEndIP OBJECT-TYPE
            SYNTAX IpAddress
            MAX-ACCESS read-write
            STATUS current
            DESCRIPTION
                "IP address for the end of the tunnel."
            ::= { tunnelStatsEntry 3 }


        -- 1.3.6.1.4.1.4329.15.3.2.7.7.1.4
        tunnelEndHWC OBJECT-TYPE
            SYNTAX OCTET STRING
            MAX-ACCESS read-write
            STATUS current
            DESCRIPTION
                "Name of the access controller for the end of the tunnel."
            ::= { tunnelStatsEntry 4 }


        -- 1.3.6.1.4.1.4329.15.3.2.7.7.1.5
        tunnelStatus OBJECT-TYPE
            SYNTAX INTEGER
                {
                disconnected(1),
                connected(2)
                }
            MAX-ACCESS read-write
            STATUS current
            DESCRIPTION
                "Indicates if the mobility tunnel is up or down."
            ::= { tunnelStatsEntry 5 }


        -- 1.3.6.1.4.1.4329.15.3.2.7.7.1.6
        tunnelStatsTxBytes OBJECT-TYPE
            SYNTAX Counter32
            MAX-ACCESS read-only
            STATUS current
            DESCRIPTION
                "Number of bytes have been transmitted from the controller at the start of the tunnel to 
                the controller on the other end of the tunnel."
            ::= { tunnelStatsEntry 6 }


        -- 1.3.6.1.4.1.4329.15.3.2.7.7.1.7
        tunnelStatsRxBytes OBJECT-TYPE
            SYNTAX Counter32
            MAX-ACCESS read-only
            STATUS current
            DESCRIPTION
                "Number of bytes have been received by the controller at the end of the tunnel from the
                controller at the start of the tunnel."
            ::= { tunnelStatsEntry 7 }


        -- 1.3.6.1.4.1.4329.15.3.2.7.7.1.8
        tunnelStatsTxRxBytes OBJECT-TYPE
            SYNTAX Counter32
            MAX-ACCESS read-only
            STATUS current
            DESCRIPTION
                "Sum of transmitted and received bytes over this tunnel."
            ::= { tunnelStatsEntry 8 }





        -- 1.3.6.1.4.1.4329.15.3.2.7.8
        clearAccessRejectMsg OBJECT-TYPE
            SYNTAX INTEGER
                {
                clear(1)
                }
            MAX-ACCESS read-write
            STATUS current
            DESCRIPTION
                "Set this OID to one to erase the contents of the accessRejectMessage table. 
                The OID always returns 0 when read."
            ::= { controllerStats 8 }




        -- 1.3.6.1.4.1.4329.15.3.2.7.9
        accessRejectMsgTable OBJECT-TYPE
            SYNTAX SEQUENCE OF AccessRejectMsgEntry
            MAX-ACCESS not-accessible
            STATUS current
            DESCRIPTION
                "This table lists each of the reply messages returned in RADIUS Access-Reject messages
                and for each reply message, a count of the number of times it has been received."
            ::= { controllerStats 9 }


        -- 1.3.6.1.4.1.4329.15.3.2.7.9.1
        accessRejectMsgEntry OBJECT-TYPE
            SYNTAX AccessRejectMsgEntry
            MAX-ACCESS not-accessible
            STATUS current
            DESCRIPTION
                "One entry consisting of a unique Access-Reject Reply-Message (accessRejectReplyMessage) and
                count of this message."
            INDEX { armIndex }
            ::= { accessRejectMsgTable 1 }


        AccessRejectMsgEntry ::=
            SEQUENCE { 
                armIndex
                    Integer32,
                armCount
                       Counter64,
                   armReplyMessage
                       DisplayString
                       }


        -- 1.3.6.1.4.1.4329.15.3.2.7.9.1
        armIndex OBJECT-TYPE
            SYNTAX Integer32(1..100)
            MAX-ACCESS not-accessible
            STATUS current
            DESCRIPTION
                "A number uniquely identifying each conceptual row in the accessRejectMsgTable. "
            ::= { accessRejectMsgEntry 1 }

        -- 1.3.6.1.4.1.4329.15.3.2.7.9.2
        armCount OBJECT-TYPE
            SYNTAX Counter64
            MAX-ACCESS read-only
            STATUS current
            DESCRIPTION
                "Count of the number of times the controller has received an Access-Reject 
                response from a RADIUS server that contained the associated armReplyMessage."
            ::= { accessRejectMsgEntry 2 }



        -- 1.3.6.1.4.1.4329.15.3.2.7.9.3
        armReplyMessage OBJECT-TYPE
            SYNTAX DisplayString
            MAX-ACCESS read-only
            STATUS current
            DESCRIPTION
                "A reply message attribute received by the controller from a RADIUS server
                in an Access-Reject message." 
            ::= { accessRejectMsgEntry 3 }




        -- 1.3.6.1.4.1.4329.15.3.2.8
        availability OBJECT IDENTIFIER ::= { hiPathWirelessController 8 }


        -- 1.3.6.1.4.1.4329.15.3.2.8.1
        availabilityStatus OBJECT-TYPE
            SYNTAX INTEGER
                {
                standalone(0),
                paired(1)
                }
            MAX-ACCESS read-write
            STATUS current
            DESCRIPTION
                "This field can be used to enable or disable availability. If it is set to paired(1), 
                then availability is enabled on this controller, otherwise it is considered that
                the controller operates in stand-alone mode.  All other availability fields have no
                meaning if this field is set to standalone(0)."
            ::= { availability 1 }


        -- 1.3.6.1.4.1.4329.15.3.2.8.2
        pairIPAddress OBJECT-TYPE
            SYNTAX IpAddress
            MAX-ACCESS read-write
            STATUS current
            DESCRIPTION
                "IP address of paired controller in availability pairing mode."
            ::= { availability 2 }


        -- 1.3.6.1.4.1.4329.15.3.2.8.3
        hwcAvailabilityRank OBJECT-TYPE
            SYNTAX INTEGER
                {
                notConfigured(0),
                secondary(1),
                primary(2)
                }
            MAX-ACCESS read-write
            STATUS current
            DESCRIPTION
                "Rank of controller in Availability pairing mode. This is legacy field and applies to
                releases before 5.x and in current releases it is used for reporting only."
            ::= { availability 3 }


        -- 1.3.6.1.4.1.4329.15.3.2.8.4
        fastFailover OBJECT-TYPE
            SYNTAX INTEGER
                {
                disabled(0),
                enabled(1)
                }
            MAX-ACCESS read-write
            STATUS current
            DESCRIPTION
                "Enables or disables fast failover when controller operates in Availability pairing mode."
            ::= { availability 4 }


        -- 1.3.6.1.4.1.4329.15.3.2.8.5
        detectLinkFailure OBJECT-TYPE
            SYNTAX Unsigned32 (2..30)
            UNITS "seconds"
            MAX-ACCESS read-write
            STATUS current
            DESCRIPTION
                "Time to detect link failure between two controllers in availability pairing.
                The value can be set to values between 2-30 seconds"
            DEFVAL { 10 }
            ::= { availability 5 }


        -- 1.3.6.1.4.1.4329.15.3.2.8.6
        synchronizeSystemConfig OBJECT-TYPE
            SYNTAX TruthValue
            MAX-ACCESS read-write
            STATUS current
            DESCRIPTION
                "If this flag is set to enabled then system configuration is synchronized between 
                paired controllers operating in Availabilty pairing mode."
            ::= { availability 6 }


        -- 1.3.6.1.4.1.4329.15.3.2.8.7
        synchronizeGuestPort OBJECT-TYPE
            SYNTAX TruthValue
            MAX-ACCESS read-write
            STATUS current
            DESCRIPTION
                "If this flag is set to enabled then Guest Portal user accounts are synchronized between 
                paired controllers operating in Availabilty pairing mode."
            ::= { availability 7 }


        -- 1.3.6.1.4.1.4329.15.3.2.9
        secureConnection OBJECT IDENTIFIER ::= { hiPathWirelessController 9 }


        -- 1.3.6.1.4.1.4329.15.3.2.9.1
        weakCipherEnable OBJECT-TYPE
            SYNTAX INTEGER
                {
                disable(0),
                enable(1)
                }
            MAX-ACCESS read-write
            STATUS current
            DESCRIPTION
                "By default usage of weak cipher is enabled on EWC. Weak cipher can be disabled
                using this field. "
            ::= { secureConnection 1 }


        -- 1.3.6.1.4.1.4329.15.3.2.10
        dashboard OBJECT IDENTIFIER ::= { hiPathWirelessController 10 }


        -- 1.3.6.1.4.1.4329.15.3.2.10.1
        licensingInformation OBJECT IDENTIFIER ::= { dashboard 1 }


        -- 1.3.6.1.4.1.4329.15.3.2.10.1.1
        licenseRegulatoryDomain OBJECT-TYPE
            SYNTAX DisplayString
            MAX-ACCESS read-only
            STATUS current
            DESCRIPTION
                "Regulatory domain that this wireless controller system has been licensed
                for to operate."
            ::= { licensingInformation 1 }


        -- 1.3.6.1.4.1.4329.15.3.2.10.1.2
        licenseType OBJECT-TYPE
            SYNTAX INTEGER
                {
                permanent(1),
                temporary(2)
                }
            MAX-ACCESS read-only
            STATUS current
            DESCRIPTION
                "Type of license for the controller. Temporary lincese allows controller 
                to operate within defined number of days after which a permanent license
                is required for the operation of the controller system."
            ::= { licensingInformation 2 }


        -- 1.3.6.1.4.1.4329.15.3.2.10.1.3
        licenseDaysRemaining OBJECT-TYPE
            SYNTAX Unsigned32
            MAX-ACCESS read-only
            STATUS current
            DESCRIPTION
                "Number of days is left for the temporary license to expire. This value has
                meaning if the license type is temporary(1)."
            ::= { licensingInformation 3 }


        -- 1.3.6.1.4.1.4329.15.3.2.10.1.4
        licenseAvailableAP OBJECT-TYPE
            SYNTAX Unsigned32
            MAX-ACCESS read-only
            STATUS current
            DESCRIPTION
                "If licenseMode is standAlone, this is the maximum number of APs that can be 
                 active on the controller without violating the licensing agreement. If licenseMode 
                 is availabilityPaired, this is the maximum number of APs that can be active on 
                 both members of the availability pair without violating the licensing agreement."
            ::= { licensingInformation 4 }

        -- 1.3.6.1.4.1.4329.15.3.2.10.1.5
        licenseInServiceRadarAP OBJECT-TYPE
            SYNTAX Unsigned32
            MAX-ACCESS read-only
            STATUS current
            DESCRIPTION
                "If licenseMode is standalone this is the maximum number of APs that can be 
                 active on this controller and can operate as Guardians or in-service Radar APs 
                 without violating the licensing agreement. If licenseMode is availabilityPaired, 
                 this is the maximum number of APs that can be active on both members of the 
                 availability pair and can operate as Guardians or in-service Radar APs without 
                 violating the licensing agreement."
            ::= { licensingInformation 5 }


        -- 1.3.6.1.4.1.4329.15.3.2.10.1.6
        licenseMode OBJECT-TYPE
            SYNTAX INTEGER
                {
                standAlone(1),
                availabilityPaired(2)
                }
            MAX-ACCESS read-only
            STATUS current
            DESCRIPTION
                "License mode determines how to interpret the license capacity OIDs. licenseMode 
                 is standalone if the controller is not part of an availability pair. licenseMode is 
                 availabilityPaired if the controller is part of an availability pair."
            ::= { licensingInformation 6 }

        -- 1.3.6.1.4.1.4329.15.3.2.10.1.7
        licenseLocalAP OBJECT-TYPE
            SYNTAX Unsigned32
            MAX-ACCESS read-only
            STATUS current
            DESCRIPTION
                "The total number of AP capacity licenses installed on this controller. "
            ::= { licensingInformation 7 }

        -- 1.3.6.1.4.1.4329.15.3.2.10.1.8
        licenseForeignAP OBJECT-TYPE
            SYNTAX Unsigned32
            MAX-ACCESS read-only
            STATUS current
            DESCRIPTION
                "The total number of AP capacity licenses installed on this controller's availability partner."
            ::= { licensingInformation 8 }

        -- 1.3.6.1.4.1.4329.15.3.2.10.1.9
        licenseLocalRadarAP OBJECT-TYPE
            SYNTAX Unsigned32
            MAX-ACCESS read-only
            STATUS current
            DESCRIPTION
                "The total number of AP Radar capacity licenses installed on this controller."
            ::= { licensingInformation 9 }

        -- 1.3.6.1.4.1.4329.15.3.2.10.1.10
        licenseForeignRadarAP OBJECT-TYPE
            SYNTAX Unsigned32
            MAX-ACCESS read-only
            STATUS current
            DESCRIPTION
                "The total number of AP Radar capacity licenses installed on this controller's availability partner. "
            ::= { licensingInformation 10 }

        -- 1.3.6.1.4.1.4329.15.3.2.10.2
        stationsByProtocol OBJECT IDENTIFIER ::= { dashboard 2 }

        -- 1.3.6.1.4.1.4329.15.3.2.10.2.1
        stationsByProtocolA OBJECT-TYPE
            SYNTAX Unsigned32
            MAX-ACCESS read-only
            STATUS current
            DESCRIPTION
                "Number of stations using 802.11a mode to access the network."
            ::= { stationsByProtocol 1 }


        -- 1.3.6.1.4.1.4329.15.3.2.10.2.2
        stationsByProtocolB OBJECT-TYPE
            SYNTAX Unsigned32
            MAX-ACCESS read-only
            STATUS current
            DESCRIPTION
                "Number of stations using 802.11b mode to access the network."
            ::= { stationsByProtocol 2 }


        -- 1.3.6.1.4.1.4329.15.3.2.10.2.3
        stationsByProtocolG OBJECT-TYPE
            SYNTAX Unsigned32
            MAX-ACCESS read-only
            STATUS current
            DESCRIPTION
                "Number of stations using 802.11b mode to access the network."
            ::= { stationsByProtocol 3 }


        -- 1.3.6.1.4.1.4329.15.3.2.10.2.4
        stationsByProtocolN24 OBJECT-TYPE
            SYNTAX Unsigned32
            MAX-ACCESS read-only
            STATUS current
            DESCRIPTION
                "Number of stations using 802.11n mode with frequency of 2.4Gig to access
                the network."
            ::= { stationsByProtocol 4 }


        -- 1.3.6.1.4.1.4329.15.3.2.10.2.5
        stationsByProtocolN5 OBJECT-TYPE
            SYNTAX Unsigned32
            MAX-ACCESS read-only
            STATUS current
            DESCRIPTION
                "Number of stations using 802.11n mode with frequency of 5Gig to access
                the network."
            ::= { stationsByProtocol 5 }


        -- 1.3.6.1.4.1.4329.15.3.2.10.2.6
        stationsByProtocolUnavailable OBJECT-TYPE
            SYNTAX Unsigned32
            MAX-ACCESS read-only
            STATUS current
            DESCRIPTION
                "The total number of stations with sessions on this controller for which 
                 the 802.11 protocol type (a, b, g, n, ac) for which the protocol could 
                 not be determined."
            ::= { stationsByProtocol 6 }

        -- 1.3.6.1.4.1.4329.15.3.2.10.2.7
        stationsByProtocolError OBJECT-TYPE
            SYNTAX Unsigned32
            MAX-ACCESS read-only
            STATUS current
            DESCRIPTION
                "The total number of stations with sessions on this controller for which an AP 
                 reported an invalid (out of range) value as the station's 802.11 protocol type."
            ::= { stationsByProtocol 7 }

        -- 1.3.6.1.4.1.4329.15.3.2.10.2.8
        stationsByProtocolAC OBJECT-TYPE
            SYNTAX Unsigned32
            MAX-ACCESS read-only
            STATUS current
            DESCRIPTION
                "Number of stations using 802.11ac mode to access the network."
            ::= { stationsByProtocol 8 }



        -- 1.3.6.1.4.1.4329.15.3.2.10.3
        apByChannelTable OBJECT-TYPE
            SYNTAX SEQUENCE OF ApByChannelEntry
            MAX-ACCESS not-accessible
            STATUS current
            DESCRIPTION
                "List of aggregated access points that are operating on a specific wireless
                channels."
            ::= { dashboard 3 }


        -- 1.3.6.1.4.1.4329.15.3.2.10.3.1
        apByChannelEntry OBJECT-TYPE
            SYNTAX ApByChannelEntry
            MAX-ACCESS not-accessible
            STATUS current
            DESCRIPTION
                "An entry in this table for one wireless channel and aggregated access point
                on that channel."
            INDEX { apByChannelNumber }
            ::= { apByChannelTable 1 }


        ApByChannelEntry ::=
            SEQUENCE { 
                apByChannelNumber
                    Unsigned32,
                apByChannelAPs
                    Unsigned32
             }

        -- 1.3.6.1.4.1.4329.15.3.2.10.3.1.1
        apByChannelNumber OBJECT-TYPE
            SYNTAX Unsigned32
            MAX-ACCESS not-accessible
            STATUS current
            DESCRIPTION
                "The channel on which a set of access points are presently operating.
                  If this number is 0, this means the AP is in Guardian mode or the AP's radios
                  are turned off."
            ::= { apByChannelEntry 1 }


        -- 1.3.6.1.4.1.4329.15.3.2.10.3.1.2
        apByChannelAPs OBJECT-TYPE
            SYNTAX Unsigned32
            MAX-ACCESS read-only
            STATUS current
            DESCRIPTION
                "Total number of the access point on the channel that this row is indexed on."
            ::= { apByChannelEntry 2 }


        -- 1.3.6.1.4.1.4329.15.3.3
        virtualNetworks OBJECT IDENTIFIER ::= { hiPathWirelessMgmt 3 }


        -- 1.3.6.1.4.1.4329.15.3.3.1
        vnsConfigObjects OBJECT IDENTIFIER ::= { virtualNetworks 1 }


        -- 1.3.6.1.4.1.4329.15.3.3.1.1
        vnsCount OBJECT-TYPE
            SYNTAX Integer32
            MAX-ACCESS read-only
            STATUS current
            DESCRIPTION
                "Number of VNSes defined in vnsConfigTable."
            ::= { vnsConfigObjects 1 }


        -- 1.3.6.1.4.1.4329.15.3.3.1.2
        vnsConfigTable OBJECT-TYPE
            SYNTAX SEQUENCE OF VnsConfigEntry
            MAX-ACCESS not-accessible
            STATUS current
            DESCRIPTION
                "Contains definitions of the Virtual Network Segments 
                defined on this WirelessController."
            ::= { vnsConfigObjects 2 }


        -- 1.3.6.1.4.1.4329.15.3.3.1.2.1
        vnsConfigEntry OBJECT-TYPE
            SYNTAX VnsConfigEntry
            MAX-ACCESS not-accessible
            STATUS current
            DESCRIPTION
                "Configuration elements for a specific Virtual Network Segment."
            INDEX { vnsIfIndex }
            ::= { vnsConfigTable 1 }

        VnsConfigEntry ::=
            SEQUENCE { 
                vnsDescription
                    DisplayString,
                vnsAssignmentMode
                    INTEGER,
                vnsMUSessionTimeout
                    Integer32,
                vnsAllowMulticast
                    TruthValue,
                vnsSSID
                    DisplayString,
                vnsDomain
                    DisplayString,
                vnsDNSServers
                    DisplayString,
                vnsWINSServers
                    DisplayString,
                vnsAuthModel
                    INTEGER,
                vnsParentIfIndex
                    Integer32,
                vnsMgmtTrafficEnable
                    TruthValue,
                vnsUseDHCPRelay
                    INTEGER,
                vns3rdPartyAP
                    TruthValue,
                vnsStatus
                    RowStatus,
                vnsMode
                    INTEGER,
                vnsVlanID
                    Integer32,
                vnsInterfaceName
                    OCTET STRING,
                vnsMgmIpAddress
                    IpAddress,
                vnsSuppressSSID
                    TruthValue,
                vnsEnable11hSupport
                    TruthValue,
                vnsApplyPowerBackOff
                    TruthValue,
                vnsProcessClientIEReq
                    TruthValue,
                vnsDLSSupportEnable
                    TruthValue,
                vnsDLSAddress
                    DisplayString,
                vnsDLSPort
                    Integer32,
                vnsRateControlProfile
                    DisplayString,
                vnsSessionAvailabilityEnable
                    TruthValue,
                vnsEnabled
                    INTEGER,
                vnsStrictSubnetAdherence
                    INTEGER,
                vnsSLPEnabled
                    INTEGER,
                vnsConfigWLANID
                    Unsigned32
             }

        -- 1.3.6.1.4.1.4329.15.3.3.1.2.1.1
        vnsDescription OBJECT-TYPE
            SYNTAX DisplayString
            MAX-ACCESS read-write
            STATUS current
            DESCRIPTION
                "Textual description of the VNS."
            ::= { vnsConfigEntry 1 }

        -- 1.3.6.1.4.1.4329.15.3.3.1.2.1.2
        vnsAssignmentMode OBJECT-TYPE
            SYNTAX INTEGER
                {
                ssid(1),
                aaa(2)
                }
            MAX-ACCESS read-write
            STATUS obsolete
            DESCRIPTION
                "Determines the method by which mobile units are assigned an 
                address within this VNS.  If vnsAssignmentMode = ssid, any 
                client with an SSID matching the VNS will be assigned an 
                address from this VNS.  If vnsAssignmentMode == aaa, then
                address assignment is not completed until after the user is
                authenticated."
            ::= { vnsConfigEntry 2 }

        -- 1.3.6.1.4.1.4329.15.3.3.1.2.1.3
        vnsMUSessionTimeout OBJECT-TYPE
            SYNTAX Integer32
            MAX-ACCESS read-write
            STATUS current
            DESCRIPTION
                "Client session idle time out, in seconds."
            ::= { vnsConfigEntry 3 }

        -- 1.3.6.1.4.1.4329.15.3.3.1.2.1.4
        vnsAllowMulticast OBJECT-TYPE
            SYNTAX TruthValue
            MAX-ACCESS read-write
            STATUS current
            DESCRIPTION
                "When true, allows IP multicast packets to be broadcast 
                to the clients on this VNS."
            ::= { vnsConfigEntry 4 }

        -- 1.3.6.1.4.1.4329.15.3.3.1.2.1.5
        vnsSSID OBJECT-TYPE
            SYNTAX DisplayString
            MAX-ACCESS read-write
            STATUS current
            DESCRIPTION
                "Service Set Identifier (i.e. Network Name) that will be 
                configured on the AccessPoints associated with this VNS."
            ::= { vnsConfigEntry 5 }

        -- 1.3.6.1.4.1.4329.15.3.3.1.2.1.6
        vnsDomain OBJECT-TYPE
            SYNTAX DisplayString
            MAX-ACCESS read-write
            STATUS current
            DESCRIPTION
                "Domain name to be supplied to the wireless clients if internal DHCP address assignment."
            ::= { vnsConfigEntry 6 }

        -- 1.3.6.1.4.1.4329.15.3.3.1.2.1.7
        vnsDNSServers OBJECT-TYPE
            SYNTAX DisplayString
            MAX-ACCESS read-write
            STATUS current
            DESCRIPTION
                "List of DNSs to be supplied to the wireless clients if internal DHCP address assignment."
            ::= { vnsConfigEntry 7 }

        -- 1.3.6.1.4.1.4329.15.3.3.1.2.1.8
        vnsWINSServers OBJECT-TYPE
            SYNTAX DisplayString
            MAX-ACCESS read-write
            STATUS current
            DESCRIPTION
                "List of WINSs to be supplied to the wireless clients if internal DHCP address assignment."
            ::= { vnsConfigEntry 8 }

        -- 1.3.6.1.4.1.4329.15.3.3.1.2.1.9
        vnsAuthModel OBJECT-TYPE
            SYNTAX INTEGER
                {
                none(1),
                captivePortal(2),
                dot1X(3)
                }
            MAX-ACCESS read-write
            STATUS current
            DESCRIPTION
                "vnsAuthModel specifies the authentication method used 
                for clients in the VNS.  None indicates that the VNS is
                open, and no authentication is required.
                vnsAuthModel=captivePortal may only be specified for 
                a VNS with vnsAssignmentMode=ssid.  Likewise, 
                vnsAuthModel=dot1X may only be specified for a VNS with
                vnsAssignmentMode=aaa."
            ::= { vnsConfigEntry 9 }

        -- 1.3.6.1.4.1.4329.15.3.3.1.2.1.10
        vnsParentIfIndex OBJECT-TYPE
            SYNTAX Integer32
            MAX-ACCESS read-write
            STATUS obsolete
            DESCRIPTION
                "Specifies the ifIndex of the parent VNS, if this VNS
                is a child.
                If this is a top level VNS, vnsParentIfIndex will return 
                null or 0."
            ::= { vnsConfigEntry 10 }

        -- 1.3.6.1.4.1.4329.15.3.3.1.2.1.11
        vnsMgmtTrafficEnable OBJECT-TYPE
            SYNTAX TruthValue
            MAX-ACCESS read-write
            STATUS current
            DESCRIPTION
                "Specifies whether clients in the VNS have access 
                to EWC management elements."
            ::= { vnsConfigEntry 11 }

        -- 1.3.6.1.4.1.4329.15.3.3.1.2.1.12
        vnsUseDHCPRelay OBJECT-TYPE
            SYNTAX INTEGER
                {
                none(0),
                dhcpRelay(1),
                localDhcp(2)
                }
            MAX-ACCESS read-write
            STATUS current
            DESCRIPTION
                "This variable indicates what type of DHCP is used for the VNS.
                none(0): No DHCP server on the VNS.
                dhcpRelay(1): Uses DHCP relay to reach the DHCP server.
                localDhcp(2): Uses local DHCP server on the controler."
            ::= { vnsConfigEntry 12 }

        -- 1.3.6.1.4.1.4329.15.3.3.1.2.1.13
        vns3rdPartyAP OBJECT-TYPE
            SYNTAX TruthValue
            MAX-ACCESS read-write
            STATUS current
            DESCRIPTION
                "When true, specifies that the VNS contains 3rd party 
                access points.  Only one such VNS may be defined for
                a WirelessController."
            ::= { vnsConfigEntry 13 }

        -- 1.3.6.1.4.1.4329.15.3.3.1.2.1.14
        vnsStatus OBJECT-TYPE
            SYNTAX RowStatus
            MAX-ACCESS read-write
            STATUS current
            DESCRIPTION
                "RowStatus variable for performing row operations on 
                vnsConfigTable."
            ::= { vnsConfigEntry 14 }

        
        -- 1.3.6.1.4.1.4329.15.3.3.1.2.1.15
        vnsMode OBJECT-TYPE
            SYNTAX INTEGER
                {
                routed(1),
                bridgeAtController(2),
                bridgeAtAP(3),
                wds(4),
                thirdParty(5)
                }
            MAX-ACCESS read-write
            STATUS current
            DESCRIPTION
                "Type of traffic for this VNS. 
                routed(1): The traffic is routed at the controller.
                bridgeAtController(2): Traffic is bridged at controller.
                bridgeAtAP(3): Traffic is bridged at Access Points.
                wds(4): Wireless Distributed System (WDS) type of VNS.
                
                If VNS is type of wds(4), then only vnsSupressSSID, 
                vnsDescription and vnsSSID has meaning."
            DEFVAL { routed }
            ::= { vnsConfigEntry 15 }

        
        -- 1.3.6.1.4.1.4329.15.3.3.1.2.1.16
        vnsVlanID OBJECT-TYPE
            SYNTAX Integer32 (-1..4094)
            MAX-ACCESS read-write
            STATUS current
            DESCRIPTION
                "VLAN tag for the packets trasmitted to/from of the VNS. This value has
                meaning if vnsMode is bridgeAtController(2) or bridgeAtAP(3).
                If vnsMode = bridgeAtController(2), tagging is done at controller.
                If vnsMode = bridgeAtAP(3), tagging is done at Access Point.
                Value ranges: (-1) it is not tagged, zero(0) means reserved, 1-4094 tag value."
            DEFVAL { -1 }
            ::= { vnsConfigEntry 16 }

        
        -- 1.3.6.1.4.1.4329.15.3.3.1.2.1.17
        vnsInterfaceName OBJECT-TYPE
            SYNTAX OCTET STRING
            MAX-ACCESS read-write
            STATUS current
            DESCRIPTION
                "Physical interface to be used in the controller for trasmitting/receiving packets
                for the VNS. This value has meaning if vnsMode is bridgeAtController(2)."
            ::= { vnsConfigEntry 17 }

        
        -- 1.3.6.1.4.1.4329.15.3.3.1.2.1.18
        vnsMgmIpAddress OBJECT-TYPE
            SYNTAX IpAddress
            MAX-ACCESS read-write
            STATUS current
            DESCRIPTION
                "IP address of the management port associated to this VNS.
                This value has meaning if vnsMode is bridgeAtController(2)."
            ::= { vnsConfigEntry 18 }

        
        -- 1.3.6.1.4.1.4329.15.3.3.1.2.1.19
        vnsSuppressSSID OBJECT-TYPE
            SYNTAX TruthValue
            MAX-ACCESS read-write
            STATUS current
            DESCRIPTION
                "If set to true, this prevents this SSID from appearing in the beacon message."
            ::= { vnsConfigEntry 19 }

        
        -- 1.3.6.1.4.1.4329.15.3.3.1.2.1.20
        vnsEnable11hSupport OBJECT-TYPE
            SYNTAX TruthValue
            MAX-ACCESS read-write
            STATUS current
            DESCRIPTION
                "If true, enables 802.11h support."
            ::= { vnsConfigEntry 20 }

        
        -- 1.3.6.1.4.1.4329.15.3.3.1.2.1.21
        vnsApplyPowerBackOff OBJECT-TYPE
            SYNTAX TruthValue
            MAX-ACCESS read-write
            STATUS current
            DESCRIPTION
                "Indicates whether the AP will direct 802.11h-enabled clients to
                apply the same power back-off setting that the AP is using"
            ::= { vnsConfigEntry 21 }

        
        -- 1.3.6.1.4.1.4329.15.3.3.1.2.1.22
        vnsProcessClientIEReq OBJECT-TYPE
            SYNTAX TruthValue
            MAX-ACCESS read-write
            STATUS current
            DESCRIPTION
                "If true, enables support for 802.11d client information request."
            ::= { vnsConfigEntry 22 }

        
        -- 1.3.6.1.4.1.4329.15.3.3.1.2.1.23
        vnsDLSSupportEnable OBJECT-TYPE
            SYNTAX TruthValue
            MAX-ACCESS read-write
            STATUS current
            DESCRIPTION
                "If true, enables support for DLS Support. This value has 
                meaning only if vnsUseDHCPRelay is selected as localDhcp(2) and
                vnsMode is select as either routed(1) or bridgeAtController(2)."
            ::= { vnsConfigEntry 23 }

        
        -- 1.3.6.1.4.1.4329.15.3.3.1.2.1.24
        vnsDLSAddress OBJECT-TYPE
            SYNTAX DisplayString
            MAX-ACCESS read-write
            STATUS current
            DESCRIPTION
                "DNS IP Address for DLS associated to this VNS. It could be IP address
                or Name"
            ::= { vnsConfigEntry 24 }

        
        -- 1.3.6.1.4.1.4329.15.3.3.1.2.1.25
        vnsDLSPort OBJECT-TYPE
            SYNTAX Integer32
            MAX-ACCESS read-write
            STATUS current
            DESCRIPTION
                "DNS Port for DLS associated to this VNS."
            DEFVAL { 18443 }
            ::= { vnsConfigEntry 25 }

        
        -- 1.3.6.1.4.1.4329.15.3.3.1.2.1.26
        vnsRateControlProfile OBJECT-TYPE
            SYNTAX DisplayString
            MAX-ACCESS read-write
            STATUS current
            DESCRIPTION
                "The Rate Control Profile that is referenced by this VNS."
            ::= { vnsConfigEntry 26 }

        
        -- 1.3.6.1.4.1.4329.15.3.3.1.2.1.27
        vnsSessionAvailabilityEnable OBJECT-TYPE
            SYNTAX TruthValue
            MAX-ACCESS read-write
            STATUS current
            DESCRIPTION
                "To indicate if Session Availability feature is enabled."
            ::= { vnsConfigEntry 27 }

        
        -- 1.3.6.1.4.1.4329.15.3.3.1.2.1.28
        vnsEnabled OBJECT-TYPE
            SYNTAX INTEGER
                {
                disabled(0),
                enabled(1)
                }
            MAX-ACCESS read-write
            STATUS current
            DESCRIPTION
                "VNS status of being enabled or disabled."
            ::= { vnsConfigEntry 28 }

        
        -- 1.3.6.1.4.1.4329.15.3.3.1.2.1.29
        vnsStrictSubnetAdherence OBJECT-TYPE
            SYNTAX INTEGER
                {
                disabled(0),
                enabled(1)
                }
            MAX-ACCESS read-write
            STATUS current
            DESCRIPTION
                "Subnet adherence verification status for the VNS. Controller only
                learns devices whose address is within range of VNS segment definition. 
                Disabling this field causes to not enforce validation. Doing so,
                may expose the controller to in-advertent Learning DoS attacks.
                "
            ::= { vnsConfigEntry 29 }

        
        -- 1.3.6.1.4.1.4329.15.3.3.1.2.1.30
        vnsSLPEnabled OBJECT-TYPE
            SYNTAX INTEGER
                {
                disabled(0),
                enabled(1)
                }
            MAX-ACCESS read-write
            STATUS current
            DESCRIPTION
                "Status of SLP flag on Bridge at Controller type VNS. This field does
                not have any meaning for other types of VNS."
            ::= { vnsConfigEntry 30 }

        
        -- 1.3.6.1.4.1.4329.15.3.3.1.2.1.31
        vnsConfigWLANID OBJECT-TYPE
            SYNTAX Unsigned32
            MAX-ACCESS read-write
            STATUS current
            DESCRIPTION
                "Creation of VNS requires existing of a free WLAN. One WLAN can only be used in 
                one VNS only.  This ID identifies the WLAN that is used for creation of VNS that is
                identified by this row."
            ::= { vnsConfigEntry 31 }

        
        -- 1.3.6.1.4.1.4329.15.3.3.1.3
        vnsDHCPRangeTable OBJECT-TYPE
            SYNTAX SEQUENCE OF VnsDHCPRangeEntry
            MAX-ACCESS not-accessible
            STATUS current
            DESCRIPTION
                "vnsDHCPRangeTable contains the IP address ranges that DHCP
                will serve to clients associated with this VNS."
            ::= { vnsConfigObjects 3 }

        
        -- 1.3.6.1.4.1.4329.15.3.3.1.3.1
        vnsDHCPRangeEntry OBJECT-TYPE
            SYNTAX VnsDHCPRangeEntry
            MAX-ACCESS not-accessible
            STATUS current
            DESCRIPTION
                "Configuration information for a DHCP range."
            INDEX { ifIndex, vnsDHCPRangeIndex }
            ::= { vnsDHCPRangeTable 1 }

        
        VnsDHCPRangeEntry ::=
            SEQUENCE { 
                vnsDHCPRangeIndex
                    Integer32,
                vnsDHCPRangeStart
                    IpAddress,
                vnsDHCPRangeEnd
                    IpAddress,
                vnsDHCPRangeType
                    INTEGER,
                vnsDHCPRangeStatus
                    RowStatus
             }

        -- 1.3.6.1.4.1.4329.15.3.3.1.3.1.1
        vnsDHCPRangeIndex OBJECT-TYPE
            SYNTAX Integer32 (1..2147483647)
            MAX-ACCESS read-write
            STATUS current
            DESCRIPTION
                "Index for the DHCP row element."
            ::= { vnsDHCPRangeEntry 1 }

        
        -- 1.3.6.1.4.1.4329.15.3.3.1.3.1.2
        vnsDHCPRangeStart OBJECT-TYPE
            SYNTAX IpAddress
            MAX-ACCESS read-write
            STATUS current
            DESCRIPTION
                "First IP address in the range."
            ::= { vnsDHCPRangeEntry 2 }

        
        -- 1.3.6.1.4.1.4329.15.3.3.1.3.1.3
        vnsDHCPRangeEnd OBJECT-TYPE
            SYNTAX IpAddress
            MAX-ACCESS read-write
            STATUS current
            DESCRIPTION
                "Last IP address in the range."
            ::= { vnsDHCPRangeEntry 3 }

        
        -- 1.3.6.1.4.1.4329.15.3.3.1.3.1.4
        vnsDHCPRangeType OBJECT-TYPE
            SYNTAX INTEGER
                {
                inclusion(1),
                exclusion(2)
                }
            MAX-ACCESS read-write
            STATUS current
            DESCRIPTION
                "Determines whether addresses in the specified range will 
                be included, or excluded by the DHCP server."
            ::= { vnsDHCPRangeEntry 4 }

        
        -- 1.3.6.1.4.1.4329.15.3.3.1.3.1.5
        vnsDHCPRangeStatus OBJECT-TYPE
            SYNTAX RowStatus
            MAX-ACCESS read-write
            STATUS current
            DESCRIPTION
                "Row status variable for row operations on the vnsDHCPRangeTable"
            ::= { vnsDHCPRangeEntry 5 }

        
        -- 1.3.6.1.4.1.4329.15.3.3.1.4
        vnsCaptivePortalTable OBJECT-TYPE
            SYNTAX SEQUENCE OF VnsCaptivePortalEntry
            MAX-ACCESS not-accessible
            STATUS current
            DESCRIPTION
                "Details of the Captive Portal login page for 
                VNSes that have vnsAssignment=ssid and 
                vnsAuthModel=captivePortal."
            ::= { vnsConfigObjects 4 }

        
        -- 1.3.6.1.4.1.4329.15.3.3.1.4.1
        vnsCaptivePortalEntry OBJECT-TYPE
            SYNTAX VnsCaptivePortalEntry
            MAX-ACCESS not-accessible
            STATUS current
            DESCRIPTION
                "Captive Portal Information for the VNS."
            INDEX { ifIndex }
            ::= { vnsCaptivePortalTable 1 }

        
        VnsCaptivePortalEntry ::=
            SEQUENCE { 
                cpURL
                    DisplayString,
                cpLoginLabel
                    DisplayString,
                cpPasswordLabel
                    DisplayString,
                cpHeaderURL
                    DisplayString,
                cpFooterURL
                    DisplayString,
                cpMessage
                    DisplayString,
                cpReplaceGatewayWithFQDN
                    DisplayString,
                cpDefaultRedirectionURL
                    DisplayString,
                cpConnectionIP
                    IpAddress,
                cpConnectionPort
                    Integer32,
                cpSharedSecret
                    OCTET STRING,
                cpLogOff
                    INTEGER,
                cpStatusCheck
                    INTEGER,
                cpType
                    INTEGER
             }

        -- 1.3.6.1.4.1.4329.15.3.3.1.4.1.1
        cpURL OBJECT-TYPE
            SYNTAX DisplayString
            MAX-ACCESS read-write
            STATUS current
            DESCRIPTION
                "Redirect URL of the Captive Portal login page."
            ::= { vnsCaptivePortalEntry 1 }

        
        -- 1.3.6.1.4.1.4329.15.3.3.1.4.1.2
        cpLoginLabel OBJECT-TYPE
            SYNTAX DisplayString
            MAX-ACCESS read-write
            STATUS deprecated
            DESCRIPTION
                "Label that appears in front of the login field
                on the Captive Portal login page."
            ::= { vnsCaptivePortalEntry 2 }

        
        -- 1.3.6.1.4.1.4329.15.3.3.1.4.1.3
        cpPasswordLabel OBJECT-TYPE
            SYNTAX DisplayString
            MAX-ACCESS read-write
            STATUS deprecated
            DESCRIPTION
                "Label that appears in front of the password field
                on the Captive Portal login page."
            ::= { vnsCaptivePortalEntry 3 }

        
        -- 1.3.6.1.4.1.4329.15.3.3.1.4.1.4
        cpHeaderURL OBJECT-TYPE
            SYNTAX DisplayString
            MAX-ACCESS read-write
            STATUS deprecated
            DESCRIPTION
                "URL of the Captive Portal header."
            ::= { vnsCaptivePortalEntry 4 }

        
        -- 1.3.6.1.4.1.4329.15.3.3.1.4.1.5
        cpFooterURL OBJECT-TYPE
            SYNTAX DisplayString
            MAX-ACCESS read-write
            STATUS deprecated
            DESCRIPTION
                "URL of the Captive Portal footer."
            ::= { vnsCaptivePortalEntry 5 }

        
        -- 1.3.6.1.4.1.4329.15.3.3.1.4.1.6
        cpMessage OBJECT-TYPE
            SYNTAX DisplayString
            MAX-ACCESS read-write
            STATUS deprecated
            DESCRIPTION
                "A welcome message, or set of instructions that is to 
                appear on the Captive Portal login page."
            ::= { vnsCaptivePortalEntry 6 }

        
        -- 1.3.6.1.4.1.4329.15.3.3.1.4.1.7
        cpReplaceGatewayWithFQDN OBJECT-TYPE
            SYNTAX DisplayString
            MAX-ACCESS read-write
            STATUS current
            DESCRIPTION
                "Fully Qualified Domain Name (FQDN) to be used as the gateway IP address."
            ::= { vnsCaptivePortalEntry 7 }

        
        -- 1.3.6.1.4.1.4329.15.3.3.1.4.1.8
        cpDefaultRedirectionURL OBJECT-TYPE
            SYNTAX DisplayString
            MAX-ACCESS read-write
            STATUS current
            DESCRIPTION
                "Default Redirect URL of the Captive Portal login page."
            ::= { vnsCaptivePortalEntry 8 }

        
        -- 1.3.6.1.4.1.4329.15.3.3.1.4.1.9
        cpConnectionIP OBJECT-TYPE
            SYNTAX IpAddress
            MAX-ACCESS read-write
            STATUS current
            DESCRIPTION
                "IP address of the Controller interface for Captive Portal."
            ::= { vnsCaptivePortalEntry 9 }

        
        -- 1.3.6.1.4.1.4329.15.3.3.1.4.1.10
        cpConnectionPort OBJECT-TYPE
            SYNTAX Integer32
            MAX-ACCESS read-write
            STATUS current
            DESCRIPTION
                "Port number on the cpConnectionIP interface."
            ::= { vnsCaptivePortalEntry 10 }

        
        -- 1.3.6.1.4.1.4329.15.3.3.1.4.1.11
        cpSharedSecret OBJECT-TYPE
            SYNTAX OCTET STRING
            MAX-ACCESS read-write
            STATUS current
            DESCRIPTION
                "Secret Key to be used to encrypt the information passed between the
                Controller and the external web server. It is the password common to
                both Controller and the external web server."
            ::= { vnsCaptivePortalEntry 11 }

        
        -- 1.3.6.1.4.1.4329.15.3.3.1.4.1.12
        cpLogOff OBJECT-TYPE
            SYNTAX INTEGER
                {
                off(0),
                on(1)
                }
            MAX-ACCESS read-write
            STATUS current
            DESCRIPTION
                "Toggles the display of logoff popup screen, allowing users to control their logoff."
            ::= { vnsCaptivePortalEntry 12 }

        
        -- 1.3.6.1.4.1.4329.15.3.3.1.4.1.13
        cpStatusCheck OBJECT-TYPE
            SYNTAX INTEGER
                {
                off(0),
                on(1)
                }
            MAX-ACCESS read-write
            STATUS current
            DESCRIPTION
                "Toggles the display of popup window with session statistics for users to
                monitor their usage and time left in session."
            ::= { vnsCaptivePortalEntry 13 }

        
        -- 1.3.6.1.4.1.4329.15.3.3.1.4.1.14
        cpType OBJECT-TYPE
            SYNTAX INTEGER
                {
                none(1),
                internal(2),
                external(4),
                guestPortal(5)
                }
            MAX-ACCESS read-write
            STATUS current
            DESCRIPTION
                "Type of captive portal is enabled for the selected VNS.
                none(1) = no captive portal configured or type is unknown.
                internal(2) = internal captive portal.
                external(4) = external captive portal.
                guestPortal (5) = open host captive portal."
            ::= { vnsCaptivePortalEntry 14 }

        
        -- 1.3.6.1.4.1.4329.15.3.3.1.5
        vnsRadiusServerTable OBJECT-TYPE
            SYNTAX SEQUENCE OF VnsRadiusServerEntry
            MAX-ACCESS not-accessible
            STATUS current
            DESCRIPTION
                "List of RADIUS servers to be utilized for authentication in the VNS."
            ::= { vnsConfigObjects 5 }

        
        -- 1.3.6.1.4.1.4329.15.3.3.1.5.1
        vnsRadiusServerEntry OBJECT-TYPE
            SYNTAX VnsRadiusServerEntry
            MAX-ACCESS not-accessible
            STATUS current
            DESCRIPTION
                "Configuration information for a RADIUS server."
            INDEX { ifIndex, vnsRadiusServerName }
            ::= { vnsRadiusServerTable 1 }

        
        VnsRadiusServerEntry ::=
            SEQUENCE { 
                vnsRadiusServerName
                    DisplayString,
                vnsRadiusServerPort
                    Integer32,
                vnsRadiusServerRetries
                    Integer32,
                vnsRadiusServerTimeout
                    Integer32,
                vnsRadiusServerSharedSecret
                    DisplayString,
                vnsRadiusServerNASIdentifier
                    DisplayString,
                vnsRadiusServerAuthType
                    INTEGER,
                vnsRadiusServerRowStatus
                    RowStatus,
                vnsRadiusServerNasAddress
                    IpAddress
             }

        -- 1.3.6.1.4.1.4329.15.3.3.1.5.1.1
        vnsRadiusServerName OBJECT-TYPE
            SYNTAX DisplayString (SIZE (0..64))
            MAX-ACCESS read-write
            STATUS current
            DESCRIPTION
                "Name of the RADIUS server."
            ::= { vnsRadiusServerEntry 1 }

        
        -- 1.3.6.1.4.1.4329.15.3.3.1.5.1.2
        vnsRadiusServerPort OBJECT-TYPE
            SYNTAX Integer32
            MAX-ACCESS read-write
            STATUS current
            DESCRIPTION
                "Port number for the RADIUS server."
            ::= { vnsRadiusServerEntry 2 }

        
        -- 1.3.6.1.4.1.4329.15.3.3.1.5.1.3
        vnsRadiusServerRetries OBJECT-TYPE
            SYNTAX Integer32
            MAX-ACCESS read-write
            STATUS current
            DESCRIPTION
                "Number of retries for a RADIUS authentication request."
            ::= { vnsRadiusServerEntry 3 }

        
        -- 1.3.6.1.4.1.4329.15.3.3.1.5.1.4
        vnsRadiusServerTimeout OBJECT-TYPE
            SYNTAX Integer32
            MAX-ACCESS read-write
            STATUS current
            DESCRIPTION
                "Delay between requests."
            ::= { vnsRadiusServerEntry 4 }

        
        -- 1.3.6.1.4.1.4329.15.3.3.1.5.1.5
        vnsRadiusServerSharedSecret OBJECT-TYPE
            SYNTAX DisplayString
            MAX-ACCESS read-write
            STATUS current
            DESCRIPTION
                "Shared secret to be used between the NAS and RADIUS server."
            ::= { vnsRadiusServerEntry 5 }

        
        -- 1.3.6.1.4.1.4329.15.3.3.1.5.1.6
        vnsRadiusServerNASIdentifier OBJECT-TYPE
            SYNTAX DisplayString
            MAX-ACCESS read-write
            STATUS current
            DESCRIPTION
                "NAS identifier to be included in RADIUS request."
            ::= { vnsRadiusServerEntry 6 }

        
        -- 1.3.6.1.4.1.4329.15.3.3.1.5.1.7
        vnsRadiusServerAuthType OBJECT-TYPE
            SYNTAX INTEGER
                {
                pap(0),
                chap(1),
                msChap(2),
                msChapV2(3),
                notApplicable(4)
                }
            MAX-ACCESS read-write
            STATUS current
            DESCRIPTION
                "Challenge mechanism for the request."
            ::= { vnsRadiusServerEntry 7 }

        
        -- 1.3.6.1.4.1.4329.15.3.3.1.5.1.8
        vnsRadiusServerRowStatus OBJECT-TYPE
            SYNTAX RowStatus
            MAX-ACCESS read-write
            STATUS current
            DESCRIPTION
                "RowStatus value for manipulating vnsRADIUSServerTable."
            ::= { vnsRadiusServerEntry 8 }

        
        -- 1.3.6.1.4.1.4329.15.3.3.1.5.1.9
        vnsRadiusServerNasAddress OBJECT-TYPE
            SYNTAX IpAddress
            MAX-ACCESS read-write
            STATUS current
            DESCRIPTION
                "NAS address to be included in RADIUS request."
            ::= { vnsRadiusServerEntry 9 }

        
        -- 1.3.6.1.4.1.4329.15.3.3.1.6
        vnsFilterIDTable OBJECT-TYPE
            SYNTAX SEQUENCE OF VnsFilterIDEntry
            MAX-ACCESS not-accessible
            STATUS current
            DESCRIPTION
                "Table of names filters for a VNS."
            ::= { vnsConfigObjects 6 }

        
        -- 1.3.6.1.4.1.4329.15.3.3.1.6.1
        vnsFilterIDEntry OBJECT-TYPE
            SYNTAX VnsFilterIDEntry
            MAX-ACCESS not-accessible
            STATUS current
            DESCRIPTION
                "Name of a specific filter in the VNS."
            INDEX { ifIndex, vnsFilterID }
            ::= { vnsFilterIDTable 1 }

        
        VnsFilterIDEntry ::=
            SEQUENCE { 
                vnsFilterID
                    DisplayString,
                vnsFilterIDStatus
                    RowStatus
             }

        -- 1.3.6.1.4.1.4329.15.3.3.1.6.1.1
        vnsFilterID OBJECT-TYPE
            SYNTAX DisplayString
            MAX-ACCESS read-write
            STATUS current
            DESCRIPTION
                "Filter names."
            ::= { vnsFilterIDEntry 1 }

        
        -- 1.3.6.1.4.1.4329.15.3.3.1.6.1.2
        vnsFilterIDStatus OBJECT-TYPE
            SYNTAX RowStatus
            MAX-ACCESS read-write
            STATUS current
            DESCRIPTION
                "RowStatus for operating on vnsFilterIDTable."
            ::= { vnsFilterIDEntry 2 }

        
        -- 1.3.6.1.4.1.4329.15.3.3.1.7
        vnsFilterRuleTable OBJECT-TYPE
            SYNTAX SEQUENCE OF VnsFilterRuleEntry
            MAX-ACCESS not-accessible
            STATUS current
            DESCRIPTION
                "Table containing specific filters for a named filter."
            ::= { vnsConfigObjects 7 }

        
        -- 1.3.6.1.4.1.4329.15.3.3.1.7.1
        vnsFilterRuleEntry OBJECT-TYPE
            SYNTAX VnsFilterRuleEntry
            MAX-ACCESS not-accessible
            STATUS current
            DESCRIPTION
                "Filter elements for an individual VNS filter."
            INDEX { ifIndex, vnsFilterID, vnsFilterRuleOrder }
            ::= { vnsFilterRuleTable 1 }

        
        VnsFilterRuleEntry ::=
            SEQUENCE { 
                vnsFilterRuleOrder
                    Integer32,
                vnsFilterRuleDirection
                    INTEGER,
                vnsFilterRuleAction
                    INTEGER,
                vnsFilterRuleIPAddress
                    IpAddress,
                vnsFilterRulePortLow
                    Integer32,
                vnsFilterRulePortHigh
                    Integer32,
                vnsFilterRuleProtocol
                    INTEGER,
                vnsFilterRuleEtherType
                    INTEGER,
                vnsFilterRuleStatus
                    RowStatus
             }

        -- 1.3.6.1.4.1.4329.15.3.3.1.7.1.1
        vnsFilterRuleOrder OBJECT-TYPE
            SYNTAX Integer32 (1..65532)
            MAX-ACCESS read-write
            STATUS current
            DESCRIPTION
                "Position of the filter in the filter list."
            ::= { vnsFilterRuleEntry 1 }

        
        -- 1.3.6.1.4.1.4329.15.3.3.1.7.1.2
        vnsFilterRuleDirection OBJECT-TYPE
            SYNTAX INTEGER
                {
                none(0),
                in(1),
                out(2),
                both(3)
                }
            MAX-ACCESS read-write
            STATUS current
            DESCRIPTION
                "Traffic direction defined by the rule."
            ::= { vnsFilterRuleEntry 2 }

        
        -- 1.3.6.1.4.1.4329.15.3.3.1.7.1.3
        vnsFilterRuleAction OBJECT-TYPE
            SYNTAX INTEGER
                {
                allow(1),
                disallow(2)
                }
            MAX-ACCESS read-write
            STATUS current
            DESCRIPTION
                "Allow or deny traffic for the filter."
            ::= { vnsFilterRuleEntry 3 }

        
        -- 1.3.6.1.4.1.4329.15.3.3.1.7.1.4
        vnsFilterRuleIPAddress OBJECT-TYPE
            SYNTAX IpAddress
            MAX-ACCESS read-write
            STATUS current
            DESCRIPTION
                "IP address to apply the filter."
            ::= { vnsFilterRuleEntry 4 }

        
        -- 1.3.6.1.4.1.4329.15.3.3.1.7.1.5
        vnsFilterRulePortLow OBJECT-TYPE
            SYNTAX Integer32
            MAX-ACCESS read-write
            STATUS current
            DESCRIPTION
                "Low port number for the filter."
            ::= { vnsFilterRuleEntry 5 }

        
        -- 1.3.6.1.4.1.4329.15.3.3.1.7.1.6
        vnsFilterRulePortHigh OBJECT-TYPE
            SYNTAX Integer32
            MAX-ACCESS read-write
            STATUS current
            DESCRIPTION
                "High port number for the filter."
            ::= { vnsFilterRuleEntry 6 }

        
        -- 1.3.6.1.4.1.4329.15.3.3.1.7.1.7
        vnsFilterRuleProtocol OBJECT-TYPE
            SYNTAX INTEGER
                {
                none(0),
                notApplicable(1),
                tcp(2),
                udp(3),
                icmp(4),
                ipsecESP(5),
                ipsecAH(6)
                }
            MAX-ACCESS read-write
            STATUS current
            DESCRIPTION
                "Specific protocol to filter."
            ::= { vnsFilterRuleEntry 7 }

        
        -- 1.3.6.1.4.1.4329.15.3.3.1.7.1.8
        vnsFilterRuleEtherType OBJECT-TYPE
            SYNTAX INTEGER
                {
                none(0),
                ip(1),
                arp(2),
                rarp(3)
                }
            MAX-ACCESS read-write
            STATUS current
            DESCRIPTION
                "Specific ethertype to filter."
            ::= { vnsFilterRuleEntry 8 }

        
        -- 1.3.6.1.4.1.4329.15.3.3.1.7.1.9
        vnsFilterRuleStatus OBJECT-TYPE
            SYNTAX RowStatus
            MAX-ACCESS read-write
            STATUS current
            DESCRIPTION
                "RowStatus value for the vnsFilterRuleTable."
            ::= { vnsFilterRuleEntry 9 }

        
        -- 1.3.6.1.4.1.4329.15.3.3.1.8
        vnsPrivacyTable OBJECT-TYPE
            SYNTAX SEQUENCE OF VnsPrivacyEntry
            MAX-ACCESS not-accessible
            STATUS current
            DESCRIPTION
                "Table of privacy settings for the VNS."
            ::= { vnsConfigObjects 8 }

        
        -- 1.3.6.1.4.1.4329.15.3.3.1.8.1
        vnsPrivacyEntry OBJECT-TYPE
            SYNTAX VnsPrivacyEntry
            MAX-ACCESS not-accessible
            STATUS current
            DESCRIPTION
                "Configuration values for a specific privacy setting."
            INDEX { ifIndex }
            ::= { vnsPrivacyTable 1 }

        
        VnsPrivacyEntry ::=
            SEQUENCE { 
                vnsPrivWEPKeyType
                    INTEGER,
                vnsPrivDynamicRekeyFrequency
                    Integer32,
                vnsPrivWEPKeyLength
                    Integer32,
                vnsPrivWPA1Enabled
                    TruthValue,
                vnsPrivUseSharedKey
                    TruthValue,
                vnsPrivWPASharedKey
                    DisplayString,
                vnsPrivWPA2Enabled
                    TruthValue
             }

        -- 1.3.6.1.4.1.4329.15.3.3.1.8.1.1
        vnsPrivWEPKeyType OBJECT-TYPE
            SYNTAX INTEGER
                {
                none(1),
                wepstatic(2),
                wpapsk(3),
                dynamic(4),
                wpa(5)
                }
            MAX-ACCESS read-write
            STATUS current
            DESCRIPTION
                "Type of key in use. 
                none(1) = not cofigured, 
                wepstatic(2) = static WEP, 
                wpapsk(3) = WPA Pre-Shared Key,
                dynamic(4) = dynamically assigned,
                wpa(5) = WPA."
            ::= { vnsPrivacyEntry 1 }

        
        -- 1.3.6.1.4.1.4329.15.3.3.1.8.1.2
        vnsPrivDynamicRekeyFrequency OBJECT-TYPE
            SYNTAX Integer32
            MAX-ACCESS read-write
            STATUS current
            DESCRIPTION
                "Dynamic WEP re-keying frequency, in seconds.  Setting this 
                value to 0 disables rekeying.
                
                This value is only meaningful if vnsPrivWEPKeyType = wpapsk(3).
                For any other values of vnsPrivWEPKeyType, reading or setting 
                this value will return an unsuccessful status and will return 
                a value of null or zero."
            ::= { vnsPrivacyEntry 2 }

        
        -- 1.3.6.1.4.1.4329.15.3.3.1.8.1.3
        vnsPrivWEPKeyLength OBJECT-TYPE
            SYNTAX Integer32
            MAX-ACCESS read-write
            STATUS current
            DESCRIPTION
                "WEP key length,  64, 128, or 152 bits.  If vnsPrivWEPKeyType
                is none, reading or setting this value will return an 
                unsuccessful status and will return a value of null or zero."
            ::= { vnsPrivacyEntry 3 }

        
        -- 1.3.6.1.4.1.4329.15.3.3.1.8.1.4
        vnsPrivWPA1Enabled OBJECT-TYPE
            SYNTAX TruthValue
            MAX-ACCESS read-write
            STATUS current
            DESCRIPTION
                "Enables WPA.1 (Wi-Fi Protected Access)."
            ::= { vnsPrivacyEntry 4 }

        
        -- 1.3.6.1.4.1.4329.15.3.3.1.8.1.5
        vnsPrivUseSharedKey OBJECT-TYPE
            SYNTAX TruthValue
            MAX-ACCESS read-write
            STATUS current
            DESCRIPTION
                "Enables the use of WPA shared key for this VNS."
            ::= { vnsPrivacyEntry 5 }

        
        -- 1.3.6.1.4.1.4329.15.3.3.1.8.1.6
        vnsPrivWPASharedKey OBJECT-TYPE
            SYNTAX DisplayString
            MAX-ACCESS read-write
            STATUS current
            DESCRIPTION
                "The value of the WPA shared key for this VNS.  
                This value is logically WRITE ONLY.  Attempts 
                to read this value shall return unsuccessful 
                status and values of null or zero."
            ::= { vnsPrivacyEntry 6 }

        
        -- 1.3.6.1.4.1.4329.15.3.3.1.8.1.7
        vnsPrivWPA2Enabled OBJECT-TYPE
            SYNTAX TruthValue
            MAX-ACCESS read-write
            STATUS current
            DESCRIPTION
                "When true, WPA v.2 support is enabled."
            ::= { vnsPrivacyEntry 7 }

        
        -- 1.3.6.1.4.1.4329.15.3.3.1.9
        vnsWEPKeyTable OBJECT-TYPE
            SYNTAX SEQUENCE OF VnsWEPKeyEntry
            MAX-ACCESS not-accessible
            STATUS current
            DESCRIPTION
                "Table of WEP key entries for a static WEP definition."
            ::= { vnsConfigObjects 9 }

        
        -- 1.3.6.1.4.1.4329.15.3.3.1.9.1
        vnsWEPKeyEntry OBJECT-TYPE
            SYNTAX VnsWEPKeyEntry
            MAX-ACCESS not-accessible
            STATUS current
            DESCRIPTION
                "WEP key for a single entry in the table."
            INDEX { ifIndex, vnsWEPKeyIndex }
            ::= { vnsWEPKeyTable 1 }

        
        VnsWEPKeyEntry ::=
            SEQUENCE { 
                vnsWEPKeyIndex
                    Integer32,
                vnsWEPKeyValue
                    WEPKeytype
             }

        -- 1.3.6.1.4.1.4329.15.3.3.1.9.1.1
        vnsWEPKeyIndex OBJECT-TYPE
            SYNTAX Integer32 (1..4)
            MAX-ACCESS read-write
            STATUS current
            DESCRIPTION
                "Table index for the WEP key."
            ::= { vnsWEPKeyEntry 1 }

        
        -- 1.3.6.1.4.1.4329.15.3.3.1.9.1.2
        vnsWEPKeyValue OBJECT-TYPE
            SYNTAX WEPKeytype
            MAX-ACCESS read-write
            STATUS current
            DESCRIPTION
                "Value of a WEP key for this VNS.
                
                This value is logically WRITE ONLY.  Attempts 
                to read this value shall return unsuccessful 
                status and values of null or zero."
            ::= { vnsWEPKeyEntry 2 }

        
        -- 1.3.6.1.4.1.4329.15.3.3.1.10
        vns3rdPartyAPTable OBJECT-TYPE
            SYNTAX SEQUENCE OF Vns3rdPartyAPEntry
            MAX-ACCESS not-accessible
            STATUS current
            DESCRIPTION
                "Contains a list of 3rd Party access points for 
                the EWC."
            ::= { vnsConfigObjects 10 }

        
        -- 1.3.6.1.4.1.4329.15.3.3.1.10.1
        vns3rdPartyAPEntry OBJECT-TYPE
            SYNTAX Vns3rdPartyAPEntry
            MAX-ACCESS not-accessible
            STATUS current
            DESCRIPTION
                "Configuration information for a 3rd party access point."
            INDEX { ifIndex, apMacAddress }
            ::= { vns3rdPartyAPTable 1 }

        
        Vns3rdPartyAPEntry ::=
            SEQUENCE { 
                apMacAddress
                    MacAddress,
                apIpAddress
                    IpAddress
             }

        -- 1.3.6.1.4.1.4329.15.3.3.1.10.1.1
        apMacAddress OBJECT-TYPE
            SYNTAX MacAddress
            MAX-ACCESS read-write
            STATUS current
            DESCRIPTION
                "Ethernet MAC address of the 3rd party access point."
            ::= { vns3rdPartyAPEntry 1 }

        
        -- 1.3.6.1.4.1.4329.15.3.3.1.10.1.2
        apIpAddress OBJECT-TYPE
            SYNTAX IpAddress
            MAX-ACCESS read-write
            STATUS current
            DESCRIPTION
                "IP address of the 3rd party access point."
            ::= { vns3rdPartyAPEntry 2 }

        
        -- 1.3.6.1.4.1.4329.15.3.3.1.11
        vnsQoSTable OBJECT-TYPE
            SYNTAX SEQUENCE OF VnsQoSEntry
            MAX-ACCESS not-accessible
            STATUS current
            DESCRIPTION
                "This table contains list of per-VNS QoS related configuration."
            ::= { vnsConfigObjects 11 }

        
        -- 1.3.6.1.4.1.4329.15.3.3.1.11.1
        vnsQoSEntry OBJECT-TYPE
            SYNTAX VnsQoSEntry
            MAX-ACCESS not-accessible
            STATUS current
            DESCRIPTION
                "An entry related to QoS configuration for the VNS indexed by vnsIfIndex."
            INDEX { vnsIfIndex }
            ::= { vnsQoSTable 1 }

        
        VnsQoSEntry ::=
            SEQUENCE { 
                vnsQoSWirelessLegacyFlag
                    INTEGER,
                vnsQoSWirelessWMMFlag
                    INTEGER,
                vnsQoSWireless80211eFlag
                    INTEGER,
                vnsQoSWirelessTurboVoiceFlag
                    INTEGER,
                vnsQoSPriorityOverrideFlag
                    INTEGER,
                vnsQoSPriorityOverrideSC
                    INTEGER,
                vnsQoSPriorityOverrideDSCP
                    Integer32,
                vnsQoSClassificationServiceClass
                    OCTET STRING,
                vnsQoSWirelessEnableUAPSD
                    INTEGER,
                vnsQoSWirelessUseAdmControlVoice
                    INTEGER,
                vnsQoSWirelessUseAdmControlVideo
                    INTEGER,
                vnsQoSWirelessULPolicerAction
                    INTEGER,
                vnsQoSWirelessDLPolicerAction
                    INTEGER,
        vnsQoSWirelessUseAdmControlBestEffort
                    INTEGER,
        vnsQoSWirelessUseAdmControlBackground
                    INTEGER
                    
             }

        -- 1.3.6.1.4.1.4329.15.3.3.1.11.1.1
        vnsQoSWirelessLegacyFlag OBJECT-TYPE
            SYNTAX INTEGER
                {
                enabled(1),
                disabled(2)
                }
            MAX-ACCESS read-write
            STATUS current
            DESCRIPTION
                "This variable is used to enable/disable legacy QoS feature."
            ::= { vnsQoSEntry 1 }

        
        -- 1.3.6.1.4.1.4329.15.3.3.1.11.1.2
        vnsQoSWirelessWMMFlag OBJECT-TYPE
            SYNTAX INTEGER
                {
                enabled(1),
                disabled(2)
                }
            MAX-ACCESS read-write
            STATUS current
            DESCRIPTION
                "This variable is used to enable/disable WMM feature."
            ::= { vnsQoSEntry 2 }

        
        -- 1.3.6.1.4.1.4329.15.3.3.1.11.1.3
        vnsQoSWireless80211eFlag OBJECT-TYPE
            SYNTAX INTEGER
                {
                enabled(1),
                disabled(2)
                }
            MAX-ACCESS read-write
            STATUS current
            DESCRIPTION
                "This variable is used to enable/disable 802.11e feature."
            ::= { vnsQoSEntry 3 }

        
        -- 1.3.6.1.4.1.4329.15.3.3.1.11.1.4
        vnsQoSWirelessTurboVoiceFlag OBJECT-TYPE
            SYNTAX INTEGER
                {
                enabled(1),
                disabled(2)
                }
            MAX-ACCESS read-write
            STATUS current
            DESCRIPTION
                "This variable is used to enable/disable turbo feature."
            ::= { vnsQoSEntry 4 }

        
        -- 1.3.6.1.4.1.4329.15.3.3.1.11.1.5
        vnsQoSPriorityOverrideFlag OBJECT-TYPE
            SYNTAX INTEGER
                {
                enabled(1),
                disabled(2)
                }
            MAX-ACCESS read-write
            STATUS current
            DESCRIPTION
                "Enable/disable the use of DSCP to override Servic Class (SC) value."
            DEFVAL { disabled }
            ::= { vnsQoSEntry 5 }

        
        -- 1.3.6.1.4.1.4329.15.3.3.1.11.1.6
        vnsQoSPriorityOverrideSC OBJECT-TYPE
            SYNTAX INTEGER
                {
                background(0),
                bestEffort(1),
                bronze(2),
                silver(3),
                gold(4),
                platinum(5),
                premiumVoice(6),
                networkControl(7)
                }
            MAX-ACCESS read-write
            STATUS current
            DESCRIPTION
                "Service class (SC) of the override value. This field has a meaning
                if vnsQoSPriorityOverrideFlag is enabled."
            DEFVAL { background }
            ::= { vnsQoSEntry 6 }

        
        -- 1.3.6.1.4.1.4329.15.3.3.1.11.1.7
        vnsQoSPriorityOverrideDSCP OBJECT-TYPE
            SYNTAX Integer32 (0..63)
            MAX-ACCESS read-write
            STATUS current
            DESCRIPTION
                "DSCP override value to be used for the service class. This field has a meaning
                if vnsQoSPriorityOverrideFlag is enabled."
            DEFVAL { 0 }
            ::= { vnsQoSEntry 7 }

        
        -- 1.3.6.1.4.1.4329.15.3.3.1.11.1.8
        vnsQoSClassificationServiceClass OBJECT-TYPE
            SYNTAX OCTET STRING (SIZE (0..64))
            MAX-ACCESS read-write
            STATUS current
            DESCRIPTION
                "Service Class value for the DSCP code. This field is 64-bytes long. Each
                byte represents mapping between DSCP and Service Class. Position of each
                byte in the array represents DSCP code and the content of each byte 
                represents the service class value for that DSCP code. For example, 
                second byte represents DSCP code 1 and its value represents SC value.
                Value for each byte is equivalent to either of:
                background = 0, 
                bestEffort = 1, 
                bronze = 2,
                silver = 3,
                gold = 4,
                platinum = 5,
                premiumVoice = 6,
                networkControl = 7"
            ::= { vnsQoSEntry 8 }

        
        -- 1.3.6.1.4.1.4329.15.3.3.1.11.1.9
        vnsQoSWirelessEnableUAPSD OBJECT-TYPE
            SYNTAX INTEGER
                {
                enabled(1),
                disabled(2)
                }
            MAX-ACCESS read-write
            STATUS current
            DESCRIPTION
                "This variable is used to enable/disable U-APSD feature."
            ::= { vnsQoSEntry 9 }

        
        -- 1.3.6.1.4.1.4329.15.3.3.1.11.1.10
        vnsQoSWirelessUseAdmControlVoice OBJECT-TYPE
            SYNTAX INTEGER
                {
                enabled(1),
                disabled(2)
                }
            MAX-ACCESS read-write
            STATUS current
            DESCRIPTION
                "If enabled, admission control for voice traffic is used."
            ::= { vnsQoSEntry 10 }

        
        -- 1.3.6.1.4.1.4329.15.3.3.1.11.1.11
        vnsQoSWirelessUseAdmControlVideo OBJECT-TYPE
            SYNTAX INTEGER
                {
                enabled(1),
                disabled(2)
                }
            MAX-ACCESS read-write
            STATUS current
            DESCRIPTION
                "If enabled, admission control for vedio traffic is used.
                This field has a meaning if vnsQoSUseGlobalAdmVoice is enabled."
            ::= { vnsQoSEntry 11 }

        
        -- 1.3.6.1.4.1.4329.15.3.3.1.11.1.12
        vnsQoSWirelessULPolicerAction OBJECT-TYPE
            SYNTAX INTEGER
                {
                doNothing(0),
                sendDELTStoClient(1)
                }
            MAX-ACCESS read-write
            STATUS current
            DESCRIPTION
                "If doNothing is selected, no action is taken. This is default value.
                If sendDELTStoClient is selected, AP will send DELTS if a client 
                is abusing in uplink. This field has a meaning only if admission
                control is enabled for VO or VI."
            DEFVAL { doNothing }
            ::= { vnsQoSEntry 12 }

        
        -- 1.3.6.1.4.1.4329.15.3.3.1.11.1.13
        vnsQoSWirelessDLPolicerAction OBJECT-TYPE
            SYNTAX INTEGER
                {
                doNothing(0),
                downgrade(1),
                drop(2)
                }
            MAX-ACCESS read-write
            STATUS current
            DESCRIPTION
                "If doNothing is selected, no action is taken. This is default value.
                If downgrade is selected, AP will downgrade all traffic to the 
                   highest AC that does not require CAC in downlink.
                If drop is selected, AP will drop client if it observes a client 
                   that is illegally using an AC that has CAC mandatory in downlink.
                This field has a meaning only if admission control is enabled for 
                      VO or VI."
            DEFVAL { doNothing }
            ::= { vnsQoSEntry 13 }


        -- 1.3.6.1.4.1.4329.15.3.3.1.11.1.14
        vnsQoSWirelessUseAdmControlBestEffort OBJECT-TYPE
            SYNTAX INTEGER
                {
                disabled(0),
                enabled(1)
                }
            MAX-ACCESS read-write
            STATUS current
            DESCRIPTION
                "If enabled, admission control for video traffic is set to Best Effort.
                This field has a meaning if vnsQoSUseGlobalAdmVoice is enabled."
            ::= { vnsQoSEntry 14 }

        -- 1.3.6.1.4.1.4329.15.3.3.1.11.1.15
        vnsQoSWirelessUseAdmControlBackground OBJECT-TYPE
            SYNTAX INTEGER
                {
                disabled(0),
                enabled(1)
                }
            MAX-ACCESS read-write
            STATUS current
            DESCRIPTION
                "If enabled, admission control for video traffic is set to Background.
                This field has a meaning if vnsQoSUseGlobalAdmVoice is enabled."
            ::= { vnsQoSEntry 15 }


            

        
        -- 1.3.6.1.4.1.4329.15.3.3.1.12
        vnsWDSRFTable OBJECT-TYPE
            SYNTAX SEQUENCE OF VnsWDSRFEntry
            MAX-ACCESS not-accessible
            STATUS obsolete
            DESCRIPTION
                "ontains definitions of the Wireless Distirbution System (WDS) VNS defined on this Controller."
            ::= { vnsConfigObjects 12 }

        
        -- 1.3.6.1.4.1.4329.15.3.3.1.12.1
        vnsWDSRFEntry OBJECT-TYPE
            SYNTAX VnsWDSRFEntry
            MAX-ACCESS not-accessible
            STATUS obsolete
            DESCRIPTION
                "Configuration elements for a specific WDS VNS."
            INDEX { vnsIfIndex, apIndex }
            ::= { vnsWDSRFTable 1 }

        
        VnsWDSRFEntry ::=
            SEQUENCE { 
                vnsWDSRFAPName
                    DisplayString,
                vnsWDSRFbgService
                    INTEGER,
                vnsWDSRFaService
                    INTEGER,
                vnsWDSRFPreferredParent
                    DisplayString,
                vnsWDSRFBackupParent
                    DisplayString,
                vnsWDSRFBridge
                    INTEGER
             }

        -- 1.3.6.1.4.1.4329.15.3.3.1.12.1.1
        vnsWDSRFAPName OBJECT-TYPE
            SYNTAX DisplayString
            MAX-ACCESS read-write
            STATUS obsolete
            DESCRIPTION
                "AP name."
            ::= { vnsWDSRFEntry 1 }

        
        -- 1.3.6.1.4.1.4329.15.3.3.1.12.1.2
        vnsWDSRFbgService OBJECT-TYPE
            SYNTAX INTEGER
                {
                notAvailable(0),
                none(1),
                child(2),
                parent(3),
                both(4)
                }
            MAX-ACCESS read-write
            STATUS obsolete
            DESCRIPTION
                "Type of service offered by this radio."
            ::= { vnsWDSRFEntry 2 }

        
        -- 1.3.6.1.4.1.4329.15.3.3.1.12.1.3
        vnsWDSRFaService OBJECT-TYPE
            SYNTAX INTEGER
                {
                notAvailable(0),
                none(1),
                child(2),
                parent(3),
                both(4)
                }
            MAX-ACCESS read-write
            STATUS obsolete
            DESCRIPTION
                "Type of service offered by this radio."
            ::= { vnsWDSRFEntry 3 }

        
        -- 1.3.6.1.4.1.4329.15.3.3.1.12.1.4
        vnsWDSRFPreferredParent OBJECT-TYPE
            SYNTAX DisplayString
            MAX-ACCESS read-write
            STATUS obsolete
            DESCRIPTION
                "Desired preferred parent."
            ::= { vnsWDSRFEntry 4 }

        
        -- 1.3.6.1.4.1.4329.15.3.3.1.12.1.5
        vnsWDSRFBackupParent OBJECT-TYPE
            SYNTAX DisplayString
            MAX-ACCESS read-write
            STATUS obsolete
            DESCRIPTION
                "Desired backup parent."
            ::= { vnsWDSRFEntry 5 }

        
        -- 1.3.6.1.4.1.4329.15.3.3.1.12.1.6
        vnsWDSRFBridge OBJECT-TYPE
            SYNTAX INTEGER
                {
                bridged(1),
                notBridged(2)
                }
            MAX-ACCESS read-write
            STATUS obsolete
            DESCRIPTION
                "WDS bridge status."
            ::= { vnsWDSRFEntry 6 }

        
        -- 1.3.6.1.4.1.4329.15.3.3.1.13
        vnsRateControlProfTable OBJECT-TYPE
            SYNTAX SEQUENCE OF VnsRateControlProfEntry
            MAX-ACCESS not-accessible
            STATUS obsolete
            DESCRIPTION
                "Table of Rate Control Profiles."
            ::= { vnsConfigObjects 13 }

        
        -- 1.3.6.1.4.1.4329.15.3.3.1.13.1
        vnsRateControlProfEntry OBJECT-TYPE
            SYNTAX VnsRateControlProfEntry
            MAX-ACCESS not-accessible
            STATUS obsolete
            DESCRIPTION
                "Name of a specific Rate Control Profile."
            INDEX { vnsRateControlProfInd }
            ::= { vnsRateControlProfTable 1 }

        
        VnsRateControlProfEntry ::=
            SEQUENCE { 
                vnsRateControlProfInd
                    Unsigned32,
                vnsRateControlProfName
                    DisplayString,
                vnsRateControlCIR
                    Unsigned32,
                vnsRateControlCBS
                    Unsigned32
             }

        -- 1.3.6.1.4.1.4329.15.3.3.1.13.1.1
        vnsRateControlProfInd OBJECT-TYPE
            SYNTAX Unsigned32
            MAX-ACCESS read-write
            STATUS obsolete
            DESCRIPTION
                "A monotonically increasing integer which acts as index of entries
                within the named Rate Control Profiles."
            ::= { vnsRateControlProfEntry 1 }

        
        -- 1.3.6.1.4.1.4329.15.3.3.1.13.1.2
        vnsRateControlProfName OBJECT-TYPE
            SYNTAX DisplayString
            MAX-ACCESS read-write
            STATUS obsolete
            DESCRIPTION
                "Rate Control Profile Name."
            ::= { vnsRateControlProfEntry 2 }

        
        -- 1.3.6.1.4.1.4329.15.3.3.1.13.1.3
        vnsRateControlCIR OBJECT-TYPE
            SYNTAX Unsigned32
            MAX-ACCESS read-write
            STATUS obsolete
            DESCRIPTION
                "Rate Control Average Rate (CIR) in kbps."
            ::= { vnsRateControlProfEntry 3 }

        
        -- 1.3.6.1.4.1.4329.15.3.3.1.13.1.4
        vnsRateControlCBS OBJECT-TYPE
            SYNTAX Unsigned32
            MAX-ACCESS read-write
            STATUS obsolete
            DESCRIPTION
                "Rate Control Burst Size (CBS) in bytes."
            ::= { vnsRateControlProfEntry 4 }

        
        -- 1.3.6.1.4.1.4329.15.3.3.1.14
        vnsAPFilterTable OBJECT-TYPE
            SYNTAX SEQUENCE OF VnsAPFilterEntry
            MAX-ACCESS not-accessible
            STATUS current
            DESCRIPTION
                "Filters applied to Access Points via VNS settings and assignments."
            ::= { vnsConfigObjects 14 }

        
        -- 1.3.6.1.4.1.4329.15.3.3.1.14.1
        vnsAPFilterEntry OBJECT-TYPE
            SYNTAX VnsAPFilterEntry
            MAX-ACCESS not-accessible
            STATUS current
            DESCRIPTION
                "An entry containing filters definition for Access Points assigned
                to VNS that is identified by VNS index."
            INDEX { ifIndex, vnsFilterID, vnsAPFilterRuleOrder }
            ::= { vnsAPFilterTable 1 }

        
        VnsAPFilterEntry ::=
            SEQUENCE { 
                vnsAPFilterRuleOrder
                    Integer32,
                vnsAPFilterRuleDirection
                    INTEGER,
                vnsAPFilterAction
                    Integer32,
                vnsAPFilterIPAddress
                    IpAddress,
                vnsAPFilterMask
                    IpAddress,
                vnsAPFilterPortLow
                    Integer32,
                vnsAPFilterPortHigh
                    Integer32,
                vnsAPFilterProtocol
                    Integer32,
                vnsAPFilterEtherType
                    INTEGER,
                vnsAPFilterRowStatus
                    Integer32
             }

        -- 1.3.6.1.4.1.4329.15.3.3.1.14.1.1
        vnsAPFilterRuleOrder OBJECT-TYPE
            SYNTAX Integer32 (1..65535)
            MAX-ACCESS read-create
            STATUS current
            DESCRIPTION
                "Position of the filter in the filter list."
            ::= { vnsAPFilterEntry 1 }

        
        -- 1.3.6.1.4.1.4329.15.3.3.1.14.1.2
        vnsAPFilterRuleDirection OBJECT-TYPE
            SYNTAX INTEGER
                {
                in(1),
                out(2),
                both(3)
                }
            MAX-ACCESS read-create
            STATUS current
            DESCRIPTION
                "Traffic direction related to the filter rule."
            ::= { vnsAPFilterEntry 2 }

        
        -- 1.3.6.1.4.1.4329.15.3.3.1.14.1.3
        vnsAPFilterAction OBJECT-TYPE
            SYNTAX Integer32
            MAX-ACCESS read-create
            STATUS current
            DESCRIPTION
                "Allow or deny traffic for the filter."
            ::= { vnsAPFilterEntry 3 }

        
        -- 1.3.6.1.4.1.4329.15.3.3.1.14.1.4
        vnsAPFilterIPAddress OBJECT-TYPE
            SYNTAX IpAddress
            MAX-ACCESS read-create
            STATUS current
            DESCRIPTION
                "IP address applied to the filter."
            ::= { vnsAPFilterEntry 4 }

        
        -- 1.3.6.1.4.1.4329.15.3.3.1.14.1.5
        vnsAPFilterMask OBJECT-TYPE
            SYNTAX IpAddress
            MAX-ACCESS read-create
            STATUS current
            DESCRIPTION
                "The mask, number of bits set to one in the mask, applied to filter IP address."
            ::= { vnsAPFilterEntry 5 }

        
        -- 1.3.6.1.4.1.4329.15.3.3.1.14.1.6
        vnsAPFilterPortLow OBJECT-TYPE
            SYNTAX Integer32
            MAX-ACCESS read-create
            STATUS current
            DESCRIPTION
                "Low port number for the filter."
            ::= { vnsAPFilterEntry 6 }

        
        -- 1.3.6.1.4.1.4329.15.3.3.1.14.1.7
        vnsAPFilterPortHigh OBJECT-TYPE
            SYNTAX Integer32
            MAX-ACCESS read-create
            STATUS current
            DESCRIPTION
                "High port number for the filter."
            ::= { vnsAPFilterEntry 7 }

        
        -- 1.3.6.1.4.1.4329.15.3.3.1.14.1.8
        vnsAPFilterProtocol OBJECT-TYPE
            SYNTAX Integer32
            MAX-ACCESS read-create
            STATUS current
            DESCRIPTION
                "Specific protocol for the filter."
            ::= { vnsAPFilterEntry 8 }

        
        -- 1.3.6.1.4.1.4329.15.3.3.1.14.1.9
        vnsAPFilterEtherType OBJECT-TYPE
            SYNTAX INTEGER
                {
                ip(1),
                arp(2),
                rarp(3)
                }
            MAX-ACCESS read-create
            STATUS current
            DESCRIPTION
                "Specific ethertype to the filter."
            ::= { vnsAPFilterEntry 9 }

        
        -- 1.3.6.1.4.1.4329.15.3.3.1.14.1.10
        vnsAPFilterRowStatus OBJECT-TYPE
            SYNTAX Integer32
            MAX-ACCESS read-create
            STATUS current
            DESCRIPTION
                "RowStatus value for this table entry."
            ::= { vnsAPFilterEntry 10 }

        
        -- 1.3.6.1.4.1.4329.15.3.3.2
        vnsStatsObjects OBJECT IDENTIFIER ::= { virtualNetworks 2 }

        
        -- 1.3.6.1.4.1.4329.15.3.3.2.1
        activeVNSSessionCount OBJECT-TYPE
            SYNTAX Integer32
            MAX-ACCESS read-write
            STATUS current
            DESCRIPTION
                "Number of active VNSs."
            ::= { vnsStatsObjects 1 }

        
        -- 1.3.6.1.4.1.4329.15.3.3.2.2
        vnsStatTable OBJECT-TYPE
            SYNTAX SEQUENCE OF VnsStatEntry
            MAX-ACCESS not-accessible
            STATUS obsolete
            DESCRIPTION
                "Description."
            ::= { vnsStatsObjects 2 }

        
        -- 1.3.6.1.4.1.4329.15.3.3.2.2.1
        vnsStatEntry OBJECT-TYPE
            SYNTAX VnsStatEntry
            MAX-ACCESS not-accessible
            STATUS obsolete
            DESCRIPTION
                "Description."
            INDEX { vnsIfIndex }
            ::= { vnsStatTable 1 }

        
        VnsStatEntry ::=
            SEQUENCE { 
                vnsStatName
                    OCTET STRING,
                vnsStatTxPkts
                    Counter64,
                vnsStatRxPkts
                    Counter64,
                vnsStatTxOctects
                    Counter64,
                vnsStatRxOctects
                    Counter64,
                vnsStatMulticastTxPkts
                    Counter64,
                vnsStatMulticastRxPkts
                    Counter64,
                vnsStatBroadcastTxPkts
                    Counter64,
                vnsStatBroadcastRxPkts
                    Counter64,
                vnsStatRadiusTotRequests
                    Counter64,
                vnsStatRadiusReqFailed
                    Counter64,
                vnsStatRadiusReqRejected
                    Counter64
             }

        -- 1.3.6.1.4.1.4329.15.3.3.2.2.1.1
        vnsStatName OBJECT-TYPE
            SYNTAX OCTET STRING
            MAX-ACCESS read-write
            STATUS obsolete
            DESCRIPTION
                "Name of the VNS."
            ::= { vnsStatEntry 1 }

        
        -- 1.3.6.1.4.1.4329.15.3.3.2.2.1.2
        vnsStatTxPkts OBJECT-TYPE
            SYNTAX Counter64
            MAX-ACCESS read-only
            STATUS obsolete
            DESCRIPTION
                "Trasmitted packets."
            ::= { vnsStatEntry 2 }

        
        -- 1.3.6.1.4.1.4329.15.3.3.2.2.1.3
        vnsStatRxPkts OBJECT-TYPE
            SYNTAX Counter64
            MAX-ACCESS read-only
            STATUS obsolete
            DESCRIPTION
                "Received packtes."
            ::= { vnsStatEntry 3 }

        
        -- 1.3.6.1.4.1.4329.15.3.3.2.2.1.4
        vnsStatTxOctects OBJECT-TYPE
            SYNTAX Counter64
            MAX-ACCESS read-only
            STATUS obsolete
            DESCRIPTION
                "Trasmitted octects."
            ::= { vnsStatEntry 4 }

        
        -- 1.3.6.1.4.1.4329.15.3.3.2.2.1.5
        vnsStatRxOctects OBJECT-TYPE
            SYNTAX Counter64
            MAX-ACCESS read-only
            STATUS obsolete
            DESCRIPTION
                "Received octets."
            ::= { vnsStatEntry 5 }

        
        -- 1.3.6.1.4.1.4329.15.3.3.2.2.1.6
        vnsStatMulticastTxPkts OBJECT-TYPE
            SYNTAX Counter64
            MAX-ACCESS read-only
            STATUS obsolete
            DESCRIPTION
                "Multicast trasmitted packets."
            ::= { vnsStatEntry 6 }

        
        -- 1.3.6.1.4.1.4329.15.3.3.2.2.1.7
        vnsStatMulticastRxPkts OBJECT-TYPE
            SYNTAX Counter64
            MAX-ACCESS read-only
            STATUS obsolete
            DESCRIPTION
                "Multicast received packets."
            ::= { vnsStatEntry 7 }

        
        -- 1.3.6.1.4.1.4329.15.3.3.2.2.1.8
        vnsStatBroadcastTxPkts OBJECT-TYPE
            SYNTAX Counter64
            MAX-ACCESS read-only
            STATUS obsolete
            DESCRIPTION
                "Broadcast trasmitted packets."
            ::= { vnsStatEntry 8 }

        
        -- 1.3.6.1.4.1.4329.15.3.3.2.2.1.9
        vnsStatBroadcastRxPkts OBJECT-TYPE
            SYNTAX Counter64
            MAX-ACCESS read-only
            STATUS obsolete
            DESCRIPTION
                "Broadcast received packets."
            ::= { vnsStatEntry 9 }

        
        -- 1.3.6.1.4.1.4329.15.3.3.2.2.1.10
        vnsStatRadiusTotRequests OBJECT-TYPE
            SYNTAX Counter64
            MAX-ACCESS read-only
            STATUS obsolete
            DESCRIPTION
                "Total requests sent to radius server."
            ::= { vnsStatEntry 10 }

        
        -- 1.3.6.1.4.1.4329.15.3.3.2.2.1.11
        vnsStatRadiusReqFailed OBJECT-TYPE
            SYNTAX Counter64
            MAX-ACCESS read-only
            STATUS obsolete
            DESCRIPTION
                "Requests that failed to be processed by radius server."
            ::= { vnsStatEntry 11 }

        
        -- 1.3.6.1.4.1.4329.15.3.3.2.2.1.12
        vnsStatRadiusReqRejected OBJECT-TYPE
            SYNTAX Counter64
            MAX-ACCESS read-only
            STATUS obsolete
            DESCRIPTION
                "Requests that have been rejected by radius server."
            ::= { vnsStatEntry 12 }

        
        -- 1.3.6.1.4.1.4329.15.3.3.2.3
        vnsExceptionStatTable OBJECT-TYPE
            SYNTAX SEQUENCE OF VnsExceptionStatEntry
            MAX-ACCESS not-accessible
            STATUS obsolete
            DESCRIPTION
                "Description."
            ::= { vnsStatsObjects 3 }

        
        -- 1.3.6.1.4.1.4329.15.3.3.2.3.1
        vnsExceptionStatEntry OBJECT-TYPE
            SYNTAX VnsExceptionStatEntry
            MAX-ACCESS not-accessible
            STATUS obsolete
            DESCRIPTION
                "Description."
            INDEX { vnsIfIndex, vnsExceptionFiterName }
            ::= { vnsExceptionStatTable 1 }

        
        VnsExceptionStatEntry ::=
            SEQUENCE { 
                vnsExceptionFiterName
                    OCTET STRING,
                vnsExceptionStatPktsDenied
                    Counter64,
                vnsExceptionStatPktsAllowed
                    Counter64
             }

        -- 1.3.6.1.4.1.4329.15.3.3.2.3.1.1
        vnsExceptionFiterName OBJECT-TYPE
            SYNTAX OCTET STRING (SIZE (1..64))
            MAX-ACCESS read-write
            STATUS obsolete
            DESCRIPTION
                "Filter name."
            ::= { vnsExceptionStatEntry 1 }

        
        -- 1.3.6.1.4.1.4329.15.3.3.2.3.1.2
        vnsExceptionStatPktsDenied OBJECT-TYPE
            SYNTAX Counter64
            MAX-ACCESS read-only
            STATUS obsolete
            DESCRIPTION
                "Total packets that are denied by defined filters."
            ::= { vnsExceptionStatEntry 2 }

        
        -- 1.3.6.1.4.1.4329.15.3.3.2.3.1.3
        vnsExceptionStatPktsAllowed OBJECT-TYPE
            SYNTAX Counter64
            MAX-ACCESS read-only
            STATUS obsolete
            DESCRIPTION
                "Total packets that are allowed by defined filters."
            ::= { vnsExceptionStatEntry 3 }

        
        -- 1.3.6.1.4.1.4329.15.3.3.2.4
        vnsWDSStatTable OBJECT-TYPE
            SYNTAX SEQUENCE OF VnsWDSStatEntry
            MAX-ACCESS not-accessible
            STATUS obsolete
            DESCRIPTION
                "Description."
            ::= { vnsStatsObjects 4 }

        
        -- 1.3.6.1.4.1.4329.15.3.3.2.4.1
        vnsWDSStatEntry OBJECT-TYPE
            SYNTAX VnsWDSStatEntry
            MAX-ACCESS not-accessible
            STATUS obsolete
            DESCRIPTION
                "Description."
            INDEX { vnsIfIndex, apIndex }
            ::= { vnsWDSStatTable 1 }

        
        VnsWDSStatEntry ::=
            SEQUENCE { 
                vnsWDSStatAPName
                    DisplayString,
                vnsWDSStatAPRole
                    INTEGER,
                vnsWDSStatAPRadio
                    DisplayString,
                vnsWDSStatAPParent
                    DisplayString,
                vnsWDSStatSSID
                    DisplayString,
                vnsWDSStatRxFrame
                    Counter64,
                vnsWDSStatTxFrame
                    Counter64,
                vnsWDSStatRxError
                    Counter64,
                vnsWDSStatTxError
                    Counter64,
                vnsWDSStatRxRSSI
                    Integer32,
                vnsWDSStatRxRate
                    Counter64,
                vnsWDSStatTxRate
                    Counter64
             }

        -- 1.3.6.1.4.1.4329.15.3.3.2.4.1.1
        vnsWDSStatAPName OBJECT-TYPE
            SYNTAX DisplayString
            MAX-ACCESS read-write
            STATUS obsolete
            DESCRIPTION
                "AP name serving WDS VNS."
            ::= { vnsWDSStatEntry 1 }

        
        -- 1.3.6.1.4.1.4329.15.3.3.2.4.1.2
        vnsWDSStatAPRole OBJECT-TYPE
            SYNTAX INTEGER
                {
                unknown(-1),
                none(0),
                satellite(1),
                root(2),
                repeater(3)
                }
            MAX-ACCESS read-write
            STATUS obsolete
            DESCRIPTION
                "Role of the AP in WDS tree. All the statistics and configuration information 
                in this table has no meaning if the role is unknown(-1)."
            ::= { vnsWDSStatEntry 2 }

        
        -- 1.3.6.1.4.1.4329.15.3.3.2.4.1.3
        vnsWDSStatAPRadio OBJECT-TYPE
            SYNTAX DisplayString (SIZE (0..15))
            MAX-ACCESS read-write
            STATUS obsolete
            DESCRIPTION
                "Radio and freq on which uplink WDS is established, N/A if connected
                over etherent (value are 'a:<freq>', 'b/g:<freq>', or 'N/A') "
            ::= { vnsWDSStatEntry 3 }

        
        -- 1.3.6.1.4.1.4329.15.3.3.2.4.1.4
        vnsWDSStatAPParent OBJECT-TYPE
            SYNTAX DisplayString
            MAX-ACCESS read-write
            STATUS obsolete
            DESCRIPTION
                "AP Name of the parent AP."
            ::= { vnsWDSStatEntry 4 }

        
        -- 1.3.6.1.4.1.4329.15.3.3.2.4.1.5
        vnsWDSStatSSID OBJECT-TYPE
            SYNTAX DisplayString (SIZE (0..32))
            MAX-ACCESS read-write
            STATUS obsolete
            DESCRIPTION
                "SSID of the WDS VNS where parent WDS link is established."
            ::= { vnsWDSStatEntry 5 }

        
        -- 1.3.6.1.4.1.4329.15.3.3.2.4.1.6
        vnsWDSStatRxFrame OBJECT-TYPE
            SYNTAX Counter64
            MAX-ACCESS read-write
            STATUS obsolete
            DESCRIPTION
                "Received frames from the parent AP."
            ::= { vnsWDSStatEntry 6 }

        
        -- 1.3.6.1.4.1.4329.15.3.3.2.4.1.7
        vnsWDSStatTxFrame OBJECT-TYPE
            SYNTAX Counter64
            MAX-ACCESS read-write
            STATUS obsolete
            DESCRIPTION
                "Transmitted frames to the parent AP."
            ::= { vnsWDSStatEntry 7 }

        
        -- 1.3.6.1.4.1.4329.15.3.3.2.4.1.8
        vnsWDSStatRxError OBJECT-TYPE
            SYNTAX Counter64
            MAX-ACCESS read-write
            STATUS obsolete
            DESCRIPTION
                "Received frames in error from the parent AP."
            ::= { vnsWDSStatEntry 8 }

        
        -- 1.3.6.1.4.1.4329.15.3.3.2.4.1.9
        vnsWDSStatTxError OBJECT-TYPE
            SYNTAX Counter64
            MAX-ACCESS read-write
            STATUS obsolete
            DESCRIPTION
                "Transmitted frames in error to the parent AP."
            ::= { vnsWDSStatEntry 9 }

        
        -- 1.3.6.1.4.1.4329.15.3.3.2.4.1.10
        vnsWDSStatRxRSSI OBJECT-TYPE
            SYNTAX Integer32 (0..64)
            MAX-ACCESS read-write
            STATUS obsolete
            DESCRIPTION
                "Average Received Signal Strength Indicator (RSSI)."
            ::= { vnsWDSStatEntry 10 }

        
        -- 1.3.6.1.4.1.4329.15.3.3.2.4.1.11
        vnsWDSStatRxRate OBJECT-TYPE
            SYNTAX Counter64
            MAX-ACCESS read-write
            STATUS obsolete
            DESCRIPTION
                "Average receive rate."
            ::= { vnsWDSStatEntry 11 }

        
        -- 1.3.6.1.4.1.4329.15.3.3.2.4.1.12
        vnsWDSStatTxRate OBJECT-TYPE
            SYNTAX Counter64
            MAX-ACCESS read-write
            STATUS obsolete
            DESCRIPTION
                "Average transmission rate."
            ::= { vnsWDSStatEntry 12 }

        
        -- 1.3.6.1.4.1.4329.15.3.3.3
        vnsGlobalSetting OBJECT IDENTIFIER ::= { virtualNetworks 3 }

        
        -- 1.3.6.1.4.1.4329.15.3.3.3.1
        wirelessQoS OBJECT IDENTIFIER ::= { vnsGlobalSetting 1 }

        
        -- 1.3.6.1.4.1.4329.15.3.3.3.1.1
        maxVoiceBWforReassociation OBJECT-TYPE
            SYNTAX Integer32 (0..100)
            MAX-ACCESS read-write
            STATUS current
            DESCRIPTION
                "Maximum voice bandwidth to be used for re-association."
            DEFVAL { 80 }
            ::= { wirelessQoS 1 }

        
        -- 1.3.6.1.4.1.4329.15.3.3.3.1.2
        maxVoiceBWforAssociation OBJECT-TYPE
            SYNTAX Integer32 (0..100)
            MAX-ACCESS read-write
            STATUS current
            DESCRIPTION
                "Maximum voice bandwidth to be used for association."
            DEFVAL { 60 }
            ::= { wirelessQoS 2 }

        
        -- 1.3.6.1.4.1.4329.15.3.3.3.1.3
        maxVideoBWforReassociation OBJECT-TYPE
            SYNTAX Integer32 (0..100)
            MAX-ACCESS read-write
            STATUS current
            DESCRIPTION
                "Maximum video bandwidth to be used for re-association."
            DEFVAL { 60 }
            ::= { wirelessQoS 3 }

        
        -- 1.3.6.1.4.1.4329.15.3.3.3.1.4
        maxVideoBWforAssociation OBJECT-TYPE
            SYNTAX Integer32 (0..100)
            MAX-ACCESS read-write
            STATUS current
            DESCRIPTION
                "Maximum video bandwidth to be used for association."
            DEFVAL { 40 }
            ::= { wirelessQoS 4 }


        -- 1.3.6.1.4.1.4329.15.3.3.3.1.5
        maxBestEffortBWforReassociation OBJECT-TYPE
            SYNTAX Integer32 (0..100)
            MAX-ACCESS read-write
            STATUS current
            DESCRIPTION
                "Maximum best effort bandwidth to be used for reassociation."
            DEFVAL { 40 }
            ::= { wirelessQoS 5 }


        -- 1.3.6.1.4.1.4329.15.3.3.3.1.6
        maxBestEffortBWforAssociation OBJECT-TYPE
            SYNTAX Integer32 (0..100)
            MAX-ACCESS read-write
            STATUS current
            DESCRIPTION
                "Maximum best effort bandwidth to be used for association."
            DEFVAL { 30 }
            ::= { wirelessQoS 6 }

        -- 1.3.6.1.4.1.4329.15.3.3.3.1.7
        maxBackgroundBWforReassociation OBJECT-TYPE
            SYNTAX Integer32 (0..100)
            MAX-ACCESS read-write
            STATUS current
            DESCRIPTION
                "Maximum background bandwidth to be used for reassociation. "
            DEFVAL { 30 }
            ::= { wirelessQoS 7 }


        -- 1.3.6.1.4.1.4329.15.3.3.3.1.8
        maxBackgroundBWforAssociation OBJECT-TYPE
            SYNTAX Integer32 (0..100)
            MAX-ACCESS read-write
            STATUS current
            DESCRIPTION
                "Maximum background bandwidth to be used for association. "
            DEFVAL { 20 }
            ::= { wirelessQoS 8 }

            

        
        -- 1.3.6.1.4.1.4329.15.3.3.3.2
        radiusInfo OBJECT IDENTIFIER ::= { vnsGlobalSetting 2 }

        
        -- 1.3.6.1.4.1.4329.15.3.3.3.2.2
        externalRadiusServerTable OBJECT-TYPE
            SYNTAX SEQUENCE OF ExternalRadiusServerEntry
            MAX-ACCESS not-accessible
            STATUS obsolete
            DESCRIPTION
                "Table of external RADIUS servers available for authentication services."
            ::= { radiusInfo 2 }

        
        -- 1.3.6.1.4.1.4329.15.3.3.3.2.2.1
        externalRadiusServerEntry OBJECT-TYPE
            SYNTAX ExternalRadiusServerEntry
            MAX-ACCESS not-accessible
            STATUS obsolete
            DESCRIPTION
                "Configuration information about the RADIUS server entry."
            INDEX { externalRadiusServerName }
            ::= { externalRadiusServerTable 1 }

        
        ExternalRadiusServerEntry ::=
            SEQUENCE { 
                externalRadiusServerName
                    DisplayString,
                externalRadiusServerAddress
                    DisplayString,
                externalRadiusServerSharedSecret
                    OCTET STRING,
                externalRadiusServerRowStatus
                    RowStatus
             }

        -- 1.3.6.1.4.1.4329.15.3.3.3.2.2.1.1
        externalRadiusServerName OBJECT-TYPE
            SYNTAX DisplayString
            MAX-ACCESS read-write
            STATUS obsolete
            DESCRIPTION
                "RADIUS server name."
            ::= { externalRadiusServerEntry 1 }

        
        -- 1.3.6.1.4.1.4329.15.3.3.3.2.2.1.2
        externalRadiusServerAddress OBJECT-TYPE
            SYNTAX DisplayString
            MAX-ACCESS read-write
            STATUS obsolete
            DESCRIPTION
                "RADIUS server address, it can be either string or IP address."
            ::= { externalRadiusServerEntry 2 }

        
        -- 1.3.6.1.4.1.4329.15.3.3.3.2.2.1.3
        externalRadiusServerSharedSecret OBJECT-TYPE
            SYNTAX OCTET STRING (SIZE (0..64))
            MAX-ACCESS read-write
            STATUS obsolete
            DESCRIPTION
                "Shared secret between Radius and the client."
            ::= { externalRadiusServerEntry 3 }

        
        -- 1.3.6.1.4.1.4329.15.3.3.3.2.2.1.4
        externalRadiusServerRowStatus OBJECT-TYPE
            SYNTAX RowStatus
            MAX-ACCESS read-write
            STATUS obsolete
            DESCRIPTION
                "Row Status for the entry."
            ::= { externalRadiusServerEntry 4 }

        
        -- 1.3.6.1.4.1.4329.15.3.3.3.3
        dasInfo OBJECT IDENTIFIER ::= { vnsGlobalSetting 3 }

        
        -- 1.3.6.1.4.1.4329.15.3.3.3.3.1
        dasPort OBJECT-TYPE
            SYNTAX Integer32 (1024..65535)
            MAX-ACCESS read-write
            STATUS current
            DESCRIPTION
                "Dynamic Authorization Server (DAS) port. "
            DEFVAL { 3799 }
            ::= { dasInfo 1 }

        
        -- 1.3.6.1.4.1.4329.15.3.3.3.3.2
        dasReplayInterval OBJECT-TYPE
            SYNTAX Integer32 (0..1000)
            UNITS "seconds"
            MAX-ACCESS read-write
            STATUS current
            DESCRIPTION
                "The time window for message timeliness and replay protection
                for DAS packets. Packets should be dropped that their time
                generation is outside of this specified interval.
                Value zero indicates that the timeliness checking will be performed."
            DEFVAL { 300 }
            ::= { dasInfo 2 }

        
        -- 1.3.6.1.4.1.4329.15.3.3.3.4
        advancedFilteringMode OBJECT-TYPE
            SYNTAX INTEGER
                {
                disabled(0),
                enabled(1)
                }
            MAX-ACCESS read-write
            STATUS current
            DESCRIPTION
                "Value of 'enabled(1)' means EWC is operating in advanced filtering configuration mode.
                Value of 'disabled(0)' means EWC is operating in mode that is compatible with releases
                prior to 7.41. This field can only be set to 'enabled(1)' and after setting it to that
                value, the only way to undo that is by resetting the database."
            ::= { vnsGlobalSetting 4 }

        
        -- 1.3.6.1.4.1.4329.15.3.3.3.5
        radiusStrictMode OBJECT-TYPE
            SYNTAX INTEGER
                {
                strictModeDisabled(0),
                strictModeEnabled(1)
                }
            MAX-ACCESS read-write
            STATUS current
            DESCRIPTION
                "If this variable set to true, then assignment of RADIUS server(s) to WLAN
                are automatic during WLAN creation, otherwise, assignment of RADIUS server(s)
                to WLAN must be done manually. "
            ::= { vnsGlobalSetting 5 }




        -- 1.3.6.1.4.1.4329.15.3.3.3.6
        radiusFastFailoverEvents OBJECT IDENTIFIER ::= { vnsGlobalSetting 6 }

        -- 1.3.6.1.4.1.4329.15.3.3.3.6.1
        radiusFastFailoverEventsTable OBJECT-TYPE
            SYNTAX SEQUENCE OF RadiusFastFailoverEventsEntry
            MAX-ACCESS not-accessible
            STATUS current
            DESCRIPTION
                "Table in which to configure which RADIUS servers will be sent interim accounting 
                reports for stations when a fast failover incident occurs "
            ::= { radiusFastFailoverEvents 1 }

        
        -- 1.3.6.1.4.1.4329.15.3.3.3.6.1.1
        radiusFastFailoverEventsEntry OBJECT-TYPE
            SYNTAX RadiusFastFailoverEventsEntry
            MAX-ACCESS not-accessible
            STATUS current
            DESCRIPTION
                "An entry for each radius server."
            INDEX { radiusFFOEid }
            ::= { radiusFastFailoverEventsTable 1 }

        
        RadiusFastFailoverEventsEntry ::=
            SEQUENCE { 
                radiusFFOEid
                    DisplayString,
                fastFailoverEvents
                    INTEGER
             }
                    
        -- 1.3.6.1.4.1.4329.15.3.3.3.6.1.1
        radiusFFOEid OBJECT-TYPE
            SYNTAX DisplayString (SIZE (1..64))
            MAX-ACCESS not-accessible
            STATUS current
            DESCRIPTION
                "The IP address or hostname of configured radius server. If the hostname is created from GUI/CLI 
                and the size is bigger than 64 characters, snmp will display the first 64 characters only. "
            ::= { radiusFastFailoverEventsEntry 1 }


        -- 1.3.6.1.4.1.4329.15.3.3.3.6.1.2
        fastFailoverEvents OBJECT-TYPE
            SYNTAX INTEGER
                {
                fastFailoverEventsDisabled(0),
                fastFailoverEventsEnabled(1)
                }
            MAX-ACCESS read-write
            STATUS current
            DESCRIPTION
                "If true, send an interim accounting record to the RADIUS server for each affected 
                station when a fast failover event occurs. This field can be modified when controller
                is operated in availablity paired mode and fast failover is enabled "
            ::= { radiusFastFailoverEventsEntry 2 }




        -- 1.3.6.1.4.1.4329.15.3.3.3.7
        dhcpRelayListeners OBJECT IDENTIFIER ::= { vnsGlobalSetting 7 }

        -- 1.3.6.1.4.1.4329.15.3.3.3.7.1
        dhcpRelayListenersMaxEntries OBJECT-TYPE
            SYNTAX Unsigned32
            MAX-ACCESS read-only
            STATUS current
            DESCRIPTION
                "Maximum number of servers to which DHCP messages are relayed ."
            ::= { dhcpRelayListeners 1 }

        
        -- 1.3.6.1.4.1.4329.15.3.3.3.7.2
        dhcpRelayListenersNumEntries OBJECT-TYPE
            SYNTAX Unsigned32
            MAX-ACCESS read-only
            STATUS current
            DESCRIPTION
                "The current number of entries in the dhcpRelayListenersTable."
            ::= { dhcpRelayListeners 2 }

        
        -- 1.3.6.1.4.1.4329.15.3.3.3.7.3
        dhcpRelayListenersNextIndex OBJECT-TYPE
            SYNTAX Integer32
            MAX-ACCESS read-only
            STATUS current
            DESCRIPTION
                "This object indicates numerically lowest available index within this entity,
                which may be used for the value of index in the creation of new entry in
                dhcpRelayListenersTable. An index is considered available if the index falls within the 
                range of 1 to dhcpRelayListenersMaxEntries and it is not being used to index an existing 
                entry in the dhcpRelayListenersTable contained this entity. This value should only be used
                as guideline for the management application and there is no requirement on the
                management application to create entries based upon this index value. 
                Value of zero indicates there is no more room for new dhcpRelayListenersTable creation."
            ::= { dhcpRelayListeners 3 }

        -- 1.3.6.1.4.1.4329.15.3.3.3.7.4
        dhcpRelayListenersTable OBJECT-TYPE
            SYNTAX SEQUENCE OF DHCPRelayingIPaddressEntry
            MAX-ACCESS not-accessible
            STATUS current
            DESCRIPTION
                "A list of servers to which DHCP messages are relayed but from which no responses are 
                expected. "
            ::= { dhcpRelayListeners 4 }

        
        -- 1.3.6.1.4.1.4329.15.3.3.3.7.4.4.1
        dhcpRelayListenersEntry OBJECT-TYPE
            SYNTAX DHCPRelayingIPaddressEntry
            MAX-ACCESS not-accessible
            STATUS current
            DESCRIPTION
                "An entry for each dhcpRelayListeners."
            INDEX { dhcpRelayListenersID }
            ::= { dhcpRelayListenersTable 1 }

        
        DHCPRelayingIPaddressEntry ::=
            SEQUENCE { 
                dhcpRelayListenersID
                    Unsigned32,
                dhcpRelayListenersRowStatus
                    RowStatus,
                destinationName
                    DisplayString,
                destinationIP
                    IpAddress
            }
                    
        -- 1.3.6.1.4.1.4329.15.3.3.3.7.4.4.1.1
        dhcpRelayListenersID OBJECT-TYPE
            SYNTAX Unsigned32
            MAX-ACCESS not-accessible
            STATUS current
            DESCRIPTION
                "The id corresponds to the 'server number' in the controller GUI and CLI."
            ::= { dhcpRelayListenersEntry 1 }


        -- 1.3.6.1.4.1.4329.15.3.3.3.7.4.4.1.2
        dhcpRelayListenersRowStatus OBJECT-TYPE
            SYNTAX RowStatus
            MAX-ACCESS read-create
            STATUS current
            DESCRIPTION
                "This object allows dynamic creation and deletion of entries within dhcpRelayListenersTable 
                as well as activation and deactivation of these entries. For row creation, EWC only supports
                creatAndWait. "
            ::= { dhcpRelayListenersEntry 2 }


        -- 1.3.6.1.4.1.4329.15.3.3.3.7.4.4.1.3
        destinationName OBJECT-TYPE
            SYNTAX DisplayString
            MAX-ACCESS read-write
            STATUS current
            DESCRIPTION
                "Text string uniquely identifying NAC Server Name. Allowable characters for this
                field are from the set of A-Z, a-z, -_!#$, 0-9, and space. max len is 63 chars Howerver, 
                it is recommended to avoid leading and trailing spaces."
            ::= { dhcpRelayListenersEntry 3 }


        -- 1.3.6.1.4.1.4329.15.3.3.3.7.4.4.1.4
        destinationIP OBJECT-TYPE
            SYNTAX IpAddress
            MAX-ACCESS read-write
            STATUS current
            DESCRIPTION
                "IPv4 address to which DHCP messages are relayed."
            ::= { dhcpRelayListenersEntry 4 }


        -- 1.3.6.1.4.1.4329.15.3.3.3.8
        clientAutologinOption OBJECT-TYPE
            SYNTAX INTEGER
                {
                hide(0),
                redirect(1),
                drop(2)
                }
            MAX-ACCESS read-write
            STATUS current
            DESCRIPTION
                "Many devices such as those made by Apple(R) implement an autologin feature that prompts the user 
                to login as soon as the device detects the presence of a Captive Portal. This feature sometimes 
                causes problems for users who actually interact with the captive portal.
                hide(0) - Hide the captive portal from Autologin detector.
                redirect(1) - Redirect detection messages to the Captive Portal. This option is to allow client autologin 
                                   to detect the captive portal & prompt the user to login. This may cause post-authentication
                                   redirection to fail.
                drop(2) - Drop detection messages."
            ::= { vnsGlobalSetting 8 }



        -- 1.3.6.1.4.1.4329.15.3.3.3.9
        authenticationAdvanced OBJECT IDENTIFIER ::= { vnsGlobalSetting 9 }

        
        -- 1.3.6.1.4.1.4329.15.3.3.3.9.1
        includeServiceType OBJECT-TYPE
            SYNTAX INTEGER 
                {
                    disable(0),
                    enable(1)
                }
            MAX-ACCESS read-write
            STATUS current
            DESCRIPTION
                " Include the Service-Type attribute in client access request messages 
                when this field is set to enable(1). "
            ::= { authenticationAdvanced 1 }

        -- 1.3.6.1.4.1.4329.15.3.3.3.9.2
        clientMessageDelayTime OBJECT-TYPE
            SYNTAX Integer32 
            MAX-ACCESS read-write
            STATUS current
            DESCRIPTION
                "This field specifies how long, in seconds, the notice Web page is displayed to the 
                client when the topology changes as a result of a role change. The notice Web page 
                indicates that authentication was successful and that the user must close all 
                browser windows and then restart the browser for access to the network.
                Currently this is supported for Internal Captive Portal, Guest Portal, and 
                Guest Splash. "
            ::= { authenticationAdvanced 2 }
            
        -- 1.3.6.1.4.1.4329.15.3.3.3.9.3
        radiusAccounting OBJECT-TYPE
            SYNTAX INTEGER 
                {
                    disable(0),
                    enable(1)
                }
            MAX-ACCESS read-write
            STATUS current
            DESCRIPTION
                "This field enables or disables RADIUS accounting.  Disabling RADIUS accounting 
                overrides the RADIUS accounting settings of individual WLAN Services. Enabling 
                RADIUS accounting activates RADIUS accounting only in WLAN Services specifically 
                configured to perform it."
            ::= { authenticationAdvanced 3 }

        -- 1.3.6.1.4.1.4329.15.3.3.3.9.4
        serverUsageModel OBJECT-TYPE
            SYNTAX INTEGER 
                {
                    roundRobin(0),
                    primaryBackup(1)
                }
            MAX-ACCESS read-write
            STATUS current
            DESCRIPTION
                "This field specifies RADIUS server failover behavior when the primary server goes down. 
                When the primary server is down the controller moves on to the secondary or tertiary configured RADIUS Servers. 
                If this field is set to primaryBackup(1), then the controller starts polling the primary RADIUS server to see if it 
                is up. When the primary RADIUS server comes back, the controller automatically starts sending new access 
                requests to the primary RADIUS server but pending requests continue with backup RADIUS server.
                The administrator can select between the two strategies, i.e. the existing 
                roundRobin(0) or new primaryBackup(1). This only applies to Authentication, not to Accounting."
            ::= { authenticationAdvanced 4 }


        -- 1.3.6.1.4.1.4329.15.3.3.3.9.5
        radacctStartOnIPAddr OBJECT-TYPE
            SYNTAX INTEGER 
                {
                    disable(0),
                    enable(1)
                }
            MAX-ACCESS read-write
            STATUS current
            DESCRIPTION
                "When this OID is set to disabled (0) the controller sends a RADIUS accounting 
                start message as soon as it receives an Access-Accept for the user from a RADIUS 
                server. When this OID is set to enabled(1) the controller defers sending the 
                RADIUS accounting start message until an Access-Accept for the client is 
                received and the client's IP address is known."
            ::= { authenticationAdvanced 5 }
            

        -- 1.3.6.1.4.1.4329.15.3.3.3.9.6
        clientServiceTypeLogin OBJECT-TYPE
            SYNTAX INTEGER 
                {
                    disable(0),
                    enable(1)
                }
            MAX-ACCESS read-write
            STATUS current
            DESCRIPTION
                "When this OID is set to enabled(1) the controller sets the Service-Type
                attribute of a station's Access-Request to 'Login'. When this OID is set to
                disabled(0) the controller sets the Service-Type attribute of a station's 
                Access-Request to 'Framed'. By default this OID is set to 'disabled'.
                You cannot use RADIUS servers to authenticate administrators 
                for local server access when this OID is set to 'enabled'."
            ::= { authenticationAdvanced 6 }
    

        -- 1.3.6.1.4.1.4329.15.3.3.3.9.7
        applyMacAddressFormat OBJECT-TYPE
            SYNTAX INTEGER 
                {
                    disable(0),
                    enable(1)
                }
            MAX-ACCESS read-write
            STATUS current
            DESCRIPTION
                "When this OID is set to enabled(1), the controller uses MAC-Based 
                Authentication MAC address format (refer to radiusMacAddressFormatOption)
                for user authentication and accounting via RADIUS."
            ::= { authenticationAdvanced 7 }



        -- 1.3.6.1.4.1.4329.15.3.3.3.10
        radiusExtnsSetting OBJECT IDENTIFIER ::= { vnsGlobalSetting 10 }

        -- 1.3.6.1.4.1.4329.15.3.3.3.10.1
        radiusExtnsSettingTable OBJECT-TYPE
            SYNTAX SEQUENCE OF RadiusExtnsSettingEntry
            MAX-ACCESS not-accessible
            STATUS current
            DESCRIPTION
                "List of RADIUS servers that will be used. "
            ::= { radiusExtnsSetting 1 }

        
        -- 1.3.6.1.4.1.4329.15.3.3.3.10.1.1
        radiusExtnsSettingEntry OBJECT-TYPE
            SYNTAX RadiusExtnsSettingEntry
            MAX-ACCESS not-accessible
            STATUS current
            DESCRIPTION
                "An entry for each RADIUS server."
            INDEX { radiusExtnsIndex }
            ::= { radiusExtnsSettingTable 1 }

        
        RadiusExtnsSettingEntry ::=
            SEQUENCE { 
            radiusExtnsIndex
                Integer32,
            pollingMechanism
                INTEGER,
            serverPollingInterval
                Integer32
             }
                    
        -- 1.3.6.1.4.1.4329.15.3.3.3.10.1.1
        radiusExtnsIndex OBJECT-TYPE
            SYNTAX Integer32( 1..2147483647 )
            MAX-ACCESS not-accessible
            STATUS current
            DESCRIPTION
                "A number uniquely identifying each conceptual row in the radiusExtnsSettingTable. 
                This value also equivalent to etsysRadiusAuthServerIndex of enterasys-radius-auth-client-mib.txt 
                file."
            ::= { radiusExtnsSettingEntry 1 }


        -- 1.3.6.1.4.1.4329.15.3.3.3.10.1.2
        pollingMechanism OBJECT-TYPE
            SYNTAX INTEGER
                {
            authorizeAsActualUser(0),
            useRFC5997StatusServerRequest(1)
                }
            MAX-ACCESS read-write
            STATUS current
            DESCRIPTION
                "This field specifies the method to determine the health of the RADIUS server.  If set to 
                useRFC5997StatusServerRequest(1), RFC 5997 Status-Server packets will be sent to the 
                primary server to determine it's health.  If set to authorizeAsActualUser(0), access-request
                messages for a specified user account will be sent to the primary server to determine it's health."
            ::= { radiusExtnsSettingEntry 2 }


        -- 1.3.6.1.4.1.4329.15.3.3.3.10.1.3
        serverPollingInterval OBJECT-TYPE
            SYNTAX Integer32
            MAX-ACCESS read-write
            STATUS current
            DESCRIPTION
                "Interval in seconds for the controller to poll the primary server."
            ::= { radiusExtnsSettingEntry 3 }



 
        -- 1.3.6.1.4.1.4329.15.3.3.3.1
        netflowAndMirrorN OBJECT IDENTIFIER ::= { vnsGlobalSetting 11 }

        
        -- 1.3.6.1.4.1.4329.15.3.3.3.11.1
       netflowDestinationIP OBJECT-TYPE
            SYNTAX IpAddress
            MAX-ACCESS read-write
            STATUS current
            DESCRIPTION
                "The IP address for the Purview engine that will receive netflow records."
            ::= { netflowAndMirrorN 1 }

        
        -- 1.3.6.1.4.1.4329.15.3.3.3.11.2
        netflowInterval OBJECT-TYPE
            SYNTAX Integer32 (30..360)
            MAX-ACCESS read-write
            STATUS current
            DESCRIPTION
                "The netflow record sending interval."
            DEFVAL { 60 }
            ::= { netflowAndMirrorN 2 }

        -- 1.3.6.1.4.1.4329.15.3.3.3.11.3
        mirrorFirstN OBJECT-TYPE
            SYNTAX Integer32 
            MAX-ACCESS read-write
            STATUS current
            DESCRIPTION
                "If non-zero, the first N packets of a particular flow will be mirrored.  If 0, all packets will be mirrored."
            DEFVAL { 15 }
            ::= { netflowAndMirrorN 3 }

        -- 1.3.6.1.4.1.4329.15.3.3.3.11.4
        mirrorL2Ports OBJECT-TYPE
            SYNTAX OCTET STRING
            MAX-ACCESS read-write
            STATUS current
            DESCRIPTION
                "Configure the mirror port(s) on the controller. The default value is None. 
                Only l2ports will be allowed to be selected and only when not referred to
                elsewhere (lag, topologies). 
                The most significant bit of the most significant octet represents the first esa port (esa0).
                The second most significant bit of the most significant octet represents the second esa port (esa1) and so on."
            ::= { netflowAndMirrorN 4 }


        -- 1.3.6.1.4.1.4329.15.3.3.3.12
        radiusMacAddressFormatOption OBJECT-TYPE
            SYNTAX INTEGER
                {
                option1(1),
                option2(2),
                option3(3),
                option4(4),
                option5(5),
                option6(6),
                option7(7),
                option8(9),
                option10(10),
                option11(11),
                option12(12)
                }
            MAX-ACCESS read-write
            STATUS current
            DESCRIPTION
                "The controller allows configuring different kinds of Mac address format in RADIUS messages.
                option1:  mac address format as XXXXXXXXXXXX
                option2:  mac address format as XX:XX:XX:XX:XX:XX
                option3:  mac address format as XX-XX-XX-XX-XX-XX
                option4:  mac address format as XXXX.XXXX.XXXX
                option5:  mac address format as XXXXXX-XXXXXX
                option6:  mac address format as XX XX XX XX XX XX
                option7:  mac address format as xxxxxxxxxxxx
                option8:  mac address format as xx:xx:xx:xx:xx:xx
                option9:  mac address format as xx-xx-xx-xx-xx-xx
                option10:  mac address format as xxxx.xxxx.xxxx
                option11:  mac address format as xxxxxx-xxxxxx
                option12:  mac address format as xx xx xx xx xx xx"
            ::= { vnsGlobalSetting 12 }

            


        
        -- 1.3.6.1.4.1.4329.15.3.3.4
        wlan OBJECT IDENTIFIER ::= { virtualNetworks 4 }

        
        -- 1.3.6.1.4.1.4329.15.3.3.4.1
        wlanMaxEntries OBJECT-TYPE
            SYNTAX Unsigned32
            MAX-ACCESS read-only
            STATUS current
            DESCRIPTION
                "Maximum number of WLAN supported by the device."
            ::= { wlan 1 }

        
        -- 1.3.6.1.4.1.4329.15.3.3.4.2
        wlanNumEntries OBJECT-TYPE
            SYNTAX Unsigned32
            MAX-ACCESS read-only
            STATUS current
            DESCRIPTION
                "The current number of entries in the wlanTable."
            ::= { wlan 2 }

        
        -- 1.3.6.1.4.1.4329.15.3.3.4.3
        wlanTableNextAvailableIndex OBJECT-TYPE
            SYNTAX Integer32
            MAX-ACCESS read-only
            STATUS current
            DESCRIPTION
                "This object indicates numerically lowest available index within this entity,
                which may be used for the value of index in the creation of new entry in
                wlanTable. An index is considered available if the index falls within the 
                range of 1 to wlanMaxEntries and it is not being used to index an existing 
                entry in the wlanTable contained this entity. This value should only be used
                as guideline for the management application and there is no requirement on the
                management application to create entries based upon this index value. 
                Value of zero indicates there is no more room for new wlanTable creation."
            ::= { wlan 3 }

        
        -- 1.3.6.1.4.1.4329.15.3.3.4.4
        wlanTable OBJECT-TYPE
            SYNTAX SEQUENCE OF WlanEntry
            MAX-ACCESS not-accessible
            STATUS current
            DESCRIPTION
                "Table of configured WLAN. "
            ::= { wlan 4 }

        
        -- 1.3.6.1.4.1.4329.15.3.3.4.4.1
        wlanEntry OBJECT-TYPE
            SYNTAX WlanEntry
            MAX-ACCESS not-accessible
            STATUS current
            DESCRIPTION
                "An entry for each WLAN."
            INDEX { wlanID }
            ::= { wlanTable 1 }

        
        WlanEntry ::=
            SEQUENCE { 
                wlanID
                    Unsigned32,
                wlanRowStatus
                    RowStatus,
                wlanServiceType
                    INTEGER,
                wlanName
                    DisplayString,
                wlanSSID
                    DisplayString,
                wlanSynchronize
                    TruthValue,
                wlanEnabled
                    TruthValue,
                wlanDefaultTopologyID
                    INTEGER,
                wlanSessionTimeout
                    Unsigned32,
                wlanIdleTimeoutPreAuth
                    Unsigned32,
                wlanIdleSessionPostAuth
                    Unsigned32,
                wlanSupressSSID
                    TruthValue,
                wlanDot11hSupport
                    TruthValue,
                wlanDot11hClientPowerReduction
                    TruthValue,
                wlanProcessClientIE
                    TruthValue,
                wlanEngerySaveMode
                    TruthValue,
                wlanBlockMuToMuTraffic
                    TruthValue,
                wlanRemoteable
                    TruthValue,
                wlanVNSID
                    Unsigned32,
                wlanRadioManagement11k
                    INTEGER,
                wlanBeaconReport
                    INTEGER,
                wlanQuietIE
                    INTEGER,
                wlanMirrorN
                   INTEGER,
                wlanNetFlow
                   INTEGER,
                wlanAppVisibility
                   INTEGER
    }

        -- 1.3.6.1.4.1.4329.15.3.3.4.4.1.1
        wlanID OBJECT-TYPE
            SYNTAX Unsigned32
            MAX-ACCESS read-only
            STATUS current
            DESCRIPTION
                "Unique internal ID associated with WLAN."
            ::= { wlanEntry 1 }

        
        -- 1.3.6.1.4.1.4329.15.3.3.4.4.1.2
        wlanRowStatus OBJECT-TYPE
            SYNTAX RowStatus
            MAX-ACCESS read-write
            STATUS current
            DESCRIPTION
                "This object allows dynamic creation and deletion of entries within wlanTable as well
                as activation and deactivation of these entries. For row creation, EWC only supports
                creatAndWait. WLAN name must be set before making the row active and persistent. Any
                WLAN that is associated to a VNS cannot be deleted unless it is first disassociated
                from VNS before being deleted. Any inactive entry will not be persistent and it will
                be lost during controller's restart."
            ::= { wlanEntry 2 }

        
        -- 1.3.6.1.4.1.4329.15.3.3.4.4.1.3
        wlanServiceType OBJECT-TYPE
            SYNTAX INTEGER
                {
                standard(0),
                wds(3),
                thirdParty(4),
                remote(5),
                mesh(6)
                }
            MAX-ACCESS read-write
            STATUS current
            DESCRIPTION
                "Service type of WLAN."
            DEFVAL { standard }
            ::= { wlanEntry 3 }

        
        -- 1.3.6.1.4.1.4329.15.3.3.4.4.1.4
        wlanName OBJECT-TYPE
            SYNTAX DisplayString
            MAX-ACCESS read-write
            STATUS current
            DESCRIPTION
                "Text string uniquely identifying WLAN within EWC. Allowable characters for this
                field are from the set of A-Z, a-z, -!#$:, 0-9, and space. Howerver, it is recommended
                to avoid leading and trailing spaces."
            ::= { wlanEntry 4 }

        
        -- 1.3.6.1.4.1.4329.15.3.3.4.4.1.5
        wlanSSID OBJECT-TYPE
            SYNTAX DisplayString (SIZE (1..32))
            MAX-ACCESS read-write
            STATUS current
            DESCRIPTION
                "SSID (broadcast string) associated with WLAN. Allowable characters for this field are 
                from the set of A-Z, a-z, _-.@, 0-9, and space. Howerver, it is recommendedto avoid 
                leading and trailing spaces."
            ::= { wlanEntry 5 }

        
        -- 1.3.6.1.4.1.4329.15.3.3.4.4.1.6
        wlanSynchronize OBJECT-TYPE
            SYNTAX TruthValue
            MAX-ACCESS read-write
            STATUS current
            DESCRIPTION
                "If it is set to true, then WLAN will be replicated to peer controller if
                availability is configured and enabled."
            DEFVAL { 1 }
            ::= { wlanEntry 6 }

        
        -- 1.3.6.1.4.1.4329.15.3.3.4.4.1.7
        wlanEnabled OBJECT-TYPE
            SYNTAX TruthValue
            MAX-ACCESS read-write
            STATUS current
            DESCRIPTION
                "This field is used to enable or disable this WLAN. If WLAN is disabled, then no traffic
                will be passed on behalf of this WLAN."
            DEFVAL { 1 }
            ::= { wlanEntry 7 }

        
        -- 1.3.6.1.4.1.4329.15.3.3.4.4.1.8
        wlanDefaultTopologyID OBJECT-TYPE
            SYNTAX INTEGER (-1 | 0..65535)
            MAX-ACCESS read-write
            STATUS current
            DESCRIPTION
                "The ID of topology from topologyTable associated to this WLAN. Topology
                ID of -1 means no default topology is associated to this WLAN. Physical
                topologies cannot be assigned to WLAN. The default topology indicates which
                topology to use for this WLAN if there is no topology associated with VNS via
                policy assignment."
            ::= { wlanEntry 8 }

        
        -- 1.3.6.1.4.1.4329.15.3.3.4.4.1.9
        wlanSessionTimeout OBJECT-TYPE
            SYNTAX Unsigned32
            UNITS "minute"
            MAX-ACCESS read-write
            STATUS current
            DESCRIPTION
                "MU session that is associated to this WLAN will be terminated after elapse of this
                number of minutes from the start of its current session."
            DEFVAL { 0 }
            ::= { wlanEntry 9 }

        
        -- 1.3.6.1.4.1.4329.15.3.3.4.4.1.10
        wlanIdleTimeoutPreAuth OBJECT-TYPE
            SYNTAX Unsigned32
            UNITS "minute"
            MAX-ACCESS read-write
            STATUS current
            DESCRIPTION
                "Elapse time between association and authentication after which MU session will be 
                terminated if the user is idle this amount of time without being authenticated."
            DEFVAL { 5 }
            ::= { wlanEntry 10 }

        
        -- 1.3.6.1.4.1.4329.15.3.3.4.4.1.11
        wlanIdleSessionPostAuth OBJECT-TYPE
            SYNTAX Unsigned32
            UNITS "minute"
            MAX-ACCESS read-write
            STATUS current
            DESCRIPTION
                "MU session that is associated to this WLAN will be terminated if the user is idle this
                amount of time after being authenticated."
            DEFVAL { 30 }
            ::= { wlanEntry 11 }

        
        -- 1.3.6.1.4.1.4329.15.3.3.4.4.1.12
        wlanSupressSSID OBJECT-TYPE
            SYNTAX TruthValue
            MAX-ACCESS read-write
            STATUS current
            DESCRIPTION
                "If it is set to true then broadcast string (SSID) for this WLAN will not be broadcasted
                over the air."
            DEFVAL { 2 }
            ::= { wlanEntry 12 }

        
        -- 1.3.6.1.4.1.4329.15.3.3.4.4.1.13
        wlanDot11hSupport OBJECT-TYPE
            SYNTAX TruthValue
            MAX-ACCESS read-write
            STATUS current
            DESCRIPTION
                "If it is set to true then dot11h support is enabled for clients associated to this WLAN."
            DEFVAL { 2 }
            ::= { wlanEntry 13 }

        
        -- 1.3.6.1.4.1.4329.15.3.3.4.4.1.14
        wlanDot11hClientPowerReduction OBJECT-TYPE
            SYNTAX TruthValue
            MAX-ACCESS read-write
            STATUS current
            DESCRIPTION
                "If it is set to true then apply power reduction to dot11h clients associated to this WLAN.
                This field has meaning if wlanDot11hSupport is enabled (set to true)."
            DEFVAL { 2 }
            ::= { wlanEntry 14 }

        
        -- 1.3.6.1.4.1.4329.15.3.3.4.4.1.15
        wlanProcessClientIE OBJECT-TYPE
            SYNTAX TruthValue
            MAX-ACCESS read-write
            STATUS current
            DESCRIPTION
                "If it is set to true then clients that are associated to this WLAN their IE requests 
                will be processed."
            DEFVAL { 2 }
            ::= { wlanEntry 15 }

        
        -- 1.3.6.1.4.1.4329.15.3.3.4.4.1.16
        wlanEngerySaveMode OBJECT-TYPE
            SYNTAX TruthValue
            MAX-ACCESS read-write
            STATUS current
            DESCRIPTION
                "If it is set to true then engergy saving mode is enabled."
            DEFVAL { 2 }
            ::= { wlanEntry 16 }

        
        -- 1.3.6.1.4.1.4329.15.3.3.4.4.1.17
        wlanBlockMuToMuTraffic OBJECT-TYPE
            SYNTAX TruthValue
            MAX-ACCESS read-write
            STATUS current
            DESCRIPTION
                "If it is set to true then two MU associated to this WLAN cannot communicate with each
                other."
            DEFVAL { 2 }
            ::= { wlanEntry 17 }

        
        -- 1.3.6.1.4.1.4329.15.3.3.4.4.1.18
        wlanRemoteable OBJECT-TYPE
            SYNTAX TruthValue
            MAX-ACCESS read-write
            STATUS current
            DESCRIPTION
                "If it is set to true then this WLAN can be used as remote WLAN within mobility zone
                that this controller is partaking."
            DEFVAL { 2 }
            ::= { wlanEntry 18 }

        
        -- 1.3.6.1.4.1.4329.15.3.3.4.4.1.19
        wlanVNSID OBJECT-TYPE
            SYNTAX Unsigned32
            MAX-ACCESS read-only
            STATUS current
            DESCRIPTION
                "The ID of the VNS that uses this WLAN. WLAN can be created but not used in any
                VNS, in that case alue of zero indicates WLAN has not been used in any VNS.  
                The value of this field set during VNS creation no during the WLAN creation. "
            DEFVAL { 0 }
            ::= { wlanEntry 19 }


        -- 1.3.6.1.4.1.4329.15.3.3.4.4.1.20
        wlanRadioManagement11k OBJECT-TYPE
        SYNTAX INTEGER
        {
            disable(0),
            enable(1)
        }
        MAX-ACCESS read-write
        STATUS current
        DESCRIPTION
                "When this bit is set to enable, the Radio Management (802.11k) feature is enabled on those 
                  APs who have this wlan configuration and 802.11k capability. "
             ::= { wlanEntry 20}


        -- 1.3.6.1.4.1.4329.15.3.3.4.4.1.21
        wlanBeaconReport OBJECT-TYPE
        SYNTAX INTEGER
        {
            disable(0),
            enable(1)
        }
        MAX-ACCESS read-write
        STATUS current
        DESCRIPTION
                "Enable/disable AP to send out beacon report. This field is configurable only if 
                wlanRadioManagement11k is set to enable(1)."
             ::= { wlanEntry 21}


        -- 1.3.6.1.4.1.4329.15.3.3.4.4.1.22
        wlanQuietIE OBJECT-TYPE
        SYNTAX INTEGER
        {
            disable(0),
            enable(1)
        }
        MAX-ACCESS read-write
        STATUS current
        DESCRIPTION
                "Enable/disable AP to advertise a Quiet Element. This field is configurable only if 
                wlanRadioManagement11k is set to enable(1)."
             ::= { wlanEntry 22}

        -- 1.3.6.1.4.1.4329.15.3.3.4.4.1.23
        wlanMirrorN OBJECT-TYPE
        SYNTAX INTEGER
        {
            prohibited(0),
            bothDirection(1),
            rxDirectionOnly(2)
        }
        MAX-ACCESS read-write
        STATUS current
        DESCRIPTION
                "prohibited(0): Mirroring is prohibited. 
                 bothDirection(1) :  Both direction packets will be mirrored.
                 rxDirectionOnly(2): Only receive direction packets will be mirrored.
                 Note: This will only take effect when the user's runtime current Roles's MirrorN action is None. "
             ::= { wlanEntry 23}


        -- 1.3.6.1.4.1.4329.15.3.3.4.4.1.24
        wlanNetFlow OBJECT-TYPE
        SYNTAX INTEGER
        {
            disable(0),
            enable(1)
        }
        MAX-ACCESS read-write
        STATUS current
        DESCRIPTION
                "Enable/disable netflow on this WLAN service."
             ::= { wlanEntry 24}


        -- 1.3.6.1.4.1.4329.15.3.3.4.4.1.25
        wlanAppVisibility OBJECT-TYPE
        SYNTAX INTEGER
        {
            enable(1),
            disable(2)
        }
        MAX-ACCESS read-write
        STATUS current
        DESCRIPTION
                "Enable/disable both application visibility and control for this WLAN service."
             ::= { wlanEntry 25}


        
        -- 1.3.6.1.4.1.4329.15.3.3.4.5
        wlanStatsTable OBJECT-TYPE
            SYNTAX SEQUENCE OF WlanStatsEntry
            MAX-ACCESS not-accessible
            STATUS current
            DESCRIPTION
                "Stats related to WLAN (RFS) created on EWC."
            ::= { wlan 5 }

        
        -- 1.3.6.1.4.1.4329.15.3.3.4.5.1
        wlanStatsEntry OBJECT-TYPE
            SYNTAX WlanStatsEntry
            MAX-ACCESS not-accessible
            STATUS current
            DESCRIPTION
                "An entery for each existing WLAN on EWC."
            INDEX { wlanStatsID }
            ::= { wlanStatsTable 1 }

        
        WlanStatsEntry ::=
            SEQUENCE { 
                wlanStatsID
                    Unsigned32,
                wlanStatsAssociatedClients
                    Counter32,
                wlanStatsRadiusTotRequests
                    Counter32,
                wlanStatsRadiusReqFailed
                    Counter32,
                wlanStatsRadiusReqRejected
                    Counter32
             }

        -- 1.3.6.1.4.1.4329.15.3.3.4.5.1.1
        wlanStatsID OBJECT-TYPE
            SYNTAX Unsigned32
            MAX-ACCESS read-only
            STATUS current
            DESCRIPTION
                "Unique internal ID associated with WLAN."
            ::= { wlanStatsEntry 1 }

        
        -- 1.3.6.1.4.1.4329.15.3.3.4.5.1.2
        wlanStatsAssociatedClients OBJECT-TYPE
            SYNTAX Counter32
            MAX-ACCESS read-only
            STATUS current
            DESCRIPTION
                "Number of clients that are currently associated to this WLAN. "
            ::= { wlanStatsEntry 2 }

        
        -- 1.3.6.1.4.1.4329.15.3.3.4.5.1.3
        wlanStatsRadiusTotRequests OBJECT-TYPE
            SYNTAX Counter32
            MAX-ACCESS read-only
            STATUS current
            DESCRIPTION
                "Number of requests that were sent to RADIUS servers associated to this WLAN on behalf
                of MUs' requests using SSID associated to the WLAN for association, authentication or
                authorization to this WLAN."
            ::= { wlanStatsEntry 3 }

        
        -- 1.3.6.1.4.1.4329.15.3.3.4.5.1.4
        wlanStatsRadiusReqFailed OBJECT-TYPE
            SYNTAX Counter32
            MAX-ACCESS read-only
            STATUS current
            DESCRIPTION
                "Number of requests that were sent to RADIUS servers associated to this WLAN on behalf of
                MUs' requests for association, authentication or authorization to this WLAN but failed 
                to be processed by RADIUS servers."
            ::= { wlanStatsEntry 4 }

        
        -- 1.3.6.1.4.1.4329.15.3.3.4.5.1.5
        wlanStatsRadiusReqRejected OBJECT-TYPE
            SYNTAX Counter32
            MAX-ACCESS read-only
            STATUS current
            DESCRIPTION
                "Number of requests that were sent to RADIUS servers associated to this WLAN on behalf of
                MUs' requests for association, authentication or authorization to this WLAN but rejected
                to be processed by RADIUS servers."
            ::= { wlanStatsEntry 5 }

        
        -- 1.3.6.1.4.1.4329.15.3.3.4.6
        wlanPrivTable OBJECT-TYPE
            SYNTAX SEQUENCE OF WlanPrivEntry
            MAX-ACCESS not-accessible
            STATUS current
            DESCRIPTION
                "This table contains configuration of privacy settings for all configured WLAN on EWC.
                For each of the configured WLAN on the controller one entry is added to this table.
                Addition/deletion of entries in this table are automatic depending on the addition
                or deletion of entries in wlanTable table."
            ::= { wlan 6 }

        
        -- 1.3.6.1.4.1.4329.15.3.3.4.6.1
        wlanPrivEntry OBJECT-TYPE
            SYNTAX WlanPrivEntry
            MAX-ACCESS not-accessible
            STATUS current
            DESCRIPTION
                "An entry in wlanPrivTable for each configured WLAN on EWC. Each entry is indexed
                with corresponding wlan ID of wlanTable. The writable fields in this table can be 
                modified depending on the corresponding wlanTable."
            INDEX { wlanID }
            ::= { wlanPrivTable 1 }

        
        WlanPrivEntry ::=
            SEQUENCE { 
                wlanPrivPrivacyType
                    INTEGER,
                wlanPrivWEPKeyIndex
                    INTEGER,
                wlanPrivWEPKeyLength
                    INTEGER,
                wlanPrivWEPKey
                    DisplayString,
                wlanPrivWPAv1EncryptionType
                    INTEGER,
                wlanPrivWPAv2EncryptionType
                    INTEGER,
                wlanPrivKeyManagement
                    INTEGER,
                wlanPrivBroadcastRekeying
                    TruthValue,
                wlanPrivRekeyInterval
                    Unsigned32,
                wlanPrivGroupKPSR
                    TruthValue,
                wlanPrivWPAPSK
                    OCTET STRING,
                wlanPrivWPAversion
                    INTEGER,
                wlanPrivfastTransition
                    INTEGER,
                wlanPrivManagementFrameProtection
                    INTEGER
             }

        -- 1.3.6.1.4.1.4329.15.3.3.4.6.1.1
        wlanPrivPrivacyType OBJECT-TYPE
            SYNTAX INTEGER
                {
                none(0),
                staticWEP(1),
                dynamicWEP(2),
                wpa(3),
                wpaPSK(4)
                }
            MAX-ACCESS read-write
            STATUS current
            DESCRIPTION
                "Type of privacy applied to the corresponding configured WLAN. Configuration of
                the other fields in this table depends on the value of this field, e.g. if this
                field is set to none(0), then no other field in this table are settable. "
            ::= { wlanPrivEntry 1 }

        
        -- 1.3.6.1.4.1.4329.15.3.3.4.6.1.2
        wlanPrivWEPKeyIndex OBJECT-TYPE
            SYNTAX INTEGER (1..4)
            MAX-ACCESS read-write
            STATUS current
            DESCRIPTION
                "Index of configured WEP.
                This field is required if and only if privacy type is staticWEP(1)."
            ::= { wlanPrivEntry 2 }

        
        -- 1.3.6.1.4.1.4329.15.3.3.4.6.1.3
        wlanPrivWEPKeyLength OBJECT-TYPE
            SYNTAX INTEGER
                {
                sixtyFourBits(1),
                oneHundred28Bits(2),
                oneHundred52Bits(3)
                }
            MAX-ACCESS read-write
            STATUS current
            DESCRIPTION
                "Key legnth for the configured WEP key.
                This field is required if and only if privacy type is staticWEP(1)."
            ::= { wlanPrivEntry 3 }

        
        -- 1.3.6.1.4.1.4329.15.3.3.4.6.1.4
        wlanPrivWEPKey OBJECT-TYPE
            SYNTAX DisplayString (SIZE (8..19))
            MAX-ACCESS read-write
            STATUS current
            DESCRIPTION
                "The configured WEP key length must match the wlanPrivWEPKeyLength field. Any key
                with length longer or shorter than that length will be rejected.
                This field is required if and only if privacy type is staticWEP(1).
                This key can only be viewed in SNMPv3 mode with privacy."
            ::= { wlanPrivEntry 4 }

        
        -- 1.3.6.1.4.1.4329.15.3.3.4.6.1.5
        wlanPrivWPAv1EncryptionType OBJECT-TYPE
            SYNTAX INTEGER
                {
                undefined(0),
                tkipOnly(1),
                auto(2)
                }
            MAX-ACCESS read-write
            STATUS current
            DESCRIPTION
                "The type of encryption used for WPA version 1 associations. This OID is undefined unless 
                 wlanPrivPrivacyType is wpa (3) or wpaPSK (4) and wlanPrivWPAversion is set to 
                 wpaV1 (1) or wpaV1andV2 (3)."
            ::= { wlanPrivEntry 5 }

        
        -- 1.3.6.1.4.1.4329.15.3.3.4.6.1.6
        wlanPrivWPAv2EncryptionType OBJECT-TYPE
            SYNTAX INTEGER
                {
                undefined(0),
                auto(2),
                aesOnly(3)
                }
            MAX-ACCESS read-write
            STATUS current
            DESCRIPTION
                "The type of encryption used for WPA version 2 associations. This OID is undefined 
                 unless wlanPrivPrivacyType is wpa (3) or wpaPSK (4) and wlanPrivWPAversion is 
                 set to wpaV2 (2) or wpaV1 and V2 (3)."
            ::= { wlanPrivEntry 6 }

        
        -- 1.3.6.1.4.1.4329.15.3.3.4.6.1.7
        wlanPrivKeyManagement OBJECT-TYPE
            SYNTAX INTEGER
                {
                none(0),
                opportunisticKey(1),
                preAuthentication(2),
                both(3)
                }
            MAX-ACCESS read-write
            STATUS current
            DESCRIPTION
                "Key management option available for the WPA2.
                This field has meaning if privacy type is WPA with WPA2 option enabled.
                This field can be modified only if wlanPrivPrivacyType is set to wpa(3) and 
                wlanPrivWPAversion set to wpaV2(2) or wpaV1andV2(3).
                ."
            ::= { wlanPrivEntry 7 }

        
        -- 1.3.6.1.4.1.4329.15.3.3.4.6.1.8
        wlanPrivBroadcastRekeying OBJECT-TYPE
            SYNTAX TruthValue
            MAX-ACCESS read-write
            STATUS current
            DESCRIPTION
                "Broadcast rekeying if this value is set to true.
                This field can be modified only if wlanPrivPrivacyType is set to wpa(3) or wpaPSK(4)."
            ::= { wlanPrivEntry 8 }

        
        -- 1.3.6.1.4.1.4329.15.3.3.4.6.1.9
        wlanPrivRekeyInterval OBJECT-TYPE
            SYNTAX Unsigned32 (30..86400)
            UNITS "seconds"
            MAX-ACCESS read-write
            STATUS current
            DESCRIPTION
                "Interval in seconds for requesting rekeying. This field has meaning if privacy
                type is WPA and broadcast rekeying is enabled (wlanPrivBroadcastRekeying is set 
                to true). This field can be modified only if wlanPrivBroadcastRekeying is set to true."
            DEFVAL { 3600 }
            ::= { wlanPrivEntry 9 }

        
        -- 1.3.6.1.4.1.4329.15.3.3.4.6.1.10
        wlanPrivGroupKPSR OBJECT-TYPE
            SYNTAX TruthValue
            MAX-ACCESS read-write
            STATUS current
            DESCRIPTION
                "Group Key Power Save Retry (GKPSR) value for the WPA type of privacy.
                This field can be modified only if wlanPrivPrivacyType is set to wpa(3) or wpaPSK(4)."
            ::= { wlanPrivEntry 10 }

        
        -- 1.3.6.1.4.1.4329.15.3.3.4.6.1.11
        wlanPrivWPAPSK OBJECT-TYPE
            SYNTAX OCTET STRING (SIZE (8..63))
            MAX-ACCESS read-write
            STATUS current
            DESCRIPTION
                "WPA-PSK shared key.  This field has meaning if and only if WLAN privacy type 
                is set to WPA-PSK. Input type can be either HEX formatted string or ASCII string.
                In case of HEX string, it must be 64 octets from set of hex characters.
                In case of ASCII string, the length is limited between 8 to 63 octets.
                This key can only be viewed in SNMPv3 mode with privacy.
                This field can be modified only if wlanPrivPrivacyType is set to wpaPSK(4)."
            ::= { wlanPrivEntry 11 }

        -- 1.3.6.1.4.1.4329.15.3.3.4.6.1.12
        wlanPrivWPAversion OBJECT-TYPE
            SYNTAX INTEGER
                {
                wpaNone(0),
                wpaV1(1),
                wpaV2(2),
                wpaV1andV2(3)
                }
            MAX-ACCESS read-write
            STATUS current
            DESCRIPTION
                "Type of wpa version selected. This field can be modified only if wlanPrivPrivacyType is set to wpa(3) or wpaPSK(4).
                  Note: wpa version v1 only is not allowed.
                0 - no wpa version selected.
                1 - wpa version v1 selected.
                2 - wpa version v2 selected.
                3 - both wpa version v1 and v2 selected."
            ::= { wlanPrivEntry 12 }


        -- 1.3.6.1.4.1.4329.15.3.3.4.6.1.13
        wlanPrivfastTransition OBJECT-TYPE
            SYNTAX INTEGER
                {
                disable(0),
                enable(1)
                 }
            MAX-ACCESS read-write
            STATUS current
            DESCRIPTION
                "When this field is set to enable(1), the 802.11r (fast transition) is enabled.
                This field can be modified only if wlanPrivPrivacyType is set to wpa(2)."
        ::= { wlanPrivEntry 13 }

        -- 1.3.6.1.4.1.4329.15.3.3.4.6.1.14
        wlanPrivManagementFrameProtection OBJECT-TYPE
            SYNTAX INTEGER
                {
                disable(0),
                enable(1),
                require(2)
                 }
            MAX-ACCESS read-write
            STATUS current
            DESCRIPTION
                "Disable(0) : The AP will not encrypt any management frames.
                  Enable(1): The AP will encrypt management frames for clients who also support
                              this feature. If the clients do not support this feature, they are still able to 
                              connect to the AP but with no management frames encryption.
                  Require(2): The AP will only allow clients who have the PMF feature to connect. Supported 
                              management frames will be encrypted to 802.11w standards. Clients who 
                              do not support this feature will not be able to associate. "
        ::= { wlanPrivEntry 14 }


        
        -- 1.3.6.1.4.1.4329.15.3.3.4.7
        wlanAuthTable OBJECT-TYPE
            SYNTAX SEQUENCE OF WlanAuthEntry
            MAX-ACCESS not-accessible
            STATUS current
            DESCRIPTION
                "This table contains configuration of authentication settings for all configured WLAN
                on EWC. For each of the configured WLAN on the controller one entry is added to this
                table. Addition/deletion of entries in this table are automatic depending on the 
                addition/deletion of entries in wlanTable table."
            ::= { wlan 7 }

        
        -- 1.3.6.1.4.1.4329.15.3.3.4.7.1
        wlanAuthEntry OBJECT-TYPE
            SYNTAX WlanAuthEntry
            MAX-ACCESS not-accessible
            STATUS current
            DESCRIPTION
                "An entry in wlanAuthTable for each configured WLAN on EWC. Each entry is indexed
                with corresponding wlan ID of wlanTable. The writable fields in this table can be 
                modified depending on the corresponding wlanTable.
                Note:
                All the fields in this table except wlanAuthType and wlanAuthCollectAcctInformation
                have meaning if MAC-based authentication filed (wlanAuthMacBasedAuth) is set to true. "
            INDEX { wlanID }
            ::= { wlanAuthTable 1 }

        
        WlanAuthEntry ::=
            SEQUENCE { 
                wlanAuthType
                    INTEGER,
                wlanAuthMacBasedAuth
                    TruthValue,
                wlanAuthMACBasedAuthOnRoam
                    TruthValue,
                wlanAuthAutoAuthAuthorizedUser
                    TruthValue,
                wlanAuthAllowUnauthorizedUser
                    TruthValue,
                wlanAuthRadiusIncludeAP
                    TruthValue,
                wlanAuthRadiusIncludeVNS
                    TruthValue,
                wlanAuthRadiusIncludeSSID
                    TruthValue,
                wlanAuthRadiusIncludePolicy
                    TruthValue,
                wlanAuthRadiusIncludeTopology
                    TruthValue,
                wlanAuthRadiusIncludeIngressRC
                    TruthValue,
                wlanAuthRadiusIncludeEgressRC
                    TruthValue,
                wlanAuthCollectAcctInformation
                    TruthValue,
                wlanAuthReplaceCalledStationIDWithZone
                    TruthValue,
                 wlanAuthRadiusAcctAfterMacBaseAuthorization
                    TruthValue,
                 wlanAuthRadiusTimeoutRole
                    Integer32,
                 wlanAuthRadiusOperatorNameSpace
                    INTEGER,
                 wlanAuthRadiusOperatorName
                    DisplayString,
                  wlanAuthMACBasedAuthReAuthOnAreaRoam
                    TruthValue
                    
             }

        -- 1.3.6.1.4.1.4329.15.3.3.4.7.1.1
        wlanAuthType OBJECT-TYPE
            SYNTAX INTEGER
                {
                disabled(1),
                internalCP(2),
                dot1x(3),
                externalCP(4),
                easyGuestCP(5),
                guestSplash(6),
                firewallFriendlyExCP(7)
                }
            MAX-ACCESS read-write
            STATUS current
            DESCRIPTION
                "The type of authentication applied to stations attempting to associate to a BSSID 
                 belonging to this WLAN Service. If the dot1x type is selected, then this WLAN 
                 must have privacy. When the dot1x or internalCP is selected, the controller must 
                 have a RADIUS server, and SNMP will auto assign one RADIUS server to this 
                 WLAN if the user did not assign one."
            ::= { wlanAuthEntry 1 }

        
        -- 1.3.6.1.4.1.4329.15.3.3.4.7.1.2
        wlanAuthMacBasedAuth OBJECT-TYPE
            SYNTAX TruthValue
            MAX-ACCESS read-write
            STATUS current
            DESCRIPTION
                "MAC based authorization is enabled if this field is set to true. When this field set to true, SNMP 
                will auto configure one RADIUS server to enable MAC authorization.  "
            ::= { wlanAuthEntry 2 }

        
        -- 1.3.6.1.4.1.4329.15.3.3.4.7.1.3
        wlanAuthMACBasedAuthOnRoam OBJECT-TYPE
            SYNTAX TruthValue
            MAX-ACCESS read-write
            STATUS current
            DESCRIPTION
                "If it is set to true, the client will be forced to go through MAC based 
                authorization when the client roamed. This field has meaning only when 
                wlanAuthMacBasedAuth is set to true. This field can be modified only when 
                wlanAuthMacBasedAuth is set to true. "
            ::= { wlanAuthEntry 3 }

        
        -- 1.3.6.1.4.1.4329.15.3.3.4.7.1.4
        wlanAuthAutoAuthAuthorizedUser OBJECT-TYPE
            SYNTAX TruthValue
            MAX-ACCESS read-write
            STATUS current
            DESCRIPTION
                "All authorized users will be considered authenticated automatically. This field 
                 has meaning only when wlanAuthMacBasedAuth is set to true. This field can 
                 be modified only when wlanAuthMacBasedAuth is set to true."
            ::= { wlanAuthEntry 4 }

        
        -- 1.3.6.1.4.1.4329.15.3.3.4.7.1.5
        wlanAuthAllowUnauthorizedUser OBJECT-TYPE
            SYNTAX TruthValue
            MAX-ACCESS read-write
            STATUS current
            DESCRIPTION
                "Unauthorized users will be allowed if this field is set to true.This field has meaning only when 
                wlanAuthMacBasedAuth is set to true. This field can be modified only when 
                wlanAuthMacBasedAuth is set to true."
            ::= { wlanAuthEntry 5 }

        
        -- 1.3.6.1.4.1.4329.15.3.3.4.7.1.6
        wlanAuthRadiusIncludeAP OBJECT-TYPE
            SYNTAX TruthValue
            MAX-ACCESS read-write
            STATUS current
            DESCRIPTION
                "AP serial number will be included in RADIUS request packet as VSA if this
                field is set to true."
            ::= { wlanAuthEntry 6 }

        
        -- 1.3.6.1.4.1.4329.15.3.3.4.7.1.7
        wlanAuthRadiusIncludeVNS OBJECT-TYPE
            SYNTAX TruthValue
            MAX-ACCESS read-write
            STATUS current
            DESCRIPTION
                "VNS name will be included in RADIUS request packet as VSA if this field is set to true."
            ::= { wlanAuthEntry 7 }

        
        -- 1.3.6.1.4.1.4329.15.3.3.4.7.1.8
        wlanAuthRadiusIncludeSSID OBJECT-TYPE
            SYNTAX TruthValue
            MAX-ACCESS read-write
            STATUS current
            DESCRIPTION
                "WLAN SSID will be included in RADIUS request packet as VSA if this
                field is set to true."
            ::= { wlanAuthEntry 8 }

        
        -- 1.3.6.1.4.1.4329.15.3.3.4.7.1.9
        wlanAuthRadiusIncludePolicy OBJECT-TYPE
            SYNTAX TruthValue
            MAX-ACCESS read-write
            STATUS current
            DESCRIPTION
                "Policy name will be included in RADIUS request packet as VSA if this
                field is set to true."
            ::= { wlanAuthEntry 9 }

        
        -- 1.3.6.1.4.1.4329.15.3.3.4.7.1.10
        wlanAuthRadiusIncludeTopology OBJECT-TYPE
            SYNTAX TruthValue
            MAX-ACCESS read-write
            STATUS current
            DESCRIPTION
                "Topology name will be included in RADIUS request packet as VSA if this
                field is set to true."
            ::= { wlanAuthEntry 10 }

        
        -- 1.3.6.1.4.1.4329.15.3.3.4.7.1.11
        wlanAuthRadiusIncludeIngressRC OBJECT-TYPE
            SYNTAX TruthValue
            MAX-ACCESS read-write
            STATUS current
            DESCRIPTION
                "Ingress rate control name will be included in RADIUS request packet as VSA if this
                field is set to true."
            ::= { wlanAuthEntry 11 }

        
        -- 1.3.6.1.4.1.4329.15.3.3.4.7.1.12
        wlanAuthRadiusIncludeEgressRC OBJECT-TYPE
            SYNTAX TruthValue
            MAX-ACCESS read-write
            STATUS current
            DESCRIPTION
                "Egress rate control name will be included in RADIUS request packet as VSA if this
                field is set to true."
            ::= { wlanAuthEntry 12 }

        
        -- 1.3.6.1.4.1.4329.15.3.3.4.7.1.13
        wlanAuthCollectAcctInformation OBJECT-TYPE
            SYNTAX TruthValue
            MAX-ACCESS read-write
            STATUS current
            DESCRIPTION
                "Accounting information is collected for clients if this field is set to true."
            ::= { wlanAuthEntry 13 }

        
        -- 1.3.6.1.4.1.4329.15.3.3.4.7.1.14
        wlanAuthReplaceCalledStationIDWithZone OBJECT-TYPE
            SYNTAX TruthValue
            MAX-ACCESS read-write
            STATUS current
            DESCRIPTION
                "Replace called station ID with Zone if this field is set to true."
            ::= { wlanAuthEntry 14 }


        -- 1.3.6.1.4.1.4329.15.3.3.4.7.1.15
        wlanAuthRadiusAcctAfterMacBaseAuthorization OBJECT-TYPE
            SYNTAX TruthValue
            MAX-ACCESS read-write
            STATUS current
            DESCRIPTION
                "RADIUS accounting begins after MAC-based authorization completes if this field is set to true.
                This field has meaning only when wlanAuthMacBasedAuth is set to true. 
                This field can be modified only when wlanAuthMacBasedAuth is set to true."
            ::= { wlanAuthEntry 15 }


        -- 1.3.6.1.4.1.4329.15.3.3.4.7.1.16
        wlanAuthRadiusTimeoutRole OBJECT-TYPE
            SYNTAX Integer32
            MAX-ACCESS read-write
            STATUS current
            DESCRIPTION
                "Apply this role to clients when  the RADIUS server  timed out. 
                '-1' is treat like access reject.  Any other number is the Role ID. This field has meaning only when 
                wlanAuthMacBasedAuth is set to true. This field can be modified only when 
                wlanAuthMacBasedAuth is set to true."
            ::= { wlanAuthEntry 16 }

        -- 1.3.6.1.4.1.4329.15.3.3.4.7.1.17
        wlanAuthRadiusOperatorNameSpace OBJECT-TYPE
            SYNTAX INTEGER
               {
                disabled(-1),
                tadig(48),
                realm(49),
                e212(50),
                icc(51)
                }

            MAX-ACCESS read-write
            STATUS current
            DESCRIPTION
                "wlanAuthRadiusOperatorNameSpace is the Namespace ID as defined in RFC 5580. The value within this field contains
                 the operator namespace identifier.  The Namespace ID value is encoded in ASCII and has the following
                 values.
                -1 : disabled.
                48 : TADIG. 
                49 : REALM.
                50 : E212.
                51 : ICC. "
            ::= { wlanAuthEntry 17 }

        -- 1.3.6.1.4.1.4329.15.3.3.4.7.1.18
        wlanAuthRadiusOperatorName OBJECT-TYPE
            SYNTAX DisplayString
            MAX-ACCESS read-write
            STATUS current
            DESCRIPTION
                "RADIUS accounting message will include this string when the wlanAuthRadiusOperatorNameSpace is not
                  set to -1."
            ::= { wlanAuthEntry 18 }

        -- 1.3.6.1.4.1.4329.15.3.3.4.7.1.19
        wlanAuthMACBasedAuthReAuthOnAreaRoam OBJECT-TYPE
            SYNTAX TruthValue
            MAX-ACCESS read-write
            STATUS current
            DESCRIPTION
                "If this field is set to true, the client will be forced to go through MAC based 
                authorization when the client roams to another area. This field has meaning
                and can be modified only when wlanAuthMacBasedAuth is set to true. "
            ::= { wlanAuthEntry 19 }



        
        -- 1.3.6.1.4.1.4329.15.3.3.4.8
        wlanRadiusTable OBJECT-TYPE
            SYNTAX SEQUENCE OF WlanRadiusEntry
            MAX-ACCESS not-accessible
            STATUS current
            DESCRIPTION
                "This table contains configuration of RADIUS settings for all configured WLAN on EWC.
                For each of the configured WLAN on the controller there may exist one or more entries
                of RADIUS server(s) serving the WLAN. Addition/deletion of entries in this table are
                automatic depending on the addition/deletion of entries in wlanTable table."
            ::= { wlan 8 }

        
        -- 1.3.6.1.4.1.4329.15.3.3.4.8.1
        wlanRadiusEntry OBJECT-TYPE
            SYNTAX WlanRadiusEntry
            MAX-ACCESS not-accessible
            STATUS current
            DESCRIPTION
                "An entry in wlanRadiusTable for each RADIUS server used by the WLAN indexed by wlanID."
            INDEX { wlanID, wlanRadiusIndex }
            ::= { wlanRadiusTable 1 }

        
        WlanRadiusEntry ::=
            SEQUENCE { 
                wlanRadiusIndex
                    Unsigned32,
                wlanRadiusName
                    DisplayString,
                wlanRadiusUsage
                    INTEGER,
                wlanRadiusPriority
                    Integer32,
                wlanRadiusPort
                    Unsigned32,
                wlanRadiusRetries
                    Unsigned32,
                wlanRadiusTimeout
                    Unsigned32,
                wlanRadiusNASUseVnsIP
                    TruthValue,
                wlanRadiusNASIP
                    DisplayString,
                wlanRadiusNASIDUseVNSName
                    TruthValue,
                wlanRadiusNASID
                    DisplayString,
                wlanRadiusAuthType
                    INTEGER
             }

        -- 1.3.6.1.4.1.4329.15.3.3.4.8.1.1
        wlanRadiusIndex OBJECT-TYPE
            SYNTAX Unsigned32
            MAX-ACCESS not-accessible
            STATUS current
            DESCRIPTION
                "Internally generated index and it has no external meaning."
            ::= { wlanRadiusEntry 1 }

        
        -- 1.3.6.1.4.1.4329.15.3.3.4.8.1.2
        wlanRadiusName OBJECT-TYPE
            SYNTAX DisplayString
            MAX-ACCESS read-write
            STATUS current
            DESCRIPTION
                "Name of the RADIUS server associated to this entry."
            ::= { wlanRadiusEntry 2 }

        
        -- 1.3.6.1.4.1.4329.15.3.3.4.8.1.3
        wlanRadiusUsage OBJECT-TYPE
            SYNTAX INTEGER
                {
                auth(1),
                mac(2),
                acc(3)
                }
            MAX-ACCESS read-write
            STATUS current
            DESCRIPTION
                "Usage type associated to this entry for authentication."
            ::= { wlanRadiusEntry 3 }

        
        -- 1.3.6.1.4.1.4329.15.3.3.4.8.1.4
        wlanRadiusPriority OBJECT-TYPE
            SYNTAX Integer32
            MAX-ACCESS read-write
            STATUS current
            DESCRIPTION
                "Priority associated to this entry for authentication. RADIUS servers are contacted
                for authentication requests in the order of their priority defined in this field.
                The highest priority servers (priorities with lower numerical values have higher
                priority order) are consulted first for any authentication request."
            ::= { wlanRadiusEntry 4 }

        
        -- 1.3.6.1.4.1.4329.15.3.3.4.8.1.5
        wlanRadiusPort OBJECT-TYPE
            SYNTAX Unsigned32
            MAX-ACCESS read-write
            STATUS current
            DESCRIPTION
                "The RADIUS authentication requests should be sent to this authentication port."
            DEFVAL { 1812 }
            ::= { wlanRadiusEntry 5 }

        
        -- 1.3.6.1.4.1.4329.15.3.3.4.8.1.6
        wlanRadiusRetries OBJECT-TYPE
            SYNTAX Unsigned32 (1..32)
            MAX-ACCESS read-write
            STATUS current
            DESCRIPTION
                "Maximum number of retries attempted for an specific authentication request."
            DEFVAL { 3 }
            ::= { wlanRadiusEntry 6 }

        
        -- 1.3.6.1.4.1.4329.15.3.3.4.8.1.7
        wlanRadiusTimeout OBJECT-TYPE
            SYNTAX Unsigned32 (1..360)
            UNITS "seconds"
            MAX-ACCESS read-write
            STATUS current
            DESCRIPTION
                "Number of seconds to wait for a response from authentication server for each
                request sent to the server before considering the request as failure."
            DEFVAL { 5 }
            ::= { wlanRadiusEntry 7 }

        
        -- 1.3.6.1.4.1.4329.15.3.3.4.8.1.8
        wlanRadiusNASUseVnsIP OBJECT-TYPE
            SYNTAX TruthValue
            MAX-ACCESS read-write
            STATUS current
            DESCRIPTION
                "If this value is set to true, then VNS IP address associated to the WLAN indexed
                by wlanID to this entry is used as NAS IP address. Otherwise NAS IP address should be 
                configured manually."
            ::= { wlanRadiusEntry 8 }

        
        -- 1.3.6.1.4.1.4329.15.3.3.4.8.1.9
        wlanRadiusNASIP OBJECT-TYPE
            SYNTAX DisplayString
            MAX-ACCESS read-write
            STATUS current
            DESCRIPTION
                "NAS IP associated to this RADIUS server. Configuration of this field is directly
                affected by the value of wlanRadiusNASUseVnsIP."
            ::= { wlanRadiusEntry 9 }

        
        -- 1.3.6.1.4.1.4329.15.3.3.4.8.1.10
        wlanRadiusNASIDUseVNSName OBJECT-TYPE
            SYNTAX TruthValue
            MAX-ACCESS read-write
            STATUS current
            DESCRIPTION
                "If this value is set to true, then use VNS name associated to the WLAN indexed
                by wlanID for this entry as NAS ID. Otherwise NAS ID should be configured manually."
            ::= { wlanRadiusEntry 10 }

        
        -- 1.3.6.1.4.1.4329.15.3.3.4.8.1.11
        wlanRadiusNASID OBJECT-TYPE
            SYNTAX DisplayString
            MAX-ACCESS read-write
            STATUS current
            DESCRIPTION
                "NAS ID associated to this RADIUS server. Configuration of this field is directly
                affected by the value of wlanRadiusNASIDUseVNSName."
            ::= { wlanRadiusEntry 11 }

        
        -- 1.3.6.1.4.1.4329.15.3.3.4.8.1.12
        wlanRadiusAuthType OBJECT-TYPE
            SYNTAX INTEGER
                {
                pap(0),
                chap(1),
                mschap(2),
                mschap2(3)
                }
            MAX-ACCESS read-write
            STATUS current
            DESCRIPTION
                "Authentication type used for this WLAN when using this RADIUS server to
                authenticate users."
            DEFVAL { pap }
            ::= { wlanRadiusEntry 12 }

        
        -- 1.3.6.1.4.1.4329.15.3.3.4.9
        wlanCPTable OBJECT-TYPE
            SYNTAX SEQUENCE OF WlanCPEntry
            MAX-ACCESS not-accessible
            STATUS current
            DESCRIPTION
                "This table contains configuration of Captive Portal settings for all configured WLAN
                on EWC. For each of the configured WLAN on the controller one entry is added to this 
                table. Addition/deletion of entries in this table are automatic depending on the 
                addition/deletion of entries in wlanTable table. This table can be accessed using SNMPv3 on
                behalf of users with privacy."
            ::= { wlan 9 }

        
        -- 1.3.6.1.4.1.4329.15.3.3.4.9.1
        wlanCPEntry OBJECT-TYPE
            SYNTAX WlanCPEntry
            MAX-ACCESS not-accessible
            STATUS current
            DESCRIPTION
                "An entry in wlanCPTable for each configured WLAN on EWC. Each entry is indexed
                with corresponding wlan ID of wlanTable. The writable fields in this table can be
                modified depending on the corresponding wlanTable and type of CP assigned to the 
                WLAN. If the authentication type is 'disabled(0)' for the WLAN, then all other entries in
                this table have no meaning."
            INDEX { wlanID }
            ::= { wlanCPTable 1 }

        
        WlanCPEntry ::=
            SEQUENCE { 
                wlanCPAuthType
                    INTEGER,
                wlanCP802HttpRedirect
                    TruthValue,
                wlanCPExtConnection
                    IpAddress,
                wlanCPExtPort
                    Unsigned32,
                wlanCPExtEnableHttps
                    TruthValue,
                wlanCPExtEncryption
                    INTEGER,
                wlanCPExtSharedSecret
                    OCTET STRING,
                wlanCPExtTosOverride
                    TruthValue,
                wlanCPExtTosValue
                    Unsigned32,
                wlanCPExtAddIPtoURL
                    TruthValue,
                wlanCPIntLogoffButton
                    TruthValue,
                wlanCPIntStatusCheckButton
                    TruthValue,
                wlanCPReplaceIPwithFQDN
                    DisplayString,
                wlanCPSendLoginTo
                    INTEGER,
                wlanCPRedirectURL
                    DisplayString,
                wlanCPGuestAccLifetime
                    Unsigned32,
                wlanCPGuestAllowedLifetimeAcct
                    TruthValue,
                wlanCPGuestSessionLifetime
                    Unsigned32,
                wlanCPGuestIDPrefix
                    DisplayString,
                wlanCPGuestMinPassLength
                    Unsigned32,
                wlanCPGuestMaxConcurrentSession
                    Unsigned32,
                 wlanCPUseHTTPSforConnection
                   TruthValue,
                 wlanCPIdentity
                    DisplayString,
                  wlanCPCustomSpecificURL
                    DisplayString,
                  wlanCPSelectionOption
                    BITS

             }

        -- 1.3.6.1.4.1.4329.15.3.3.4.9.1.1
        wlanCPAuthType OBJECT-TYPE
            SYNTAX INTEGER
                {
                disabled(1),
                internalCP(2),
                dot1x(3),
                externalCP(4),
                easyGuestCP(5),
                guestSplash(6),
                firewallFriendlyExCP(7)
                }
            MAX-ACCESS read-write
            STATUS current
            DESCRIPTION
                "Type of authentication applied to MU requesting association using SSID associated
                to this WLAN."
            ::= { wlanCPEntry 1 }

        
        -- 1.3.6.1.4.1.4329.15.3.3.4.9.1.2
        wlanCP802HttpRedirect OBJECT-TYPE
            SYNTAX TruthValue
            MAX-ACCESS read-write
            STATUS current
            DESCRIPTION
                "If it is set to true, then CP will be redirected to configured CP. This value 
                has meaning only for CP of the type 'dot1x(3)'."
            ::= { wlanCPEntry 2 }

        
        -- 1.3.6.1.4.1.4329.15.3.3.4.9.1.3
        wlanCPExtConnection OBJECT-TYPE
            SYNTAX IpAddress
            MAX-ACCESS read-write
            STATUS current
            DESCRIPTION
                "IP address of the interface for this CP."
            ::= { wlanCPEntry 3 }

        
        -- 1.3.6.1.4.1.4329.15.3.3.4.9.1.4
        wlanCPExtPort OBJECT-TYPE
            SYNTAX Unsigned32 (32768..65535)
            MAX-ACCESS read-write
            STATUS current
            DESCRIPTION
                "The port associated to the CP IP address."
            ::= { wlanCPEntry 4 }

        
        -- 1.3.6.1.4.1.4329.15.3.3.4.9.1.5
        wlanCPExtEnableHttps OBJECT-TYPE
            SYNTAX TruthValue
            MAX-ACCESS read-write
            STATUS current
            DESCRIPTION
                "HTTPS support is enabled if this field is set to true."
            ::= { wlanCPEntry 5 }

        
        -- 1.3.6.1.4.1.4329.15.3.3.4.9.1.6
        wlanCPExtEncryption OBJECT-TYPE
            SYNTAX INTEGER
                {
                none(0),
                legacy(1),
                aes(2)
                }
            MAX-ACCESS read-write
            STATUS current
            DESCRIPTION
                "Type of encryption for the CP."
            ::= { wlanCPEntry 6 }

        
        -- 1.3.6.1.4.1.4329.15.3.3.4.9.1.7
        wlanCPExtSharedSecret OBJECT-TYPE
            SYNTAX OCTET STRING (SIZE (16..64))
            MAX-ACCESS read-write
            STATUS current
            DESCRIPTION
                "Shared secret used for this captive portal."
            ::= { wlanCPEntry 7 }

        
        -- 1.3.6.1.4.1.4329.15.3.3.4.9.1.8
        wlanCPExtTosOverride OBJECT-TYPE
            SYNTAX TruthValue
            MAX-ACCESS read-write
            STATUS current
            DESCRIPTION
                "Override ToS of NAC server usage only."
            DEFVAL { false }
            ::= { wlanCPEntry 8 }

        
        -- 1.3.6.1.4.1.4329.15.3.3.4.9.1.9
        wlanCPExtTosValue OBJECT-TYPE
            SYNTAX Unsigned32 (0..255)
            MAX-ACCESS read-write
            STATUS deprecated
            DESCRIPTION
                "ToS value for NAC server only."
            ::= { wlanCPEntry 9 }

        
        -- 1.3.6.1.4.1.4329.15.3.3.4.9.1.10
        wlanCPExtAddIPtoURL OBJECT-TYPE
            SYNTAX TruthValue
            MAX-ACCESS read-write
            STATUS current
            DESCRIPTION
                "If this value is set to true, then add EWC IP address and port number to the redirection URL."
            ::= { wlanCPEntry 10 }

        
        -- 1.3.6.1.4.1.4329.15.3.3.4.9.1.11
        wlanCPIntLogoffButton OBJECT-TYPE
            SYNTAX TruthValue
            MAX-ACCESS read-write
            STATUS current
            DESCRIPTION
                "If set to true provide 'Logoff' button to the user in CP page."
            ::= { wlanCPEntry 11 }

        
        -- 1.3.6.1.4.1.4329.15.3.3.4.9.1.12
        wlanCPIntStatusCheckButton OBJECT-TYPE
            SYNTAX TruthValue
            MAX-ACCESS read-write
            STATUS current
            DESCRIPTION
                "If set to true provide 'Status Check' button to the user in CP page."
            ::= { wlanCPEntry 12 }

        
        -- 1.3.6.1.4.1.4329.15.3.3.4.9.1.13
        wlanCPReplaceIPwithFQDN OBJECT-TYPE
            SYNTAX DisplayString
            MAX-ACCESS read-write
            STATUS current
            DESCRIPTION
                "Replace CP gateway IP address with FQDN."
            ::= { wlanCPEntry 13 }

        
        -- 1.3.6.1.4.1.4329.15.3.3.4.9.1.14
        wlanCPSendLoginTo OBJECT-TYPE
            SYNTAX INTEGER
                {
                originalDestination(0),
                cpSessionPage(1),
                customURL(2)
                }
            MAX-ACCESS read-write
            STATUS current
            DESCRIPTION
                "This field indicates to what URL the successful login session must be redirected.
                This field qualifies wlanCPRedirectURL."
            ::= { wlanCPEntry 14 }

        
        -- 1.3.6.1.4.1.4329.15.3.3.4.9.1.15
        wlanCPRedirectURL OBJECT-TYPE
            SYNTAX DisplayString
            MAX-ACCESS read-write
            STATUS current
            DESCRIPTION
                "Text string identifying default redirection URL."
            ::= { wlanCPEntry 15 }

        
        -- 1.3.6.1.4.1.4329.15.3.3.4.9.1.16
        wlanCPGuestAccLifetime OBJECT-TYPE
            SYNTAX Unsigned32
            UNITS "days"
            MAX-ACCESS read-write
            STATUS current
            DESCRIPTION
                "This value indicates for how many days the guest account is valid. Value of zero
                indicates that there is no limit for the guest account."
            ::= { wlanCPEntry 16 }

        
        -- 1.3.6.1.4.1.4329.15.3.3.4.9.1.17
        wlanCPGuestAllowedLifetimeAcct OBJECT-TYPE
            SYNTAX TruthValue
            MAX-ACCESS read-write
            STATUS current
            DESCRIPTION
                "If this value is set to true, then guest admin can obtain lifetime account."
            ::= { wlanCPEntry 17 }

        
        -- 1.3.6.1.4.1.4329.15.3.3.4.9.1.18
        wlanCPGuestSessionLifetime OBJECT-TYPE
            SYNTAX Unsigned32
            UNITS "hours"
            MAX-ACCESS read-write
            STATUS current
            DESCRIPTION
                "The guess account session using this CP cannot last longer than this number of
                hours. Value of zero means there is no limit for the session."
            ::= { wlanCPEntry 18 }

        
        -- 1.3.6.1.4.1.4329.15.3.3.4.9.1.19
        wlanCPGuestIDPrefix OBJECT-TYPE
            SYNTAX DisplayString
            MAX-ACCESS read-write
            STATUS current
            DESCRIPTION
                "The prefix used for guest portal user ID label."
            ::= { wlanCPEntry 19 }

        
        -- 1.3.6.1.4.1.4329.15.3.3.4.9.1.20
        wlanCPGuestMinPassLength OBJECT-TYPE
            SYNTAX Unsigned32 (1..32)
            MAX-ACCESS read-write
            STATUS current
            DESCRIPTION
                "Minimum password length for the guest user account associated to this WLAN."
            DEFVAL { 8 }
            ::= { wlanCPEntry 20 }

        
        -- 1.3.6.1.4.1.4329.15.3.3.4.9.1.21
        wlanCPGuestMaxConcurrentSession OBJECT-TYPE
            SYNTAX Unsigned32 (0..10)
            MAX-ACCESS read-write
            STATUS current
            DESCRIPTION
                "Maximum number of the guest users can use this set of credentials to access this concurrent session."
            DEFVAL { 8 }
            ::= { wlanCPEntry 21 }



        -- 1.3.6.1.4.1.4329.15.3.3.4.9.1.22
        wlanCPUseHTTPSforConnection OBJECT-TYPE
            SYNTAX TruthValue
            MAX-ACCESS read-write
            STATUS current
            DESCRIPTION
                "When this value set to true, use HTTPS for user connection. It has meaning only when wlanCPAuthType is set to
                internalCP(2) or easyGuestCP(5) or guestSplash(6)  "
            ::= { wlanCPEntry 22 }

        -- 1.3.6.1.4.1.4329.15.3.3.4.9.1.23
        wlanCPIdentity OBJECT-TYPE
            SYNTAX DisplayString
            MAX-ACCESS read-write
            STATUS current
            DESCRIPTION
                "wlanCPIdentity is used to identify the EWC to the external captive portal server (ECP)
                and the ECP to the EWC."
            ::= { wlanCPEntry 23 }

        -- 1.3.6.1.4.1.4329.15.3.3.4.9.1.24
        wlanCPCustomSpecificURL OBJECT-TYPE
            SYNTAX DisplayString
            MAX-ACCESS read-write
            STATUS current
            DESCRIPTION
                "After a user successfully logs in, the user will be redirected to the URL as defined in the 
                wlanCPCustomSpecificURL."
            ::= { wlanCPEntry 24 }


        -- 1.3.6.1.4.1.4329.15.3.3.4.9.1.25
        wlanCPSelectionOption OBJECT-TYPE
            SYNTAX BITS
                {
                addEWCPortAndIP(0),
                apNameAndSerial(1),
                associatedBSSID(2),
                vnsName(3),
                userMacAddress(4),
                currentlyAssignedRole(5),
                containmentVLAN(6),
                timeStamp(7),
                signature(8),
                ssid(9)
                }
            MAX-ACCESS read-write
            STATUS current
            DESCRIPTION
                "Append the above parameter(s) to the EWC captive portal redirection URL if one or more of the bits are set.  "
            ::= { wlanCPEntry 25 }


        
        -- 1.3.6.1.4.1.4329.15.3.3.4.10
        wlanUnsecuredWlanCounts OBJECT-TYPE
            SYNTAX Counter32
            MAX-ACCESS read-only
            STATUS current
            DESCRIPTION
                "Total number of WLAN with security issues. The details of security issues
                can be found in wlanSecurityReportTable."
            ::= { wlan 10 }

        
        -- 1.3.6.1.4.1.4329.15.3.3.4.11
        wlanSecurityReportTable OBJECT-TYPE
            SYNTAX SEQUENCE OF WlanSecurityReportEntry
            MAX-ACCESS not-accessible
            STATUS current
            DESCRIPTION
                "This table contains the weak configuration settings for all configured WLAN on EWC.
                For each of the configured WLAN on the controller there exist one entry in this table.
                Addition/deletion of entries in this table are automatic depending on the addition
                or deletion of entries in wlanTable table. This table can be accessed using SNMPv3 on
                behalf of users with privacy."
            ::= { wlan 11 }

        
        -- 1.3.6.1.4.1.4329.15.3.3.4.11.1
        wlanSecurityReportEntry OBJECT-TYPE
            SYNTAX WlanSecurityReportEntry
            MAX-ACCESS not-accessible
            STATUS current
            DESCRIPTION
                "An entry in wlanSecurityReportTable for each configured WLAN on EWC. Each entry is indexed
                with corresponding wlan ID of wlanTable."
            INDEX { wlanID }
            ::= { wlanSecurityReportTable 1 }

        
        WlanSecurityReportEntry ::=
            SEQUENCE { 
                wlanSecurityReportFlag
                    INTEGER,
                wlanSecurityReportUnsecureType
                    BITS,
                wlanSecurityReportNotes
                    DisplayString
             }

        -- 1.3.6.1.4.1.4329.15.3.3.4.11.1.1
        wlanSecurityReportFlag OBJECT-TYPE
            SYNTAX INTEGER
                {
                unsecureSetting(1),
                secureSetting(2)
                }
            MAX-ACCESS read-only
            STATUS current
            DESCRIPTION
                "Value of secureSetting(2) indicates that WLAN has secure configuration."
            ::= { wlanSecurityReportEntry 1 }

        
        -- 1.3.6.1.4.1.4329.15.3.3.4.11.1.2
        wlanSecurityReportUnsecureType OBJECT-TYPE
            SYNTAX BITS
                {
                open(0),
                wep(1),
                tkip(2),
                defaultSsid(3),
                hotspotSsid(4),
                rainbowSsid(5),
                dictionaryWordKey(6),
                dictionaryWordSubstring(7),
                passwordTooShort(8)
                }
            MAX-ACCESS read-only
            STATUS current
            DESCRIPTION
                "bit 0: by setting this bit means this WLAN does not use any kind of encryption
                bit 1: by setting this bit means this WLAN uses weak WEP encryption
                bit 2: by setting this bit means this WLAN uses weak tkip encryption
                bit 3: by setting this bit means this WLAN uses default SSID
                bit 4: by setting this bit means this WLAN uses HotSpot SSID
                bit 5: by setting this bit means this WLAN uses Rainbow SSID
                bit 6: by setting this bit means this WLAN uses dictionary word as an encryption key
                bit 7: by setting this bit means this WLAN uses dictionary word in an encryption key string
                bit 8: by setting this bit means this WLAN uses a short password key"
            ::= { wlanSecurityReportEntry 2 }

        
        -- 1.3.6.1.4.1.4329.15.3.3.4.11.1.3
        wlanSecurityReportNotes OBJECT-TYPE
            SYNTAX DisplayString
            MAX-ACCESS read-only
            STATUS current
            DESCRIPTION
                "Textual description of any security issues related to the WLAN is reflected in this field."
            ::= { wlanSecurityReportEntry 3 }


        -- 1.3.6.1.4.1.4329.15.3.3.4.12
        wlanRadiusServerTable OBJECT-TYPE
            SYNTAX SEQUENCE OF WlanRadiusServerEntry
            MAX-ACCESS not-accessible
            STATUS current
            DESCRIPTION
                "This table contains configuration of RADIUS Servers settings for all configured WLANs on the Wireless Controller.
                For each of the configured WLANs on the controller there may exist one or more entries
                of RADIUS server(s) serving the WLAN. Addition/deletion of entries in this table are
                automatic depending on the addition/deletion of entries in wlanTable table."
            ::= { wlan 12 }

        
        -- 1.3.6.1.4.1.4329.15.3.3.4.12.1
        wlanRadiusServerEntry OBJECT-TYPE
            SYNTAX WlanRadiusServerEntry
            MAX-ACCESS not-accessible
            STATUS current
            DESCRIPTION
                "An entry in wlanRadiusServerTable for each RADIUS server used by the WLAN indexed by wlanID and radiusId.
                The radiusId is the controller's internal radius server index."
            INDEX { wlanID, radiusId }
            ::= { wlanRadiusServerTable 1 }

        
        WlanRadiusServerEntry ::=
            SEQUENCE { 
                radiusId
                    Unsigned32,
                wlanRadiusServerName
                    DisplayString,
                wlanRadiusServerUse
                    Integer32,
                wlanRadiusServerUsage
                    BITS,
                wlanRadiusServerAuthUseVNSIPAddr
                    TruthValue,
                wlanRadiusServerAuthNASIP
                    DisplayString,
                wlanRadiusServerAuthUseVNSName
                    TruthValue,
                wlanRadiusServerAuthNASId
                    DisplayString,
                wlanRadiusServerAuthAuthType
                    Integer32,
               wlanRadiusServerAcctUseVNSIPAddr
                    TruthValue,
                wlanRadiusServerAcctNASIP
                    DisplayString,
                wlanRadiusServerAcctUseVNSName
                    TruthValue,
                wlanRadiusServerAcctNASId
                    DisplayString,
                wlanRadiusServerAcctSIAR
                    Integer32, 
                wlanRadiusServerMacUseVNSIPAddr
                    TruthValue,
                wlanRadiusServerMacNASIP
                    DisplayString,
                wlanRadiusServerMacUseVNSName
                    TruthValue,
                wlanRadiusServerMacNASId
                    DisplayString,
                wlanRadiusServerMacAuthType
                    Integer32,
                wlanRadiusServerMacPW
                    DisplayString
             }

        -- 1.3.6.1.4.1.4329.15.3.3.4.12.1.1
        radiusId OBJECT-TYPE
            SYNTAX Unsigned32
            MAX-ACCESS not-accessible
            STATUS current
            DESCRIPTION
                "Controller's internal RADIUS index."
            ::= { wlanRadiusServerEntry 1 }

        
        -- 1.3.6.1.4.1.4329.15.3.3.4.12.1.2
        wlanRadiusServerName OBJECT-TYPE
            SYNTAX DisplayString
            MAX-ACCESS read-only
            STATUS current
            DESCRIPTION
                "Name of the RADIUS server."
            ::= { wlanRadiusServerEntry 2 }

        
        -- 1.3.6.1.4.1.4329.15.3.3.4.12.1.3
        wlanRadiusServerUse OBJECT-TYPE
            SYNTAX INTEGER
                {
                notUse(0),
                use(1)
                }
            MAX-ACCESS read-write
            STATUS current
            DESCRIPTION
                "use : This means that this WLAN service indexed by wlanID uses this RADIUS server which it is indexed by the radiusId. "
            ::= { wlanRadiusServerEntry 3 }

        
        -- 1.3.6.1.4.1.4329.15.3.3.4.12.1.4
        wlanRadiusServerUsage OBJECT-TYPE
            SYNTAX  BITS
                    {
                        auth(0),
                        mac(1),
                        acct(2)
                       }
            MAX-ACCESS read-write
            STATUS current
            DESCRIPTION
                "bit 0: By setting this bit, this RADIUS server is used for authentication. This bit has meaning only when wlanAuthType is set to internalCP(2), 
                          dot1x(3), or externalCP(4).
                bit 1: By setting this bit, this RADIUS server is used for MAC-based authentication. This bit has meaning only when 
                         wlanAuthMacBasedAuth is set to true.
                bit 2: By setting this bit, this RADIUS server is used for accounting. This bit has meaning only when wlanAuthType is set to internalCP(2), dot1x(3),
                         or externalCP(4)."
            ::= { wlanRadiusServerEntry 4 }

        


        -- 1.3.6.1.4.1.4329.15.3.3.4.12.1.5
            wlanRadiusServerAuthUseVNSIPAddr OBJECT-TYPE
                SYNTAX TruthValue
                MAX-ACCESS read-write
                STATUS current
                DESCRIPTION
                    "When this value set to true, use the VNS's IP address as NAS IP address during the authentication."
            ::= { wlanRadiusServerEntry 5 }


        
        -- 1.3.6.1.4.1.4329.15.3.3.4.12.1.6
        wlanRadiusServerAuthNASIP OBJECT-TYPE
            SYNTAX DisplayString
            MAX-ACCESS read-write
            STATUS current
            DESCRIPTION
                "Use this IP address as the NAS IP addresss during the authentication. The default IP address is the VNS IP address.
                This field has meaning only when the wlanRadiusServerUsage's bit 0 is set. "
            ::= { wlanRadiusServerEntry 6 }

                
        -- 1.3.6.1.4.1.4329.15.3.3.4.12.1.7
            wlanRadiusServerAuthUseVNSName OBJECT-TYPE
                SYNTAX TruthValue
                MAX-ACCESS read-write
                STATUS current
                DESCRIPTION
                    "When this value set to true, use the VNS's name as the NAS identifier during the authentication."
            ::= { wlanRadiusServerEntry 7 }
        
        -- 1.3.6.1.4.1.4329.15.3.3.4.12.1.8
        wlanRadiusServerAuthNASId OBJECT-TYPE
            SYNTAX DisplayString
            MAX-ACCESS read-write
            STATUS current
            DESCRIPTION
                "Use this name as the NAS identifier during the authentication. The default name is the VNS name.
                This field has meaning only when the wlanRadiusServerUsage's bit 0 is set."
            ::= { wlanRadiusServerEntry 8 }



        -- 1.3.6.1.4.1.4329.15.3.3.4.12.1.9
        wlanRadiusServerAuthAuthType OBJECT-TYPE
            SYNTAX INTEGER
                {
                pap(0),
                chap(1),
                mschap(2),
                mschap2(3),
                eap(4)
                }
            MAX-ACCESS read-write
            STATUS current
            DESCRIPTION
                "Authentication type.
                 This field has meaning only when the wlanRadiusServerUsage's bit 0 is set."
            ::= { wlanRadiusServerEntry 9 }

            

        -- 1.3.6.1.4.1.4329.15.3.3.4.12.1.10
            wlanRadiusServerAcctUseVNSIPAddr OBJECT-TYPE
                SYNTAX TruthValue
                MAX-ACCESS read-write
                STATUS current
                DESCRIPTION
                    "When this value set to true, use the VNS's IP address as NAS IP address during the accounting."
            ::= { wlanRadiusServerEntry 10 }

        
        -- 1.3.6.1.4.1.4329.15.3.3.4.12.1.11
        wlanRadiusServerAcctNASIP OBJECT-TYPE
            SYNTAX DisplayString
            MAX-ACCESS read-write
            STATUS current
            DESCRIPTION
                "Use this IP address as the NAS IP addresss during the accounting. The default IP address is the VNS IP address.
                This field has meaning only when the wlanRadiusServerUsage's bit 2 is set."
            ::= { wlanRadiusServerEntry 11 }

        -- 1.3.6.1.4.1.4329.15.3.3.4.12.1.12
            wlanRadiusServerAcctUseVNSName OBJECT-TYPE
                SYNTAX TruthValue
                MAX-ACCESS read-write
                STATUS current
                DESCRIPTION
                    "When this value set to true, use the VNS's name as the NAS identifier during the accounting."
            ::= { wlanRadiusServerEntry 12 }

        
        -- 1.3.6.1.4.1.4329.15.3.3.4.12.1.13
        wlanRadiusServerAcctNASId OBJECT-TYPE
            SYNTAX DisplayString
            MAX-ACCESS read-write
            STATUS current
            DESCRIPTION
                "Use this name as the NAS identifier during the accounting. The default name is the VNS name.
                This field has meaning only when the wlanRadiusServerUsage's bit 2 is set."
            ::= { wlanRadiusServerEntry 13 }

        
        -- 1.3.6.1.4.1.4329.15.3.3.4.8.1.14
        wlanRadiusServerAcctSIAR OBJECT-TYPE
            SYNTAX TruthValue
            MAX-ACCESS read-write
            STATUS current
            DESCRIPTION
                "If this value is set to true, then the controller sends interrim accounting records for fast failover events.
                This field has meaning only when the wlanRadiusServerUsage's bit 2 is set."
            ::= { wlanRadiusServerEntry 14 }

        -- 1.3.6.1.4.1.4329.15.3.3.4.12.1.15
            wlanRadiusServerMacUseVNSIPAddr OBJECT-TYPE
                SYNTAX TruthValue
                MAX-ACCESS read-write
                STATUS current
                DESCRIPTION
                    "When this value set to true, use the VNS's IP address as NAS IP address during  the MAC based authentication."
            ::= { wlanRadiusServerEntry 15 }


        
        -- 1.3.6.1.4.1.4329.15.3.3.4.12.1.16
        wlanRadiusServerMacNASIP OBJECT-TYPE
            SYNTAX DisplayString
            MAX-ACCESS read-write
            STATUS current
            DESCRIPTION
                "Use this IP address as the NAS IP addresss during the MAC based authentication. The default IP address is the VNS IP address.
                This field has meaning only when the wlanRadiusServerUsage's bit 1 is set."
            ::= { wlanRadiusServerEntry 16 }

        -- 1.3.6.1.4.1.4329.15.3.3.4.12.1.17
            wlanRadiusServerMacUseVNSName OBJECT-TYPE
                SYNTAX TruthValue
                MAX-ACCESS read-write
                STATUS current
                DESCRIPTION
                    "When this value set to true, use the VNS's name as the NAS identifier during  the MAC based authentication."
            ::= { wlanRadiusServerEntry 17 }


        
        -- 1.3.6.1.4.1.4329.15.3.3.4.12.1.18
        wlanRadiusServerMacNASId OBJECT-TYPE
            SYNTAX DisplayString
            MAX-ACCESS read-write
            STATUS current
            DESCRIPTION
                "Use this name as the NAS identifier during the MAC based authentication. The default name is the VNS name.
                This field has meaning only when the wlanRadiusServerUsage's bit 1 is set."
            ::= { wlanRadiusServerEntry 18 }

        -- 1.3.6.1.4.1.4329.15.3.3.4.12.1.19
        wlanRadiusServerMacAuthType OBJECT-TYPE
            SYNTAX INTEGER
                {
                pap(0),
                chap(1),
                mschap(2),
                mschap2(3)
                }
            MAX-ACCESS read-write
            STATUS current
            DESCRIPTION
                "Authentication type.
                 This field has meaning only when the wlanRadiusServerUsage's bit 1 is set."
            ::= { wlanRadiusServerEntry 19 }


        -- 1.3.6.1.4.1.4329.15.3.3.4.12.1.20
        wlanRadiusServerMacPW OBJECT-TYPE
            SYNTAX DisplayString
            MAX-ACCESS read-write
            STATUS current
            DESCRIPTION
                "The password is used for MAC based authentication.
                This field has meaning only when the wlanRadiusServerUsage's bit 1 is set."
            ::= { wlanRadiusServerEntry 20 }



            


        
        -- 1.3.6.1.4.1.4329.15.3.4
        topology OBJECT IDENTIFIER ::= { hiPathWirelessMgmt 4 }

        
        -- 1.3.6.1.4.1.4329.15.3.4.1
        topologyConfig OBJECT IDENTIFIER ::= { topology 1 }

        
        -- 1.3.6.1.4.1.4329.15.3.4.1.1
        topologyTable OBJECT-TYPE
            SYNTAX SEQUENCE OF TopologyEntry
            MAX-ACCESS not-accessible
            STATUS current
            DESCRIPTION
                "List of topologies configured on EWC."
            ::= { topologyConfig 1 }

        
        -- 1.3.6.1.4.1.4329.15.3.4.1.1.1
        topologyEntry OBJECT-TYPE
            SYNTAX TopologyEntry
            MAX-ACCESS not-accessible
            STATUS current
            DESCRIPTION
                "Configuration information about a topology in topology table. EWC supports different
                types of topologies, therefore, for complete configuration of a topology not all fields
                are necessary to be defined or have meaning. Definition of each field in this table
                specifies topolog-specific characteristics of the field and its relevance."
            INDEX { topologyID }
            ::= { topologyTable 1 }

        
        TopologyEntry ::=
            SEQUENCE { 
                topologyID
                    Unsigned32,
                topologyName
                    DisplayString,
                topologyMode
                    INTEGER,
                topologyTagged
                    INTEGER,
                topologyVlanID
                    Integer32,
                topologyEgressPort
                    OCTET STRING,
                topologyLayer3
                    TruthValue,
                topologyIPAddress
                    IpAddress,
                topologyIPMask
                    IpAddress,
                topologyMTUsize
                    Unsigned32,
                topologyGateway
                    IpAddress,
                topologyDHCPUsage
                    INTEGER,
                topologyAPRegistration
                    TruthValue,
                topologyManagementTraffic
                    TruthValue,
                topologySynchronize
                    TruthValue,
                topologySyncGateway
                    IpAddress,
                topologySyncMask
                    IpAddress,
                topologySyncIPStart
                    IpAddress,
                topologySyncIPEnd
                    IpAddress,
                topologyStaticIPv6Address
                    DisplayString,
                topologyLinkLocalIPv6Address
                    DisplayString,
                topologyPreFixLength
                    Unsigned32,
                topologyIPv6Gateway
                    DisplayString,
                topologyDynamicEgress
                    INTEGER,
        topologyIsGroup
                    INTEGER,
                topologyGroupMembers
                    OCTET STRING,
                topologyMemberId
                    Integer32
    }

        -- 1.3.6.1.4.1.4329.15.3.4.1.1.1.1
        topologyID OBJECT-TYPE
            SYNTAX Unsigned32
            MAX-ACCESS not-accessible
            STATUS current
            DESCRIPTION
                "Unique internal identifier of the topology. This item is generated
                internally by EWC and has no external meaning."
            ::= { topologyEntry 1 }

        
        -- 1.3.6.1.4.1.4329.15.3.4.1.1.1.2
        topologyName OBJECT-TYPE
            SYNTAX DisplayString
            MAX-ACCESS read-write
            STATUS current
            DESCRIPTION
                "Name associated with topology. This name must be unique within EWC. Allowable
                characters for this field are from the set of A-Z, a-z, -!#$:, 0-9, and space.
                Howerver, it is recommended to avoid leading and trailing spaces."
            ::= { topologyEntry 2 }

        
        -- 1.3.6.1.4.1.4329.15.3.4.1.1.1.3
        topologyMode OBJECT-TYPE
            SYNTAX INTEGER
                {
                undefined(-1),
                routed(0),
                bridgedAtAP(1),
                bridgedAtAC(2),
                thirdPartyAP(4),
                physical(5),
                management(6)
                }
            MAX-ACCESS read-write
            STATUS current
            DESCRIPTION
                "Type of this topology. This field implies the meaning and necessity of 
                other attributes associated to the topology."
            ::= { topologyEntry 3 }

        
        -- 1.3.6.1.4.1.4329.15.3.4.1.1.1.4
        topologyTagged OBJECT-TYPE
            SYNTAX INTEGER
                {
                tagged(1),
                untagged(2)
                }
            MAX-ACCESS read-write
            STATUS current
            DESCRIPTION
                "If topology is tagged, then a VLAN ID must be assigned to the topology. 
                
                Meaning associated to this field is topology specific:
                - For Admin topology (management port) is always untagged
                - Ror routed topology has no meaning and always untagged
                - For all other topologies this field is configurable."
            ::= { topologyEntry 4 }

        
        -- 1.3.6.1.4.1.4329.15.3.4.1.1.1.5
        topologyVlanID OBJECT-TYPE
            SYNTAX Integer32 (-1 | 1..4095)
            MAX-ACCESS read-write
            STATUS current
            DESCRIPTION
                "VLAN ID assigned to a tagged topology. For untagged topology this field has no meaning
                and it is set to -1."
            DEFVAL { -1 }
            ::= { topologyEntry 5 }

        
        -- 1.3.6.1.4.1.4329.15.3.4.1.1.1.6
        topologyEgressPort OBJECT-TYPE
            SYNTAX OCTET STRING (SIZE (0..12))
            MAX-ACCESS read-write
            STATUS current
            DESCRIPTION
                "Egress port associated to this topology if it is tagged and VLANID defined
                for the topology. This field is represented as octect string:
                The most significant bit of most significant octet represent first physical
                port (lowest number port) and second most significant bit of most 
                significant octet represent second physical port and so on.
                
                Meaning associated to this field is topology specific:
                - For Admin topology (management port) this field has no meaning.
                - Ror routed topology this field has no meaning 
                - For all other topologies: physical, bridge at controller, and bridge at AP
                 topologies this field is configurable."
            ::= { topologyEntry 6 }

        
        -- 1.3.6.1.4.1.4329.15.3.4.1.1.1.7
        topologyLayer3 OBJECT-TYPE
            SYNTAX TruthValue
            MAX-ACCESS read-write
            STATUS current
            DESCRIPTION
                "If set to true, then topology has layer three persence.  Any topology 
                with layer three presence must have IP address and gateway assigned to it.
                
                Meaning associated to this field is topology specific:
                - For Admin topology (management port) it is always set to true.
                - Ror bridge at AP this field has no meaning and it is set to false.
                - For routed and physical topologies it is always set to true.
                - For bridge at controller type of topology this field is configurable."
            ::= { topologyEntry 7 }

        
        -- 1.3.6.1.4.1.4329.15.3.4.1.1.1.8
        topologyIPAddress OBJECT-TYPE
            SYNTAX IpAddress
            MAX-ACCESS read-write
            STATUS current
            DESCRIPTION
                "IP address assigned to the topology as its interface.
                
                Meaning associated to this field is topology specific:
                - This field has meaning if topology has layer three presence.
                - Ror bridge at AP this field has no meaning and set 0.0.0.0."
            ::= { topologyEntry 8 }

        
        -- 1.3.6.1.4.1.4329.15.3.4.1.1.1.9
        topologyIPMask OBJECT-TYPE
            SYNTAX IpAddress
            MAX-ACCESS read-write
            STATUS current
            DESCRIPTION
                "Mask for topology's IP address. This field is only applicable to those
                topologies that have IP address assigned to them, otherwise it is set either
                to 255.255.255.255 or 0.0.0.0."
            ::= { topologyEntry 9 }

        
        -- 1.3.6.1.4.1.4329.15.3.4.1.1.1.10
        topologyMTUsize OBJECT-TYPE
            SYNTAX Unsigned32
            MAX-ACCESS read-write
            STATUS current
            DESCRIPTION
                "Default MTU size for the topology. This field is only configurable for a 
                topologies that has layer three presence."
            DEFVAL { 1436 }
            ::= { topologyEntry 10 }

        
        -- 1.3.6.1.4.1.4329.15.3.4.1.1.1.11
        topologyGateway OBJECT-TYPE
            SYNTAX IpAddress
            MAX-ACCESS read-write
            STATUS current
            DESCRIPTION
                "Gateway associated to this topology. This field has meaning for a topology
                that has layer three presence."
            ::= { topologyEntry 11 }

        
        -- 1.3.6.1.4.1.4329.15.3.4.1.1.1.12
        topologyDHCPUsage OBJECT-TYPE
            SYNTAX INTEGER
                {
                none(0),
                useRelay(1),
                localServer(2)
                }
            MAX-ACCESS read-write
            STATUS current
            DESCRIPTION
                "The type of DHCP to be used for IP address assignment to associated MU. 
                This field has meaning only if the topology has layer three persense.
                
                Meaning associated to this field is topology specific:
                - For Admin topology (management port) has no meaning.
                - Ror bridge at AP this field has no meaning.
                - For all other topologies that their layer three presence is enabled this
                  field is configurable."
            ::= { topologyEntry 12 }

        
        -- 1.3.6.1.4.1.4329.15.3.4.1.1.1.13
        topologyAPRegistration OBJECT-TYPE
            SYNTAX TruthValue
            MAX-ACCESS read-write
            STATUS current
            DESCRIPTION
                "If set to true, then AP registration can be achieved using via this topology.
                
                Meaning associated to this field is topology specific:
                - Always false for Admin (management port) and routed topologies
                - Always false and has no meaning for bridge at AP topology.
                - For physical and bridge at controller type topologies that have layer three
                  presence this field can be set to either true or false."
            ::= { topologyEntry 13 }

        
        -- 1.3.6.1.4.1.4329.15.3.4.1.1.1.14
        topologyManagementTraffic OBJECT-TYPE
            SYNTAX TruthValue
            MAX-ACCESS read-write
            STATUS current
            DESCRIPTION
                "If set to true, then management data traffic is allowed on this topology.
                
                Meaning associated to this field is topology specific:
                - Always true for Admin topology (management port) 
                - Has no meaning for bridge at AP type topologies
                - For all other topologies that have layer three presence this field can be 
                  set to either true or false."
            ::= { topologyEntry 14 }

        
        -- 1.3.6.1.4.1.4329.15.3.4.1.1.1.15
        topologySynchronize OBJECT-TYPE
            SYNTAX TruthValue
            MAX-ACCESS read-write
            STATUS current
            DESCRIPTION
                "If set to true, then topology must be synchronized with peer controller
                in availability mode operation.
                
                Meaning associated to this field is topology specific:
                - Always false for Admin topology (management port) 
                - Has no meaning for topologies associated to physical ports.
                - For all other topologies: bridge at controller, routed and bridge at AP
                  type topologies this field can be set to either true or false."
            ::= { topologyEntry 15 }

        
        -- 1.3.6.1.4.1.4329.15.3.4.1.1.1.16
        topologySyncGateway OBJECT-TYPE
            SYNTAX IpAddress
            MAX-ACCESS read-write
            STATUS current
            DESCRIPTION
                "Gateway associated to synchronized topology. This field has meaning for
                those topologies that their topologySynchornize field is set to true."
            ::= { topologyEntry 16 }

        
        -- 1.3.6.1.4.1.4329.15.3.4.1.1.1.17
        topologySyncMask OBJECT-TYPE
            SYNTAX IpAddress
            MAX-ACCESS read-write
            STATUS current
            DESCRIPTION
                "Mask of synchronized gateway IP address.  This field has meaning for
                those topologies that their topologySynchornize field is set to true."
            ::= { topologyEntry 17 }

        
        -- 1.3.6.1.4.1.4329.15.3.4.1.1.1.18
        topologySyncIPStart OBJECT-TYPE
            SYNTAX IpAddress
            MAX-ACCESS read-write
            STATUS current
            DESCRIPTION
                "Range of IP addresses assigned to remote synchronized topology. This IP
                address represents starting IP address. This field has meaning for those
                topologies that their topologySynchornize field is set to true."
            ::= { topologyEntry 18 }

        
        -- 1.3.6.1.4.1.4329.15.3.4.1.1.1.19
        topologySyncIPEnd OBJECT-TYPE
            SYNTAX IpAddress
            MAX-ACCESS read-write
            STATUS current
            DESCRIPTION
                "Range of IP addresses assigned to remote synchronized topology. This IP
                address represents ending IP address. This field has meaning for those
                topologies that their topologySynchornize field is set to true."
            ::= { topologyEntry 19 }

        
        -- 1.3.6.1.4.1.4329.15.3.4.1.1.1.20
        topologyStaticIPv6Address OBJECT-TYPE
            SYNTAX DisplayString
            MAX-ACCESS read-write
            STATUS current
            DESCRIPTION
                "Statically configured IPv6 address assigned to the admin port."
            ::= { topologyEntry 20 }

        
        -- 1.3.6.1.4.1.4329.15.3.4.1.1.1.21
        topologyLinkLocalIPv6Address OBJECT-TYPE
            SYNTAX DisplayString
            MAX-ACCESS read-only
            STATUS current
            DESCRIPTION
                "Automatically generated link-local IPv6 address assigned to the admin port."
            ::= { topologyEntry 21 }

        
        -- 1.3.6.1.4.1.4329.15.3.4.1.1.1.22
        topologyPreFixLength OBJECT-TYPE
            SYNTAX Unsigned32
            MAX-ACCESS read-write
            STATUS current
            DESCRIPTION
                "The prfix length of the statically configured IPv6 address of the topology."
            ::= { topologyEntry 22 }

        
        -- 1.3.6.1.4.1.4329.15.3.4.1.1.1.23
        topologyIPv6Gateway OBJECT-TYPE
            SYNTAX DisplayString
            MAX-ACCESS read-write
            STATUS current
            DESCRIPTION
                "The gateway of IPv6 address that is associated to the admin topology."
            ::= { topologyEntry 23 }




        -- 1.3.6.1.4.1.4329.15.3.4.1.1.1.24
        topologyDynamicEgress OBJECT-TYPE
            SYNTAX INTEGER
                {
                disable(0),
                enable(1)
                }
            MAX-ACCESS read-write
            STATUS current
            DESCRIPTION
                "Enable/disable dynamic egress for this topology. Dynamic egress allows a station to
                receive from this VLAN if it can send to this VLAN."
            ::= { topologyEntry 24 }


        -- 1.3.6.1.4.1.4329.15.3.4.1.1.1.25
        topologyIsGroup OBJECT-TYPE
            SYNTAX INTEGER
                {
                no(0),
                yes(1)
                }
            MAX-ACCESS read-write
            STATUS current
            DESCRIPTION
                "When this flag is yes, this means the
                topology is created as a group topology."
            ::= { topologyEntry 25 }


        -- 1.3.6.1.4.1.4329.15.3.4.1.1.1.26
        topologyGroupMembers OBJECT-TYPE
            SYNTAX OCTET STRING (SIZE (0..12))
            MAX-ACCESS read-write
            STATUS current
            DESCRIPTION
                "This field specifies the topologies for this group.  This field has meaning only when topologyIsGroup is set to 1. 
        This field is represented as octect string.
                The most significant bit of the most significant octet of the octet string represents the first topology with topologyID = 0
                and second most significant bit of the most significant octet represents the second topology with
                topologyID = 1 and so on."
            ::= { topologyEntry 26 }

        -- 1.3.6.1.4.1.4329.15.3.4.1.1.1.27
        topologyMemberId OBJECT-TYPE
            SYNTAX Integer32
            MAX-ACCESS read-write
            STATUS current
            DESCRIPTION
                " -1 : Means this topology is not a member of a group topology.
                  valid topology ID : Means this topology is a member of a configured group topology that has  
                  this group topology ID."
            ::= { topologyEntry 27 }


        -- 1.3.6.1.4.1.4329.15.3.4.2
        topologyStat OBJECT IDENTIFIER ::= { topology 2 }

        
        -- 1.3.6.1.4.1.4329.15.3.4.2.1
        topoStatTable OBJECT-TYPE
            SYNTAX SEQUENCE OF TopoStatEntry
            MAX-ACCESS not-accessible
            STATUS current
            DESCRIPTION
                "Statistics describing traffic transmitted or received for a single topology. 
                This is the traffic on the topology that is coming from or going to
                destinations on the wired network."
            ::= { topologyStat 1 }

        
        -- 1.3.6.1.4.1.4329.15.3.4.2.1.1
        topoStatEntry OBJECT-TYPE
            SYNTAX TopoStatEntry
            MAX-ACCESS not-accessible
            STATUS current
            DESCRIPTION
                "Statistic related an entry in topology table."
            INDEX { topologyID }
            ::= { topoStatTable 1 }

        
        TopoStatEntry ::=
            SEQUENCE { 
                topoStatName
                    DisplayString,
                topoStatTxPkts
                    Counter64,
                topoStatRxPkts
                    Counter64,
                topoStatTxOctets
                    Counter64,
                topoStatRxOctets
                    Counter64,
                topoStatMulticastTxPkts
                    Counter64,
                topoStatMulticastRxPkts
                    Counter64,
                topoStatBroadcastTxPkts
                    Counter64,
                topoStatBroadcastRxPkts
                    Counter64,
                topoStatFrameChkSeqErrors
                    Counter64,
                topoStatFrameTooLongErrors
                    Counter64
             }

        -- 1.3.6.1.4.1.4329.15.3.4.2.1.1.1
        topoStatName OBJECT-TYPE
            SYNTAX DisplayString
            MAX-ACCESS read-only
            STATUS current
            DESCRIPTION
                "Topology name."
            ::= { topoStatEntry 1 }

        
        -- 1.3.6.1.4.1.4329.15.3.4.2.1.1.2
        topoStatTxPkts OBJECT-TYPE
            SYNTAX Counter64
            MAX-ACCESS read-only
            STATUS current
            DESCRIPTION
                "Number of packets transmitted to the wired 
                network on the topology/vlan."
            ::= { topoStatEntry 2 }

        
        -- 1.3.6.1.4.1.4329.15.3.4.2.1.1.3
        topoStatRxPkts OBJECT-TYPE
            SYNTAX Counter64
            MAX-ACCESS read-only
            STATUS current
            DESCRIPTION
                "Number of packets received from the wired 
                network on the topology/vlan."
            ::= { topoStatEntry 3 }

        
        -- 1.3.6.1.4.1.4329.15.3.4.2.1.1.4
        topoStatTxOctets OBJECT-TYPE
            SYNTAX Counter64
            MAX-ACCESS read-only
            STATUS current
            DESCRIPTION
                "Number of octets transmitted in frames to 
                the wired network on the topology/vlan."
            ::= { topoStatEntry 4 }

        
        -- 1.3.6.1.4.1.4329.15.3.4.2.1.1.5
        topoStatRxOctets OBJECT-TYPE
            SYNTAX Counter64
            MAX-ACCESS read-only
            STATUS current
            DESCRIPTION
                "Number of octets received in frames from the wired 
                network on the topology/vlan."        
            ::= { topoStatEntry 5 }

        
        -- 1.3.6.1.4.1.4329.15.3.4.2.1.1.6
        topoStatMulticastTxPkts OBJECT-TYPE
            SYNTAX Counter64
            MAX-ACCESS read-only
            STATUS current
            DESCRIPTION
                "Number of multicast frames transmitted to 
                the wired network on the topology/vlan."
            ::= { topoStatEntry 6 }

        
        -- 1.3.6.1.4.1.4329.15.3.4.2.1.1.7
        topoStatMulticastRxPkts OBJECT-TYPE
            SYNTAX Counter64
            MAX-ACCESS read-only
            STATUS current
            DESCRIPTION
                "Number of multicast frames received from 
                the wired network on the topology/vlan."
            ::= { topoStatEntry 7 }

        
        -- 1.3.6.1.4.1.4329.15.3.4.2.1.1.8
        topoStatBroadcastTxPkts OBJECT-TYPE
            SYNTAX Counter64
            MAX-ACCESS read-only
            STATUS current
            DESCRIPTION
                "Number of broadcast frames transmitted to 
                the wired network on the topology/vlan."
            ::= { topoStatEntry 8 }

        
        -- 1.3.6.1.4.1.4329.15.3.4.2.1.1.9
        topoStatBroadcastRxPkts OBJECT-TYPE
            SYNTAX Counter64
            MAX-ACCESS read-only
            STATUS current
            DESCRIPTION
                "Number of broadcast frames received from 
                the wired network on the topology/vlan."                
            ::= { topoStatEntry 9 }

        
        -- 1.3.6.1.4.1.4329.15.3.4.2.1.1.10
        topoStatFrameChkSeqErrors OBJECT-TYPE
            SYNTAX Counter64
            MAX-ACCESS read-only
            STATUS current
            DESCRIPTION
                "Number of frames with checksum errors received 
                from the wired network on the topology/vlan."
            ::= { topoStatEntry 10 }

        
        -- 1.3.6.1.4.1.4329.15.3.4.2.1.1.11
        topoStatFrameTooLongErrors OBJECT-TYPE
            SYNTAX Counter64
            MAX-ACCESS read-only
            STATUS current
            DESCRIPTION
                "Number of oversized frames received from 
                the wired network on the topology/vlan."
            ::= { topoStatEntry 11 }

        
        -- 1.3.6.1.4.1.4329.15.3.4.2.2
        topoExceptionStatTable OBJECT-TYPE
            SYNTAX SEQUENCE OF TopoExceptionStatEntry
            MAX-ACCESS not-accessible
            STATUS current
            DESCRIPTION
                "The table contains list of exception-specific filters statistics for configured
                topologies in EWC."
            ::= { topologyStat 2 }

        
        -- 1.3.6.1.4.1.4329.15.3.4.2.2.1
        topoExceptionStatEntry OBJECT-TYPE
            SYNTAX TopoExceptionStatEntry
            MAX-ACCESS not-accessible
            STATUS current
            DESCRIPTION
                "An entry in topology exception statistic table."
            INDEX { topologyID }
            ::= { topoExceptionStatTable 1 }

        
        TopoExceptionStatEntry ::=
            SEQUENCE { 
                topoExceptionFiterName
                    OCTET STRING,
                topoExceptionStatPktsDenied
                    Counter64,
                topoExceptionStatPktsAllowed
                    Counter64
             }

        -- 1.3.6.1.4.1.4329.15.3.4.2.2.1.1
        topoExceptionFiterName OBJECT-TYPE
            SYNTAX OCTET STRING (SIZE (1..64))
            MAX-ACCESS read-write
            STATUS current
            DESCRIPTION
                "Exception filter name."
            ::= { topoExceptionStatEntry 1 }

        
        -- 1.3.6.1.4.1.4329.15.3.4.2.2.1.2
        topoExceptionStatPktsDenied OBJECT-TYPE
            SYNTAX Counter64
            MAX-ACCESS read-only
            STATUS current
            DESCRIPTION
                "Number of packets that were denied by defined filters since device's last restart."
            ::= { topoExceptionStatEntry 2 }

        
        -- 1.3.6.1.4.1.4329.15.3.4.2.2.1.3
        topoExceptionStatPktsAllowed OBJECT-TYPE
            SYNTAX Counter64
            MAX-ACCESS read-only
            STATUS current
            DESCRIPTION
                "Number packets that were allowed by defined filters since device's last restart."
            ::= { topoExceptionStatEntry 3 }


        
        -- 1.3.6.1.4.1.4329.15.3.4.2.3
        topoWireStatTable OBJECT-TYPE
            SYNTAX SEQUENCE OF TopoWireStatEntry
            MAX-ACCESS not-accessible
            STATUS deprecated
            DESCRIPTION
                "The table contains statistics describing traffic transmitted or received 
                unencapsulated (i.e. not wrapped in WASSP) for each topology"
            ::= { topologyStat 3 }

        -- 1.3.6.1.4.1.4329.15.3.4.2.3.1
        topoWireStatEntry OBJECT-TYPE
            SYNTAX TopoWireStatEntry
            MAX-ACCESS not-accessible
            STATUS deprecated
            DESCRIPTION
                "Statistics describing traffic transmitted or received unencapsulated (i.e. not wrapped in WASSP)
                for a single topology. This is the traffic on the topology that is coming from or going to destinations 
                on the wired network other than to the controller's APs."
            INDEX { topologyID }
            ::= { topoWireStatTable 1 }

        
        TopoWireStatEntry ::=
            SEQUENCE { 
                topoWireStatName
                    DisplayString,
                topoWireStatTxPkts
                    Counter64,
                topoWireStatRxPkts
                    Counter64,
                topoWireStatTxOctets
                    Counter64,
                topoWireStatRxOctets
                    Counter64,
                topoWireStatMulticastTxPkts
                    Counter64,
                topoWireStatMulticastRxPkts
                    Counter64,
                topoWireStatBroadcastTxPkts
                    Counter64,
                topoWireStatBroadcastRxPkts
                    Counter64,
                topoWireStatFrameChkSeqErrors
                    Counter64,
                topoWireStatFrameTooLongErrors
                    Counter64
             }

        -- 1.3.6.1.4.1.4329.15.3.4.2.3.1.1
        topoWireStatName OBJECT-TYPE
            SYNTAX DisplayString
            MAX-ACCESS read-only
            STATUS deprecated
            DESCRIPTION
                "Topology name."
            ::= { topoWireStatEntry 1 }



        
        -- 1.3.6.1.4.1.4329.15.3.4.2.3.1.2
        topoWireStatTxPkts OBJECT-TYPE
            SYNTAX Counter64
            MAX-ACCESS read-only
            STATUS deprecated
            DESCRIPTION
                "Number of packets transmitted unencapsulated to 
                the wired network on the topology/vlan."
            ::= { topoWireStatEntry 2 }

        
        -- 1.3.6.1.4.1.4329.15.3.4.2.3.1.3
        topoWireStatRxPkts OBJECT-TYPE
            SYNTAX Counter64
            MAX-ACCESS read-only
            STATUS deprecated
            DESCRIPTION
                "Number of packets received unencapsulated from 
                the wired network on the topology/vlan."
            ::= { topoWireStatEntry 3 }

        
        -- 1.3.6.1.4.1.4329.15.3.4.2.3.1.4
        topoWireStatTxOctets OBJECT-TYPE
            SYNTAX Counter64
            MAX-ACCESS read-only
            STATUS deprecated
            DESCRIPTION
                "Number of octets transmitted in unencapsulated frames
                to the wired network on the topology/vlan."
            ::= { topoWireStatEntry 4 }

        
        -- 1.3.6.1.4.1.4329.15.3.4.2.3.1.5
        topoWireStatRxOctets OBJECT-TYPE
            SYNTAX Counter64
            MAX-ACCESS read-only
            STATUS deprecated
            DESCRIPTION
                "Number of octets received in unencapsulated frames 
                to the wired network on the topology/vlan."
            ::= { topoWireStatEntry 5 }

        
        -- 1.3.6.1.4.1.4329.15.3.4.2.3.1.6
        topoWireStatMulticastTxPkts OBJECT-TYPE
            SYNTAX Counter64
            MAX-ACCESS read-only
            STATUS deprecated
            DESCRIPTION
                "Number of multicast frames transmitted unencapsulated 
                to the wired network on the topology/vlan."
            ::= { topoWireStatEntry 6 }

        
        -- 1.3.6.1.4.1.4329.15.3.4.2.3.1.7
        topoWireStatMulticastRxPkts OBJECT-TYPE
            SYNTAX Counter64
            MAX-ACCESS read-only
            STATUS deprecated
            DESCRIPTION
                "Number of multicast frames received unencapsulated 
                from the wired network on the topology/vlan."
            ::= { topoWireStatEntry 7 }

        
        -- 1.3.6.1.4.1.4329.15.3.4.2.3.1.8
        topoWireStatBroadcastTxPkts OBJECT-TYPE
            SYNTAX Counter64
            MAX-ACCESS read-only
            STATUS deprecated
            DESCRIPTION
                "Number of broadcast frames transmitted unencapsulated 
                to the wired network on the topology/vlan."
            ::= { topoWireStatEntry 8 }

        
        -- 1.3.6.1.4.1.4329.15.3.4.2.3.1.9
        topoWireStatBroadcastRxPkts OBJECT-TYPE
            SYNTAX Counter64
            MAX-ACCESS read-only
            STATUS deprecated
            DESCRIPTION
                "Number of broadcast frames received unencapsulated from 
                the wired network on the topology/vlan."
            ::= { topoWireStatEntry 9 }

        
        -- 1.3.6.1.4.1.4329.15.3.4.2.3.1.10
        topoWireStatFrameChkSeqErrors OBJECT-TYPE
            SYNTAX Counter64
            MAX-ACCESS read-only
            STATUS deprecated
            DESCRIPTION
                "Number of unencapsulated frames with checksum errors 
                received from the wired network on the topology/vlan."
            ::= { topoWireStatEntry 10 }

        -- 1.3.6.1.4.1.4329.15.3.4.2.3.1.11
        topoWireStatFrameTooLongErrors OBJECT-TYPE
            SYNTAX Counter64
            MAX-ACCESS read-only
            STATUS deprecated
            DESCRIPTION
                "Number of unencapsulated frames with length longer than 
                permitted received from the wired network on the topology/vlan."
            ::= { topoWireStatEntry 11 }
        

        
        -- 1.3.6.1.4.1.4329.15.3.4.2.4
        topoCompleteStatTable OBJECT-TYPE
            SYNTAX SEQUENCE OF TopoCompleteStatEntry
            MAX-ACCESS not-accessible
            STATUS current
            DESCRIPTION
        "The table contains statistics describing traffic transmitted 
        and received for each topology on both the wired side and 
        the wireless side."            
       ::= { topologyStat 4 }

        -- 1.3.6.1.4.1.4329.15.3.4.2.4.1
        topoCompleteStatEntry OBJECT-TYPE
            SYNTAX TopoCompleteStatEntry
            MAX-ACCESS not-accessible
            STATUS current
            DESCRIPTION
                "Statistics describing traffic transmitted and received on 
                a single topology on both the wired side and the wireless side."
            INDEX { topologyID }
            ::= { topoCompleteStatTable 1 }

        
        TopoCompleteStatEntry ::=
            SEQUENCE { 
                topoCompleteStatName
                    DisplayString,
                topoCompleteStatTxPkts
                    Counter64,
                topoCompleteStatRxPkts
                    Counter64,
                topoCompleteStatTxOctets
                    Counter64,
                topoCompleteStatRxOctets
                    Counter64,
                topoCompleteStatMulticastTxPkts
                    Counter64,
                topoCompleteStatMulticastRxPkts
                    Counter64,
                topoCompleteStatBroadcastTxPkts
                    Counter64,
                topoCompleteStatBroadcastRxPkts
                    Counter64,
                topoCompleteStatFrameChkSeqErrors
                    Counter64,
                topoCompleteStatFrameTooLongErrors
                    Counter64
             }

        -- 1.3.6.1.4.1.4329.15.3.4.2.4.1.1
        topoCompleteStatName OBJECT-TYPE
            SYNTAX DisplayString
            MAX-ACCESS read-only
            STATUS current
            DESCRIPTION
                "Topology name."                
            ::= { topoCompleteStatEntry 1 }



        
        -- 1.3.6.1.4.1.4329.15.3.4.2.4.1.2
        topoCompleteStatTxPkts OBJECT-TYPE
            SYNTAX Counter64
            MAX-ACCESS read-only
            STATUS current
            DESCRIPTION
                "Number of packets transmitted to the wired and 
                wireless networks on the topology/vlan."
            ::= { topoCompleteStatEntry 2 }

        
        -- 1.3.6.1.4.1.4329.15.3.4.2.4.1.3
        topoCompleteStatRxPkts OBJECT-TYPE
            SYNTAX Counter64
            MAX-ACCESS read-only
            STATUS current
            DESCRIPTION
                "Number of packets received from the wired and 
                wireless networks on the topology/vlan."
            ::= { topoCompleteStatEntry 3 }

        
        -- 1.3.6.1.4.1.4329.15.3.4.2.4.1.4
        topoCompleteStatTxOctets OBJECT-TYPE
            SYNTAX Counter64
            MAX-ACCESS read-only
            STATUS current
            DESCRIPTION
                "Number of octets transmitted in frames to the wired
                and wireless networks on the topology/vlan."
            ::= { topoCompleteStatEntry 4 }

        
        -- 1.3.6.1.4.1.4329.15.3.4.2.4.1.5
        topoCompleteStatRxOctets OBJECT-TYPE
            SYNTAX Counter64
            MAX-ACCESS read-only
            STATUS current
            DESCRIPTION
                "Number of octets received in frames from the wired
                and wireless networks on the topology/vlan."
            ::= { topoCompleteStatEntry 5 }

        
        -- 1.3.6.1.4.1.4329.15.3.4.2.4.1.6
        topoCompleteStatMulticastTxPkts OBJECT-TYPE
            SYNTAX Counter64
            MAX-ACCESS read-only
            STATUS current
            DESCRIPTION
                "Number of multicast frames transmitted to the wired
                and wireless networks on the topology/vlan."
            ::= { topoCompleteStatEntry 6 }

        
        -- 1.3.6.1.4.1.4329.15.3.4.2.4.1.7
        topoCompleteStatMulticastRxPkts OBJECT-TYPE
            SYNTAX Counter64
            MAX-ACCESS read-only
            STATUS current
            DESCRIPTION
                "Number of multicast frames received from the wired
                and wireless networks on the topology/vlan."
            ::= { topoCompleteStatEntry 7 }

        
        -- 1.3.6.1.4.1.4329.15.3.4.2.4.1.8
        topoCompleteStatBroadcastTxPkts OBJECT-TYPE
            SYNTAX Counter64
            MAX-ACCESS read-only
            STATUS current
            DESCRIPTION
                "Number of broadcast frames transmitted to the wired
                and wireless networks on the topology/vlan."
            ::= { topoCompleteStatEntry 8 }

        
        -- 1.3.6.1.4.1.4329.15.3.4.2.4.1.9
        topoCompleteStatBroadcastRxPkts OBJECT-TYPE
            SYNTAX Counter64
            MAX-ACCESS read-only
            STATUS current
            DESCRIPTION
                "Number of broadcast frames received from the wired
                and wireless networks on the topology/vlan."
            ::= { topoCompleteStatEntry 9 }

        
        -- 1.3.6.1.4.1.4329.15.3.4.2.4.1.10
        topoCompleteStatFrameChkSeqErrors OBJECT-TYPE
            SYNTAX Counter64
            MAX-ACCESS read-only
            STATUS current
            DESCRIPTION
                "Number of frames with checksum errors received from
                the wired and wireless networks on the topology/vlan."
            ::= { topoCompleteStatEntry 10 }

        -- 1.3.6.1.4.1.4329.15.3.4.2.4.1.11
        topoCompleteStatFrameTooLongErrors OBJECT-TYPE
            SYNTAX Counter64
            MAX-ACCESS read-only
            STATUS current
            DESCRIPTION
                "Number of oversized frames received from the wired 
                and wireless networks on the topology/vlan."
            ::= { topoCompleteStatEntry 11 }
        


        
        -- 1.3.6.1.4.1.4329.15.3.5
        accessPoints OBJECT IDENTIFIER ::= { hiPathWirelessMgmt 5 }

        
        -- 1.3.6.1.4.1.4329.15.3.5.1
        apConfigObjects OBJECT IDENTIFIER ::= { accessPoints 1 }

        
        -- 1.3.6.1.4.1.4329.15.3.5.1.1
        apCount OBJECT-TYPE
            SYNTAX Integer32
            MAX-ACCESS read-only
            STATUS current
            DESCRIPTION
                "The count of currently configured AccessPoints associated with this WirelessController."
            ::= { apConfigObjects 1 }

        
        -- 1.3.6.1.4.1.4329.15.3.5.1.2
        apTable OBJECT-TYPE
            SYNTAX SEQUENCE OF ApEntry
            MAX-ACCESS not-accessible
            STATUS current
            DESCRIPTION
                "Contains a list of all configured APs associated with the Wireless Controller."
            ::= { apConfigObjects 2 }

        
        -- 1.3.6.1.4.1.4329.15.3.5.1.2.1
        apEntry OBJECT-TYPE
            SYNTAX ApEntry
            MAX-ACCESS not-accessible
            STATUS current
            DESCRIPTION
                "Configuration information for an access point."
            INDEX { apIndex }
            ::= { apTable 1 }

        
        ApEntry ::=
            SEQUENCE { 
                apIndex
                    Integer32,
                apName
                    DisplayString,
                apDesc
                    DisplayString,
                apSerialNumber
                    OCTET STRING,
                apPortifIndex
                    InterfaceIndex,
                apWiredIfIndex
                    InterfaceIndex,
                apSoftwareVersion
                    OCTET STRING,
                apSpecific
                    OBJECT IDENTIFIER,
                apBroadcastDisassociate
                    TruthValue,
                apRowStatus
                    RowStatus,
                apVlanID
                    Integer32,
                apIpAssignmentType
                    INTEGER,
                apIfMAC
                    MacAddress,
                apIPAddress
                    IpAddress,
                apHwVersion
                    DisplayString,
                apSwVersion
                    DisplayString,
                apEnvironment
                    INTEGER,
                apHome
                    INTEGER,
                apRole
                    INTEGER,
                apState
                    INTEGER,
                apStatus
                    INTEGER,
                apPollTimeout
                    Gauge32,
                apPollInterval
                    Gauge32,
                apTelnetAccess
                    INTEGER,
                apMaintainClientSession
                    TruthValue,
                apRestartServiceContAbsent
                    TruthValue,
                apHostname
                    DisplayString,
                apLocation
                    DisplayString,
                apStaticMTUsize
                    Unsigned32,
                apSiteID
                    Integer32,
                apZone
                    DisplayString,
                apLLDP
                    TruthValue,
                apSSHAccess
                    TruthValue,
                apLEDMode
                    INTEGER,
                apLocationbasedService
                    TruthValue,
                apSecureTunnel
                    TruthValue,
                apEncryptCntTraffic
                    TruthValue,
                apMICErrorWarning
                    TruthValue,
                apSecureDataTunnelType
                    INTEGER,
                apIPMulticastAssembly
                    TruthValue,
                apSSHConnection
                    INTEGER
             }

        -- 1.3.6.1.4.1.4329.15.3.5.1.2.1.1
        apIndex OBJECT-TYPE
            SYNTAX Integer32 (1..2147483647)
            MAX-ACCESS read-write
            STATUS current
            DESCRIPTION
                "Table index for the access point."
            ::= { apEntry 1 }

        
        -- 1.3.6.1.4.1.4329.15.3.5.1.2.1.2
        apName OBJECT-TYPE
            SYNTAX DisplayString
            MAX-ACCESS read-write
            STATUS current
            DESCRIPTION
                "Access Point's name."
            ::= { apEntry 2 }

        
        -- 1.3.6.1.4.1.4329.15.3.5.1.2.1.3
        apDesc OBJECT-TYPE
            SYNTAX DisplayString
            MAX-ACCESS read-write
            STATUS current
            DESCRIPTION
                "Text description of the AP."
            ::= { apEntry 3 }

        
        -- 1.3.6.1.4.1.4329.15.3.5.1.2.1.4
        apSerialNumber OBJECT-TYPE
            SYNTAX OCTET STRING (SIZE (16))
            MAX-ACCESS read-only
            STATUS current
            DESCRIPTION
                "16-character serial number of the AccessPoint."
            ::= { apEntry 4 }

        
        -- 1.3.6.1.4.1.4329.15.3.5.1.2.1.5
        apPortifIndex OBJECT-TYPE
            SYNTAX InterfaceIndex
            MAX-ACCESS read-write
            STATUS current
            DESCRIPTION
                "ifIndex of the physical port to which this AP is assigned."
            ::= { apEntry 5 }

        
        -- 1.3.6.1.4.1.4329.15.3.5.1.2.1.6
        apWiredIfIndex OBJECT-TYPE
            SYNTAX InterfaceIndex
            MAX-ACCESS read-write
            STATUS current
            DESCRIPTION
                "ifIndex of the wired interface on the AP."
            ::= { apEntry 6 }

        
        -- 1.3.6.1.4.1.4329.15.3.5.1.2.1.7
        apSoftwareVersion OBJECT-TYPE
            SYNTAX OCTET STRING
            MAX-ACCESS read-only
            STATUS current
            DESCRIPTION
                "Software version currently installed on the AP."
            ::= { apEntry 7 }

        
        -- 1.3.6.1.4.1.4329.15.3.5.1.2.1.8
        apSpecific OBJECT-TYPE
            SYNTAX OBJECT IDENTIFIER
            MAX-ACCESS read-only
            STATUS current
            DESCRIPTION
                "A link back to the OID under the hiPathWirelessProducts
                branch that identifies the specific version of this AP."
            ::= { apEntry 8 }

        
        -- 1.3.6.1.4.1.4329.15.3.5.1.2.1.9
        apBroadcastDisassociate OBJECT-TYPE
            SYNTAX TruthValue
            MAX-ACCESS read-write
            STATUS current
            DESCRIPTION
                "True indicates that the AP should broadcast
                disassociation requests, False indicates unicast."
            ::= { apEntry 9 }

        
        -- 1.3.6.1.4.1.4329.15.3.5.1.2.1.10
        apRowStatus OBJECT-TYPE
            SYNTAX RowStatus
            MAX-ACCESS read-write
            STATUS current
            DESCRIPTION
                "RowStatus for the apTable."
            ::= { apEntry 10 }

        
        -- 1.3.6.1.4.1.4329.15.3.5.1.2.1.11
        apVlanID OBJECT-TYPE
            SYNTAX Integer32
            MAX-ACCESS read-write
            STATUS current
            DESCRIPTION
                "VLAN tag for the packets trasmitted to/from Access Point.
                Value ranges: (-1) it is not tagged, zero(0) means reserved, 1-4094 tag value."
            DEFVAL { -1 }
            ::= { apEntry 11 }

        
        -- 1.3.6.1.4.1.4329.15.3.5.1.2.1.12
        apIpAssignmentType OBJECT-TYPE
            SYNTAX INTEGER
                {
                dhcp(1),
                static(2)
                }
            MAX-ACCESS read-write
            STATUS current
            DESCRIPTION
                "IP address assignment type, dhcp(1) = uses DHCP to obtain IP address, 
                static(2) = static IP address is assigned to the access point."
            ::= { apEntry 12 }

        
        -- 1.3.6.1.4.1.4329.15.3.5.1.2.1.13
        apIfMAC OBJECT-TYPE
            SYNTAX MacAddress
            MAX-ACCESS read-only
            STATUS current
            DESCRIPTION
                "Acess Point's wired interface MAC address."
            ::= { apEntry 13 }

        
        -- 1.3.6.1.4.1.4329.15.3.5.1.2.1.14
        apIPAddress OBJECT-TYPE
            SYNTAX IpAddress
            MAX-ACCESS read-write
            STATUS current
            DESCRIPTION
                "Access Point's wired interface IP address."
            ::= { apEntry 14 }

        
        -- 1.3.6.1.4.1.4329.15.3.5.1.2.1.17
        apHwVersion OBJECT-TYPE
            SYNTAX DisplayString
            MAX-ACCESS read-write
            STATUS current
            DESCRIPTION
                "Text description of Access Point's hardware version."
            ::= { apEntry 17 }

        
        -- 1.3.6.1.4.1.4329.15.3.5.1.2.1.18
        apSwVersion OBJECT-TYPE
            SYNTAX DisplayString
            MAX-ACCESS read-write
            STATUS current
            DESCRIPTION
                "Text description of Access Point's major software version."
            ::= { apEntry 18 }

        
        -- 1.3.6.1.4.1.4329.15.3.5.1.2.1.19
        apEnvironment OBJECT-TYPE
            SYNTAX INTEGER
                {
                indoor(1),
                outdoor(2)
                }
            MAX-ACCESS read-write
            STATUS current
            DESCRIPTION
                "Access Point's environment."
            ::= { apEntry 19 }

        
        -- 1.3.6.1.4.1.4329.15.3.5.1.2.1.20
        apHome OBJECT-TYPE
            SYNTAX INTEGER
                {
                local(1),
                foreign(2)
                }
            MAX-ACCESS read-write
            STATUS current
            DESCRIPTION
                "Local session is created when access point registers directly with the controller.
                Foreign session is mirrored session created via availability feature."
            ::= { apEntry 20 }

        
        -- 1.3.6.1.4.1.4329.15.3.5.1.2.1.21
        apRole OBJECT-TYPE
            SYNTAX INTEGER
                {
                accessPoint(1),
                sensor(2),
                guardian(3)
                }
            MAX-ACCESS read-write
            STATUS current
            DESCRIPTION
                "Indicates whether Access Point is a traffic fordwarder, sensor or guardian"
            ::= { apEntry 21 }

        
        -- 1.3.6.1.4.1.4329.15.3.5.1.2.1.22
        apState OBJECT-TYPE
            SYNTAX INTEGER
                {
                active(1),
                inactive(2)
                }
            MAX-ACCESS read-write
            STATUS current
            DESCRIPTION
                "Active means that access point has registered with this controller at some point of
                time and still has active connection with this controller. This variable has meaning
                in the context of the controller that query is done. Inactive mean access point has
                lost the connection with this controller."
            ::= { apEntry 22 }

        
        -- 1.3.6.1.4.1.4329.15.3.5.1.2.1.23
        apStatus OBJECT-TYPE
            SYNTAX INTEGER
                {
                approved(1),
                pending(2)
                }
            MAX-ACCESS read-write
            STATUS current
            DESCRIPTION
                "Registration state for the access point at the time of query, approved(1) means the
                registration was completed, pending(2) means access point has registered but waiting
                manual approval from admin."
            ::= { apEntry 23 }

        
        -- 1.3.6.1.4.1.4329.15.3.5.1.2.1.24
        apPollTimeout OBJECT-TYPE
            SYNTAX Gauge32 (3..3600)
            MAX-ACCESS read-write
            STATUS current
            DESCRIPTION
                "Duration after which the access point's connection to controller is 
                considered has been lost if polling fails.
                "
            ::= { apEntry 24 }

        
        -- 1.3.6.1.4.1.4329.15.3.5.1.2.1.25
        apPollInterval OBJECT-TYPE
            SYNTAX Gauge32
            MAX-ACCESS read-write
            STATUS current
            DESCRIPTION
                "Interval between each poll sent to the controller."
            ::= { apEntry 25 }

        
        -- 1.3.6.1.4.1.4329.15.3.5.1.2.1.26
        apTelnetAccess OBJECT-TYPE
            SYNTAX INTEGER
                {
                enabled(1),
                disabled(2),
                na(3)
                }
            MAX-ACCESS read-write
            STATUS current
            DESCRIPTION
                "Indicates whether telnet access is enabled/disabled. This value only applys to AP26xx, W788, W786 and AP4102x APs.
                1 : Enabled.
                2 : Disabled.
                3 : Telnet is not supported."
            ::= { apEntry 26 }

        
        -- 1.3.6.1.4.1.4329.15.3.5.1.2.1.27
        apMaintainClientSession OBJECT-TYPE
            SYNTAX TruthValue
            MAX-ACCESS read-write
            STATUS current
            DESCRIPTION
                "If true, Access Point maintains client's session in the event of poll failure."
            ::= { apEntry 27 }

        
        -- 1.3.6.1.4.1.4329.15.3.5.1.2.1.28
        apRestartServiceContAbsent OBJECT-TYPE
            SYNTAX TruthValue
            MAX-ACCESS read-write
            STATUS current
            DESCRIPTION
                "If true, Access Point restarts the service in the absence of controller."
            ::= { apEntry 28 }

        
        -- 1.3.6.1.4.1.4329.15.3.5.1.2.1.29
        apHostname OBJECT-TYPE
            SYNTAX DisplayString
            MAX-ACCESS read-only
            STATUS current
            DESCRIPTION
                "Hostname assigned to Access Point."
            ::= { apEntry 29 }

        
        -- 1.3.6.1.4.1.4329.15.3.5.1.2.1.30
        apLocation OBJECT-TYPE
            SYNTAX DisplayString
            MAX-ACCESS read-write
            STATUS current
            DESCRIPTION
                "Text identifying location of the access point."
            ::= { apEntry 30 }

        
        -- 1.3.6.1.4.1.4329.15.3.5.1.2.1.31
        apStaticMTUsize OBJECT-TYPE
            SYNTAX Unsigned32 (600..1500)
            MAX-ACCESS read-write
            STATUS current
            DESCRIPTION
                "Configured MTU size for the access point. Access point will use the lower value of
                MTU size between statically configured MTU size and dynamically learned MTU size."
            DEFVAL { 1500 }
            ::= { apEntry 31 }

        
        -- 1.3.6.1.4.1.4329.15.3.5.1.2.1.32
        apSiteID OBJECT-TYPE
            SYNTAX Integer32
            MAX-ACCESS read-write
            STATUS current
            DESCRIPTION
                "The site ID, as defined in siteTable, that this AP is member of. The value of -1
                indicates that AP is not member of any site."
            DEFVAL { -1 }
            ::= { apEntry 32 }

        
        -- 1.3.6.1.4.1.4329.15.3.5.1.2.1.33
        apZone OBJECT-TYPE
            SYNTAX DisplayString
            MAX-ACCESS read-write
            STATUS current
            DESCRIPTION
                "The Zone to which the Access Point belongs. "
            ::= { apEntry 33 }

        
        -- 1.3.6.1.4.1.4329.15.3.5.1.2.1.34
        apLLDP OBJECT-TYPE
            SYNTAX TruthValue
            MAX-ACCESS read-write
            STATUS current
            DESCRIPTION
                "Enable or disable broadcasting of LLDP information by the wireless AP."
            ::= { apEntry 34 }

        
        -- 1.3.6.1.4.1.4329.15.3.5.1.2.1.35
        apSSHAccess OBJECT-TYPE
            SYNTAX TruthValue
            MAX-ACCESS read-write
            STATUS deprecated
            DESCRIPTION
                "Enable or Disable SSH access to the Wireless AP. This value only applys to AP36xx, 
                AP37xx, W788C and W786C APs."
            ::= { apEntry 35 }

        
        -- 1.3.6.1.4.1.4329.15.3.5.1.2.1.36
        apLEDMode OBJECT-TYPE
            SYNTAX INTEGER
                {
                off(0),
                wdsSignalStrength(1),
                identify(2),
                normal(3)
                }
            MAX-ACCESS read-write
            STATUS current
            DESCRIPTION
                "LED status field for the Access Point. 
                off(0):  LED is set to off for the AP.
                wdsSignalStrength(1): LED conveys the strength of the singal, for the details please refer to user manual.
                indentify(2): Can be used to lacate the AP by making AP to flashing LED repeatedly.
                normal(3): This indicates AP's normal operational mode."
            ::= { apEntry 36 }

        
        -- 1.3.6.1.4.1.4329.15.3.5.1.2.1.37
        apLocationbasedService OBJECT-TYPE
            SYNTAX TruthValue
            MAX-ACCESS read-write
            STATUS current
            DESCRIPTION
                "Enable or disable the AeroScout or Ekahau location-based service for the Wireless AP."
            ::= { apEntry 37 }

        
        -- 1.3.6.1.4.1.4329.15.3.5.1.2.1.38
        apSecureTunnel OBJECT-TYPE
            SYNTAX TruthValue
            MAX-ACCESS read-write
            STATUS current
            DESCRIPTION
                "Enable or disable Secure Tunnel between Ap and Controller"
            ::= { apEntry 38 }

        
        -- 1.3.6.1.4.1.4329.15.3.5.1.2.1.39
        apEncryptCntTraffic OBJECT-TYPE
            SYNTAX TruthValue
            MAX-ACCESS read-write
            STATUS current
            DESCRIPTION
                "Enable or disable  encrypt of control traffic between AP & Controller. 
                This value has meaning only if apSecureTunnel is enabled."
            ::= { apEntry 39 }

        
        -- 1.3.6.1.4.1.4329.15.3.5.1.2.1.40
        apMICErrorWarning OBJECT-TYPE
            SYNTAX TruthValue
            MAX-ACCESS read-write
            STATUS current
            DESCRIPTION
                "Enable or disable MIC error warning generation."
            ::= { apEntry 40 }


        -- 1.3.6.1.4.1.4329.15.3.5.1.2.1.41
        apSecureDataTunnelType OBJECT-TYPE
            SYNTAX INTEGER
                {
                disable(0),
                encryptControlTraffic(1),
                encryptControlDataTraffic(2),
                debugMode(3)
                }
            MAX-ACCESS read-write
            STATUS current
            DESCRIPTION
                "secure data tunnel status between  controller and acesss point.
                disable(0):  disable  encryption of control and data traffic between AP & Controller.
                encryptControlTraffic(1): encrypt control traffic between AP & Controller.
                encryptControlDataTraffic(2): encrypt control and data traffic between AP & Controller.
                debugMode(3): preserve keys without encryption."
            ::= { apEntry 41 }

        -- 1.3.6.1.4.1.4329.15.3.5.1.2.1.42
        apIPMulticastAssembly OBJECT-TYPE
            SYNTAX TruthValue
            MAX-ACCESS read-write
            STATUS current
            DESCRIPTION
                "Enable or disable fragmentation/reassembly of the IP Multicast frames transmitted over 
                 the tunnel between AP and Controller. When set to true, an IP Multicast frame larger 
                 than the tunnel MTU will be fragmented when it is placed into the WASSP tunnel and
                 reassembled on the receiving end of the tunnel before being forwarded to the clients."
            ::= { apEntry 42 }


        -- 1.3.6.1.4.1.4329.15.3.5.1.2.1.43
        apSSHConnection OBJECT-TYPE
            SYNTAX INTEGER
                {
                enabled(1),
                disabled(2),
                na(3)
                }
            MAX-ACCESS read-write
            STATUS current
            DESCRIPTION
                "Enable or Disable SSH access to the Wireless AP. This value only applys to AP36xx, 
                AP37xx, W788C and W786C APs.
                1 : Enabled.
                2 : Disabled.
                3 : SSH is not supported."
            ::= { apEntry 43 }

            



        
        -- 1.3.6.1.4.1.4329.15.3.5.1.3
        apRadioTable OBJECT-TYPE
            SYNTAX SEQUENCE OF ApRadioEntry
            MAX-ACCESS not-accessible
            STATUS current
            DESCRIPTION
                "Table access point radio configuration information."
            ::= { apConfigObjects 3 }

        
        -- 1.3.6.1.4.1.4329.15.3.5.1.3.1
        apRadioEntry OBJECT-TYPE
            SYNTAX ApRadioEntry
            MAX-ACCESS not-accessible
            STATUS current
            DESCRIPTION
                "Configuration information for a radio on the access point."
            INDEX { apIndex, ifIndex }
            ::= { apRadioTable 1 }

        
        ApRadioEntry ::=
            SEQUENCE { 
                apRadioFrequency
                    INTEGER,
                apRadioNumber
                    Unsigned32,
                apRadioType
                    INTEGER,
                 apRadioProtocol
                    BITS
                    
             }

        -- 1.3.6.1.4.1.4329.15.3.5.1.3.1.1
        apRadioFrequency OBJECT-TYPE
            SYNTAX INTEGER
                {
                freq50GHz(1),
                freq24GHz(2)
                }
            MAX-ACCESS read-only
            STATUS current
            DESCRIPTION
                "The frequency of the radio as supported by the hardware. Supported frequencies are
                either of 2.5Ghz or 5.0Ghz."
            ::= { apRadioEntry 1 }

        
        -- 1.3.6.1.4.1.4329.15.3.5.1.3.1.2
        apRadioNumber OBJECT-TYPE
            SYNTAX Unsigned32
            MAX-ACCESS read-only
            STATUS current
            DESCRIPTION
                "Access point radios are numbered from 1 in increasing order. This numbering is limited
                in the context of AP. This field returns the radio number of the AP indexed by apIndex."
            ::= { apRadioEntry 2 }

        
        -- 1.3.6.1.4.1.4329.15.3.5.1.3.1.3
        apRadioType OBJECT-TYPE
            SYNTAX INTEGER
                {
                off(0),
                dot11a(1),
                dot11an(2),
                dot11anStrict(3),
                dot11b(4),
                dot11g(5),
                dot11bg(6),
                dot11gn(7),
                dot11bgn(8),
                dot11gnStrict(9),
                dot11j(10),
                dot11anc(11),
        dot11cStrict(12)
                }
            MAX-ACCESS read-write
            STATUS deprecated
            DESCRIPTION
                "Indicates the type of radio (a,  a/n,  a/c,  n-strict, c-strict, b, g, b/g, or b/g/n) as it is configured."
            ::= { apRadioEntry 3 }


        -- 1.3.6.1.4.1.4329.15.3.5.1.3.1.4
        apRadioProtocol OBJECT-TYPE
            SYNTAX BITS
                {
                dot1124b(0),
                dot1124g(1),
                dot1124n(2),
                dot1150a(3),
                dot1150ac(4),
                dot1150j(5),
                dot1150n(6)
                }
            MAX-ACCESS read-write
            STATUS current
            DESCRIPTION
                "Enumerates the possible types of 802.11 radio protocols."
            ::= { apRadioEntry 4 }



            

        
        -- 1.3.6.1.4.1.4329.15.3.5.1.4
        radioVNSTable OBJECT-TYPE
            SYNTAX SEQUENCE OF RadioVNSEntry
            MAX-ACCESS not-accessible
            STATUS current
            DESCRIPTION
                "Table of VNSs the radio is participating in."
            ::= { apConfigObjects 4 }

        
        -- 1.3.6.1.4.1.4329.15.3.5.1.4.1
        radioVNSEntry OBJECT-TYPE
            SYNTAX RadioVNSEntry
            MAX-ACCESS not-accessible
            STATUS current
            DESCRIPTION
                "Information for a single VNS entry."
            INDEX { radioIfIndex, vnsIfIndex }
            ::= { radioVNSTable 1 }

        
        RadioVNSEntry ::=
            SEQUENCE { 
                radioIfIndex
                    InterfaceIndex,
                vnsIfIndex
                    InterfaceIndex,
                radioVNSRowStatus
                    RowStatus
             }

        -- 1.3.6.1.4.1.4329.15.3.5.1.4.1.1
        radioIfIndex OBJECT-TYPE
            SYNTAX InterfaceIndex
            MAX-ACCESS read-write
            STATUS current
            DESCRIPTION
                "Radio participating in the VNS."
            ::= { radioVNSEntry 1 }

        
        -- 1.3.6.1.4.1.4329.15.3.5.1.4.1.2
        vnsIfIndex OBJECT-TYPE
            SYNTAX InterfaceIndex
            MAX-ACCESS read-write
            STATUS current
            DESCRIPTION
                "ifIndex for the VNS the radio is participating."
            ::= { radioVNSEntry 2 }

        
        -- 1.3.6.1.4.1.4329.15.3.5.1.4.1.3
        radioVNSRowStatus OBJECT-TYPE
            SYNTAX RowStatus
            MAX-ACCESS read-write
            STATUS current
            DESCRIPTION
                "RowStatus for the radioVNSTable."
            ::= { radioVNSEntry 3 }

        
        -- 1.3.6.1.4.1.4329.15.3.5.1.5
        apFastFailoverEnable OBJECT-TYPE
            SYNTAX TruthValue
            MAX-ACCESS read-write
            STATUS current
            DESCRIPTION
                "True indicates that Fast Failover feature is enabled at AP."
            ::= { apConfigObjects 5 }

        
        -- 1.3.6.1.4.1.4329.15.3.5.1.6
        apLinkTimeout OBJECT-TYPE
            SYNTAX Integer32
            MAX-ACCESS read-write
            STATUS current
            DESCRIPTION
                "Time to deteck link failure. The value is in 1-30 seconds."
            ::= { apConfigObjects 6 }

        
        -- 1.3.6.1.4.1.4329.15.3.5.1.7
        apAntennaTable OBJECT-TYPE
            SYNTAX SEQUENCE OF ApAntennaEntry
            MAX-ACCESS not-accessible
            STATUS current
            DESCRIPTION
                "Contains a list of antennas configured for each AP associated with the
                Wireless Controller. All elements in this table are predefined and read-only."
            ::= { apConfigObjects 7 }

        
        -- 1.3.6.1.4.1.4329.15.3.5.1.7.1
        apAntennaEntry OBJECT-TYPE
            SYNTAX ApAntennaEntry
            MAX-ACCESS not-accessible
            STATUS current
            DESCRIPTION
                "An entry in this table identifying attributes of one antenna for an AP."
            INDEX { apIndex, apAntennaIndex }
            ::= { apAntennaTable 1 }

        
        ApAntennaEntry ::=
            SEQUENCE { 
                apAntennaIndex
                    Unsigned32,
                apAntennanName
                    DisplayString,
                apAntennaType
                    DisplayString
             }

        -- 1.3.6.1.4.1.4329.15.3.5.1.7.1.1
        apAntennaIndex OBJECT-TYPE
            SYNTAX Unsigned32
            MAX-ACCESS not-accessible
            STATUS current
            DESCRIPTION
                "Index of an antenna inside an AP."
            ::= { apAntennaEntry 1 }

        
        -- 1.3.6.1.4.1.4329.15.3.5.1.7.1.2
        apAntennanName OBJECT-TYPE
            SYNTAX DisplayString
            MAX-ACCESS read-only
            STATUS current
            DESCRIPTION
                "Textual description identifying the antenna."
            ::= { apAntennaEntry 2 }

        
        -- 1.3.6.1.4.1.4329.15.3.5.1.7.1.3
        apAntennaType OBJECT-TYPE
            SYNTAX DisplayString
            MAX-ACCESS read-write
            STATUS current
            DESCRIPTION
                "Textual description of antenna type selected for that antenna."
            ::= { apAntennaEntry 3 }

            

        -- 1.3.6.1.4.1.4329.15.3.5.1.8
        apRadioAntennaTable OBJECT-TYPE
            SYNTAX SEQUENCE OF ApRadioAntennaEntry
            MAX-ACCESS not-accessible
            STATUS current
            DESCRIPTION
                "Contains a list of Radio configured for each AP associated with the
                Wireless Controller. All elements in this table are predefined and read-only."
            ::= { apConfigObjects 8 }

        
        -- 1.3.6.1.4.1.4329.15.3.5.1.8.1
        apRadioAntennaEntry OBJECT-TYPE
            SYNTAX ApRadioAntennaEntry
            MAX-ACCESS not-accessible
            STATUS current
            DESCRIPTION
                "An entry in this table identifying attributes of one radio for an AP."
            INDEX { apIndex, ifIndex }
            ::= { apRadioAntennaTable 1 }

        
        ApRadioAntennaEntry ::=
            SEQUENCE { 
                apRadioAntennaType
                    DisplayString,
                apRadioAntennaModel
                    Unsigned32,
                apRadioAttenuation
                    Integer32
             }


        
        -- 1.3.6.1.4.1.4329.15.3.5.1.8.1.3
        apRadioAntennaType OBJECT-TYPE
            SYNTAX DisplayString
            MAX-ACCESS read-only
            STATUS current
            DESCRIPTION
                "Textual description of antenna type selected for that radio."
            ::= { apRadioAntennaEntry 3 }


        -- 1.3.6.1.4.1.4329.15.3.5.1.8.1.4
        apRadioAntennaModel OBJECT-TYPE
            SYNTAX Unsigned32
            MAX-ACCESS read-only
            STATUS current
            DESCRIPTION
                "Antenna type. 0 indicates internal antenna. 1 indicates no antenna.  
                Other value indicates specific external antenna type.  "
            ::= { apRadioAntennaEntry 4 }

        
        -- 1.3.6.1.4.1.4329.15.3.5.1.8.1.5
        apRadioAttenuation OBJECT-TYPE
            SYNTAX Integer32
            MAX-ACCESS read-write
            STATUS current
            DESCRIPTION
                "Cumulative attenuation (in dB) of all components (cables, attenuators) between 
                 the radio port and the antenna. A professional installer must configure this value 
                 so it does not violate country regulations and must verify that it reflects the actual 
                 installed components.  If this field value is set to -1,  then this radio does not support the
                 attenuation configuration."
            ::= { apRadioAntennaEntry 5 }



               


        
        -- 1.3.6.1.4.1.4329.15.3.5.2
        apStatsObjects OBJECT IDENTIFIER ::= { accessPoints 2 }

        
        -- 1.3.6.1.4.1.4329.15.3.5.2.1
        apActiveCount OBJECT-TYPE
            SYNTAX Integer32
            MAX-ACCESS read-only
            STATUS current
            DESCRIPTION
                "The count of active AccessPoints associated with this WirelessController."
            ::= { apStatsObjects 1 }

        
        -- 1.3.6.1.4.1.4329.15.3.5.2.2
        apStatsTable OBJECT-TYPE
            SYNTAX SEQUENCE OF ApStatsEntry
            MAX-ACCESS not-accessible
            STATUS current
            DESCRIPTION
                "Table of statistics for the access points."
            ::= { apStatsObjects 2 }

        
        -- 1.3.6.1.4.1.4329.15.3.5.2.2.1
        apStatsEntry OBJECT-TYPE
            SYNTAX ApStatsEntry
            MAX-ACCESS not-accessible
            STATUS current
            DESCRIPTION
                "Statistics for an access point."
            INDEX { apIndex }
            ::= { apStatsTable 1 }

        
        ApStatsEntry ::=
            SEQUENCE { 
                apInUcastPkts
                    Counter64,
                apInNUcastPkts
                    Counter64,
                apInOctets
                    Counter64,
                apInErrors
                    Counter64,
                apInDiscards
                    Counter64,
                apOutUcastPkts
                    Counter64,
                apOutNUcastPkts
                    Counter64,
                apOutOctets
                    Counter64,
                apOutErrors
                    Counter64,
                apOutDiscards
                    Counter64,
                apUpTime
                    TimeTicks,
                apCredentialType
                    INTEGER,
                apCertificateExpiry
                    TimeTicks,
                apStatsMuCounts
                    Unsigned32,
                apStatsSessionDuration
                    TimeTicks,
                apTotalStationsA
                    Unsigned32,
                apTotalStationsB
                    Unsigned32,
                apTotalStationsG
                    Unsigned32,
                apTotalStationsN50
                    Unsigned32,
                apTotalStationsN24
                    Unsigned32,
                apInvalidPolicyCount
                    Unsigned32,
                apInterfaceMTU
                    Unsigned32,
                apEffectiveTunnelMTU
                    Unsigned32,
                apTotalStationsAC
                    Unsigned32,
                apTotalStationsAInOctets
                    Counter64,
                apTotalStationsAOutOctets
                  Counter64,
                apTotalStationsBInOctets
                    Counter64,
                apTotalStationsBOutOctets
                    Counter64,
                apTotalStationsGInOctets
                    Counter64,
                apTotalStationsGOutOctets
                    Counter64,
                apTotalStationsN50InOctets
                    Counter64,
                apTotalStationsN50OutOctets
                    Counter64,
                apTotalStationsN24InOctets
                    Counter64,
                apTotalStationsN24OutOctets
                    Counter64,
                apTotalStationsACInOctets
                    Counter64,
                apTotalStationsACOutOctets
                    Counter64
             }

        -- 1.3.6.1.4.1.4329.15.3.5.2.2.1.1
        apInUcastPkts OBJECT-TYPE
            SYNTAX Counter64
            MAX-ACCESS read-only
            STATUS current
            DESCRIPTION
                "Number of unicast packets from wireless-to-wired network."
            ::= { apStatsEntry 1 }

        
        -- 1.3.6.1.4.1.4329.15.3.5.2.2.1.2
        apInNUcastPkts OBJECT-TYPE
            SYNTAX Counter64
            MAX-ACCESS read-only
            STATUS current
            DESCRIPTION
                "Number of non-unicast packets from wireless-to-wired network."
            ::= { apStatsEntry 2 }

        
        -- 1.3.6.1.4.1.4329.15.3.5.2.2.1.3
        apInOctets OBJECT-TYPE
            SYNTAX Counter64
            MAX-ACCESS read-only
            STATUS current
            DESCRIPTION
                "Number of octets from wireless-to-wired network."
            ::= { apStatsEntry 3 }

        
        -- 1.3.6.1.4.1.4329.15.3.5.2.2.1.4
        apInErrors OBJECT-TYPE
            SYNTAX Counter64
            MAX-ACCESS read-only
            STATUS current
            DESCRIPTION
                "Number of error packets from wireless-to-wired network."
            ::= { apStatsEntry 4 }

        
        -- 1.3.6.1.4.1.4329.15.3.5.2.2.1.5
        apInDiscards OBJECT-TYPE
            SYNTAX Counter64
            MAX-ACCESS read-only
            STATUS current
            DESCRIPTION
                "Number of discarded packets from wireless-to-wired network."
            ::= { apStatsEntry 5 }

        
        -- 1.3.6.1.4.1.4329.15.3.5.2.2.1.6
        apOutUcastPkts OBJECT-TYPE
            SYNTAX Counter64
            MAX-ACCESS read-only
            STATUS current
            DESCRIPTION
                "Number of unicast packets from wired-to-wireless network."
            ::= { apStatsEntry 6 }

        
        -- 1.3.6.1.4.1.4329.15.3.5.2.2.1.7
        apOutNUcastPkts OBJECT-TYPE
            SYNTAX Counter64
            MAX-ACCESS read-only
            STATUS current
            DESCRIPTION
                "Number of non-unicast packets from wired-to-wireless network."
            ::= { apStatsEntry 7 }

        
        -- 1.3.6.1.4.1.4329.15.3.5.2.2.1.8
        apOutOctets OBJECT-TYPE
            SYNTAX Counter64
            MAX-ACCESS read-only
            STATUS current
            DESCRIPTION
                "Number of octets from wired-to-wireless network."
            ::= { apStatsEntry 8 }

        
        -- 1.3.6.1.4.1.4329.15.3.5.2.2.1.9
        apOutErrors OBJECT-TYPE
            SYNTAX Counter64
            MAX-ACCESS read-only
            STATUS current
            DESCRIPTION
                "Number of error packets from wired-to-wireless network."
            ::= { apStatsEntry 9 }

        
        -- 1.3.6.1.4.1.4329.15.3.5.2.2.1.10
        apOutDiscards OBJECT-TYPE
            SYNTAX Counter64
            MAX-ACCESS read-only
            STATUS current
            DESCRIPTION
                "Number of discarded packets from wired-to-wireless network."
            ::= { apStatsEntry 10 }

        
        -- 1.3.6.1.4.1.4329.15.3.5.2.2.1.11
        apUpTime OBJECT-TYPE
            SYNTAX TimeTicks
            MAX-ACCESS read-only
            STATUS current
            DESCRIPTION
                "The time (in hundredths of a second) since the
                management portion of the access point was last
                re-initialized."
            ::= { apStatsEntry 11 }

        
        -- 1.3.6.1.4.1.4329.15.3.5.2.2.1.12
        apCredentialType OBJECT-TYPE
            SYNTAX INTEGER
                {
                none(0),
                tls(1),
                peap(2),
                all(3)
                }
            MAX-ACCESS read-only
            STATUS current
            DESCRIPTION
                "Supported certificate type used by AP for commnuication.
                none(0) = not supported,
                TLS(1) = Trasport Layer Security (TLS),
                PEAP(2) = Protected Extensible Authentication Protocol,
                all(2) = supports all supported EAP."
            ::= { apStatsEntry 12 }

        
        -- 1.3.6.1.4.1.4329.15.3.5.2.2.1.13
        apCertificateExpiry OBJECT-TYPE
            SYNTAX TimeTicks
            MAX-ACCESS read-only
            STATUS current
            DESCRIPTION
                "The number of timeticks from January, 1st, 1970 to the date when 
                the certificate expires (issued certificate no longer is valid)."
            ::= { apStatsEntry 13 }

        
        -- 1.3.6.1.4.1.4329.15.3.5.2.2.1.14
        apStatsMuCounts OBJECT-TYPE
            SYNTAX Unsigned32
            MAX-ACCESS read-only
            STATUS current
            DESCRIPTION
                "Number of MUs currently associated with this AP."
            ::= { apStatsEntry 14 }

        
        -- 1.3.6.1.4.1.4329.15.3.5.2.2.1.15
        apStatsSessionDuration OBJECT-TYPE
            SYNTAX TimeTicks
            MAX-ACCESS read-only
            STATUS current
            DESCRIPTION
                "Elapse time since the access point's session has started."
            ::= { apStatsEntry 15 }

        
        -- 1.3.6.1.4.1.4329.15.3.5.2.2.1.16
        apTotalStationsA OBJECT-TYPE
            SYNTAX Unsigned32
            MAX-ACCESS read-only
            STATUS current
            DESCRIPTION
                "Number of MUs that are currently associated to this AP using dot11 connection mode 'a'."
            ::= { apStatsEntry 16 }

        
        -- 1.3.6.1.4.1.4329.15.3.5.2.2.1.17
        apTotalStationsB OBJECT-TYPE
            SYNTAX Unsigned32
            MAX-ACCESS read-only
            STATUS current
            DESCRIPTION
                "Number of MUs that are currently associated to this AP using dot11 connection mode 'b'."
            ::= { apStatsEntry 17 }

        
        -- 1.3.6.1.4.1.4329.15.3.5.2.2.1.18
        apTotalStationsG OBJECT-TYPE
            SYNTAX Unsigned32
            MAX-ACCESS read-only
            STATUS current
            DESCRIPTION
                "Number of MUs that are currently associated to this AP using dot11 connection mode 'g'."
            ::= { apStatsEntry 18 }

        
        -- 1.3.6.1.4.1.4329.15.3.5.2.2.1.19
        apTotalStationsN50 OBJECT-TYPE
            SYNTAX Unsigned32
            MAX-ACCESS read-only
            STATUS current
            DESCRIPTION
                "Number of MUs that are currently associated to this AP using dot11 connection mode 'n 5.0 Ghz'."
            ::= { apStatsEntry 19 }

        
        -- 1.3.6.1.4.1.4329.15.3.5.2.2.1.20
        apTotalStationsN24 OBJECT-TYPE
            SYNTAX Unsigned32
            MAX-ACCESS read-only
            STATUS current
            DESCRIPTION
                "Number of MUs that are currently associated to this AP using dot11 connection mode 'n 2.4 Ghz'."
            ::= { apStatsEntry 20 }



            

        -- 1.3.6.1.4.1.4329.15.3.5.2.2.1.21
        apInvalidPolicyCount OBJECT-TYPE
            SYNTAX Unsigned32
            MAX-ACCESS read-only
            STATUS current
            DESCRIPTION
                "Number of invalid role has been assigned to the AP"
            ::= { apStatsEntry 21 }


        -- 1.3.6.1.4.1.4329.15.3.5.2.2.1.22
        apInterfaceMTU OBJECT-TYPE
            SYNTAX Unsigned32
            MAX-ACCESS read-only
            STATUS current
            DESCRIPTION
                "The AP's configured ethernet interface MTU size in bytes. "
            ::= { apStatsEntry 22 }


        -- 1.3.6.1.4.1.4329.15.3.5.2.2.1.23
        apEffectiveTunnelMTU OBJECT-TYPE
            SYNTAX Unsigned32
            MAX-ACCESS read-only
            STATUS current
            DESCRIPTION
                "The AP Effective Tunnel MTU determines the maximum length of the frames that can 
                 be tunnelled without fragmentation, after subtracting the tunnel headers (WASSP and IPSEC). 
                 The AP Effective Tunnel MTU is determined for each AP tunnel as minimum between 
                 the Static MTU (configurable) and Dynamic MTU (learned from the ICMP path discovery)."
            ::= { apStatsEntry 23 }



        -- 1.3.6.1.4.1.4329.15.3.5.2.2.1.24
        apTotalStationsAC OBJECT-TYPE
            SYNTAX Unsigned32
            MAX-ACCESS read-only
            STATUS current
            DESCRIPTION
                "Number of MUs that are currently associated to this AP using dot11ac connection mode."
            ::= { apStatsEntry 24 }

        -- 1.3.6.1.4.1.4329.15.3.5.2.2.1.25
        apTotalStationsAInOctets OBJECT-TYPE
            SYNTAX Counter64
            MAX-ACCESS read-only
            STATUS current
            DESCRIPTION
                "Number of octets from client to AP for clients using protocol 802.11a."
            ::= { apStatsEntry 25 }

        -- 1.3.6.1.4.1.4329.15.3.5.2.2.1.26
        apTotalStationsAOutOctets OBJECT-TYPE
            SYNTAX Counter64
            MAX-ACCESS read-only
            STATUS current
            DESCRIPTION
                "Number of octets from AP to client for clients using protocol 802.11a."
            ::= { apStatsEntry 26 }

        -- 1.3.6.1.4.1.4329.15.3.5.2.2.1.27
        apTotalStationsBInOctets OBJECT-TYPE
            SYNTAX Counter64
            MAX-ACCESS read-only
            STATUS current
            DESCRIPTION
                "Number of octets from client to AP for clients using protocol 802.11b."
            ::= { apStatsEntry 27 }

        -- 1.3.6.1.4.1.4329.15.3.5.2.2.1.28
        apTotalStationsBOutOctets OBJECT-TYPE
            SYNTAX Counter64
            MAX-ACCESS read-only
            STATUS current
            DESCRIPTION
                "Number of octets from AP to client for clients using protocol 802.11b."
            ::= { apStatsEntry 28 }


        -- 1.3.6.1.4.1.4329.15.3.5.2.2.1.29
        apTotalStationsGInOctets OBJECT-TYPE
            SYNTAX Counter64
            MAX-ACCESS read-only
            STATUS current
            DESCRIPTION
                "Number of octets from client to AP for clients using protocol 802.11g."
            ::= { apStatsEntry 29 }

        -- 1.3.6.1.4.1.4329.15.3.5.2.2.1.30
        apTotalStationsGOutOctets OBJECT-TYPE
            SYNTAX Counter64
            MAX-ACCESS read-only
            STATUS current
            DESCRIPTION
                "Number of octets from AP to client for clients using protocol 802.11g."
            ::= { apStatsEntry 30 }

        -- 1.3.6.1.4.1.4329.15.3.5.2.2.1.31
        apTotalStationsN50InOctets OBJECT-TYPE
            SYNTAX Counter64
            MAX-ACCESS read-only
            STATUS current
            DESCRIPTION
                "Number of octets from client to AP for clients using protocol 802.11n (5Ghz)."
            ::= { apStatsEntry 31 }

        -- 1.3.6.1.4.1.4329.15.3.5.2.2.1.32
        apTotalStationsN50OutOctets OBJECT-TYPE
            SYNTAX Counter64
            MAX-ACCESS read-only
            STATUS current
            DESCRIPTION
                "Number of octets from AP to client for clients using protocol 802.11n (5Ghz)."
            ::= { apStatsEntry 32 }

        -- 1.3.6.1.4.1.4329.15.3.5.2.2.1.33
        apTotalStationsN24InOctets OBJECT-TYPE
            SYNTAX Counter64
            MAX-ACCESS read-only
            STATUS current
            DESCRIPTION
                "Number of octets from client to AP for clients using protocol 802.11n (2.4Ghz)."
            ::= { apStatsEntry 33 }

        -- 1.3.6.1.4.1.4329.15.3.5.2.2.1.34
        apTotalStationsN24OutOctets OBJECT-TYPE
            SYNTAX Counter64
            MAX-ACCESS read-only
            STATUS current
            DESCRIPTION
                "Number of octets from AP to client for clients using protocol 802.11n (2.4Ghz)."
            ::= { apStatsEntry 34 }

        -- 1.3.6.1.4.1.4329.15.3.5.2.2.1.35
        apTotalStationsACInOctets OBJECT-TYPE
            SYNTAX Counter64
            MAX-ACCESS read-only
            STATUS current
            DESCRIPTION
                "Number of octets from client to AP for clients using protocol 802.11ac."
            ::= { apStatsEntry 35 }

        -- 1.3.6.1.4.1.4329.15.3.5.2.2.1.36
        apTotalStationsACOutOctets OBJECT-TYPE
            SYNTAX Counter64
            MAX-ACCESS read-only
            STATUS current
            DESCRIPTION
                "Number of octets from AP to client for clients using protocol 802.11ac."
            ::= { apStatsEntry 36 }

        -- 1.3.6.1.4.1.4329.15.3.5.2.3
        apRegistrationRequests OBJECT-TYPE
            SYNTAX Counter32
            MAX-ACCESS read-only
            STATUS current
            DESCRIPTION
                "Total registration request have been received by all access points
                since last reboot."
            ::= { apStatsObjects 3 }


        -- 1.3.6.1.4.1.4329.15.3.5.2.4
        apRadioStatusTable OBJECT-TYPE
            SYNTAX SEQUENCE OF ApRadioStatsEntry
            MAX-ACCESS not-accessible
            STATUS current
            DESCRIPTION
                "Table of radio configuration attributes that the AP can change dynamically. 
                 It contains one entry for each radio of each active AP."
            ::= { apStatsObjects 4 }

        
        -- 1.3.6.1.4.1.4329.15.3.5.2.4.1
        apRadioStatusEntry OBJECT-TYPE
            SYNTAX ApRadioStatsEntry
            MAX-ACCESS not-accessible
            STATUS current
            DESCRIPTION
                "The configuration attributes of one AP radio that the AP can change dynamically."
            INDEX { ifIndex}
            ::= { apRadioStatusTable 1 }

        
        ApRadioStatsEntry ::=
            SEQUENCE { 
                apRadioStatusChannel
                    Unsigned32,
                apRadioStatusChannelWidth
                    INTEGER,
                 apRadioStatusChannelOffset
                    Unsigned32

                    }

        -- 1.3.6.1.4.1.4329.15.3.5.2.4.1.1
        apRadioStatusChannel OBJECT-TYPE
            SYNTAX Unsigned32
            MAX-ACCESS read-only
            STATUS current
            DESCRIPTION
                "The lowest 20 MHz channel of the 20/40/80 MHz wide channel on which the radio is 
                 operating. This can be different from the administratively configured channel as a result 
                 of the AP complying with regulatory requirements like DFS or adapting to the RF 
                 environment (e.g. DCS). If this field value is set to 0, then this means this radio is off or this AP is 
                 in Guardian mode."
            ::= { apRadioStatusEntry 1 }

        
        -- 1.3.6.1.4.1.4329.15.3.5.2.4.1.2
        apRadioStatusChannelWidth OBJECT-TYPE
            SYNTAX INTEGER {
                            width20Mhz(1), 
                            width40Mhz(2), 
                            width80Mhz(4) }
            MAX-ACCESS read-only
            STATUS current
            DESCRIPTION
                "Maximum width of the channel being served by the AP's radio. The AP may select a 
                 different channel width from the administratively configured width in order to comply 
                 with regulatory requirements and the current RF environment."
            ::= { apRadioStatusEntry 2 }

        
        -- 1.3.6.1.4.1.4329.15.3.5.2.4.1.3
        apRadioStatusChannelOffset OBJECT-TYPE
            SYNTAX Unsigned32
            MAX-ACCESS read-only
            STATUS current
            DESCRIPTION
                "This is the offset (in 20 MHz channels) of the primary channel from the lowest 20 MHz 
                 channel within an aggregated channel. The offset can be 0 if the primary channel is the 
                 same as the lowest channel or it can be 1,2 or 3 depending on the aggregate channel width. 
                 The AP may select a different channel width from the administratively configured width in 
                 order to comply with regulatory requirements and the current RF environment."
            ::= { apRadioStatusEntry 3 }



        -- 1.3.6.1.4.1.4329.15.3.5.2.5
        apPerformanceReportByRadioTable OBJECT-TYPE
            SYNTAX SEQUENCE OF ApPerformanceReportByRadioEntry
            MAX-ACCESS not-accessible
            STATUS current
            DESCRIPTION
                "Table of AP performance statistics by radio that the AP can change dynamically.
                 It contains one entry for each radio of each active AP."
            ::= { apStatsObjects 5 }

        
        -- 1.3.6.1.4.1.4329.15.3.5.2.5.1
        apPerformanceReportByRadioEntry OBJECT-TYPE
            SYNTAX ApPerformanceReportByRadioEntry
            MAX-ACCESS not-accessible
            STATUS current
            DESCRIPTION
                "The AP radio performance statistics of one AP radio."
            INDEX {apIndex, apRadioIndex}
            ::= { apPerformanceReportByRadioTable 1 }

        
        ApPerformanceReportByRadioEntry ::=
            SEQUENCE { 
                apRadioIndex
                   Integer32,
                apPerfRadioPrevPeakChannelUtilization
                    Gauge32,
                apPerfRadioCurPeakChannelUtilization
                    Gauge32,
                apPerfRadioAverageChannelUtilization
                    HundredthOfGauge32,
                apPerfRadioCurrentChannelUtilization
                    Gauge32,
                apPerfRadioPrevPeakRSS                
                    Gauge32,
                apPerfRadioCurPeakRSS
                    Gauge32,
                apPerfRadioAverageRSS
                    HundredthOfInt32,
                apPerfRadioCurrentRSS
                    Gauge32,
                apPerfRadioPrevPeakSNR
                    Gauge32,
                apPerfRadioCurPeakSNR
                    Gauge32,
                apPerfRadioAverageSNR
                    HundredthOfInt32,
                apPerfRadioCurrentSNR
                    Gauge32,
                apPerfRadioPrevPeakPktRetx    
                    HundredthOfGauge64,
                apPerfRadioCurPeakPktRetx
                    HundredthOfGauge64,
                apPerfRadioAveragePktRetx
                    HundredthOfGauge64,
                apPerfRadioCurrentPktRetx
                    HundredthOfGauge64,
                apPerfRadioPktRetx
                    Counter64

         }


        -- 1.3.6.1.4.1.4329.15.3.5.2.5.1.1
        apRadioIndex OBJECT-TYPE
            SYNTAX Integer32(1..2)
            MAX-ACCESS not-accessible
            STATUS current
            DESCRIPTION
                "Index of an radio inside an AP."
            ::= { apPerformanceReportByRadioEntry 1 }



        -- 1.3.6.1.4.1.4329.15.3.5.2.5.1.2
        apPerfRadioPrevPeakChannelUtilization OBJECT-TYPE
            SYNTAX Gauge32
            MAX-ACCESS read-only
            STATUS current
            DESCRIPTION
                "Peak channel utilization in % from last 15 minute interval."
            ::= { apPerformanceReportByRadioEntry 2 }
             

        -- 1.3.6.1.4.1.4329.15.3.5.2.5.1.3
        apPerfRadioCurPeakChannelUtilization OBJECT-TYPE
            SYNTAX Gauge32
            MAX-ACCESS read-only
            STATUS current
            DESCRIPTION
                "Peak channel utilization in % of current 15 minute interval."
            ::= { apPerformanceReportByRadioEntry 3 }


        -- 1.3.6.1.4.1.4329.15.3.5.2.5.1.4
        apPerfRadioAverageChannelUtilization OBJECT-TYPE
            SYNTAX HundredthOfGauge32
            MAX-ACCESS read-only
            STATUS current
            DESCRIPTION
                "Running average of channel utilization in hundredth of a %."
            ::= { apPerformanceReportByRadioEntry 4 }

        -- 1.3.6.1.4.1.4329.15.3.5.2.5.1.5
        apPerfRadioCurrentChannelUtilization OBJECT-TYPE
            SYNTAX Gauge32
            MAX-ACCESS read-only
            STATUS current
            DESCRIPTION
                "Channel utilization in % from latest statistics from AP."
            ::= { apPerformanceReportByRadioEntry 5 }



        -- 1.3.6.1.4.1.4329.15.3.5.2.5.1.6
        apPerfRadioPrevPeakRSS OBJECT-TYPE
            SYNTAX Gauge32
            MAX-ACCESS read-only
            STATUS current
            DESCRIPTION
                "Peak RSS in dBm from last 15 minute interval. Value of -100 means this field is not available."
            ::= { apPerformanceReportByRadioEntry 6 }





        -- 1.3.6.1.4.1.4329.15.3.5.2.5.1.7
        apPerfRadioCurPeakRSS OBJECT-TYPE
            SYNTAX Gauge32
            MAX-ACCESS read-only
            STATUS current
            DESCRIPTION
                "Peak RSS in dBm of current 15 minute interval. Value of -100 means this field is not available."
            ::= { apPerformanceReportByRadioEntry 7 }


        -- 1.3.6.1.4.1.4329.15.3.5.2.5.1.8
        apPerfRadioAverageRSS OBJECT-TYPE
            SYNTAX HundredthOfInt32
            MAX-ACCESS read-only
            STATUS current
            DESCRIPTION
                "Running average of RSS in hundredth of a dBm. Value of -10000 means this field is not available."
            ::= { apPerformanceReportByRadioEntry 8 }


        -- 1.3.6.1.4.1.4329.15.3.5.2.5.1.9
        apPerfRadioCurrentRSS OBJECT-TYPE
            SYNTAX Gauge32
            MAX-ACCESS read-only
            STATUS current
            DESCRIPTION
                "RSS in dBm from latest statistics from AP. Value of -100 means this field is not available."
            ::= { apPerformanceReportByRadioEntry 9 }



        -- 1.3.6.1.4.1.4329.15.3.5.2.5.1.10
        apPerfRadioPrevPeakSNR OBJECT-TYPE
            SYNTAX Gauge32
            MAX-ACCESS read-only
            STATUS current
            DESCRIPTION
                "Peak SNR in dB from last 15 minute interval. Value of -100 means this field is not available."
            ::= { apPerformanceReportByRadioEntry 10 }





        -- 1.3.6.1.4.1.4329.15.3.5.2.5.1.11
        apPerfRadioCurPeakSNR OBJECT-TYPE
            SYNTAX Gauge32
            MAX-ACCESS read-only
            STATUS current
            DESCRIPTION
                "Peak SNR in dB of current 15 minute interval. Value of -100 means this field is not available."
            ::= { apPerformanceReportByRadioEntry 11 }


        -- 1.3.6.1.4.1.4329.15.3.5.2.5.1.12
        apPerfRadioAverageSNR OBJECT-TYPE
            SYNTAX HundredthOfInt32
            MAX-ACCESS read-only
            STATUS current
            DESCRIPTION
                "Running average of SNR in hundredth of a dB. Value of -10000 means this field is not available."
            ::= { apPerformanceReportByRadioEntry 12 }

        -- 1.3.6.1.4.1.4329.15.3.5.2.5.1.13
        apPerfRadioCurrentSNR OBJECT-TYPE
            SYNTAX Gauge32
            MAX-ACCESS read-only
            STATUS current
            DESCRIPTION
                "SNR in dB from latest statistics from AP. Value of -100 means this field is not available."
            ::= { apPerformanceReportByRadioEntry 13 }



        -- 1.3.6.1.4.1.4329.15.3.5.2.5.1.14
        apPerfRadioPrevPeakPktRetx OBJECT-TYPE
            SYNTAX HundredthOfGauge64
            MAX-ACCESS read-only
            STATUS current
            DESCRIPTION
                "Peak packet retransmissions in hundredth of pps from last 15 minute interval."
            ::= { apPerformanceReportByRadioEntry 14 }



        -- 1.3.6.1.4.1.4329.15.3.5.2.5.1.15
        apPerfRadioCurPeakPktRetx OBJECT-TYPE
            SYNTAX HundredthOfGauge64
            MAX-ACCESS read-only
            STATUS current
            DESCRIPTION
                "Peak packet retransmissions in hundredth of pps of current 15 minute interval."
            ::= { apPerformanceReportByRadioEntry 15 }


        -- 1.3.6.1.4.1.4329.15.3.5.2.5.1.16
        apPerfRadioAveragePktRetx OBJECT-TYPE
            SYNTAX HundredthOfGauge64
            MAX-ACCESS read-only
            STATUS current
            DESCRIPTION
                "Running average of packet retransmissions in hundredth of pps."
            ::= { apPerformanceReportByRadioEntry 16 }

        -- 1.3.6.1.4.1.4329.15.3.5.2.5.1.17
        apPerfRadioCurrentPktRetx OBJECT-TYPE
            SYNTAX HundredthOfGauge64
            MAX-ACCESS read-only
            STATUS current
            DESCRIPTION
                "Packet retransmissions in hundredth of pps from latest statistics from AP."
            ::= { apPerformanceReportByRadioEntry 17 }

        -- 1.3.6.1.4.1.4329.15.3.5.2.5.1.18
        apPerfRadioPktRetx OBJECT-TYPE
            SYNTAX Counter64
            MAX-ACCESS read-only
            STATUS current
            DESCRIPTION
                "Running counter of number of packet retransmissions."
            ::= { apPerformanceReportByRadioEntry 18 }



        -- 1.3.6.1.4.1.4329.15.3.5.2.6
        apAccessibilityTable OBJECT-TYPE
            SYNTAX SEQUENCE OF ApAccessibilityEntry
            MAX-ACCESS not-accessible
            STATUS current
            DESCRIPTION
                "A table showing the rate of associations, reassociations and 
                deauthentications/dissassociations from each AP radio. The 
                table contains one row per radio per active AP."
            ::= { apStatsObjects 6 }

        
        -- 1.3.6.1.4.1.4329.15.3.5.2.6.1
        apAccessibilityEntry OBJECT-TYPE
            SYNTAX ApAccessibilityEntry
            MAX-ACCESS not-accessible
            STATUS current
            DESCRIPTION
                "The accessibility statistics of one AP radio."
            INDEX {apIndex, apRadioIndex}
            ::= { apAccessibilityTable 1 }

        
        ApAccessibilityEntry ::=
            SEQUENCE { 
                apAccPrevPeakAssocReqRx
                    HundredthOfGauge64,
                apAccCurPeakAssocReqRx
                    HundredthOfGauge64,
                apAccAverageAssocReqRx
                    HundredthOfGauge64,
                apAccCurrentAssocReqRx
                    HundredthOfGauge64,
                apAccAssocReqRx
                    Counter64,
                apAccPrevPeakReassocReqRx
                    HundredthOfGauge64,
                apAccCurPeakReassocReqRx
                    HundredthOfGauge64,
                apAccAverageReassocReqRx
                    HundredthOfGauge64,
                apAccCurrentReassocReqRx
                    HundredthOfGauge64,
                apAccReassocReqRx
                    Counter64,
                apAccPrevPeakDisassocDeauthReqTx
                    HundredthOfGauge64,
                apAccCurPeakDisassocDeauthReqTx
                    HundredthOfGauge64,
                apAccAverageDisassocDeauthReqTx
                    HundredthOfGauge64,
                apAccCurrentDisassocDeauthReqTx
                    HundredthOfGauge64,
                apAccDisassocDeauthReqTx
                    Counter64,
                apAccPrevPeakDisassocDeauthReqRx    
                    HundredthOfGauge64,
                apAccCurPeakDisassocDeauthReqRx
                    HundredthOfGauge64,
                apAccAverageDisassocDeauthReqRx
                    HundredthOfGauge64,
                apAccCurrentDisassocDeauthReqRx
                    HundredthOfGauge64,
                apAccDisassocDeauthReqRx
                    Counter64
               }



        -- 1.3.6.1.4.1.4329.15.3.5.2.6.1.1
        apAccPrevPeakAssocReqRx OBJECT-TYPE
            SYNTAX HundredthOfGauge64
            MAX-ACCESS read-only
            STATUS current
            DESCRIPTION
                "Peak number of association requests in hundredth of requests per second received by AP from last 15 minute interval."
            ::= { apAccessibilityEntry 1 }




        -- 1.3.6.1.4.1.4329.15.3.5.2.6.1.2
        apAccCurPeakAssocReqRx OBJECT-TYPE
            SYNTAX HundredthOfGauge64
            MAX-ACCESS read-only
            STATUS current
            DESCRIPTION
                "Peak number of association requests in hundredth of requests per second received by AP of current 15 minute interval."
            ::= { apAccessibilityEntry 2 }



        -- 1.3.6.1.4.1.4329.15.3.5.2.6.1.3
        apAccAverageAssocReqRx OBJECT-TYPE
            SYNTAX HundredthOfGauge64
            MAX-ACCESS read-only
            STATUS current
            DESCRIPTION
                "Running average of association requests in hundredth of requests per second received by an AP radio."
            ::= { apAccessibilityEntry 3 }



        -- 1.3.6.1.4.1.4329.15.3.5.2.6.1.4
        apAccCurrentAssocReqRx OBJECT-TYPE
            SYNTAX HundredthOfGauge64
            MAX-ACCESS read-only
            STATUS current
            DESCRIPTION
                "Association requests in hundredth of requests per second from latest statistics from AP."
            ::= { apAccessibilityEntry 4 }



        -- 1.3.6.1.4.1.4329.15.3.5.2.6.1.5
        apAccAssocReqRx OBJECT-TYPE
            SYNTAX Counter64
            MAX-ACCESS read-only
            STATUS current
            DESCRIPTION
                "Running counter of association requests."
            ::= { apAccessibilityEntry 5 }




        -- 1.3.6.1.4.1.4329.15.3.5.2.6.1.6
        apAccPrevPeakReassocReqRx OBJECT-TYPE
            SYNTAX HundredthOfGauge64
            MAX-ACCESS read-only
            STATUS current
            DESCRIPTION
                "Peak number of re-association requests in hundredth of requests per second received by an AP radio from last 15 minute interval."
            ::= { apAccessibilityEntry 6 }

        -- 1.3.6.1.4.1.4329.15.3.5.2.6.1.7
        apAccCurPeakReassocReqRx OBJECT-TYPE
            SYNTAX HundredthOfGauge64
            MAX-ACCESS read-only
            STATUS current
            DESCRIPTION
                "Peak number of re-association requests in hundredth of requests per second received by an AP radio of current 15 minute interval."
            ::= { apAccessibilityEntry 7 }



        -- 1.3.6.1.4.1.4329.15.3.5.2.6.1.8
        apAccAverageReassocReqRx OBJECT-TYPE
            SYNTAX HundredthOfGauge64
            MAX-ACCESS read-only
            STATUS current
            DESCRIPTION
                "Running average of re-association requests in hundredth of requests per second received by an AP radio."
            ::= { apAccessibilityEntry 8 }

        -- 1.3.6.1.4.1.4329.15.3.5.2.6.1.9
        apAccCurrentReassocReqRx OBJECT-TYPE
            SYNTAX HundredthOfGauge64
            MAX-ACCESS read-only
            STATUS current
            DESCRIPTION
                "Re-association requests in hundredth of requests per second received by an AP radio from latest statistics from AP."
            ::= { apAccessibilityEntry 9 }

        -- 1.3.6.1.4.1.4329.15.3.5.2.6.1.10
        apAccReassocReqRx OBJECT-TYPE
            SYNTAX Counter64
            MAX-ACCESS read-only
            STATUS current
            DESCRIPTION
                "Running counter of re-association requests received by an AP radio."
            ::= { apAccessibilityEntry 10 }




        -- 1.3.6.1.4.1.4329.15.3.5.2.6.1.11
        apAccPrevPeakDisassocDeauthReqTx OBJECT-TYPE
            SYNTAX HundredthOfGauge64
            MAX-ACCESS read-only
            STATUS current
            DESCRIPTION
                "Peak number of disassociation/deauthentication requests in hundredth of requests per 
                second transmitted by an AP radio from last 15 minute interval."
            ::= { apAccessibilityEntry 11 }

        -- 1.3.6.1.4.1.4329.15.3.5.2.6.1.12
        apAccCurPeakDisassocDeauthReqTx OBJECT-TYPE
            SYNTAX HundredthOfGauge64
            MAX-ACCESS read-only
            STATUS current
            DESCRIPTION
                "Peak number of disassociation/deauthentication requests in hundredth of requests per 
                second transmitted by an AP radio of current 15 minute interval."
            ::= { apAccessibilityEntry 12 }

        -- 1.3.6.1.4.1.4329.15.3.5.2.6.1.13
        apAccAverageDisassocDeauthReqTx OBJECT-TYPE
            SYNTAX HundredthOfGauge64
            MAX-ACCESS read-only
            STATUS current
            DESCRIPTION
                "Running average of disassociation/deauthentication requests in hundredth 
                of requests per second transmitted by an AP radio."
            ::= { apAccessibilityEntry 13 }

        -- 1.3.6.1.4.1.4329.15.3.5.2.6.1.14
        apAccCurrentDisassocDeauthReqTx OBJECT-TYPE
            SYNTAX HundredthOfGauge64
            MAX-ACCESS read-only
            STATUS current
            DESCRIPTION
                "Disassociation/deauthentication requests in hundredth of requests per second 
                transmitted by an AP radio from latest statistics from AP."
            ::= { apAccessibilityEntry 14 }

        -- 1.3.6.1.4.1.4329.15.3.5.2.6.1.15
        apAccDisassocDeauthReqTx OBJECT-TYPE
            SYNTAX Counter64
            MAX-ACCESS read-only
            STATUS current
            DESCRIPTION
                "Running counter of disassociation/deauthentication requests transmitted by an AP radio."
            ::= { apAccessibilityEntry 15 }



        -- 1.3.6.1.4.1.4329.15.3.5.2.6.1.16
        apAccPrevPeakDisassocDeauthReqRx OBJECT-TYPE
            SYNTAX HundredthOfGauge64
            MAX-ACCESS read-only
            STATUS current
            DESCRIPTION
                "Peak number of disassociation/deauthentication requests in hundredth of 
                requests per second received by an AP radio from last 15 minute interval."
            ::= { apAccessibilityEntry 16 }

        -- 1.3.6.1.4.1.4329.15.3.5.2.6.1.17
        apAccCurPeakDisassocDeauthReqRx OBJECT-TYPE
            SYNTAX HundredthOfGauge64
            MAX-ACCESS read-only
            STATUS current
            DESCRIPTION
                "Peak number of disassociation/deauthentication requests in hundredth of requests 
                per second received by an AP radio of current 15 minute interval."
            ::= { apAccessibilityEntry 17 }

        -- 1.3.6.1.4.1.4329.15.3.5.2.6.1.18
        apAccAverageDisassocDeauthReqRx OBJECT-TYPE
            SYNTAX HundredthOfGauge64
            MAX-ACCESS read-only
            STATUS current
            DESCRIPTION
                "Running average of disassociation/deauthentication requests in hundredth 
                of requests per second received by an AP radio."
            ::= { apAccessibilityEntry 18 }

        -- 1.3.6.1.4.1.4329.15.3.5.2.6.1.19
        apAccCurrentDisassocDeauthReqRx OBJECT-TYPE
            SYNTAX HundredthOfGauge64
            MAX-ACCESS read-only
            STATUS current
            DESCRIPTION
                "Disassociation/deauthentication requests in hundredth of requests per 
                second received by an AP radio from latest statistics from AP."
            ::= { apAccessibilityEntry 19 }

        -- 1.3.6.1.4.1.4329.15.3.5.2.6.1.20
        apAccDisassocDeauthReqRx OBJECT-TYPE
            SYNTAX Counter64
            MAX-ACCESS read-only
            STATUS current
            DESCRIPTION
                "Running counter of disassociation/deauthentication requests received by an AP radio."
            ::= { apAccessibilityEntry 20 }



        -- 1.3.6.1.4.1.4329.15.3.5.2.7
        apPerformanceReportbyRadioAndWlanTable OBJECT-TYPE
            SYNTAX SEQUENCE OF ApPerformanceReportbyRadioAndWlanEntry
            MAX-ACCESS not-accessible
            STATUS current
            DESCRIPTION
                "Table of AP performance statistics by AP, AP radio and WLAN. "
            ::= { apStatsObjects 7 }

        
        -- 1.3.6.1.4.1.4329.15.3.5.2.7.1
        apPerformanceReportbyRadioAndWlanEntry OBJECT-TYPE
            SYNTAX ApPerformanceReportbyRadioAndWlanEntry
            MAX-ACCESS not-accessible
            STATUS current
            DESCRIPTION
                "The AP performance statistics of one AP radio and WLAN."
            INDEX {apIndex, apRadioIndex, wlanID }
            ::= { apPerformanceReportbyRadioAndWlanTable  1 }

        
        ApPerformanceReportbyRadioAndWlanEntry ::=
            SEQUENCE { 
                apPerfWlanPrevPeakClientsPerSec
                    Gauge32,
                apPerfWlanCurPeakClientsPerSec
                    Gauge32,
                apPerfWlanAverageClientsPerSec
                    HundredthOfGauge32,
                apPerfWlanCurrentClientsPerSec
                    Gauge32,
                apPerfWlanPrevPeakULOctetsPerSec
                    HundredthOfGauge64,
                apPerfWlanCurPeakULOctetsPerSec
                    HundredthOfGauge64,
                apPerfWlanAverageULOctetsPerSec
                    HundredthOfGauge64,
                apPerfWlanCurrentULOctetsPerSec
                    HundredthOfGauge64,
                apPerfWlanULOctets
                    Counter64,
                apPerfWlanPrevPeakULPktsPerSec
                    HundredthOfGauge64,
                apPerfWlanCurPeakULPktsPerSec
                    HundredthOfGauge64,
                apPerfWlanAverageULPktsPerSec
                    HundredthOfGauge64,
                apPerfWlanCurrentULPktsPerSec
                    HundredthOfGauge64,
                apPerfWlanULPkts
                    Counter64,
                apPerfWlanPrevPeakDLOctetsPerSec   
                    HundredthOfGauge64,
                apPerfWlanCurPeakDLOctetsPerSec
                    HundredthOfGauge64,
                apPerfWlanAverageDLOctetsPerSec
                    HundredthOfGauge64,
                apPerfWlanCurrentDLOctetsPerSec
                    HundredthOfGauge64,
                apPerfWlanDLOctets
                    Counter64,
                apPerfWlanPrevPeakDLPktsPerSec
                    HundredthOfGauge64,
                apPerfWlanCurPeakDLPktsPerSec
                    HundredthOfGauge64,
                apPerfWlanAverageDLPktsPerSec
                    HundredthOfGauge64,
                apPerfWlanCurrentDLPktsPerSec
                    HundredthOfGauge64,
                apPerfWlanDLPkts
                    Counter64

                    
         }



        -- 1.3.6.1.4.1.4329.15.3.5.2.7.1.1
        apPerfWlanPrevPeakClientsPerSec OBJECT-TYPE
            SYNTAX Gauge32
            MAX-ACCESS read-only
            STATUS current
            DESCRIPTION
                "Peak clients per second from last 15 minute interval."
            ::= { apPerformanceReportbyRadioAndWlanEntry 1 }

        -- 1.3.6.1.4.1.4329.15.3.5.2.7.1.2
        apPerfWlanCurPeakClientsPerSec OBJECT-TYPE
            SYNTAX Gauge32
            MAX-ACCESS read-only
            STATUS current
            DESCRIPTION
                "Peak clients per second of current 15 minute interval."
            ::= { apPerformanceReportbyRadioAndWlanEntry 2 }



        -- 1.3.6.1.4.1.4329.15.3.5.2.7.1.3
        apPerfWlanAverageClientsPerSec OBJECT-TYPE
            SYNTAX HundredthOfGauge32
            MAX-ACCESS read-only
            STATUS current
            DESCRIPTION
                "Running average of clients in hundredth of clients per second."
            ::= { apPerformanceReportbyRadioAndWlanEntry 3 }



        -- 1.3.6.1.4.1.4329.15.3.5.2.7.1.4
        apPerfWlanCurrentClientsPerSec OBJECT-TYPE
            SYNTAX Gauge32
            MAX-ACCESS read-only
            STATUS current
            DESCRIPTION
                "Clients per second from latest statistics from AP."
            ::= { apPerformanceReportbyRadioAndWlanEntry 4 }



        -- 1.3.6.1.4.1.4329.15.3.5.2.7.1.5
        apPerfWlanPrevPeakULOctetsPerSec OBJECT-TYPE
            SYNTAX HundredthOfGauge64
            MAX-ACCESS read-only
            STATUS current
            DESCRIPTION
                "Peak uplink octets in hundredth of octets per second from last 15 minute interval."
            ::= { apPerformanceReportbyRadioAndWlanEntry 5 }




        -- 1.3.6.1.4.1.4329.15.3.5.2.7.1.6
        apPerfWlanCurPeakULOctetsPerSec OBJECT-TYPE
            SYNTAX HundredthOfGauge64
            MAX-ACCESS read-only
            STATUS current
            DESCRIPTION
                "Peak uplink octets in hundredth of octets per second of current 15 minute interval."
            ::= { apPerformanceReportbyRadioAndWlanEntry 6 }



        -- 1.3.6.1.4.1.4329.15.3.5.2.7.1.7
        apPerfWlanAverageULOctetsPerSec OBJECT-TYPE
            SYNTAX HundredthOfGauge64
            MAX-ACCESS read-only
            STATUS current
            DESCRIPTION
                "Running average of uplink hundredth of octets per second."
            ::= { apPerformanceReportbyRadioAndWlanEntry 7 }



        -- 1.3.6.1.4.1.4329.15.3.5.2.7.1.8
        apPerfWlanCurrentULOctetsPerSec OBJECT-TYPE
            SYNTAX HundredthOfGauge64
            MAX-ACCESS read-only
            STATUS current
            DESCRIPTION
                "Uplink octets in hundredth of octets per second from latest statistics from AP."
            ::= { apPerformanceReportbyRadioAndWlanEntry 8 }



        -- 1.3.6.1.4.1.4329.15.3.5.2.7.1.9
        apPerfWlanULOctets OBJECT-TYPE
            SYNTAX Counter64
            MAX-ACCESS read-only
            STATUS current
            DESCRIPTION
                "Running counter of uplink octets per second."
            ::= { apPerformanceReportbyRadioAndWlanEntry 9 }




        -- 1.3.6.1.4.1.4329.15.3.5.2.7.1.10
        apPerfWlanPrevPeakULPktsPerSec OBJECT-TYPE
            SYNTAX HundredthOfGauge64
            MAX-ACCESS read-only
            STATUS current
            DESCRIPTION
                "Peak uplink packets in hundredth of packets per second from last 15 minute interval."
            ::= { apPerformanceReportbyRadioAndWlanEntry 10 }


        -- 1.3.6.1.4.1.4329.15.3.5.2.7.1.11
        apPerfWlanCurPeakULPktsPerSec OBJECT-TYPE
            SYNTAX HundredthOfGauge64
            MAX-ACCESS read-only
            STATUS current
            DESCRIPTION
                "Peak uplink packets in hundredth of packets per second of current 15 minute interval."
            ::= { apPerformanceReportbyRadioAndWlanEntry 11 }

            

        -- 1.3.6.1.4.1.4329.15.3.5.2.7.1.12
        apPerfWlanAverageULPktsPerSec OBJECT-TYPE
            SYNTAX HundredthOfGauge64
            MAX-ACCESS read-only
            STATUS current
            DESCRIPTION
                "Running average of uplink packets in hundredth of packets per second."
            ::= { apPerformanceReportbyRadioAndWlanEntry 12 }

        -- 1.3.6.1.4.1.4329.15.3.5.2.7.1.13
        apPerfWlanCurrentULPktsPerSec OBJECT-TYPE
            SYNTAX HundredthOfGauge64
            MAX-ACCESS read-only
            STATUS current
            DESCRIPTION
                "Uplink packets in hundredth of packets per second from latest statistics from AP."
            ::= { apPerformanceReportbyRadioAndWlanEntry 13 }

        -- 1.3.6.1.4.1.4329.15.3.5.2.7.1.14
        apPerfWlanULPkts OBJECT-TYPE
            SYNTAX Counter64
            MAX-ACCESS read-only
            STATUS current
            DESCRIPTION
                "Running counter of uplink packets per second."
            ::= { apPerformanceReportbyRadioAndWlanEntry 14 }



        -- 1.3.6.1.4.1.4329.15.3.5.2.7.1.15
        apPerfWlanPrevPeakDLOctetsPerSec OBJECT-TYPE
            SYNTAX HundredthOfGauge64
            MAX-ACCESS read-only
            STATUS current
            DESCRIPTION
                "Peak downlink octets in hundredth of octets per second from last 15 minute interval."
            ::= { apPerformanceReportbyRadioAndWlanEntry 15 }



        -- 1.3.6.1.4.1.4329.15.3.5.2.7.1.16
        apPerfWlanCurPeakDLOctetsPerSec OBJECT-TYPE
            SYNTAX HundredthOfGauge64
            MAX-ACCESS read-only
            STATUS current
            DESCRIPTION
                "Peak downlink octets in hundredth of octets per second of current 15 minute interval."
            ::= { apPerformanceReportbyRadioAndWlanEntry 16 }


        -- 1.3.6.1.4.1.4329.15.3.5.2.7.1.17
        apPerfWlanAverageDLOctetsPerSec OBJECT-TYPE
            SYNTAX HundredthOfGauge64
            MAX-ACCESS read-only
            STATUS current
            DESCRIPTION
                "Running average of downlink octets in hundredth of octets per second."
            ::= { apPerformanceReportbyRadioAndWlanEntry 17 }

        -- 1.3.6.1.4.1.4329.15.3.5.2.7.1.18
        apPerfWlanCurrentDLOctetsPerSec OBJECT-TYPE
            SYNTAX HundredthOfGauge64
            MAX-ACCESS read-only
            STATUS current
            DESCRIPTION
                "Downlink octets in hundredth octets per second from latest statistics from AP."
            ::= { apPerformanceReportbyRadioAndWlanEntry 18 }

        -- 1.3.6.1.4.1.4329.15.3.5.2.7.1.19
        apPerfWlanDLOctets OBJECT-TYPE
            SYNTAX Counter64
            MAX-ACCESS read-only
            STATUS current
            DESCRIPTION
                "Running counter of downlink octets per second."
            ::= { apPerformanceReportbyRadioAndWlanEntry 19 }


        -- 1.3.6.1.4.1.4329.15.3.5.2.7.1.20
        apPerfWlanPrevPeakDLPktsPerSec OBJECT-TYPE
            SYNTAX HundredthOfGauge64
            MAX-ACCESS read-only
            STATUS current
            DESCRIPTION
                "Peak downlink packets in hundredth of packets per second from last 15 minute interval."
            ::= { apPerformanceReportbyRadioAndWlanEntry 20 }




        -- 1.3.6.1.4.1.4329.15.3.5.2.7.1.21
        apPerfWlanCurPeakDLPktsPerSec OBJECT-TYPE
            SYNTAX HundredthOfGauge64
            MAX-ACCESS read-only
            STATUS current
            DESCRIPTION
                "Peak downlink packets in hundredth of packets per second of current 15 minute interval."
            ::= { apPerformanceReportbyRadioAndWlanEntry 21 }


        -- 1.3.6.1.4.1.4329.15.3.5.2.7.1.22
        apPerfWlanAverageDLPktsPerSec OBJECT-TYPE
            SYNTAX HundredthOfGauge64
            MAX-ACCESS read-only
            STATUS current
            DESCRIPTION
                "Running average of downlink packets in hundredth of packets per second."
            ::= { apPerformanceReportbyRadioAndWlanEntry 22 }

        -- 1.3.6.1.4.1.4329.15.3.5.2.7.1.23
        apPerfWlanCurrentDLPktsPerSec OBJECT-TYPE
            SYNTAX HundredthOfGauge64
            MAX-ACCESS read-only
            STATUS current
            DESCRIPTION
                "Downlink packets in hundredth of packets per second from latest statistics from AP."
            ::= { apPerformanceReportbyRadioAndWlanEntry 23 }

        -- 1.3.6.1.4.1.4329.15.3.5.2.7.1.24
        apPerfWlanDLPkts OBJECT-TYPE
            SYNTAX Counter64
            MAX-ACCESS read-only
            STATUS current
            DESCRIPTION
                "Running counter of downlink packets per second."
            ::= { apPerformanceReportbyRadioAndWlanEntry 24 }

                    
                    


        -- 1.3.6.1.4.1.4329.15.3.5.2.8
        apChannelUtilizationTable OBJECT-TYPE
            SYNTAX SEQUENCE OF ApChannelUtilizationEntry
            MAX-ACCESS not-accessible
            STATUS current
            DESCRIPTION
                "Table of AP utilization by channel that the AP can change dynamically. 
                 It contains one entry for each radio and channel of each active AP."
            ::= { apStatsObjects 8 }

        
        -- 1.3.6.1.4.1.4329.15.3.5.2.7.1
        apChannelUtilizationEntry OBJECT-TYPE
            SYNTAX ApChannelUtilizationEntry
            MAX-ACCESS not-accessible
            STATUS current
            DESCRIPTION
                "The AP performance statistics of one AP radio and channel."
            INDEX {apIndex, apRadioIndex, channel }
            ::= { apChannelUtilizationTable 1 }

        
        ApChannelUtilizationEntry ::=
            SEQUENCE { 
         channel
                    Unsigned32,
                apChnlUtilPrevPeakUtilization
                    Gauge32,
                apChnlUtilCurPeakUtilization
                    Gauge32,
                apChnlUtilAverageUtilization
                    HundredthOfGauge32,
                apChnlUtilCurrentUtilization
                    Gauge32
         }

        -- 1.3.6.1.4.1.4329.15.3.5.2.8.1.1
        channel OBJECT-TYPE
            SYNTAX Unsigned32
            MAX-ACCESS not-accessible
            STATUS current
            DESCRIPTION
                "Channel on which utilization is measured."
            ::= { apChannelUtilizationEntry 1 }


        -- 1.3.6.1.4.1.4329.15.3.5.2.8.1.2
        apChnlUtilPrevPeakUtilization OBJECT-TYPE
            SYNTAX Gauge32
            MAX-ACCESS read-only
            STATUS current
            DESCRIPTION
                "Peak channel utilization in % from last 15 minute interval."
            ::= { apChannelUtilizationEntry 2 }


        -- 1.3.6.1.4.1.4329.15.3.5.2.8.1.3
        apChnlUtilCurPeakUtilization OBJECT-TYPE
            SYNTAX Gauge32
            MAX-ACCESS read-only
            STATUS current
            DESCRIPTION
                "Peak channel utilization in % of current 15 minute interval."
            ::= { apChannelUtilizationEntry 3 }


        -- 1.3.6.1.4.1.4329.15.3.5.2.8.1.4
        apChnlUtilAverageUtilization OBJECT-TYPE
            SYNTAX HundredthOfGauge32
            MAX-ACCESS read-only
            STATUS current
            DESCRIPTION
                "Running average of channel utilization in hundredth of %."
            ::= { apChannelUtilizationEntry 4 }

        -- 1.3.6.1.4.1.4329.15.3.5.2.8.1.5
        apChnlUtilCurrentUtilization OBJECT-TYPE
            SYNTAX Gauge32
            MAX-ACCESS read-only
            STATUS current
            DESCRIPTION
                "Channel utilization in % from latest statistics from AP."
            ::= { apChannelUtilizationEntry 5 }

                
                        



        -- 1.3.6.1.4.1.4329.15.3.5.2.9
        apNeighboursTable OBJECT-TYPE
            SYNTAX SEQUENCE OF ApNeighboursEntry
            MAX-ACCESS not-accessible
            STATUS current
            DESCRIPTION
                "A table showing the BSSID, RSS, operating radio channel and detailed information of a nearby AP.
                  The table contains one row per nearby AP per radio per active AP."
            ::= { apStatsObjects 9 }


        -- 1.3.6.1.4.1.4329.15.3.5.2.9.1
        apNeighboursEntry OBJECT-TYPE
            SYNTAX ApNeighboursEntry
            MAX-ACCESS not-accessible
            STATUS current
            DESCRIPTION
                "The configuration attributes of one nearby AP."
            INDEX { apIndex, ifIndex, nearbyApIndex }
            ::= { apNeighboursTable 1 }


    ApNeighboursEntry ::=
        SEQUENCE { 
        nearbyApIndex
            Unsigned32,
        nearbyApInfo
            DisplayString,
        nearbyApBSSID
            OCTET STRING,
        nearbyApChannel
            DisplayString,
        nearbyApRSS
            Integer32
    }


        -- 1.3.6.1.4.1.4329.15.3.5.2.9.1.1
        nearbyApIndex OBJECT-TYPE
            SYNTAX Unsigned32
            MAX-ACCESS not-accessible
            STATUS current
            DESCRIPTION
                "Nearby AP index."
            ::= { apNeighboursEntry 1 }



        -- 1.3.6.1.4.1.4329.15.3.5.2.9.1.2
        nearbyApInfo OBJECT-TYPE
            SYNTAX DisplayString
            MAX-ACCESS read-only
            STATUS current
            DESCRIPTION
                "Detailed information of a nearby AP. "
            ::= { apNeighboursEntry 2 }

        -- 1.3.6.1.4.1.4329.15.3.5.2.9.1.3
        nearbyApBSSID OBJECT-TYPE
            SYNTAX OCTET STRING (SIZE (17))
            MAX-ACCESS read-only
            STATUS current
            DESCRIPTION
                "The BSSID of a nearby AP. "
            ::= { apNeighboursEntry 3 }


        -- 1.3.6.1.4.1.4329.15.3.5.2.9.1.4
        nearbyApChannel OBJECT-TYPE
            SYNTAX DisplayString
            MAX-ACCESS read-only
            STATUS current
            DESCRIPTION
                "The operating radio channel of a nearby AP. "
            ::= { apNeighboursEntry 4 }

            
        -- 1.3.6.1.4.1.4329.15.3.5.2.9.1.5
        nearbyApRSS OBJECT-TYPE
            SYNTAX Integer32
            MAX-ACCESS read-only
            STATUS current
            DESCRIPTION
                "The Received Signal Strength of a nearby AP. "
            ::= { apNeighboursEntry 5 }





        
        -- 1.3.6.1.4.1.4329.15.3.5.3
        sensorManagement OBJECT IDENTIFIER ::= { accessPoints 3 }

        
        -- 1.3.6.1.4.1.4329.15.3.5.3.1
        tftpSever OBJECT-TYPE
            SYNTAX DisplayString
            MAX-ACCESS read-write
            STATUS current
            DESCRIPTION
                "TFTP server that sensor image resides."
            ::= { sensorManagement 1 }

        
        -- 1.3.6.1.4.1.4329.15.3.5.3.2
        imagePath26xx OBJECT-TYPE
            SYNTAX DisplayString
            MAX-ACCESS read-write
            STATUS current
            DESCRIPTION
                "Path of sensor image on TFTP server."
            ::= { sensorManagement 2 }

        
        -- 1.3.6.1.4.1.4329.15.3.5.3.3
        imagePath36xx OBJECT-TYPE
            SYNTAX DisplayString
            MAX-ACCESS read-write
            STATUS current
            DESCRIPTION
                "Path of sensor image on TFTP server."
            ::= { sensorManagement 3 }

        
        -- 1.3.6.1.4.1.4329.15.3.5.3.4
        imageVersionOfap26xx OBJECT-TYPE
            SYNTAX DisplayString
            MAX-ACCESS read-write
            STATUS current
            DESCRIPTION
                "Sensor's software version."
            ::= { sensorManagement 4 }

        
        -- 1.3.6.1.4.1.4329.15.3.5.3.5
        imageVersionOfngap36xx OBJECT-TYPE
            SYNTAX DisplayString
            MAX-ACCESS read-write
            STATUS current
            DESCRIPTION
                "Sensor's softerware version for Next Generation Access Point."
            ::= { sensorManagement 5 }

        
        -- 1.3.6.1.4.1.4329.15.3.5.4
        apRegistration OBJECT IDENTIFIER ::= { accessPoints 4 }

        
        -- 1.3.6.1.4.1.4329.15.3.5.4.1
        apRegSecurityMode OBJECT-TYPE
            SYNTAX INTEGER
                {
                allowAll(1),
                allowApprovedOnes(2)
                }
            MAX-ACCESS read-write
            STATUS current
            DESCRIPTION
                "Indicates registration mode for an AP. If allowAll(1), then all wireless
                APs are allowed to register to the controlloer, otherwise only approved
                APs in 'Approved AP' list are allowed to register to the controller."
            ::= { apRegistration 1 }

        
        -- 1.3.6.1.4.1.4329.15.3.5.4.2
        apRegDiscoveryRetries OBJECT-TYPE
            SYNTAX Unsigned32 (1..255)
            MAX-ACCESS read-write
            STATUS current
            DESCRIPTION
                "Number of retries for discovery requests from an access point to controller. After
                these number of retries, the access point will start over again after some arbitrary
                delays."
            DEFVAL { 3 }
            ::= { apRegistration 2 }

        
        -- 1.3.6.1.4.1.4329.15.3.5.4.3
        apRegDiscoveryInterval OBJECT-TYPE
            SYNTAX Unsigned32 (1..10)
            UNITS "seconds"
            MAX-ACCESS read-write
            STATUS current
            DESCRIPTION
                "Interval between two consecutive discovery requests from the same access point."
            DEFVAL { 3 }
            ::= { apRegistration 3 }

        
        -- 1.3.6.1.4.1.4329.15.3.5.4.4
        apRegTelnetPassword OBJECT-TYPE
            SYNTAX OCTET STRING
            MAX-ACCESS read-write
            STATUS current
            DESCRIPTION
                "Password used to access an AP via telnet. This field is write-only and read access
                returns empty string."
            ::= { apRegistration 4 }

        
        -- 1.3.6.1.4.1.4329.15.3.5.4.5
        apRegSSHPassword OBJECT-TYPE
            SYNTAX OCTET STRING
            MAX-ACCESS read-write
            STATUS current
            DESCRIPTION
                "SSH password used to access an access point. This field is write-only and read access
                returns empty string."
            ::= { apRegistration 5 }

        
        -- 1.3.6.1.4.1.4329.15.3.5.4.6
        apRegUseClusterEncryption OBJECT-TYPE
            SYNTAX TruthValue
            MAX-ACCESS read-write
            STATUS current
            DESCRIPTION
                "If this field set to true, then all APs in the cluster use cluster encryption."
            ::= { apRegistration 6 }

        
        -- 1.3.6.1.4.1.4329.15.3.5.4.7
        apRegClusterSharedSecret OBJECT-TYPE
            SYNTAX OCTET STRING
            MAX-ACCESS read-write
            STATUS current
            DESCRIPTION
                "Password for cluster encryption. This field is write-only and read access returns empty string."
            ::= { apRegistration 7 }

        
        -- 1.3.6.1.4.1.4329.15.3.5.5
        loadBalancing OBJECT IDENTIFIER ::= { accessPoints 5 }

        
        -- 1.3.6.1.4.1.4329.15.3.5.5.1
        loadGroupTable OBJECT-TYPE
            SYNTAX SEQUENCE OF LoadGroupEntry
            MAX-ACCESS not-accessible
            STATUS current
            DESCRIPTION
                "Table of configured load groups for access points. A set of access points can 
                be grouped together and they are identified by unique name. An access point
                can only be assigned to one group."
            ::= { loadBalancing 1 }

        
        -- 1.3.6.1.4.1.4329.15.3.5.5.1.1
        loadGroupEntry OBJECT-TYPE
            SYNTAX LoadGroupEntry
            MAX-ACCESS not-accessible
            STATUS current
            DESCRIPTION
                "An entry containing definition of a load group. There exists two types of load group:
                client-balancing-group and radio-balancing-group."
            INDEX { loadGroupID }
            ::= { loadGroupTable 1 }

        
        LoadGroupEntry ::=
            SEQUENCE { 
                loadGroupID
                    Unsigned32,
                loadGroupName
                    DisplayString,
                loadGroupType
                    INTEGER,
                loadGroupBandPreference
                    INTEGER,
                loadGroupLoadControl
                    INTEGER,
                loadGroupClientCountRadio1
                    Unsigned32,
                loadGroupClientCountRadio2
                    Unsigned32,
                loadGroupLoadControlEnableR1
                    INTEGER,
                loadGroupLoadControlEnableR2
                    INTEGER,
                loadGroupLoadControlStrictLimitR1
                    INTEGER,
                loadGroupLoadControlStrictLimitR2
                    INTEGER
             }

        -- 1.3.6.1.4.1.4329.15.3.5.5.1.1.1
        loadGroupID OBJECT-TYPE
            SYNTAX Unsigned32
            MAX-ACCESS read-only
            STATUS current
            DESCRIPTION
                "Internally generated ID for a group and cannot be changed externally."
            ::= { loadGroupEntry 1 }

        
        -- 1.3.6.1.4.1.4329.15.3.5.5.1.1.2
        loadGroupName OBJECT-TYPE
            SYNTAX DisplayString (SIZE (1..32))
            MAX-ACCESS read-write
            STATUS current
            DESCRIPTION
                "Unique name assigned to the group."
            ::= { loadGroupEntry 2 }

        
        -- 1.3.6.1.4.1.4329.15.3.5.5.1.1.3
        loadGroupType OBJECT-TYPE
            SYNTAX INTEGER
                {
                clientBalancing(0),
                radioBalancing(1)
                }
            MAX-ACCESS read-write
            STATUS current
            DESCRIPTION
                "Type of load balancing this group supports."
            ::= { loadGroupEntry 3 }

        
        -- 1.3.6.1.4.1.4329.15.3.5.5.1.1.4
        loadGroupBandPreference OBJECT-TYPE
            SYNTAX INTEGER
                {
                disabled(0),
                enabled(1)
                }
            MAX-ACCESS read-write
            STATUS current
            DESCRIPTION
                "Band preference is enabled for this group if this field is set to true and group type
                is set to radioBalancing(1)."
            ::= { loadGroupEntry 4 }

        
        -- 1.3.6.1.4.1.4329.15.3.5.5.1.1.5
        loadGroupLoadControl OBJECT-TYPE
            SYNTAX INTEGER
                {
                disabled(0),
                enabled(1)
                }
            MAX-ACCESS read-write
            STATUS deprecated
            DESCRIPTION
                "Load balancing is enabled for this group if this field is set to true and group type
                is set to radioBalancing(1)."
            DEFVAL { disabled }
            ::= { loadGroupEntry 5 }

        
        -- 1.3.6.1.4.1.4329.15.3.5.5.1.1.6
        loadGroupClientCountRadio1 OBJECT-TYPE
            SYNTAX Unsigned32 (5..60 | 121)
            MAX-ACCESS read-write
            STATUS current
            DESCRIPTION
                "Maximum number of client on this radio.  This field is only applicable to a group with 
                radioBalancing(1) type."
            DEFVAL { 121 }
            ::= { loadGroupEntry 6 }

        
        -- 1.3.6.1.4.1.4329.15.3.5.5.1.1.7
        loadGroupClientCountRadio2 OBJECT-TYPE
            SYNTAX Unsigned32 (5..60 | 121)
            MAX-ACCESS read-write
            STATUS current
            DESCRIPTION
                "Maximum number of client on this radio.  This field is only applicable to a group with 
                radioBalancing(1) type."
            DEFVAL { 121 }
            ::= { loadGroupEntry 7 }

        
        -- 1.3.6.1.4.1.4329.15.3.5.5.1.1.8
        loadGroupLoadControlEnableR1 OBJECT-TYPE
            SYNTAX INTEGER
                {
                disabled(0),
                enabled(1)
                }
            MAX-ACCESS read-write
            STATUS current
            DESCRIPTION
                "If it is enabled then load control is applicable to radio #1 of all access points that are 
                assigned to this load group.
                This field has meaning only for the load group that is of radioBalancing(1) type. "
            ::= { loadGroupEntry 8 }

        
        -- 1.3.6.1.4.1.4329.15.3.5.5.1.1.9
        loadGroupLoadControlEnableR2 OBJECT-TYPE
            SYNTAX INTEGER
                {
                disabled(0),
                enabled(1)
                }
            MAX-ACCESS read-write
            STATUS current
            DESCRIPTION
                "If it is enabled then load control is applicable to radio #2 of all access points that are 
                assigned to this load group.
                This field has meaning only for the load group that is of radioBalancing(1) type."
            ::= { loadGroupEntry 9 }

        
        -- 1.3.6.1.4.1.4329.15.3.5.5.1.1.10
        loadGroupLoadControlStrictLimitR1 OBJECT-TYPE
            SYNTAX INTEGER
                {
                disabled(0),
                enabled(1)
                }
            MAX-ACCESS read-write
            STATUS current
            DESCRIPTION
                "If it is enabled then strict limit for load control is applicable to radio #1 of all
                access points that are assigned to this load group.
                This field has meaning only for the load group that is of radioBalancing(1) type."
            ::= { loadGroupEntry 10 }

        
        -- 1.3.6.1.4.1.4329.15.3.5.5.1.1.11
        loadGroupLoadControlStrictLimitR2 OBJECT-TYPE
            SYNTAX INTEGER
                {
                disabled(0),
                enabled(1)
                }
            MAX-ACCESS read-write
            STATUS current
            DESCRIPTION
                "If it is enabled then strict limit for load control is applicable to radio #2 of all
                access points that are assigned to this load group.
                This field has meaning only for the load group that is of radioBalancing(1) type."
            ::= { loadGroupEntry 11 }

        
        -- 1.3.6.1.4.1.4329.15.3.5.5.2
        loadGrpRadiosTable OBJECT-TYPE
            SYNTAX SEQUENCE OF LoadGrpRadiosEntry
            MAX-ACCESS not-accessible
            STATUS current
            DESCRIPTION
                "Table of radio assignment to defined load groups. "
            ::= { loadBalancing 2 }

        
        -- 1.3.6.1.4.1.4329.15.3.5.5.2.1
        loadGrpRadiosEntry OBJECT-TYPE
            SYNTAX LoadGrpRadiosEntry
            MAX-ACCESS not-accessible
            STATUS current
            DESCRIPTION
                "Any entry defining radio assignment of AP, identified by apIndex, to a load group 
                identified by loadGroupID."
            INDEX { loadGroupID, apIndex }
            ::= { loadGrpRadiosTable 1 }

        
        LoadGrpRadiosEntry ::=
            SEQUENCE { 
                loadGrpRadiosRadio1
                    INTEGER,
                loadGrpRadiosRadio2
                    INTEGER
             }

        -- 1.3.6.1.4.1.4329.15.3.5.5.2.1.2
        loadGrpRadiosRadio1 OBJECT-TYPE
            SYNTAX INTEGER
                {
                notApplicable(0),
                assigned(1),
                unassigned(2)
                }
            MAX-ACCESS read-write
            STATUS current
            DESCRIPTION
                "If this field is set to 'assigned(1)', then the radio of the AP identified by the
                apIndex is a member of the load balancing group identified by the loadBlanaceID.
                For radio blanacing group, either all or none of the radios of a specific AP 
                (indentified by apIndex) are assigned to the load balancing group."
            ::= { loadGrpRadiosEntry 2 }

        
        -- 1.3.6.1.4.1.4329.15.3.5.5.2.1.3
        loadGrpRadiosRadio2 OBJECT-TYPE
            SYNTAX INTEGER
                {
                notApplicable(0),
                assigned(1),
                unassigned(2)
                }
            MAX-ACCESS read-write
            STATUS current
            DESCRIPTION
                "If this field is set to 'assigned(2)', then the radio of the AP identified by the
                apIndex is a member of the load balancing group identified by the loadBlanaceID.
                For radio blanacing group, either all or none of the radios of a specific AP 
                (indentified by apIndex) are assigned to the load balancing group."
            ::= { loadGrpRadiosEntry 3 }

        
        -- 1.3.6.1.4.1.4329.15.3.5.5.3
        loadGrpWlanTable OBJECT-TYPE
            SYNTAX SEQUENCE OF LoadGrpWlanEntry
            MAX-ACCESS not-accessible
            STATUS current
            DESCRIPTION
                "Table of WLAN assignment to defined load groups. "
            ::= { loadBalancing 3 }

        
        -- 1.3.6.1.4.1.4329.15.3.5.5.3.1
        loadGrpWlanEntry OBJECT-TYPE
            SYNTAX LoadGrpWlanEntry
            MAX-ACCESS not-accessible
            STATUS current
            DESCRIPTION
                "An entry defining WLAN, identified by wlanID, assignment to a load group identified
                by loadGroupID."
            INDEX { loadGroupID, wlanID }
            ::= { loadGrpWlanTable 1 }

        
        LoadGrpWlanEntry ::=
            SEQUENCE { 
                loadGrpWlanAssigned
                    TruthValue
             }

        -- 1.3.6.1.4.1.4329.15.3.5.5.3.1.1
        loadGrpWlanAssigned OBJECT-TYPE
            SYNTAX TruthValue
            MAX-ACCESS read-write
            STATUS current
            DESCRIPTION
                "Assignement of WLAN, identified with wlanID, to the load balancing group identified 
                bye loadGroupID."
            ::= { loadGrpWlanEntry 1 }



        -- 1.3.6.1.4.1.4329.15.3.5.6
        apMaintenanceCycle OBJECT IDENTIFIER ::= { accessPoints 6 }

        -- 1.3.6.1.4.1.4329.15.3.5.6.1
        schedule OBJECT-TYPE
           SYNTAX INTEGER
                {
                never(0),
                daily(1),
                weekly(2),
                monthly(3)
                }
            MAX-ACCESS read-write
            STATUS current
            DESCRIPTION
                "AP maintenance schedule options.
                 0 : never perform the maintenance action.
                 1 : perform the maintenance action every day.
                 2 : perform the maintenance action every week.
                 3 : perform the maintenance action every month."
            ::= { apMaintenanceCycle 1 }

        -- 1.3.6.1.4.1.4329.15.3.5.6.2
        startHour OBJECT-TYPE
           SYNTAX Integer32 (0..23)
            MAX-ACCESS read-write
            STATUS current
            DESCRIPTION
                "Maintenance action starts at this hour of the day. "
            ::= { apMaintenanceCycle 2 }

        -- 1.3.6.1.4.1.4329.15.3.5.6.3
        startMinute OBJECT-TYPE
           SYNTAX Integer32(0..59)
            MAX-ACCESS read-write
            STATUS current
            DESCRIPTION
                "Maintenance action starts at this minute of the hour. "
            ::= { apMaintenanceCycle 3 }

        -- 1.3.6.1.4.1.4329.15.3.5.6.4
        duration OBJECT-TYPE
           SYNTAX Integer32(1..23)
            MAX-ACCESS read-write
            STATUS current
            DESCRIPTION
                "Duration of the AP maintenance cycle (how often maintenance is done) in hours. "
            ::= { apMaintenanceCycle 4 }


        -- 1.3.6.1.4.1.4329.15.3.5.6.5
        recurrenceDaily OBJECT-TYPE
            SYNTAX  INTEGER
                    {
                        everyDay(0),
                        everyWeekday(1),
                        everyWeekend(2)
                       }

            MAX-ACCESS read-write
            STATUS current
            DESCRIPTION
                "This field has meaning only when the maintenance schedule option is set to daily(1). Below is the recurrence option.
                 0 : every day.
                 1 : every weekday.
                 2 : every weekend."
            ::= { apMaintenanceCycle 5 }

        -- 1.3.6.1.4.1.4329.15.3.5.6.6
        recurrenceWeekly OBJECT-TYPE
            SYNTAX  BITS
                    {
                        sunday(0),
                        monday(1),
                        tuesday(2),
                        wednesday(3),
                        thursday(4),
                        friday(5),
                        saturday(6)
                       }

            MAX-ACCESS read-write
            STATUS current
            DESCRIPTION
                "This field has meaning only when the maintenance schedule option is set to weekly(2). Below are the recurrence options.
                 BIT 0 : Sunday.
                 BIT 1 : Monday.
                 BIT 2 : Tuesday.
                 BIT 3 : Wednesday.
                 BIT 4 : Thursday.
                 BIT 5 : Friday.
                 BIT 6 : Saturday."
            ::= { apMaintenanceCycle 6 }


        -- 1.3.6.1.4.1.4329.15.3.5.6.7
        recurrenceMonthly OBJECT-TYPE
            SYNTAX  BITS
                    {
                        first(0),
                        second(1),
                        third(2),
                        fourth(3),
                        fifth(4),
                        sunday(5),
                        monday(6),
                        tuesday(7),
                        wednesday(8),
                        thursday(9),
                        friday(10),
                        saturday(11)
                       }

            MAX-ACCESS read-write
            STATUS current
            DESCRIPTION
                "This field has meaning only when the maintenance schedule option is set to monthly(3). Below are the recurrence options.
                BIT 0 : the first week of the month.
                BIT 1 : the second week of the month.
                BIT 2 : the third week of the month.
                BIT 3 : the fourth week of the month.
                BIT 4 : the fifth week of the month.
                BIT 5 : sunday of the week.
                BIT 6 : monday of the week.
                BIT 7 : tuesday of the week.
                BIT 8 : wednesday of the week.
                BIT 9 : thursday of the week.
                BIT 10 : friday of the week.
                BIT 11 : saturday of the week."
            ::= { apMaintenanceCycle 7 }

        -- 1.3.6.1.4.1.4329.15.3.5.6.8
        apPlatforms OBJECT-TYPE
            SYNTAX  BITS
                    {
                        ap2600(0),
                        ap2605(1),
                        ap2650(2),
                        ap4102(3),
                        w786(4),
                        ap3705(5),
                        ap3710(6),
                        ap3715(7),
                        ap3765(8),
                        ap3767(9),
                        ap3801(10),
                        ap3805(11),
                        ap3825(12),
                        ap3865(13),
                        ap3935(14),
                        ap3965(15),
                        w78xc(16),
                        w78xcsfp(17)
                       }

            MAX-ACCESS read-write
            STATUS current
            DESCRIPTION
                "Select which models of the AP platforms to perform the maintenance.
                BIT 0 :  AP2600 platform.
                BIT 1 :  AP2605 platform.
                BIT 2 :  AP2650 platform.
                BIT 3 :  AP4102 platform.
                BIT 4 :  W786 platform.
                BIT 5 :  AP3705 platform.
                BIT 6 :  AP3710 platform.
                BIT 7 :  AP3715 platform.
                BIT 8 :  AP3765 platform.
                BIT 9 :  AP3767 platform.
                BIT 10 :  AP3801 platform.
                BIT 11 :  AP3805 platform.
                BIT 12 :  AP3825 platform.
                BIT 13 :  AP3865 platform.
                BIT 14 :  AP3935 platform.
                BIT 15 :  AP3965 platform.
                BIT 16 :  W78XC platform.
                BIT 17 :  W78XCSFP platform."
            ::= { apMaintenanceCycle 8 }




            

        
        -- 1.3.6.1.4.1.4329.15.3.6
        mobileUnits OBJECT IDENTIFIER ::= { hiPathWirelessMgmt 6 }

        
        -- 1.3.6.1.4.1.4329.15.3.6.1
        mobileUnitCount OBJECT-TYPE
            SYNTAX Integer32
            MAX-ACCESS read-write
            STATUS current
            DESCRIPTION
                "Number of clients associated with the controller."
            ::= { mobileUnits 1 }

        
        -- 1.3.6.1.4.1.4329.15.3.6.2
        muTable OBJECT-TYPE
            SYNTAX SEQUENCE OF MuEntry
            MAX-ACCESS not-accessible
            STATUS current
            DESCRIPTION
                "Table of information for clients associated with the EWC."
            ::= { mobileUnits 2 }

        
        -- 1.3.6.1.4.1.4329.15.3.6.2.1
        muEntry OBJECT-TYPE
            SYNTAX MuEntry
            MAX-ACCESS not-accessible
            STATUS current
            DESCRIPTION
                "Information for a client associated with the EWC."
            INDEX { muMACAddress }
            ::= { muTable 1 }

        
        MuEntry ::=
            SEQUENCE { 
                muMACAddress
                    MacAddress,
                muIPAddress
                    IpAddress,
                muUser
                    OCTET STRING,
                muState
                    TruthValue,
                muAPSerialNo
                    OCTET STRING,
                muVnsSSID
                    OCTET STRING,
                muTxPackets
                    Counter64,
                muRxPackets
                    Counter64,
                muTxOctets
                    Counter64,
                muRxOctets
                    Counter64,
                muDuration
                    Counter64,
                muAPName
                    DisplayString,
                muTopologyName
                    DisplayString,
                muPolicyName
                    DisplayString,
                muDefaultCoS
                    DisplayString,
                muConnectionProtocol
                    INTEGER,
                muConnectionCapability
                    INTEGER,
                muWLANID
                    Unsigned32,
                muBSSIDMac
                    MacAddress,
                muDot11ConnectionCapability
                    BITS
             }

        -- 1.3.6.1.4.1.4329.15.3.6.2.1.1
        muMACAddress OBJECT-TYPE
            SYNTAX MacAddress
            MAX-ACCESS read-only
            STATUS current
            DESCRIPTION
                "Client MAC address."
            ::= { muEntry 1 }

        
        -- 1.3.6.1.4.1.4329.15.3.6.2.1.2
        muIPAddress OBJECT-TYPE
            SYNTAX IpAddress
            MAX-ACCESS read-only
            STATUS current
            DESCRIPTION
                "Client IP Address."
            ::= { muEntry 2 }

        
        -- 1.3.6.1.4.1.4329.15.3.6.2.1.3
        muUser OBJECT-TYPE
            SYNTAX OCTET STRING
            MAX-ACCESS read-only
            STATUS current
            DESCRIPTION
                "Client login name."
            ::= { muEntry 3 }

        
        -- 1.3.6.1.4.1.4329.15.3.6.2.1.4
        muState OBJECT-TYPE
            SYNTAX TruthValue
            MAX-ACCESS read-only
            STATUS current
            DESCRIPTION
                "True if the client is authenticated."
            ::= { muEntry 4 }

        
        -- 1.3.6.1.4.1.4329.15.3.6.2.1.5
        muAPSerialNo OBJECT-TYPE
            SYNTAX OCTET STRING
            MAX-ACCESS read-only
            STATUS current
            DESCRIPTION
                "Serial Number of the Access Point the client is associated with."
            ::= { muEntry 5 }

        
        -- 1.3.6.1.4.1.4329.15.3.6.2.1.6
        muVnsSSID OBJECT-TYPE
            SYNTAX OCTET STRING
            MAX-ACCESS read-only
            STATUS current
            DESCRIPTION
                "SSID of the VNS the client is associated with."
            ::= { muEntry 6 }

        
        -- 1.3.6.1.4.1.4329.15.3.6.2.1.7
        muTxPackets OBJECT-TYPE
            SYNTAX Counter64
            MAX-ACCESS read-only
            STATUS current
            DESCRIPTION
                "Number of packets trasmitted to the client."
            ::= { muEntry 7 }

        
        -- 1.3.6.1.4.1.4329.15.3.6.2.1.8
        muRxPackets OBJECT-TYPE
            SYNTAX Counter64
            MAX-ACCESS read-only
            STATUS current
            DESCRIPTION
                "Number of packets received from the client."
            ::= { muEntry 8 }

        
        -- 1.3.6.1.4.1.4329.15.3.6.2.1.9
        muTxOctets OBJECT-TYPE
            SYNTAX Counter64
            MAX-ACCESS read-only
            STATUS current
            DESCRIPTION
                "Number of octets transmitted to the client."
            ::= { muEntry 9 }

        
        -- 1.3.6.1.4.1.4329.15.3.6.2.1.10
        muRxOctets OBJECT-TYPE
            SYNTAX Counter64
            MAX-ACCESS read-only
            STATUS current
            DESCRIPTION
                "Number of octets received from the client."
            ::= { muEntry 10 }

        
        -- 1.3.6.1.4.1.4329.15.3.6.2.1.11
        muDuration OBJECT-TYPE
            SYNTAX Counter64
            MAX-ACCESS read-only
            STATUS current
            DESCRIPTION
                "Time client has been associated with the EWC."
            ::= { muEntry 11 }

        
        -- 1.3.6.1.4.1.4329.15.3.6.2.1.12
        muAPName OBJECT-TYPE
            SYNTAX DisplayString
            MAX-ACCESS read-only
            STATUS current
            DESCRIPTION
                "Name of the Access Point the client is associated with."
            ::= { muEntry 12 }

        
        -- 1.3.6.1.4.1.4329.15.3.6.2.1.13
        muTopologyName OBJECT-TYPE
            SYNTAX DisplayString
            MAX-ACCESS read-only
            STATUS current
            DESCRIPTION
                "Topology name that the MU is associated with."
            ::= { muEntry 13 }

        
        -- 1.3.6.1.4.1.4329.15.3.6.2.1.14
        muPolicyName OBJECT-TYPE
            SYNTAX DisplayString
            MAX-ACCESS read-only
            STATUS current
            DESCRIPTION
                "The name of the policy that provides filter for this MU."
            ::= { muEntry 14 }

        
        -- 1.3.6.1.4.1.4329.15.3.6.2.1.15
        muDefaultCoS OBJECT-TYPE
            SYNTAX DisplayString
            MAX-ACCESS read-only
            STATUS current
            DESCRIPTION
                "The CoS that is applied to the current traffic if the defined rule for 
                the current traffic has not specifically defined any CoS."
            ::= { muEntry 15 }

        
        -- 1.3.6.1.4.1.4329.15.3.6.2.1.16
        muConnectionProtocol OBJECT-TYPE
            SYNTAX INTEGER
                {
                unknown(0),
                a(1),
                g(2),
                b(3),
                n50(4),
                n24(5),
                ac(6)
                }
            MAX-ACCESS read-only
            STATUS current
            DESCRIPTION
                "The MU is using this connection protocol for current connection.
                Symbols notation:  n50 = an = n5.0Ghz,   n24 = bgn = n2.4Ghz"
            ::= { muEntry 16 }

        
        -- 1.3.6.1.4.1.4329.15.3.6.2.1.17
        muConnectionCapability OBJECT-TYPE
            SYNTAX INTEGER
                {
                unknown(0),
                a(1),
                bg(2),
                abg(3),
                an(4),
                bgn(5)
                }
            MAX-ACCESS read-only
            STATUS deprecated
            DESCRIPTION
                "This field indicates what are the MU connection capability."
            ::= { muEntry 17 }

        
        -- 1.3.6.1.4.1.4329.15.3.6.2.1.18
        muWLANID OBJECT-TYPE
            SYNTAX Unsigned32
            MAX-ACCESS read-only
            STATUS current
            DESCRIPTION
                "ID of the WLAN that the MU is associated with."
            ::= { muEntry 18 }

        
        -- 1.3.6.1.4.1.4329.15.3.6.2.1.19
        muBSSIDMac OBJECT-TYPE
            SYNTAX MacAddress
            MAX-ACCESS read-only
            STATUS current
            DESCRIPTION
                "Client BSSID MAC address."
            ::= { muEntry 19 }


        -- 1.3.6.1.4.1.4329.15.3.6.2.1.20
        muDot11ConnectionCapability OBJECT-TYPE
            SYNTAX  BITS
                    {
                        dot1150(0),
                        dot1124 (1),
                        wpaV1(2),
                        wpaV2(3),
                        oneStream(4),
                        twoStream(5),
                        threeSteam(6),
                        uapsdVoice(7),
                        uapsdVideo(8),
                        uapsdBackground(9),
                        uapsdBesteffort(10),
                        wmm(11),
                        greenfield(12),
                        fastTransition(13)
                        
                       }
            MAX-ACCESS read-write
            STATUS current
            DESCRIPTION
                "This field indicates what are the MU connection capabilities.
                bit 0 :  If this bit is set, the client is capable to tx/rx on A radio.
                bit 1 :  If this bit is set, the client is capable to tx/rx on BG radio.
                bit 2 :  If this bit is set, the client is capable of wpaV1 privacy.
                bit 3 :  If this bit is set, the client is capable of wpaV2 privacy.
                bit 4 :  If this bit is set, the client is capable to comunicate with 1 data stream.
                bit 5 :  If this bit is set, the client is capable to comunicate with 2 data streams.
                bit 6 :  If this bit is set, the client is capable to comunicate with 3 data streams.
                bit 7 :  If this bit is set, the client is capable of Unscheduled automatic power-save delivery (U-APSD) benefits.
                           The voice client can synchronize the transmission and reception of voice frames with the AP.
                bit 8 :  If this bit is set, the client is capable of Unscheduled automatic power-save delivery (U-APSD) benefits.
                           The video client can synchronize the transmission and reception of video frames with the AP.
                bit 9 :  If this bit is set, the client is capable of Unscheduled automatic power-save delivery (U-APSD) benefits.
                           The client can synchronize the transmission and reception in background queue.
                bit 10 :  If this bit is set, the client is capable of Unscheduled automatic power-save delivery (U-APSD) benefits.
                           The client can synchronize the transmission and reception in best effort queue.
                bit 11 :  If this bit is set, the client is capable of Wi-Fi Multimedia(WMM) power save.
                bit 12 :  If this bit is set, the client is capable of 802.11n Greenfield mode.
                bit 13 :  If this bit is set, the client is on fast-transition mode."
            ::= { muEntry 20 }

            

        
        -- 1.3.6.1.4.1.4329.15.3.6.3
        muTSPECTable OBJECT-TYPE
            SYNTAX SEQUENCE OF MuTSPECEntry
            MAX-ACCESS not-accessible
            STATUS current
            DESCRIPTION
                "Table of information for Admission Control Statistics by active client."
            ::= { mobileUnits 3 }

        
        -- 1.3.6.1.4.1.4329.15.3.6.3.1
        muTSPECEntry OBJECT-TYPE
            SYNTAX MuTSPECEntry
            MAX-ACCESS not-accessible
            STATUS current
            DESCRIPTION
                "Information for Admission Control Statistics by active client."
            INDEX { apIndex, muMACAddress, tspecAC, tspecDirection }
            ::= { muTSPECTable 1 }

        
        MuTSPECEntry ::=
            SEQUENCE { 
                tspecMuMACAddress
                    MacAddress,
                tspecAC
                    INTEGER,
                tspecDirection
                    INTEGER,
                tspecApSerialNumber
                    OCTET STRING,
                tspecMuIPAddress
                    IpAddress,
                tspecBssMac
                    MacAddress,
                tspecSsid
                    DisplayString,
                tspecMDR
                    Unsigned32,
                tspecNMS
                    Unsigned32,
                tspecSBA
                    Unsigned32,
                tspecDlRate
                    DisplayString,
                tspecUlRate
                    DisplayString,
                tspecDlViolations
                    DisplayString,
                tspecUlViolations
                    DisplayString,
                tspecProtocol
                    INTEGER
             }

        -- 1.3.6.1.4.1.4329.15.3.6.3.1.1
        tspecMuMACAddress OBJECT-TYPE
            SYNTAX MacAddress
            MAX-ACCESS read-only
            STATUS current
            DESCRIPTION
                "Client MAC address."
            ::= { muTSPECEntry 1 }

        
        -- 1.3.6.1.4.1.4329.15.3.6.3.1.2
        tspecAC OBJECT-TYPE
            SYNTAX INTEGER
                {
                be(0),
                bk(1),
                vi(2),
                vo(3),
                tvo(4),
                nwme(5)
                }
            MAX-ACCESS read-only
            STATUS current
            DESCRIPTION
                "Access Category, such as Best Effort, Background, Voice, Video, 
                and Reserved."
            ::= { muTSPECEntry 2 }

        
        -- 1.3.6.1.4.1.4329.15.3.6.3.1.3
        tspecDirection OBJECT-TYPE
            SYNTAX INTEGER
                {
                uplink(0),
                dnlink(1),
                reserved(2),
                bidir(3)
                }
            MAX-ACCESS read-only
            STATUS current
            DESCRIPTION
                "Traffic direction, such as uplink direction, downlink direction."
            ::= { muTSPECEntry 3 }

        
        -- 1.3.6.1.4.1.4329.15.3.6.3.1.4
        tspecApSerialNumber OBJECT-TYPE
            SYNTAX OCTET STRING
            MAX-ACCESS read-only
            STATUS current
            DESCRIPTION
                "16-character serial number of the AccessPoint."
            ::= { muTSPECEntry 4 }

        
        -- 1.3.6.1.4.1.4329.15.3.6.3.1.5
        tspecMuIPAddress OBJECT-TYPE
            SYNTAX IpAddress
            MAX-ACCESS read-only
            STATUS current
            DESCRIPTION
                "Client IP Address."
            ::= { muTSPECEntry 5 }

        
        -- 1.3.6.1.4.1.4329.15.3.6.3.1.6
        tspecBssMac OBJECT-TYPE
            SYNTAX MacAddress
            MAX-ACCESS read-only
            STATUS current
            DESCRIPTION
                "Access Point BSSID."
            ::= { muTSPECEntry 6 }

        
        -- 1.3.6.1.4.1.4329.15.3.6.3.1.7
        tspecSsid OBJECT-TYPE
            SYNTAX DisplayString
            MAX-ACCESS read-only
            STATUS current
            DESCRIPTION
                "VNS SSID."
            ::= { muTSPECEntry 7 }

        
        -- 1.3.6.1.4.1.4329.15.3.6.3.1.8
        tspecMDR OBJECT-TYPE
            SYNTAX Unsigned32
            MAX-ACCESS read-only
            STATUS current
            DESCRIPTION
                "Mean Data Rate (bytes per second)."
            ::= { muTSPECEntry 8 }

        
        -- 1.3.6.1.4.1.4329.15.3.6.3.1.9
        tspecNMS OBJECT-TYPE
            SYNTAX Unsigned32
            MAX-ACCESS read-only
            STATUS current
            DESCRIPTION
                "Nominal MSDU size (bytes)."
            ::= { muTSPECEntry 9 }

        
        -- 1.3.6.1.4.1.4329.15.3.6.3.1.10
        tspecSBA OBJECT-TYPE
            SYNTAX Unsigned32
            MAX-ACCESS read-only
            STATUS current
            DESCRIPTION
                "Surplus Bandwidth Allowance."
            ::= { muTSPECEntry 10 }

        
        -- 1.3.6.1.4.1.4329.15.3.6.3.1.11
        tspecDlRate OBJECT-TYPE
            SYNTAX DisplayString
            MAX-ACCESS read-only
            STATUS current
            DESCRIPTION
                "Downlink Rate (bytes per second)."
            ::= { muTSPECEntry 11 }

        
        -- 1.3.6.1.4.1.4329.15.3.6.3.1.12
        tspecUlRate OBJECT-TYPE
            SYNTAX DisplayString
            MAX-ACCESS read-only
            STATUS current
            DESCRIPTION
                "Uplink Rate (bytes per second)."
            ::= { muTSPECEntry 12 }

        
        -- 1.3.6.1.4.1.4329.15.3.6.3.1.13
        tspecDlViolations OBJECT-TYPE
            SYNTAX DisplayString
            MAX-ACCESS read-only
            STATUS current
            DESCRIPTION
                "Downlink Violations (bytes per second)."
            ::= { muTSPECEntry 13 }

        
        -- 1.3.6.1.4.1.4329.15.3.6.3.1.14
        tspecUlViolations OBJECT-TYPE
            SYNTAX DisplayString
            MAX-ACCESS read-only
            STATUS current
            DESCRIPTION
                "Uplink Violations (bytes per second)."
            ::= { muTSPECEntry 14 }

        
        -- 1.3.6.1.4.1.4329.15.3.6.3.1.15
        tspecProtocol OBJECT-TYPE
            SYNTAX INTEGER
                {
                proto80211a(1),
                proto80211g(2),
                proto80211b(3),
                proto80211an(4),
                proto80211bgn(5)
                }
            MAX-ACCESS read-only
            STATUS current
            DESCRIPTION
                "802.11 radio protocol."
            ::= { muTSPECEntry 15 }

        
        -- 1.3.6.1.4.1.4329.15.3.6.4
        muACLType OBJECT-TYPE
            SYNTAX INTEGER
                {
                blacklist(1),
                whitelist(2)
                }
            MAX-ACCESS read-write
            STATUS current
            DESCRIPTION
                "MUs can access EWC by sending association request and providing proper
                credentials. However, EWC allows creation of a master list of a blacklist 
                or a whitelist group to control such access. There can exist only a blacklist
                or a whitelist (mutually exclusive) at any time. The list of MUs belonging 
                to such a list is populated in muACLTable. The muACLTable content can be
                interpreted in conjunction with this field as follows:
                - blacklist(1): MUs listed in muACLTable cannot access EWC resources.
                - whitelist(2): Only MUs listed in muACLTable can access EWC resources."
            DEFVAL { 1 }
            ::= { mobileUnits 4 }

        
        -- 1.3.6.1.4.1.4329.15.3.6.5
        muACLTable OBJECT-TYPE
            SYNTAX SEQUENCE OF MuACLEntry
            MAX-ACCESS not-accessible
            STATUS current
            DESCRIPTION
                "Semantics of this list is directly related to muACLType.
                Access Control List(ACL) is list of MUs and their access rights. An MU can
                either belong to 'Blacklist', in that case its association request is denied, or
                it can belong to 'Whitelist', in that case it is allowed to associate to EWC 
                provided having proper credentials."
            ::= { mobileUnits 5 }

        
        -- 1.3.6.1.4.1.4329.15.3.6.5.1
        muACLEntry OBJECT-TYPE
            SYNTAX MuACLEntry
            MAX-ACCESS not-accessible
            STATUS current
            DESCRIPTION
                "An entry about an MU and its ACL."
            INDEX { muACLMACAddress }
            ::= { muACLTable 1 }

        
        MuACLEntry ::=
            SEQUENCE { 
                muACLMACAddress
                    MacAddress,
                muACLRowStatus
                    RowStatus
             }

        -- 1.3.6.1.4.1.4329.15.3.6.5.1.1
        muACLMACAddress OBJECT-TYPE
            SYNTAX MacAddress
            MAX-ACCESS read-only
            STATUS current
            DESCRIPTION
                "MAC address of MU."
            ::= { muACLEntry 1 }

        
        -- 1.3.6.1.4.1.4329.15.3.6.5.1.2
        muACLRowStatus OBJECT-TYPE
            SYNTAX RowStatus
            MAX-ACCESS read-create
            STATUS current
            DESCRIPTION
                "An MU can either be added or removed to this list, therefore, allowed set values
                for this field are:  createAndGo, destroy."
            ::= { muACLEntry 2 }

        
        -- 1.3.6.1.4.1.4329.15.3.6.6
        muAccessListTable OBJECT-TYPE
            SYNTAX SEQUENCE OF MuAccessListEntry
            MAX-ACCESS not-accessible
            STATUS current
            DESCRIPTION
                "Semantics of this list is directly related to muACLType.
                Access List Control(ACL) list of MUs and their access rights. An MU can
                either belong to 'Blacklist', in that case its association request is denied, or
                it can belong to 'Whitelist', in that case it is allowed to associate to EWC 
                provided having proper credentials."
            ::= { mobileUnits 6 }

        
        -- 1.3.6.1.4.1.4329.15.3.6.6.1
        muAccessListEntry OBJECT-TYPE
            SYNTAX MuAccessListEntry
            MAX-ACCESS not-accessible
            STATUS current
            DESCRIPTION
                "An entry about about an MU and its ACL."
            INDEX { muAccessListMACAddress }
            ::= { muAccessListTable 1 }

        
        MuAccessListEntry ::=
            SEQUENCE { 
                muAccessListMACAddress
                    MacAddress,
                muAccessListBitmaskLength
                    INTEGER,
                muAccessListRowStatus
                    RowStatus
             }

        -- 1.3.6.1.4.1.4329.15.3.6.6.1.1
        muAccessListMACAddress OBJECT-TYPE
            SYNTAX MacAddress
            MAX-ACCESS read-only
            STATUS current
            DESCRIPTION
                "MAC address of MU."
            ::= { muAccessListEntry 1 }

        
        -- 1.3.6.1.4.1.4329.15.3.6.6.1.2
        muAccessListBitmaskLength OBJECT-TYPE
            SYNTAX INTEGER
                {
                bits24(24),
                bits36(36),
                bits48(48)
                }
            MAX-ACCESS read-create
            STATUS current
            DESCRIPTION
                "Length of bitmask associated to the MAC address in the entry."
            ::= { muAccessListEntry 2 }

        
        -- 1.3.6.1.4.1.4329.15.3.6.6.1.3
        muAccessListRowStatus OBJECT-TYPE
            SYNTAX RowStatus
            MAX-ACCESS read-create
            STATUS current
            DESCRIPTION
                "An MU can either be added or removed to this list, therefore, allowed set values
                for this field are:  createAndGo, destroy."
            ::= { muAccessListEntry 3 }



        
        -- 1.3.6.1.4.1.4329.15.3.7
        associations OBJECT IDENTIFIER ::= { hiPathWirelessMgmt 7 }

        
        -- 1.3.6.1.4.1.4329.15.3.7.1
        assocCount OBJECT-TYPE
            SYNTAX Integer32
            MAX-ACCESS read-write
            STATUS current
            DESCRIPTION
                "Total number of current client associations to the access point."
            ::= { associations 1 }

        
        -- 1.3.6.1.4.1.4329.15.3.7.2
        assocTable OBJECT-TYPE
            SYNTAX SEQUENCE OF AssocEntry
            MAX-ACCESS not-accessible
            STATUS current
            DESCRIPTION
                "Table of information about clients associated with the access point."
            ::= { associations 2 }

        
        -- 1.3.6.1.4.1.4329.15.3.7.2.1
        assocEntry OBJECT-TYPE
            SYNTAX AssocEntry
            MAX-ACCESS not-accessible
            STATUS current
            DESCRIPTION
                "Information for a single client in the association table."
            INDEX { assocMUMacAddress, apIndex, assocStartSysUpTime }
            ::= { assocTable 1 }

        
        AssocEntry ::=
            SEQUENCE { 
                assocMUMacAddress
                    MacAddress,
                assocStartSysUpTime
                    TimeTicks,
                assocTxPackets
                    Counter64,
                assocRxPackets
                    Counter64,
                assocTxOctets
                    Counter64,
                assocRxOctets
                    Counter64,
                assocDuration
                    Integer32,
                assocVnsIfIndex
                    InterfaceIndex
             }

        -- 1.3.6.1.4.1.4329.15.3.7.2.1.1
        assocMUMacAddress OBJECT-TYPE
            SYNTAX MacAddress
            MAX-ACCESS read-only
            STATUS current
            DESCRIPTION
                "MAC address of the client."
            ::= { assocEntry 1 }

        
        -- 1.3.6.1.4.1.4329.15.3.7.2.1.2
        assocStartSysUpTime OBJECT-TYPE
            SYNTAX TimeTicks
            MAX-ACCESS read-only
            STATUS current
            DESCRIPTION
                "The system uptime that client became associated with the access point."
            ::= { assocEntry 2 }

        
        -- 1.3.6.1.4.1.4329.15.3.7.2.1.3
        assocTxPackets OBJECT-TYPE
            SYNTAX Counter64
            MAX-ACCESS read-only
            STATUS current
            DESCRIPTION
                "Nubmer of tx packets to the client."
            ::= { assocEntry 3 }

        
        -- 1.3.6.1.4.1.4329.15.3.7.2.1.4
        assocRxPackets OBJECT-TYPE
            SYNTAX Counter64
            MAX-ACCESS read-only
            STATUS current
            DESCRIPTION
                "Number of received packets from the client."
            ::= { assocEntry 4 }

        
        -- 1.3.6.1.4.1.4329.15.3.7.2.1.5
        assocTxOctets OBJECT-TYPE
            SYNTAX Counter64
            MAX-ACCESS read-only
            STATUS current
            DESCRIPTION
                "Number of octets sent to the client."
            ::= { assocEntry 5 }

        
        -- 1.3.6.1.4.1.4329.15.3.7.2.1.6
        assocRxOctets OBJECT-TYPE
            SYNTAX Counter64
            MAX-ACCESS read-only
            STATUS current
            DESCRIPTION
                "Number of octets received from the client."
            ::= { assocEntry 6 }

        
        -- 1.3.6.1.4.1.4329.15.3.7.2.1.7
        assocDuration OBJECT-TYPE
            SYNTAX Integer32
            MAX-ACCESS read-write
            STATUS current
            DESCRIPTION
                "Length of time since last association."
            ::= { assocEntry 7 }

        
        -- 1.3.6.1.4.1.4329.15.3.7.2.1.8
        assocVnsIfIndex OBJECT-TYPE
            SYNTAX InterfaceIndex
            MAX-ACCESS read-only
            STATUS current
            DESCRIPTION
                "Index of VNS to which the MU is associated with."
            ::= { assocEntry 8 }

        
        -- 1.3.6.1.4.1.4329.15.3.8
        protocols OBJECT IDENTIFIER ::= { hiPathWirelessMgmt 8 }

        
        -- 1.3.6.1.4.1.4329.15.3.8.1
        wassp OBJECT IDENTIFIER ::= { protocols 1 }

        
        -- 1.3.6.1.4.1.4329.15.3.9
        logNotifications OBJECT IDENTIFIER ::= { hiPathWirelessMgmt 9 }

        
        -- 1.3.6.1.4.1.4329.15.3.9.1
        logEventSeverityThreshold OBJECT-TYPE
            SYNTAX LogEventSeverity
            MAX-ACCESS read-write
            STATUS current
            DESCRIPTION
                "Specifies the minimum level at which the SNMP agent will 
                send notifications for log events.  I.e., setting this
                value to 'major' will send notifcations for critical and
                major log events.  Setting the threshold to minor will 
                trap critical, major, and minor events."
            ::= { logNotifications 1 }

        
        -- 1.3.6.1.4.1.4329.15.3.9.3
        logEventSeverity OBJECT-TYPE
            SYNTAX LogEventSeverity
            MAX-ACCESS read-only
            STATUS current
            DESCRIPTION
                "Contains the severity of the most recently trapped hiPathWirelessLogAlarm notification."
            ::= { logNotifications 3 }

        
        -- 1.3.6.1.4.1.4329.15.3.9.4
        logEventComponent OBJECT-TYPE
            SYNTAX OCTET STRING
            MAX-ACCESS read-only
            STATUS current
            DESCRIPTION
                "Contains the component which sent the most
                recently trapped hiPathWirelessLogAlarm notification."
            ::= { logNotifications 4 }

        
        -- 1.3.6.1.4.1.4329.15.3.9.5
        logEventDescription OBJECT-TYPE
            SYNTAX OCTET STRING
            MAX-ACCESS read-only
            STATUS current
            DESCRIPTION
                "Contains the description of the most recently trapped 
                hiPathWirelessLogAlarm."
            ::= { logNotifications 5 }

        
        -- 1.3.6.1.4.1.4329.15.3.9.6
        hiPathWirelessLogAlarm NOTIFICATION-TYPE
            OBJECTS { logEventSeverity, logEventComponent, logEventDescription }
            STATUS current
            DESCRIPTION 
                "Components of an alarm."
            ::= { logNotifications 6 }

        
        -- 1.3.6.1.4.1.4329.15.3.10
        sites OBJECT IDENTIFIER ::= { hiPathWirelessMgmt 10 }

        
        -- 1.3.6.1.4.1.4329.15.3.10.1
        siteMaxEntries OBJECT-TYPE
            SYNTAX Unsigned32
            MAX-ACCESS read-only
            STATUS current
            DESCRIPTION
                "The maximum number of entries allowed in the siteTable. This value is platform
                dependent."
            ::= { sites 1 }

        
        -- 1.3.6.1.4.1.4329.15.3.10.2
        siteNumEntries OBJECT-TYPE
            SYNTAX Unsigned32
            MAX-ACCESS read-only
            STATUS current
            DESCRIPTION
                "The current number of entries in the siteTable."
            ::= { sites 2 }

        
        -- 1.3.6.1.4.1.4329.15.3.10.3
        siteTableNextAvailableIndex OBJECT-TYPE
            SYNTAX Unsigned32
            MAX-ACCESS read-only
            STATUS current
            DESCRIPTION
                "This object indicates the numerically lowest available index within this entity,
                which may be used for the value of siteID in the creation of a new entry in the
                siteTable.
                
                An index is considered available if the index value falls within the range of 1
                to siteMaxEntries value and is not being used to index an existing entry in the
                siteTable contained within this entity.
                
                This value should only be considered a guideline for management creation of siteEntries,
                there is no requirement on management to create entries based upon this index value."
            ::= { sites 3 }

        
        -- 1.3.6.1.4.1.4329.15.3.10.4
        siteTable OBJECT-TYPE
            SYNTAX SEQUENCE OF SiteEntry
            MAX-ACCESS not-accessible
            STATUS current
            DESCRIPTION
                "A site is a logical entity that is constituted by collection of APs, CoS rules,
                policies, Radius server, WLAN, etc.  A site is identified by a unique name. "
            ::= { sites 4 }

        
        -- 1.3.6.1.4.1.4329.15.3.10.4.1
        siteEntry OBJECT-TYPE
            SYNTAX SiteEntry
            MAX-ACCESS not-accessible
            STATUS current
            DESCRIPTION
                "Definition of a site."
            INDEX { siteID }
            ::= { siteTable 1 }

        
        SiteEntry ::=
            SEQUENCE { 
                siteID
                    Unsigned32,
                siteRowStatus
                    RowStatus,
                siteName
                    DisplayString,
                siteLocalRadiusAuthentication
                    TruthValue,
                siteDefaultDNSServer
                    DisplayString,
                siteEnableSecureTunnel
                    TruthValue,
                siteEncryptCommAPtoController
                    TruthValue,
                siteEncryptCommBetweenAPs
                    TruthValue,
                siteBandPreferenceEnable
                    INTEGER,
                siteLoadControlEnableR1
                    INTEGER,
                siteLoadControlEnableR2
                    INTEGER,
                siteMaxClientR1
                    Unsigned32,
                siteMaxClientR2
                    Unsigned32,
                siteStrictLimitEnableR1
                    INTEGER,
                siteStrictLimitEnableR2
                    INTEGER,
                siteReplaceStnIDwithSiteName
                    TruthValue
             }

        -- 1.3.6.1.4.1.4329.15.3.10.4.1.1
        siteID OBJECT-TYPE
            SYNTAX Unsigned32
            MAX-ACCESS read-only
            STATUS current
            DESCRIPTION
                "An unique ID, identifying the site in the context of the controller. The site ID
                can be an integer value from 1 to the maximum number of APs supported by the EWC."
            ::= { siteEntry 1 }

        
        -- 1.3.6.1.4.1.4329.15.3.10.4.1.2
        siteRowStatus OBJECT-TYPE
            SYNTAX RowStatus
            MAX-ACCESS read-create
            STATUS current
            DESCRIPTION
                "Row status for the entry."
            ::= { siteEntry 2 }

        
        -- 1.3.6.1.4.1.4329.15.3.10.4.1.3
        siteName OBJECT-TYPE
            SYNTAX DisplayString (SIZE (1..64))
            MAX-ACCESS read-create
            STATUS current
            DESCRIPTION
                "Textual description to identify the site in the context of the controller."
            ::= { siteEntry 3 }

        
        -- 1.3.6.1.4.1.4329.15.3.10.4.1.4
        siteLocalRadiusAuthentication OBJECT-TYPE
            SYNTAX TruthValue
            MAX-ACCESS read-create
            STATUS current
            DESCRIPTION
                "If this value is set to true, then the RADIUS client is on APs, otherwise the
                RADIUS client is on controller."
            ::= { siteEntry 4 }

        
        -- 1.3.6.1.4.1.4329.15.3.10.4.1.5
        siteDefaultDNSServer OBJECT-TYPE
            SYNTAX DisplayString (SIZE (0..64))
            MAX-ACCESS read-create
            STATUS current
            DESCRIPTION
                "If the APs associated to the site uses DHCP, and DHCP server does not assign DNS
                server, then this entry will be used for that purpose. Otherwise, if AP is configured
                with static IP address, then this entry will be used for that purpose."
            ::= { siteEntry 5 }

        
        -- 1.3.6.1.4.1.4329.15.3.10.4.1.6
        siteEnableSecureTunnel OBJECT-TYPE
            SYNTAX TruthValue
            MAX-ACCESS read-create
            STATUS current
            DESCRIPTION
                "If set to true secure communication key sent to APs to be used to encrypt the traffic
                between APs within the site and the traffic between controller and APs. However, the
                encryption itself does not take place unless siteEncryptCommAPtoController and/or 
                siteEncryptCommBetweenAPs set to true."
            ::= { siteEntry 6 }

        
        -- 1.3.6.1.4.1.4329.15.3.10.4.1.7
        siteEncryptCommAPtoController OBJECT-TYPE
            SYNTAX TruthValue
            MAX-ACCESS read-create
            STATUS current
            DESCRIPTION
                "If set to true, communication between APs within the site and the controller are encrypted
                using defined encyption. For details about encryption type, please refer to user manual."
            ::= { siteEntry 7 }

        
        -- 1.3.6.1.4.1.4329.15.3.10.4.1.8
        siteEncryptCommBetweenAPs OBJECT-TYPE
            SYNTAX TruthValue
            MAX-ACCESS read-create
            STATUS current
            DESCRIPTION
                "If set to true, communication between APs within the site are encrypted using defined
                encyption. For details about encryption type, please refer to user manual."
            ::= { siteEntry 8 }

        
        -- 1.3.6.1.4.1.4329.15.3.10.4.1.9
        siteBandPreferenceEnable OBJECT-TYPE
            SYNTAX INTEGER
                {
                disable(0),
                enable(1)
                }
            MAX-ACCESS read-create
            STATUS current
            DESCRIPTION
                "Enabling/disabling band preference for the site and associated APs. By enabling
                band preference 11a-capable clients can be moved to 11a radio and relieve the
                congestion on the 11g radio. Band preference provides radio load balancing between
                11g and 11a radios."
            ::= { siteEntry 9 }

        
        -- 1.3.6.1.4.1.4329.15.3.10.4.1.10
        siteLoadControlEnableR1 OBJECT-TYPE
            SYNTAX INTEGER
                {
                disable(0),
                enable(1)
                }
            MAX-ACCESS read-create
            STATUS current
            DESCRIPTION
                "Enabling/disabling load control for the site for this radio. Load control manages
                the number of clients on the Radio #1 by disallowing additional clients on the radio
                above the configured radio limit."
            ::= { siteEntry 10 }

        
        -- 1.3.6.1.4.1.4329.15.3.10.4.1.11
        siteLoadControlEnableR2 OBJECT-TYPE
            SYNTAX INTEGER
                {
                disable(0),
                enable(1)
                }
            MAX-ACCESS read-create
            STATUS current
            DESCRIPTION
                "Enabling/disabling load control for the site for this radio. Load control manages
                the number of clients on the Radio #2 by disallowing additional clients on the radio
                above the configured radio limit."
            ::= { siteEntry 11 }

        
        -- 1.3.6.1.4.1.4329.15.3.10.4.1.12
        siteMaxClientR1 OBJECT-TYPE
            SYNTAX Unsigned32 (0..99)
            MAX-ACCESS read-create
            STATUS current
            DESCRIPTION
                "Maximum number of clients that are allowed to be associated to this radio (radio #1).
                If the Load Control is not enabled then the maximum for this radio uses default value."
            ::= { siteEntry 12 }

        
        -- 1.3.6.1.4.1.4329.15.3.10.4.1.13
        siteMaxClientR2 OBJECT-TYPE
            SYNTAX Unsigned32 (0..99)
            MAX-ACCESS read-create
            STATUS current
            DESCRIPTION
                "Maximum number of clients that are allowed to be associated to this radio (radio #2).
                If the Load Control is not enabled then the maximum for this radio uses default value."
            ::= { siteEntry 13 }

        
        -- 1.3.6.1.4.1.4329.15.3.10.4.1.14
        siteStrictLimitEnableR1 OBJECT-TYPE
            SYNTAX INTEGER
                {
                disable(0),
                enable(1)
                }
            MAX-ACCESS read-create
            STATUS current
            DESCRIPTION
                "Enabling/disabling strict limit of load control for this radio that is assigned to the
                site. Eanbleing strict limit enforces configured client limit for the radio (radio #1)
                in any circumstances. Otherwise if this field is disabled then the restriction may not
                be enforced in all circumstances."
            ::= { siteEntry 14 }

        
        -- 1.3.6.1.4.1.4329.15.3.10.4.1.15
        siteStrictLimitEnableR2 OBJECT-TYPE
            SYNTAX INTEGER
                {
                disable(0),
                enable(1)
                }
            MAX-ACCESS read-create
            STATUS current
            DESCRIPTION
                "Enabling/disabling strict limit of load control for this radio that is assigned to the
                site. Eanbleing strict limit enforces configured client limit for the radio (radio #2)
                in any circumstances. Otherwise if this field is disabled then the restriction may not
                be enforced in all circumstances."
            ::= { siteEntry 15 }

        
        -- 1.3.6.1.4.1.4329.15.3.10.4.1.16
        siteReplaceStnIDwithSiteName OBJECT-TYPE
            SYNTAX TruthValue
            MAX-ACCESS read-create
            STATUS current
            DESCRIPTION
                "If this value is set to true, then the called station ID will be replaced with the 
                site name."
            ::= { siteEntry 16 }

        
        -- 1.3.6.1.4.1.4329.15.3.10.5
        sitePolicyTable OBJECT-TYPE
            SYNTAX SEQUENCE OF SitePolicyEntry
            MAX-ACCESS not-accessible
            STATUS current
            DESCRIPTION
                "Each site can have zero or more policies assigned to it. All policies associated
                to a site are pushed to the all APs belonging to the site. This table defines the
                assignment of various policies to various sites."
            ::= { sites 5 }

        
        -- 1.3.6.1.4.1.4329.15.3.10.5.1
        sitePolicyEntry OBJECT-TYPE
            SYNTAX SitePolicyEntry
            MAX-ACCESS not-accessible
            STATUS current
            DESCRIPTION
                "An entry defining assignment of a policy, identified by sitePolicyID, to a site,
                identified by siteID."
            INDEX { siteID, sitePolicyID }
            ::= { sitePolicyTable 1 }

        
        SitePolicyEntry ::=
            SEQUENCE { 
                sitePolicyID
                    Unsigned32,
                sitePolicyMember
                    INTEGER
             }

        -- 1.3.6.1.4.1.4329.15.3.10.5.1.1
        sitePolicyID OBJECT-TYPE
            SYNTAX Unsigned32
            MAX-ACCESS not-accessible
            STATUS current
            DESCRIPTION
                "The policy index, as defined ENTERASYS-POLICY-PROFILE-MIB::etsysPolicyProfileIndex."
            ::= { sitePolicyEntry 1 }

        
        -- 1.3.6.1.4.1.4329.15.3.10.5.1.2
        sitePolicyMember OBJECT-TYPE
            SYNTAX INTEGER
                {
                notMember(0),
                isMember(1)
                }
            MAX-ACCESS read-write
            STATUS current
            DESCRIPTION
                "Indicates whether the policy associated with this row is a member of the zone
                identified by zoneID."
            ::= { sitePolicyEntry 2 }

        
        -- 1.3.6.1.4.1.4329.15.3.10.6
        siteCosTable OBJECT-TYPE
            SYNTAX SEQUENCE OF SiteCosEntry
            MAX-ACCESS not-accessible
            STATUS current
            DESCRIPTION
                "Each site can have zero or more CoS assigned to it. All CoS associated to a
                site are pushed to the all APs belonging to the site. This table defines the
                assignment of various CoS to various sites."
            ::= { sites 6 }

        
        -- 1.3.6.1.4.1.4329.15.3.10.6.1
        siteCosEntry OBJECT-TYPE
            SYNTAX SiteCosEntry
            MAX-ACCESS not-accessible
            STATUS current
            DESCRIPTION
                "An entry defining assignment of a CoS, identified by siteCoSID, to a site,
                identified by siteID."
            INDEX { siteID, siteCoSID }
            ::= { siteCosTable 1 }

        
        SiteCosEntry ::=
            SEQUENCE { 
                siteCoSID
                    Unsigned32,
                siteCoSMember
                    INTEGER
             }

        -- 1.3.6.1.4.1.4329.15.3.10.6.1.1
        siteCoSID OBJECT-TYPE
            SYNTAX Unsigned32
            MAX-ACCESS not-accessible
            STATUS current
            DESCRIPTION
                "The CoS index, as defined in ENTERASYS-POLICY-PROFILE-MIB::etsysCosIndex."
            ::= { siteCosEntry 1 }

        
        -- 1.3.6.1.4.1.4329.15.3.10.6.1.2
        siteCoSMember OBJECT-TYPE
            SYNTAX INTEGER
                {
                notMember(0),
                isMember(1)
                }
            MAX-ACCESS read-only
            STATUS current
            DESCRIPTION
                "Indicates whether the CoS associated with this row is a member of the site identified
                by siteID."
            ::= { siteCosEntry 2 }

        
        -- 1.3.6.1.4.1.4329.15.3.10.7
        siteAPTable OBJECT-TYPE
            SYNTAX SEQUENCE OF SiteAPEntry
            MAX-ACCESS not-accessible
            STATUS current
            DESCRIPTION
                "A site can have zero or more Access Points(AP) assigned to it. This table
                defines the assignment of various APs to various sites."
            ::= { sites 7 }

        
        -- 1.3.6.1.4.1.4329.15.3.10.7.1
        siteAPEntry OBJECT-TYPE
            SYNTAX SiteAPEntry
            MAX-ACCESS not-accessible
            STATUS current
            DESCRIPTION
                "An entry defining assignment of an AP, identified by apIndex, to a site,
                identified by siteID."
            INDEX { siteID, apIndex }
            ::= { siteAPTable 1 }

        
        SiteAPEntry ::=
            SEQUENCE { 
                siteAPMember
                    INTEGER
             }

        -- 1.3.6.1.4.1.4329.15.3.10.7.1.1
        siteAPMember OBJECT-TYPE
            SYNTAX INTEGER
                {
                notMember(0),
                isMember(1)
                }
            MAX-ACCESS read-write
            STATUS current
            DESCRIPTION
                "Indicates whether the AP associated with this row is a member of the site
                identified by siteID."
            ::= { siteAPEntry 1 }

        
        -- 1.3.6.1.4.1.4329.15.3.10.8
        siteWlanTable OBJECT-TYPE
            SYNTAX SEQUENCE OF SiteWlanEntry
            MAX-ACCESS not-accessible
            STATUS current
            DESCRIPTION
                "A site can have zero or more WLAN assigned to it. All WLANs that are associated
                with a site are pushed to the all APs belonging to the site. This table defines
                the assignment of various WLANs to various sites."
            ::= { sites 8 }

        
        -- 1.3.6.1.4.1.4329.15.3.10.8.1
        siteWlanEntry OBJECT-TYPE
            SYNTAX SiteWlanEntry
            MAX-ACCESS not-accessible
            STATUS current
            DESCRIPTION
                "An entry defining assignment of a WLAN identified by siteWlanID, to a site,
                identified by siteID."
            INDEX { siteID, wlanID, siteWlanApRadioIndex }
            ::= { siteWlanTable 1 }

        
        SiteWlanEntry ::=
            SEQUENCE { 
                siteWlanApRadioIndex
                    INTEGER,
                siteWlanApRadioAssigned
                    INTEGER
             }

        -- 1.3.6.1.4.1.4329.15.3.10.8.1.1
        siteWlanApRadioIndex OBJECT-TYPE
            SYNTAX INTEGER (1..2)
            MAX-ACCESS not-accessible
            STATUS current
            DESCRIPTION
                "Description."
            ::= { siteWlanEntry 1 }

        
        -- 1.3.6.1.4.1.4329.15.3.10.8.1.2
        siteWlanApRadioAssigned OBJECT-TYPE
            SYNTAX INTEGER
                {
                notAssigned(0),
                assigned(1)
                }
            MAX-ACCESS read-write
            STATUS current
            DESCRIPTION
                "Description."
            ::= { siteWlanEntry 2 }

        
        -- 1.3.6.1.4.1.4329.15.3.11
        widsWips OBJECT IDENTIFIER ::= { hiPathWirelessMgmt 11 }

        
        -- 1.3.6.1.4.1.4329.15.3.11.1
        mitigatorAnalysisEngine OBJECT-TYPE
            SYNTAX INTEGER
                {
                disable(0),
                enable(1)
                }
            MAX-ACCESS read-write
            STATUS current
            DESCRIPTION
                "Mitigator analysis engine can be enabled/disabled using this variable.
                All mitigator related objects, objects defined in widsWips subtree, can
                only be accessed using SNMPv3 provided this variable is set to enable(1) 
                on behalf of users with privacy."
            ::= { widsWips 1 }

        
        -- 1.3.6.1.4.1.4329.15.3.11.2
        scanGroupMaxEntries OBJECT-TYPE
            SYNTAX Unsigned32
            MAX-ACCESS read-only
            STATUS current
            DESCRIPTION
                "Maximum number of scan groups that can be created on the device."
            ::= { widsWips 2 }

        
        -- 1.3.6.1.4.1.4329.15.3.11.3
        scanGroupsCurrentEntries OBJECT-TYPE
            SYNTAX Unsigned32
            MAX-ACCESS read-only
            STATUS current
            DESCRIPTION
                "Number of scan groups currently have been created on the device."
            ::= { widsWips 3 }

        
        -- 1.3.6.1.4.1.4329.15.3.11.4
        activeThreatsCounts OBJECT-TYPE
            SYNTAX Unsigned32
            MAX-ACCESS read-only
            STATUS current
            DESCRIPTION
                "Number of currently active threats that have been detected."
            ::= { widsWips 4 }

        
        -- 1.3.6.1.4.1.4329.15.3.11.5
        friendlyAPCounts OBJECT-TYPE
            SYNTAX Unsigned32
            MAX-ACCESS read-only
            STATUS current
            DESCRIPTION
                "Number of friendly access points that have been discovered at this point."
            ::= { widsWips 5 }

        
        -- 1.3.6.1.4.1.4329.15.3.11.6
        uncategorizedAPCounts OBJECT-TYPE
            SYNTAX Unsigned32
            MAX-ACCESS read-only
            STATUS current
            DESCRIPTION
                "Number of uncategorized access points that have been discovered. This value
                refers to current number not the historical value."
            ::= { widsWips 6 }

        
        -- 1.3.6.1.4.1.4329.15.3.11.11
        widsWipsEngineTable OBJECT-TYPE
            SYNTAX SEQUENCE OF WidsWipsEngineEntry
            MAX-ACCESS not-accessible
            STATUS current
            DESCRIPTION
                "Table of Mitigators defined on set of controllers each identified by
                widsWipsEngineControllerIPAddress. "
            ::= { widsWips 11 }

        
        -- 1.3.6.1.4.1.4329.15.3.11.11.1
        widsWipsEngineEntry OBJECT-TYPE
            SYNTAX WidsWipsEngineEntry
            MAX-ACCESS not-accessible
            STATUS current
            DESCRIPTION
                "One entry in this table identifying a mitigator engine in a defined
                controller identified by IP address, widsWipsEngineControllerIPAddress."
            INDEX { widsWipsEngineControllerIPAddress }
            ::= { widsWipsEngineTable 1 }

        
        WidsWipsEngineEntry ::=
            SEQUENCE { 
                widsWipsEngineRowStatus
                    RowStatus,
                widsWipsEngineControllerIPAddress
                    IpAddress,
                widsWipsEnginePollInterval
                    INTEGER,
                widsWipsEnginePollRetry
                    INTEGER
             }

        -- 1.3.6.1.4.1.4329.15.3.11.11.1.1
        widsWipsEngineRowStatus OBJECT-TYPE
            SYNTAX RowStatus
            MAX-ACCESS read-create
            STATUS current
            DESCRIPTION
                "RowStatus for creation/deletion of mitigator engine row."
            ::= { widsWipsEngineEntry 1 }

        
        -- 1.3.6.1.4.1.4329.15.3.11.11.1.2
        widsWipsEngineControllerIPAddress OBJECT-TYPE
            SYNTAX IpAddress
            MAX-ACCESS read-create
            STATUS current
            DESCRIPTION
                "Ip address of the controller that the defined mitigator in this row will
                run on."
            ::= { widsWipsEngineEntry 2 }

        
        -- 1.3.6.1.4.1.4329.15.3.11.11.1.3
        widsWipsEnginePollInterval OBJECT-TYPE
            SYNTAX INTEGER (3..60)
            MAX-ACCESS read-create
            STATUS current
            DESCRIPTION
                "Poll interval in seconds between successive keep alive messages between 
                this controller and the mitigator engine to monitor status of mitigator
                engine. "
            ::= { widsWipsEngineEntry 3 }

        
        -- 1.3.6.1.4.1.4329.15.3.11.11.1.4
        widsWipsEnginePollRetry OBJECT-TYPE
            SYNTAX INTEGER (0..20)
            MAX-ACCESS read-create
            STATUS current
            DESCRIPTION
                "Number of consecutive retries of failed contact to a mitigator agent before
                declaring mitigator engine dead. "
            ::= { widsWipsEngineEntry 4 }

        
        -- 1.3.6.1.4.1.4329.15.3.11.12
        inServiceScanGroupTable OBJECT-TYPE
            SYNTAX SEQUENCE OF InServiceScanGroupEntry
            MAX-ACCESS not-accessible
            STATUS current
            DESCRIPTION
                "In service scan group enables the subsystem simultaneously scan for threats and
                performs wireless bridging based on 37xx-based APs. The threats are discovered
                and identified in the deployment environment and then classified for further
                actions. "
            ::= { widsWips 12 }

        
        -- 1.3.6.1.4.1.4329.15.3.11.12.1
        inServiceScanGroupEntry OBJECT-TYPE
            SYNTAX InServiceScanGroupEntry
            MAX-ACCESS not-accessible
            STATUS current
            DESCRIPTION
                "An entry in this table that defines attributes of a in-service scan group."
            INDEX { scanGroupProfileID }
            ::= { inServiceScanGroupTable 1 }

        
        InServiceScanGroupEntry ::=
            SEQUENCE { 
                scanGroupProfileID
                    Unsigned32,
                inSrvScanGrpName
                    DisplayString,
                inSrvScanGrpSecurityThreats
                    INTEGER,
                inSrvScanGrpMaxConcurrentAttacksPerAP
                    INTEGER,
                inSrvScanGrpCounterMeasuresType
                    BITS,
                inSrvScanGrpScan2400MHzSelection
                    BITS,
                inSrvScanGrpScan5GHzSelection
                    BITS,
                inSrvScanGrpblockAdHocClientsPeriod
                    Integer32,
                inSrvScanGrpClassifySourceIF
                    INTEGER,
                inSrvScanGrpRowStatus
                    RowStatus,
                inSrvScanGrpDetectRogueAP
                    INTEGER,
                inSrvScanGrpListeningPort
                    Integer32
                    
             }

        -- 1.3.6.1.4.1.4329.15.3.11.12.1.1
        scanGroupProfileID OBJECT-TYPE
            SYNTAX Unsigned32
            MAX-ACCESS not-accessible
            STATUS current
            DESCRIPTION
                "A internally unique identifier for a scan group. Each scan group is indexed
                by this value."
            ::= { inServiceScanGroupEntry 1 }

        
        -- 1.3.6.1.4.1.4329.15.3.11.12.1.2
        inSrvScanGrpName OBJECT-TYPE
            SYNTAX DisplayString (SIZE (1..255))
            MAX-ACCESS read-create
            STATUS current
            DESCRIPTION
                "Textual description identifying the scan group."
            ::= { inServiceScanGroupEntry 2 }

        
        -- 1.3.6.1.4.1.4329.15.3.11.12.1.3
        inSrvScanGrpSecurityThreats OBJECT-TYPE
            SYNTAX INTEGER
                {
                disable(0),
                enable(1)
                }
            MAX-ACCESS read-create
            STATUS current
            DESCRIPTION
                "Enable/disable security engine to scan for threats."
            ::= { inServiceScanGroupEntry 3 }

        
        -- 1.3.6.1.4.1.4329.15.3.11.12.1.4
        inSrvScanGrpMaxConcurrentAttacksPerAP OBJECT-TYPE
            SYNTAX INTEGER (0..6)
            MAX-ACCESS read-create
            STATUS current
            DESCRIPTION
                "Max number of concurrent attacks per AP"
            ::= { inServiceScanGroupEntry 4 }

        
        -- 1.3.6.1.4.1.4329.15.3.11.12.1.5
        inSrvScanGrpCounterMeasuresType OBJECT-TYPE
            SYNTAX BITS
                {
                externalHoneypotAPs(0),
                roamingToFriendlyAPs(1),
                internalHoneypotAPs(2),
                spoofedAPs(3),
                dropFloodAttack(4),
                removeDosAttack(5),
                adHocModeDevice(6),
                rogueAP(7)
                
                }
            MAX-ACCESS read-create
            STATUS current
            DESCRIPTION
                "bit 0: Setting this bit prevents authorized stations from roaming to external honeypot APs.
                bit 1: Setting this bit prevents authorized stations from roaming to friendly APs.
                bit 2: Setting this bit prevents any station from using an internal honeypot AP.
                bit 3: Setting this bit prevents any station from using a spoofed AP.
                bit 4: Setting this bit drops frames in a controlled fashion during a flood attack.
                bit 5: Setting this bit removes network access from clients originating DoS attacks.
                bit 6: Setting this bit prevents any station from using an ad hoc mode device.
                bit 7: Setting this bit prevents any station from using a rogue AP."
            ::= { inServiceScanGroupEntry 5 }

        
        -- 1.3.6.1.4.1.4329.15.3.11.12.1.6
        inSrvScanGrpScan2400MHzSelection OBJECT-TYPE
            SYNTAX BITS
                {
                frequency2412MHz(0),
                frequency2417MHz(1),
                frequency2422MHz(2),
                frequency2427MHz(3),
                frequency2432MHz(4),
                frequency2437MHz(5),
                frequency2442MHz(6),
                frequency2447MHz(7),
                frequency2452MHz(8),
                frequency2457MHz(9),
                frequency2462MHz(10),
                frequency2467MHz(11),
                frequency2472MHz(12),
                frequency2484MHz(13)
                }
            MAX-ACCESS read-create
            STATUS current
            DESCRIPTION
                "bit 0: by setting this bit scanning is performed on 2412 MHz frequency channel
                bit 1: by setting this bit scanning is performed on 2417 MHz frequency channel
                bit 2: by setting this bit scanning is performed on 2422 MHz frequency channel
                bit 3: by setting this bit scanning is performed on 2427 MHz frequency channel
                bit 4: by setting this bit scanning is performed on 2432 MHz frequency channel
                bit 5: by setting this bit scanning is performed on 2437 MHz frequency channel
                bit 6: by setting this bit scanning is performed on 2442 MHz frequency channel
                bit 7: by setting this bit scanning is performed on 2447 MHz frequency channel
                bit 8: by setting this bit scanning is performed on 2452 MHz frequency channel
                bit 9: by setting this bit scanning is performed on 2457 MHz frequency channel
                bit 10: by setting this bit scanning is performed on 2462 MHz frequency channel
                bit 11: by setting this bit scanning is performed on 2467 MHz frequency channel
                bit 12: by setting this bit scanning is performed on 2472 MHz frequency channel
                bit 13: by setting this bit scanning is performed on 2484 MHz frequency channel"
            ::= { inServiceScanGroupEntry 6 }

        
        -- 1.3.6.1.4.1.4329.15.3.11.12.1.7
        inSrvScanGrpScan5GHzSelection OBJECT-TYPE
            SYNTAX BITS
                {
                frequency5040MHz(0),
                frequency5060MHz(1),
                frequency5080MHz(2),
                frequency5180MHz(3),
                frequency5200MHz(4),
                frequency5220MHz(5),
                frequency5240MHz(6),
                frequency5260MHz(7),
                frequency5280MHz(8),
                frequency5300MHz(9),
                frequency5320MHz(10),
                frequency5500MHz(11),
                frequency5520MHz(12),
                frequency5540MHz(13),
                frequency5560MHz(14),
                frequency5580MHz(15),
                frequency5600MHz(16),
                frequency5620MHz(17),
                frequency5640MHz(18),
                frequency5660MHz(19),
                frequency5680MHz(20),
                frequency5700MHz(21),
                frequency5745MHz(22),
                frequency5765MHz(23),
                frequency5785MHz(24),
                frequency5805MHz(25),
                frequency5825MHz(26),
                frequency4920MHz(27),
                frequency4940MHz(28),
                frequency4960MHz(29),
                frequency4980MHz(30)
                }
            MAX-ACCESS read-create
            STATUS current
            DESCRIPTION
                "bit 0: by setting this bit scanning is performed on 5040 MHz frequency channel
                bit 1: by setting this bit scanning is performed on 5060 MHz frequency channel
                bit 2: by setting this bit scanning is performed on 5080 MHz frequency channel
                bit 3: by setting this bit scanning is performed on 5180 MHz frequency channel
                bit 4: by setting this bit scanning is performed on 5200 MHz frequency channel
                bit 5: by setting this bit scanning is performed on 5220 MHz frequency channel
                bit 6: by setting this bit scanning is performed on 5240 MHz frequency channel
                bit 7: by setting this bit scanning is performed on 5260 MHz frequency channel
                bit 8: by setting this bit scanning is performed on 5280 MHz frequency channel
                bit 9: by setting this bit scanning is performed on 5300 MHz frequency channel
                bit 10: by setting this bit scanning is performed on 5320 MHz frequency channel
                bit 11: by setting this bit scanning is performed on 5500 MHz frequency channel
                bit 12: by setting this bit scanning is performed on 5520 MHz frequency channel
                bit 13: by setting this bit scanning is performed on 5540 MHz frequency channel
                bit 14: by setting this bit scanning is performed on 5560 MHz frequency channel
                bit 15: by setting this bit scanning is performed on 5580 MHz frequency channel
                bit 16: by setting this bit scanning is performed on 5600 MHz frequency channel
                bit 17: by setting this bit scanning is performed on 5620 MHz frequency channel
                bit 18: by setting this bit scanning is performed on 5640 MHz frequency channel
                bit 19: by setting this bit scanning is performed on 5660 MHz frequency channel
                bit 20: by setting this bit scanning is performed on 5680 MHz frequency channel
                bit 21: by setting this bit scanning is performed on 5700 MHz frequency channel
                bit 22: by setting this bit scanning is performed on 5745 MHz frequency channel
                bit 23: by setting this bit scanning is performed on 5765 MHz frequency channel
                bit 24: by setting this bit scanning is performed on 5785 MHz frequency channel
                bit 25: by setting this bit scanning is performed on 5805 MHz frequency channel
                bit 26: by setting this bit scanning is performed on 5825 MHz frequency channel
                bit 27: by setting this bit scanning is performed on 4920 MHz frequency channel
                bit 28: by setting this bit scanning is performed on 4940 MHz frequency channel
                bit 29: by setting this bit scanning is performed on 4960 MHz frequency channel
                bit 30: by setting this bit scanning is performed on 4980 MHz frequency channel"
            ::= { inServiceScanGroupEntry 7 }

        
        -- 1.3.6.1.4.1.4329.15.3.11.12.1.8
        inSrvScanGrpblockAdHocClientsPeriod OBJECT-TYPE
            SYNTAX Integer32
            MAX-ACCESS read-create
            STATUS current
            DESCRIPTION
                "Number of seconds removing network access to the clients that are in ad hoc mode."
            ::= { inServiceScanGroupEntry 8 }

        
        -- 1.3.6.1.4.1.4329.15.3.11.12.1.9
        inSrvScanGrpClassifySourceIF OBJECT-TYPE
            SYNTAX INTEGER
                {
                disable(0),
                enable(1)
                }
            MAX-ACCESS read-create
            STATUS current
            DESCRIPTION
                "This variable allows to enable/disable classify sources of interference"
            ::= { inServiceScanGroupEntry 9 }

        
        -- 1.3.6.1.4.1.4329.15.3.11.12.1.10
        inSrvScanGrpRowStatus OBJECT-TYPE
            SYNTAX RowStatus
            MAX-ACCESS read-create
            STATUS current
            DESCRIPTION
                "RowStatus field for creation/deletion or changing row status."
            ::= { inServiceScanGroupEntry 10 }

        -- 1.3.6.1.4.1.4329.15.3.11.12.1.11
        inSrvScanGrpDetectRogueAP OBJECT-TYPE
            SYNTAX INTEGER
                {
                disable(0),
                enable(1)
                }
            MAX-ACCESS read-create
            STATUS current
            DESCRIPTION
                "This enables/disables rogue AP detection."
            ::= { inServiceScanGroupEntry 11 }


        -- 1.3.6.1.4.1.4329.15.3.11.12.1.12
        inSrvScanGrpListeningPort OBJECT-TYPE
            SYNTAX Integer32
            MAX-ACCESS read-write
            STATUS current
            DESCRIPTION
                "This OID represents the UDP port number that APs are to listen on while 
                  performing rogue AP detection. It has meaning only when 
                  inSrvScanGrpDetectRogueAP is enabled."
            ::= { inServiceScanGroupEntry 12 }


            

        
        -- 1.3.6.1.4.1.4329.15.3.11.13
        outOfServiceScanGroupTable OBJECT-TYPE
            SYNTAX SEQUENCE OF OutOfServiceScanGroupEntry
            MAX-ACCESS not-accessible
            STATUS current
            DESCRIPTION
                "Out of service scan group is used to collect and classify various wireless
                identifiers that are discovered in the deployment environment. Legacy
                APs (26xx-based, 36xx-based) can participate in this subsystem if they are
                configured for out-of-service scanning. The new APs, based on 37xx
                architecture, can also participate in this subsystem."
            ::= { widsWips 13 }

        
        -- 1.3.6.1.4.1.4329.15.3.11.13.1
        outOfServiceScanGroupEntry OBJECT-TYPE
            SYNTAX OutOfServiceScanGroupEntry
            MAX-ACCESS not-accessible
            STATUS current
            DESCRIPTION
                "An entry in this table that defines attributes of a out-of-service scan group."
            INDEX { scanGroupProfileID }
            ::= { outOfServiceScanGroupTable 1 }

        
        OutOfServiceScanGroupEntry ::=
            SEQUENCE { 
                outOfSrvScanGrpName
                    DisplayString,
                outOfSrvScanGrpRadio
                    INTEGER,
                outOfSrvScanGrpChannelList
                    INTEGER,
                outOfSrvScanGrpScanType
                    INTEGER,
                outOfSrvScanGrpChannelDwellTime
                    INTEGER,
                outOfSrvScanGrpScanTimeInterval
                    INTEGER,
                outOfSrvScanGrpSecurityScan
                    INTEGER,
                outOfSrvScanGrpScanActivity
                    INTEGER,
                outOfSrvScanGrpScanRowStatus
                    Integer32
             }

        -- 1.3.6.1.4.1.4329.15.3.11.13.1.1
        outOfSrvScanGrpName OBJECT-TYPE
            SYNTAX DisplayString (SIZE (1..255))
            MAX-ACCESS read-create
            STATUS current
            DESCRIPTION
                "Human readable textual description identifying scan group."
            ::= { outOfServiceScanGroupEntry 1 }

        
        -- 1.3.6.1.4.1.4329.15.3.11.13.1.2
        outOfSrvScanGrpRadio OBJECT-TYPE
            SYNTAX INTEGER
                {
                radio1(1),
                radio2(2),
                both(3)
                }
            MAX-ACCESS read-create
            STATUS current
            DESCRIPTION
                "Radio selection for the scan group. Selected radio will be used in sacn group."
            ::= { outOfServiceScanGroupEntry 2 }

        
        -- 1.3.6.1.4.1.4329.15.3.11.13.1.3
        outOfSrvScanGrpChannelList OBJECT-TYPE
            SYNTAX INTEGER
                {
                allChannel(0),
                currentChannel(999)
                }
            MAX-ACCESS read-create
            STATUS current
            DESCRIPTION
                "Identifying the channel(s) which will be used for the defined scan group."
            ::= { outOfServiceScanGroupEntry 3 }

        
        -- 1.3.6.1.4.1.4329.15.3.11.13.1.4
        outOfSrvScanGrpScanType OBJECT-TYPE
            SYNTAX INTEGER
                {
                active(0),
                passive(1)
                }
            MAX-ACCESS read-create
            STATUS current
            DESCRIPTION
                "This field allows to select the type of scanning, active/passive, this 
                scan group will be executing."
            ::= { outOfServiceScanGroupEntry 4 }

        
        -- 1.3.6.1.4.1.4329.15.3.11.13.1.5
        outOfSrvScanGrpChannelDwellTime OBJECT-TYPE
            SYNTAX INTEGER (200..500)
            MAX-ACCESS read-create
            STATUS current
            DESCRIPTION
                "Dwell time in mili-second for performing scanning."
            ::= { outOfServiceScanGroupEntry 5 }

        
        -- 1.3.6.1.4.1.4329.15.3.11.13.1.6
        outOfSrvScanGrpScanTimeInterval OBJECT-TYPE
            SYNTAX INTEGER (10..120)
            MAX-ACCESS read-create
            STATUS current
            DESCRIPTION
                "Time interval between two sucssive scanning performed for this scan group."
            ::= { outOfServiceScanGroupEntry 6 }

        
        -- 1.3.6.1.4.1.4329.15.3.11.13.1.7
        outOfSrvScanGrpSecurityScan OBJECT-TYPE
            SYNTAX INTEGER
                {
                disable(0),
                enable(1)
                }
            MAX-ACCESS read-create
            STATUS current
            DESCRIPTION
                "This field allows to enable/disable security Scan."
            ::= { outOfServiceScanGroupEntry 7 }

        
        -- 1.3.6.1.4.1.4329.15.3.11.13.1.8
        outOfSrvScanGrpScanActivity OBJECT-TYPE
            SYNTAX INTEGER
                {
                stop(0),
                start(1)
                }
            MAX-ACCESS read-create
            STATUS current
            DESCRIPTION
                "Scaning can be started or stopped using this field."
            ::= { outOfServiceScanGroupEntry 8 }

        
        -- 1.3.6.1.4.1.4329.15.3.11.13.1.9
        outOfSrvScanGrpScanRowStatus OBJECT-TYPE
            SYNTAX Integer32
            MAX-ACCESS read-create
            STATUS current
            DESCRIPTION
                "RowStatus field for the entry."
            ::= { outOfServiceScanGroupEntry 9 }

        
        -- 1.3.6.1.4.1.4329.15.3.11.14
        scanGroupAPAssignmentTable OBJECT-TYPE
            SYNTAX SEQUENCE OF ScanGroupAPAssignmentEntry
            MAX-ACCESS not-accessible
            STATUS current
            DESCRIPTION
                "The list of APs that have been assigned to a particular scan group, which 
                could include in-service and out-of-service scanning groups."
            ::= { widsWips 14 }

        
        -- 1.3.6.1.4.1.4329.15.3.11.14.1
        scanGroupAPAssignmentEntry OBJECT-TYPE
            SYNTAX ScanGroupAPAssignmentEntry
            MAX-ACCESS not-accessible
            STATUS current
            DESCRIPTION
                "An entry in this table defining an AP assignment to a group, identified by
                scanGroupProfileID."
            INDEX { scanGroupProfileID, scanGroupAPAssignApSerial, widsWipsEngineControllerIPAddress }
            ::= { scanGroupAPAssignmentTable 1 }

        
        ScanGroupAPAssignmentEntry ::=
            SEQUENCE { 
                scanGroupAPAssignApSerial
                    OCTET STRING,
                scanGroupAPAssignGroupName
                    DisplayString,
                scanGroupAPAssignName
                    DisplayString,
                scanGroupAPAssignRadio1
                    INTEGER,
                scanGroupAPAssignRadio2
                    INTEGER,
                scanGroupAPAssignInactiveAP
                    INTEGER,
                scanGroupAPAssignAllowScanning
                    INTEGER,
                scanGroupAPAssignAllowSpectrumAnalysis
                    INTEGER,
                scanGroupAPAssignControllerIPAddress
                    IpAddress,
                scanGroupAPAssignFordwardingService
                        BITS
             }

        -- 1.3.6.1.4.1.4329.15.3.11.14.1.1
        scanGroupAPAssignApSerial OBJECT-TYPE
            SYNTAX OCTET STRING (SIZE (16))
            MAX-ACCESS read-only
            STATUS current
            DESCRIPTION
                "Unique string of characters, a 16-character long, serial number of  an access point."
            ::= { scanGroupAPAssignmentEntry 1 }

        
        -- 1.3.6.1.4.1.4329.15.3.11.14.1.2
        scanGroupAPAssignGroupName OBJECT-TYPE
            SYNTAX DisplayString (SIZE (1..255))
            MAX-ACCESS read-only
            STATUS current
            DESCRIPTION
                "Human readable textual description identifying scan group."
            ::= { scanGroupAPAssignmentEntry 2 }

        
        -- 1.3.6.1.4.1.4329.15.3.11.14.1.3
        scanGroupAPAssignName OBJECT-TYPE
            SYNTAX DisplayString (SIZE (1..255))
            MAX-ACCESS read-only
            STATUS current
            DESCRIPTION
                "Access Point (AP) name associated to this scan group."
            ::= { scanGroupAPAssignmentEntry 3 }

        
        -- 1.3.6.1.4.1.4329.15.3.11.14.1.4
        scanGroupAPAssignRadio1 OBJECT-TYPE
            SYNTAX INTEGER
                {
                off(0),
                b(1),
                g(2),
                bg(3),
                a(4),
                j(8),
                n(16),
                gn(18),
                bgn(19),
                an(20),
                nStrict(32),
                gnStrict(34),
                bgnStrict(35),
                anStrict(36)
                }
            MAX-ACCESS read-write
            STATUS current
            DESCRIPTION
                "This field allows the radio #1 of the AP to be turned on/off. this field has meaning only the AP assigned to  legacy (outOfScan) scan profile"
            ::= { scanGroupAPAssignmentEntry 4 }

        
        -- 1.3.6.1.4.1.4329.15.3.11.14.1.5
        scanGroupAPAssignRadio2 OBJECT-TYPE
            SYNTAX INTEGER
                {
                off(0),
                b(1),
                g(2),
                bg(3),
                a(4),
                j(8),
                n(16),
                gn(18),
                bgn(19),
                an(20),
                nStrict(32),
                gnStrict(34),
                bgnStrict(35),
                anStrict(36)
                
                }
            MAX-ACCESS read-write
            STATUS current
            DESCRIPTION
                "This field allows the radio #2 of the AP to be turned on/off. this field has meaning 
                only the AP assigned to  legacy (outOfScan) scan profile"
            ::= { scanGroupAPAssignmentEntry 5 }

        
        -- 1.3.6.1.4.1.4329.15.3.11.14.1.6
        scanGroupAPAssignInactiveAP OBJECT-TYPE
            SYNTAX INTEGER
                {
                inactive(0),
                active(1)
                }
            MAX-ACCESS read-write
            STATUS current
            DESCRIPTION
                "This field allows to set the AP as active/inactive in scanning activities."
            ::= { scanGroupAPAssignmentEntry 6 }

        
        -- 1.3.6.1.4.1.4329.15.3.11.14.1.7
        scanGroupAPAssignAllowScanning OBJECT-TYPE
            SYNTAX INTEGER
                {
                notAllow(0),
                allow(1)
                }
            MAX-ACCESS read-write
            STATUS current
            DESCRIPTION
                "Setting scanning to active/inactive using this AP."
            ::= { scanGroupAPAssignmentEntry 7 }

        
        -- 1.3.6.1.4.1.4329.15.3.11.14.1.8
        scanGroupAPAssignAllowSpectrumAnalysis OBJECT-TYPE
            SYNTAX INTEGER
                {
                notAllow(0),
                allow(1)
                }
            MAX-ACCESS read-write
            STATUS current
            DESCRIPTION
                "Setting spectrum analysis to active/inactive using this AP."
            ::= { scanGroupAPAssignmentEntry 8 }


        -- 1.3.6.1.4.1.4329.15.3.11.14.1.9
        scanGroupAPAssignControllerIPAddress OBJECT-TYPE
            SYNTAX IpAddress
            MAX-ACCESS read-write
            STATUS current
            DESCRIPTION
                "The IP address of the controller to which the AP is connected currently."
            ::= { scanGroupAPAssignmentEntry 9 }




        -- 1.3.6.1.4.1.4329.15.3.11.14.1.10
        scanGroupAPAssignFordwardingService OBJECT-TYPE
            SYNTAX BITS
                {
                assignedToSite(0),
                assignedToLoadGroup(1),
                assignedToWlanService(2)
                }
            MAX-ACCESS read-only
            STATUS current
            DESCRIPTION
                "This OID lists the types of forwarding services that each Guardian is assigned to. A Guardian 
                  will revert to providing these services when it is removed from the Guardian role. The meanings 
                  of the individual flags are:
                                  bit 0: Set if this AP is a member of a site.
                                  bit 1: Set if this AP is assigned to a load group.
                                  bit 2: Set if this AP is assigned to at least one WLAN service.
                                  This OID is only relevant to APs in the Guardian role."
            ::= { scanGroupAPAssignmentEntry 10 }






            
            

        
        -- 1.3.6.1.4.1.4329.15.3.11.15
        scanAPTable OBJECT-TYPE
            SYNTAX SEQUENCE OF ScanAPEntry
            MAX-ACCESS not-accessible
            STATUS current
            DESCRIPTION
                "Table of sacn APs  on each collector. 
                This table can be viewed only in v3 mode when the mitigator analys engine is enabled."
            ::= { widsWips 15 }

        
        -- 1.3.6.1.4.1.4329.15.3.11.15.1
        scanAPEntry OBJECT-TYPE
            SYNTAX ScanAPEntry
            MAX-ACCESS not-accessible
            STATUS current
            DESCRIPTION
                "An entry in this table identifying one access point."
            INDEX { scanAPControllerIPAddress, scanAPSerialNumber }
            ::= { scanAPTable 1 }

        
        ScanAPEntry ::=
            SEQUENCE { 
                scanAPControllerIPAddress
                    IpAddress,
                scanAPSerialNumber
                    OCTET STRING,
                scanAPAcessPointName
                    DisplayString,
                scanAPRowStatus
                    RowStatus,
                scanAPProfileName
                    DisplayString,
                scanAPProfileType
                    INTEGER

             }

        -- 1.3.6.1.4.1.4329.15.3.11.15.1.1
        scanAPControllerIPAddress OBJECT-TYPE
            SYNTAX IpAddress
            MAX-ACCESS read-only
            STATUS current
            DESCRIPTION
                "IP address of the controller on which the scanning executed."
            ::= { scanAPEntry 1 }

        
        -- 1.3.6.1.4.1.4329.15.3.11.15.1.2
        scanAPSerialNumber OBJECT-TYPE
            SYNTAX OCTET STRING (SIZE (16))
            MAX-ACCESS read-only
            STATUS current
            DESCRIPTION
                "Serial number of the access point, 16-character human readable text, that 
                is assigned to this group."
            ::= { scanAPEntry 2 }

        
        -- 1.3.6.1.4.1.4329.15.3.11.15.1.3
        scanAPAcessPointName OBJECT-TYPE
            SYNTAX DisplayString (SIZE (1..255))
            MAX-ACCESS read-create
            STATUS current
            DESCRIPTION
                "Name of the access point belonging to this group."
            ::= { scanAPEntry 3 }

        
        -- 1.3.6.1.4.1.4329.15.3.11.15.1.4
        scanAPRowStatus OBJECT-TYPE
            SYNTAX RowStatus
            MAX-ACCESS read-create
            STATUS current
            DESCRIPTION
                "Row status for the entry."
            ::= { scanAPEntry 4 }

        -- 1.3.6.1.4.1.4329.15.3.11.15.1.5
        scanAPProfileName OBJECT-TYPE
            SYNTAX DisplayString (SIZE (1..255))
            MAX-ACCESS read-create
            STATUS current
            DESCRIPTION
                "Name of the scan profile to which this access point is assigned."
            ::= { scanAPEntry 5 }


        -- 1.3.6.1.4.1.4329.15.3.11.15.1.6
        scanAPProfileType OBJECT-TYPE
            SYNTAX INTEGER
                {
                inServiceScan(1),
                guardianScan(2),
                outOfServiceScan(3)
                
                }
            MAX-ACCESS read-create
            STATUS current
            DESCRIPTION
                "inServiceScan(1):  access point is performed In service Scan.
                guardianScan(2):  access point is performed Guardian Scan.
                outOfServiceScan(3): access point is performed out of service Scan(Legacy Scan)."
            ::= { scanAPEntry 6 }

            

        
        -- 1.3.6.1.4.1.4329.15.3.11.16
        friendlyAPTable OBJECT-TYPE
            SYNTAX SEQUENCE OF FriendlyAPEntry
            MAX-ACCESS not-accessible
            STATUS current
            DESCRIPTION
                "List of Access Points that have been categorized as not being any threat to 
                the wireless network that is managed by EWC.
                
                This table can be viewed only in v3 mode when the mitigator analys engine is enabled."
            ::= { widsWips 16 }

        
        -- 1.3.6.1.4.1.4329.15.3.11.16.1
        friendlyAPEntry OBJECT-TYPE
            SYNTAX FriendlyAPEntry
            MAX-ACCESS not-accessible
            STATUS current
            DESCRIPTION
                "An entry in this table identifying an access points and some of its attributes."
            INDEX { friendlyAPMacAddress }
            ::= { friendlyAPTable 1 }

        
        FriendlyAPEntry ::=
            SEQUENCE { 
                friendlyAPMacAddress
                    MacAddress,
                friendlyAPSSID
                    DisplayString,
                friendlyAPDescription
                    DisplayString,
                friendlyAPManufacturer
                    DisplayString
             }

        -- 1.3.6.1.4.1.4329.15.3.11.16.1.1
        friendlyAPMacAddress OBJECT-TYPE
            SYNTAX MacAddress
            MAX-ACCESS read-write
            STATUS current
            DESCRIPTION
                "Ethernet MAC address of the access point."
            ::= { friendlyAPEntry 1 }

        
        -- 1.3.6.1.4.1.4329.15.3.11.16.1.2
        friendlyAPSSID OBJECT-TYPE
            SYNTAX DisplayString (SIZE (1..32))
            MAX-ACCESS read-write
            STATUS current
            DESCRIPTION
                "SSID broadcasted by the access point."
            ::= { friendlyAPEntry 2 }

        
        -- 1.3.6.1.4.1.4329.15.3.11.16.1.3
        friendlyAPDescription OBJECT-TYPE
            SYNTAX DisplayString (SIZE (1..255))
            MAX-ACCESS read-write
            STATUS current
            DESCRIPTION
                "Textual description that is used to identify the access point."
            ::= { friendlyAPEntry 3 }

        
        -- 1.3.6.1.4.1.4329.15.3.11.16.1.4
        friendlyAPManufacturer OBJECT-TYPE
            SYNTAX DisplayString (SIZE (1..255))
            MAX-ACCESS read-only
            STATUS current
            DESCRIPTION
                "Textual description identifying the access point manufacturer."
            ::= { friendlyAPEntry 4 }

        
        -- 1.3.6.1.4.1.4329.15.3.11.17
        uncategorizedAPTable OBJECT-TYPE
            SYNTAX SEQUENCE OF UncategorizedAPEntry
            MAX-ACCESS not-accessible
            STATUS current
            DESCRIPTION
                "List of APs that have not been categorized either as friendly, threat or
                authorized."
            ::= { widsWips 17 }

        
        -- 1.3.6.1.4.1.4329.15.3.11.17.1
        uncategorizedAPEntry OBJECT-TYPE
            SYNTAX UncategorizedAPEntry
            MAX-ACCESS not-accessible
            STATUS current
            DESCRIPTION
                "An entry about an AP in this table."
            INDEX { uncategorizedAPMAC }
            ::= { uncategorizedAPTable 1 }

        
        UncategorizedAPEntry ::=
            SEQUENCE { 
                uncategorizedAPMAC
                    MacAddress,
                uncategorizedAPDescption
                    DisplayString,
                uncategorizedAPManufacturer
                    DisplayString,
                uncategorizedAPClassify
                    INTEGER,
                uncategorizedAPSSID
                    DisplayString
                    
             }

        -- 1.3.6.1.4.1.4329.15.3.11.17.1.1
        uncategorizedAPMAC OBJECT-TYPE
            SYNTAX MacAddress
            MAX-ACCESS not-accessible
            STATUS current
            DESCRIPTION
                "MAC address of access point."
            ::= { uncategorizedAPEntry 1 }

        
        -- 1.3.6.1.4.1.4329.15.3.11.17.1.2
        uncategorizedAPDescption OBJECT-TYPE
            SYNTAX DisplayString
            MAX-ACCESS read-only
            STATUS current
            DESCRIPTION
                "Textual description of access point."
            ::= { uncategorizedAPEntry 2 }

        
        -- 1.3.6.1.4.1.4329.15.3.11.17.1.3
        uncategorizedAPManufacturer OBJECT-TYPE
            SYNTAX DisplayString
            MAX-ACCESS read-only
            STATUS current
            DESCRIPTION
                "Access point manufacturer."
            ::= { uncategorizedAPEntry 3 }

        
        -- 1.3.6.1.4.1.4329.15.3.11.17.1.4
        uncategorizedAPClassify OBJECT-TYPE
            SYNTAX INTEGER
                {
                noAction(0),
                clasifyAsAuthorized(1),
                classifyAsFriendlyAP(2),
                clasifyAsThreatForReport(3),
                clasifyAsInternalHoneypotThreat(4),
                clasifyAsExternalHoneypotThreat(5)
                }
            MAX-ACCESS read-write
            STATUS current
            DESCRIPTION
                "By setting this field, access point can be reclassified and moved to 
                different group."
            ::= { uncategorizedAPEntry 4 }


        -- 1.3.6.1.4.1.4329.15.3.11.17.1.5
        uncategorizedAPSSID OBJECT-TYPE
            SYNTAX DisplayString (SIZE (1..32))
            MAX-ACCESS read-only
            STATUS current
            DESCRIPTION
                "SSID broadcasted by the access point."
            ::= { uncategorizedAPEntry 5 }




            

        
        -- 1.3.6.1.4.1.4329.15.3.11.18
        authorizedAPTable OBJECT-TYPE
            SYNTAX SEQUENCE OF AuthorizedAPEntry
            MAX-ACCESS not-accessible
            STATUS current
            DESCRIPTION
                "List of authorized access point."
            ::= { widsWips 18 }

        
        -- 1.3.6.1.4.1.4329.15.3.11.18.1
        authorizedAPEntry OBJECT-TYPE
            SYNTAX AuthorizedAPEntry
            MAX-ACCESS not-accessible
            STATUS current
            DESCRIPTION
                "An entry in this table describing an authorized AP."
            INDEX { authorizedAPMAC }
            ::= { authorizedAPTable 1 }

        
        AuthorizedAPEntry ::=
            SEQUENCE { 
                authorizedAPMAC
                    MacAddress,
                authorizedAPDescription
                    DisplayString,
                authorizedAPManufacturer
                    DisplayString,
                authorizedAPClassify
                    INTEGER,
                authorizedAPRowStatus
                    RowStatus
             }

        -- 1.3.6.1.4.1.4329.15.3.11.18.1.1
        authorizedAPMAC OBJECT-TYPE
            SYNTAX MacAddress
            MAX-ACCESS not-accessible
            STATUS current
            DESCRIPTION
                "MAC address of access point."
            ::= { authorizedAPEntry 1 }

        
        -- 1.3.6.1.4.1.4329.15.3.11.18.1.2
        authorizedAPDescription OBJECT-TYPE
            SYNTAX DisplayString
            MAX-ACCESS read-create
            STATUS current
            DESCRIPTION
                "Discription of the access point."
            ::= { authorizedAPEntry 2 }

        
        -- 1.3.6.1.4.1.4329.15.3.11.18.1.3
        authorizedAPManufacturer OBJECT-TYPE
            SYNTAX DisplayString
            MAX-ACCESS read-create
            STATUS current
            DESCRIPTION
                "Access point's manufacturer. This field is cannot be set and it is deduced
                by MAC addressed."
            ::= { authorizedAPEntry 3 }

        
        -- 1.3.6.1.4.1.4329.15.3.11.18.1.4
        authorizedAPClassify OBJECT-TYPE
            SYNTAX INTEGER
                {
                noAction(0),
                classifyAsFriendlyAP(1)
                }
            MAX-ACCESS read-create
            STATUS current
            DESCRIPTION
                "By setting this field, access point can be reclassified and moved to 
                different group."
            ::= { authorizedAPEntry 4 }

        
        -- 1.3.6.1.4.1.4329.15.3.11.18.1.5
        authorizedAPRowStatus OBJECT-TYPE
            SYNTAX RowStatus
            MAX-ACCESS read-create
            STATUS current
            DESCRIPTION
                "Action permitted are 'delete/add' row."
            ::= { authorizedAPEntry 5 }

        
        -- 1.3.6.1.4.1.4329.15.3.11.19
        prohibitedAPTable OBJECT-TYPE
            SYNTAX SEQUENCE OF ProhibitedAPEntry
            MAX-ACCESS not-accessible
            STATUS current
            DESCRIPTION
                "List of prohibited access points."
            ::= { widsWips 19 }

        
        -- 1.3.6.1.4.1.4329.15.3.11.19.1
        prohibitedAPEntry OBJECT-TYPE
            SYNTAX ProhibitedAPEntry
            MAX-ACCESS not-accessible
            STATUS current
            DESCRIPTION
                "An entry in this table describing an access point."
            INDEX { prohibitedAPMAC }
            ::= { prohibitedAPTable 1 }

        
        ProhibitedAPEntry ::=
            SEQUENCE { 
                prohibitedAPMAC
                    MacAddress,
                prohibitedAPCategory
                    INTEGER,
                prohibitedAPDescription
                    DisplayString,
                prohibitedAPManufacturer
                    DisplayString,
                prohibitedAPClassify
                    INTEGER,
                prohibitedAPRowStatus
                    RowStatus
             }


        -- 1.3.6.1.4.1.4329.15.3.11.19.1.1
        prohibitedAPMAC OBJECT-TYPE
            SYNTAX MacAddress
            MAX-ACCESS not-accessible
            STATUS current
            DESCRIPTION
                "MAC address of access point."
            ::= { prohibitedAPEntry 1 }

        
        -- 1.3.6.1.4.1.4329.15.3.11.19.1.2
        prohibitedAPCategory OBJECT-TYPE
            SYNTAX INTEGER
                {
                notAvailable(0),
                reportPresenceOnly(65529),
                externalHoneyPot(65530),
                internalHoneyPot(65531),
                friendly(65532),
                perauthorized(65533),
                authorized(65534)
                }
            MAX-ACCESS read-create
            STATUS current
            DESCRIPTION
                "The category the access point in this row belongs to."
            ::= { prohibitedAPEntry 2 }

        
        -- 1.3.6.1.4.1.4329.15.3.11.19.1.3
        prohibitedAPDescription OBJECT-TYPE
            SYNTAX DisplayString
            MAX-ACCESS read-create
            STATUS current
            DESCRIPTION
                "Description of the access point."
            ::= { prohibitedAPEntry 3 }

        
        -- 1.3.6.1.4.1.4329.15.3.11.19.1.4
        prohibitedAPManufacturer OBJECT-TYPE
            SYNTAX DisplayString
            MAX-ACCESS read-create
            STATUS current
            DESCRIPTION
                "Access point's manufacturer. This field is cannot be set and it is deduced
                by MAC addressed."
            ::= { prohibitedAPEntry 4 }

        
        -- 1.3.6.1.4.1.4329.15.3.11.19.1.5
        prohibitedAPClassify OBJECT-TYPE
            SYNTAX INTEGER
                {
                classifyAsFriendlyAP(1),
                noAction(2)
                }
            MAX-ACCESS read-create
            STATUS current
            DESCRIPTION
                "By setting this field, access point can be reclassified and moved to 
                different group."
            ::= { prohibitedAPEntry 5 }

        
        -- 1.3.6.1.4.1.4329.15.3.11.19.1.6
        prohibitedAPRowStatus OBJECT-TYPE
            SYNTAX RowStatus
            MAX-ACCESS read-create
            STATUS current
            DESCRIPTION
                "Action permitted are 'delete/add' row."
            ::= { prohibitedAPEntry 6 }



        -- 1.3.6.1.4.1.4329.15.3.11.20
        dedicatedScanGroupTable OBJECT-TYPE
            SYNTAX SEQUENCE OF DedicatedScanGroupEntry
            MAX-ACCESS not-accessible
            STATUS current
            DESCRIPTION
                "dedicated scan group enables the subsystem full time scan for threats based 
                on 37xx-based APs. The threats are discovered and identified in the deployment 
                environment and then classified for further actions. "
            ::= { widsWips 20 }

        
        -- 1.3.6.1.4.1.4329.15.3.11.20.1
        dedicatedScanGroupEntry OBJECT-TYPE
            SYNTAX DedicatedScanGroupEntry
            MAX-ACCESS not-accessible
            STATUS current
            DESCRIPTION
                "An entry in this table that defines attributes of a dedicated scan group."
            INDEX { scanGroupProfileID }
            ::= { dedicatedScanGroupTable 1 }

        
        DedicatedScanGroupEntry ::=
            SEQUENCE { 
                dedicatedScanGrpName
                    DisplayString,
                dedicatedScanGrpSecurityThreats
                    INTEGER,
                dedicatedScanGrpMaxConcurrentAttacksPerAP
                    Integer32,
                dedicatedScanGrpCounterMeasures
                    BITS,
                dedicatedScanGrpScan2400MHzFreq
                    BITS,
                dedicatedScanGrpScan5GHzFreq
                    BITS,
                dedicatedScanGrpBlockAdHocPeriod
                    Integer32,
                dedicatedScanGrpClassifySourceIF
                    INTEGER,
                dedicatedScanGrpRowStatus
                    RowStatus,
                dedicatedScanGrpDetectRogueAP
                    INTEGER,
                dedicatedScanGrpListeningPort  
                    Integer32
             }


        
        -- 1.3.6.1.4.1.4329.15.3.11.20.1.1
        dedicatedScanGrpName OBJECT-TYPE
            SYNTAX DisplayString (SIZE (1..255))
            MAX-ACCESS read-create
            STATUS current
            DESCRIPTION
                "Textual description identifying the scan group."
            ::= { dedicatedScanGroupEntry 1 }

        
        -- 1.3.6.1.4.1.4329.15.3.11.20.1.2
        dedicatedScanGrpSecurityThreats OBJECT-TYPE
            SYNTAX INTEGER
                {
                disable(0),
                enable(1)
                }
            MAX-ACCESS read-create
            STATUS current
            DESCRIPTION
                "Enable/disable security engine to scan for threats."
            ::= { dedicatedScanGroupEntry 2 }

        
        -- 1.3.6.1.4.1.4329.15.3.11.20.1.3
        dedicatedScanGrpMaxConcurrentAttacksPerAP OBJECT-TYPE
            SYNTAX Integer32 (0..6)
            MAX-ACCESS read-create
            STATUS current
            DESCRIPTION
                "Max number of concurrent attacks per AP"
            ::= { dedicatedScanGroupEntry 3 }

        
        -- 1.3.6.1.4.1.4329.15.3.11.20.1.4
        dedicatedScanGrpCounterMeasures OBJECT-TYPE
            SYNTAX BITS
                {
                externalHoneypotAPs(0),
                roamingToFriendlyAPs(1),
                internalHoneypotAPs(2),
                spoofedAPs(3),
                dropFloodAttack(4),
                removeDosAttack(5),
                adHocModeDevice(6),
                rogueAP(7)
                }
            MAX-ACCESS read-create
            STATUS current
            DESCRIPTION
                "bit 0: Setting this bit prevents authorized stations from roaming to external honeypot APs.
                bit 1: Setting this bit prevents authorized stations from roaming to friendly APs.
                bit 2: Setting this bit prevents any station from using an internal honeypot AP.
                bit 3: Setting this bit prevents any station from using a spoofed AP.
                bit 4: Setting this bit drops frames in a controlled fashion during a flood attack.
                bit 5: Setting this bit removes network access from clients originating DoS attacks.
                bit 6: Setting this bit prevents any station from using an ad hoc mode device.
                bit 7: Setting this bit prevents any station from using a rogue AP."
            ::= { dedicatedScanGroupEntry 4 }

        
        -- 1.3.6.1.4.1.4329.15.3.11.20.1.5
        dedicatedScanGrpScan2400MHzFreq OBJECT-TYPE
            SYNTAX BITS
                {
                frequency2412MHz(0),
                frequency2417MHz(1),
                frequency2422MHz(2),
                frequency2427MHz(3),
                frequency2432MHz(4),
                frequency2437MHz(5),
                frequency2442MHz(6),
                frequency2447MHz(7),
                frequency2452MHz(8),
                frequency2457MHz(9),
                frequency2462MHz(10),
                frequency2467MHz(11),
                frequency2472MHz(12),
                frequency2484MHz(13)
                }
            MAX-ACCESS read-create
            STATUS current
            DESCRIPTION
                "bit 0: by setting this bit scanning is performed on 2412 MHz frequency channel
                bit 1: by setting this bit scanning is performed on 2417 MHz frequency channel
                bit 2: by setting this bit scanning is performed on 2422 MHz frequency channel
                bit 3: by setting this bit scanning is performed on 2427 MHz frequency channel
                bit 4: by setting this bit scanning is performed on 2432 MHz frequency channel
                bit 5: by setting this bit scanning is performed on 2437 MHz frequency channel
                bit 6: by setting this bit scanning is performed on 2442 MHz frequency channel
                bit 7: by setting this bit scanning is performed on 2447 MHz frequency channel
                bit 8: by setting this bit scanning is performed on 2452 MHz frequency channel
                bit 9: by setting this bit scanning is performed on 2457 MHz frequency channel
                bit 10: by setting this bit scanning is performed on 2462 MHz frequency channel
                bit 11: by setting this bit scanning is performed on 2467 MHz frequency channel
                bit 12: by setting this bit scanning is performed on 2472 MHz frequency channel
                bit 13: by setting this bit scanning is performed on 2484 MHz frequency channel"
            ::= { dedicatedScanGroupEntry 5 }

        
        -- 1.3.6.1.4.1.4329.15.3.11.20.1.6
        dedicatedScanGrpScan5GHzFreq OBJECT-TYPE
            SYNTAX BITS
                {
                frequency5040MHz(0),
                frequency5060MHz(1),
                frequency5080MHz(2),
                frequency5180MHz(3),
                frequency5200MHz(4),
                frequency5220MHz(5),
                frequency5240MHz(6),
                frequency5260MHz(7),
                frequency5280MHz(8),
                frequency5300MHz(9),
                frequency5320MHz(10),
                frequency5500MHz(11),
                frequency5520MHz(12),
                frequency5540MHz(13),
                frequency5560MHz(14),
                frequency5580MHz(15),
                frequency5600MHz(16),
                frequency5620MHz(17),
                frequency5640MHz(18),
                frequency5660MHz(19),
                frequency5680MHz(20),
                frequency5700MHz(21),
                frequency5745MHz(22),
                frequency5765MHz(23),
                frequency5785MHz(24),
                frequency5805MHz(25),
                frequency5825MHz(26),
                frequency4920MHz(27),
                frequency4940MHz(28),
                frequency4960MHz(29),
                frequency4980MHz(30)
                }
            MAX-ACCESS read-create
            STATUS current
            DESCRIPTION
                "bit 0: by setting this bit scanning is performed on 5040 MHz frequency channel
                bit 1: by setting this bit scanning is performed on 5060 MHz frequency channel
                bit 2: by setting this bit scanning is performed on 5080 MHz frequency channel
                bit 3: by setting this bit scanning is performed on 5180 MHz frequency channel
                bit 4: by setting this bit scanning is performed on 5200 MHz frequency channel
                bit 5: by setting this bit scanning is performed on 5220 MHz frequency channel
                bit 6: by setting this bit scanning is performed on 5240 MHz frequency channel
                bit 7: by setting this bit scanning is performed on 5260 MHz frequency channel
                bit 8: by setting this bit scanning is performed on 5280 MHz frequency channel
                bit 9: by setting this bit scanning is performed on 5300 MHz frequency channel
                bit 10: by setting this bit scanning is performed on 5320 MHz frequency channel
                bit 11: by setting this bit scanning is performed on 5500 MHz frequency channel
                bit 12: by setting this bit scanning is performed on 5520 MHz frequency channel
                bit 13: by setting this bit scanning is performed on 5540 MHz frequency channel
                bit 14: by setting this bit scanning is performed on 5560 MHz frequency channel
                bit 15: by setting this bit scanning is performed on 5580 MHz frequency channel
                bit 16: by setting this bit scanning is performed on 5600 MHz frequency channel
                bit 17: by setting this bit scanning is performed on 5620 MHz frequency channel
                bit 18: by setting this bit scanning is performed on 5640 MHz frequency channel
                bit 19: by setting this bit scanning is performed on 5660 MHz frequency channel
                bit 20: by setting this bit scanning is performed on 5680 MHz frequency channel
                bit 21: by setting this bit scanning is performed on 5700 MHz frequency channel
                bit 22: by setting this bit scanning is performed on 5745 MHz frequency channel
                bit 23: by setting this bit scanning is performed on 5765 MHz frequency channel
                bit 24: by setting this bit scanning is performed on 5785 MHz frequency channel
                bit 25: by setting this bit scanning is performed on 5805 MHz frequency channel
                bit 26: by setting this bit scanning is performed on 5825 MHz frequency channel
                bit 27: by setting this bit scanning is performed on 4920 MHz frequency channel
                bit 28: by setting this bit scanning is performed on 4940 MHz frequency channel
                bit 29: by setting this bit scanning is performed on 4960 MHz frequency channel
                bit 30: by setting this bit scanning is performed on 4980 MHz frequency channel"
            ::= { dedicatedScanGroupEntry 6 }

        
        -- 1.3.6.1.4.1.4329.15.3.11.20.1.7
        dedicatedScanGrpBlockAdHocPeriod OBJECT-TYPE
            SYNTAX Integer32
            MAX-ACCESS read-create
            STATUS current
            DESCRIPTION
                "Number of seconds removing network access to the clients that are in ad hoc mode."
            ::= { dedicatedScanGroupEntry 7 }

        
        -- 1.3.6.1.4.1.4329.15.3.11.20.1.8
        dedicatedScanGrpClassifySourceIF OBJECT-TYPE
            SYNTAX INTEGER
                {
                disable(0),
                enable(1)
                }
            MAX-ACCESS read-create
            STATUS current
            DESCRIPTION
                "This variable allows to enable/disable classify sources of interference"
            ::= { dedicatedScanGroupEntry 8 }

        
        -- 1.3.6.1.4.1.4329.15.3.11.20.1.9
        dedicatedScanGrpRowStatus OBJECT-TYPE
            SYNTAX RowStatus
            MAX-ACCESS read-create
            STATUS current
            DESCRIPTION
                "RowStatus field for creation/deletion or changing row status."
            ::= { dedicatedScanGroupEntry 9 }

        -- 1.3.6.1.4.1.4329.15.3.11.20.1.10
        dedicatedScanGrpDetectRogueAP OBJECT-TYPE
            SYNTAX INTEGER
                {
                disable(0),
                enable(1)
                }
            MAX-ACCESS read-create
            STATUS current
            DESCRIPTION
                "This enables/disables rogue AP detection."
            ::= { dedicatedScanGroupEntry 10 }

        -- 1.3.6.1.4.1.4329.15.3.11.20.1.11
        dedicatedScanGrpListeningPort OBJECT-TYPE
            SYNTAX Integer32
            MAX-ACCESS read-create
            STATUS current
            DESCRIPTION
                "This variable has meaning only when dedicatedScanGrpDetectRogueAP is enabled. 
                The port number is the port for listening for rogue AP detection."
            ::= { dedicatedScanGroupEntry 11 }





        
        -- 1.3.6.1.4.1.4329.15.3.11.30
        widsWipsReport OBJECT IDENTIFIER ::= { widsWips 30 }

        
        -- 1.3.6.1.4.1.4329.15.3.11.30.1
        activeThreatTable OBJECT-TYPE
            SYNTAX SEQUENCE OF ActiveThreatEntry
            MAX-ACCESS not-accessible
            STATUS current
            DESCRIPTION
                "List of active threats that have been discovered to this point of time."
            ::= { widsWipsReport 1 }

        
        -- 1.3.6.1.4.1.4329.15.3.11.30.1.1
        activeThreatEntry OBJECT-TYPE
            SYNTAX ActiveThreatEntry
            MAX-ACCESS not-accessible
            STATUS current
            DESCRIPTION
                "An entry in this table describing an idividual threat charactersitics and
                attributes."
            INDEX { activeThreatIndex }
            ::= { activeThreatTable 1 }

        
        ActiveThreatEntry ::=
            SEQUENCE { 
                activeThreatIndex
                    Unsigned32,
                activeThreatCategory
                    DisplayString,
                activeThreatDeviceMAC
                    MacAddress,
                activeThreatDateTime
                    DisplayString,
                activeThreatCounterMeasure
                    INTEGER,
                activeThreatAPName
                    DisplayString,
                activeThreatRSS
                    DisplayString,
                activeThreatExtraDetails
                    DisplayString,
                activeThreatThreat
                    DisplayString
             }

        -- 1.3.6.1.4.1.4329.15.3.11.30.1.1.1
        activeThreatIndex OBJECT-TYPE
            SYNTAX Unsigned32
            MAX-ACCESS not-accessible
            STATUS current
            DESCRIPTION
                "Internally generated number without any significat meaning except used
                as indexing in this table."
            ::= { activeThreatEntry 1 }

        
        -- 1.3.6.1.4.1.4329.15.3.11.30.1.1.2
        activeThreatCategory OBJECT-TYPE
            SYNTAX DisplayString
            MAX-ACCESS read-only
            STATUS current
            DESCRIPTION
                "Textual description describing the type of the threat."
            ::= { activeThreatEntry 2 }

        
        -- 1.3.6.1.4.1.4329.15.3.11.30.1.1.3
        activeThreatDeviceMAC OBJECT-TYPE
            SYNTAX MacAddress
            MAX-ACCESS read-only
            STATUS current
            DESCRIPTION
                "MAC address of the device that the threat appears to be originated."
            ::= { activeThreatEntry 3 }

        
        -- 1.3.6.1.4.1.4329.15.3.11.30.1.1.4
        activeThreatDateTime OBJECT-TYPE
            SYNTAX DisplayString
            MAX-ACCESS read-only
            STATUS current
            DESCRIPTION
                "Date and time the threat was discovered. "
            ::= { activeThreatEntry 4 }

        
        -- 1.3.6.1.4.1.4329.15.3.11.30.1.1.5
        activeThreatCounterMeasure OBJECT-TYPE
            SYNTAX INTEGER
                {
                noCounterMeasure(0),
                rateLimit(1),
                preventUse(2),
                preventRoaming(4),
                blacklisted(8)
                }
            MAX-ACCESS read-only
            STATUS current
            DESCRIPTION
                "Counter measure has been taken to tackle the threat."
            ::= { activeThreatEntry 5 }

        
        -- 1.3.6.1.4.1.4329.15.3.11.30.1.1.6
        activeThreatAPName OBJECT-TYPE
            SYNTAX DisplayString
            MAX-ACCESS read-only
            STATUS current
            DESCRIPTION
                "Name of the access point."
            ::= { activeThreatEntry 6 }

        
        -- 1.3.6.1.4.1.4329.15.3.11.30.1.1.7
        activeThreatRSS OBJECT-TYPE
            SYNTAX DisplayString
            MAX-ACCESS read-only
            STATUS current
            DESCRIPTION
                "Signal strength of the device considered to be a threat."
            ::= { activeThreatEntry 7 }

        
        -- 1.3.6.1.4.1.4329.15.3.11.30.1.1.8
        activeThreatExtraDetails OBJECT-TYPE
            SYNTAX DisplayString
            MAX-ACCESS read-only
            STATUS current
            DESCRIPTION
                "Extra comments related to the threat."
            ::= { activeThreatEntry 8 }

        
        -- 1.3.6.1.4.1.4329.15.3.11.30.1.1.9
        activeThreatThreat OBJECT-TYPE
            SYNTAX DisplayString
            MAX-ACCESS read-only
            STATUS current
            DESCRIPTION
                "Textual description of the threat."
            ::= { activeThreatEntry 9 }

        
        -- 1.3.6.1.4.1.4329.15.3.11.30.2
        countermeasureAPTable OBJECT-TYPE
            SYNTAX SEQUENCE OF CountermeasureAPEntry
            MAX-ACCESS not-accessible
            STATUS current
            DESCRIPTION
                "List of APs engaged in countermeasure activities to thwart coming threats."
            ::= { widsWipsReport 2 }

        
        -- 1.3.6.1.4.1.4329.15.3.11.30.2.1
        countermeasureAPEntry OBJECT-TYPE
            SYNTAX CountermeasureAPEntry
            MAX-ACCESS not-accessible
            STATUS current
            DESCRIPTION
                "An entry in this table identifying an AP engaged in countermeasure activities."
            INDEX { countermeasureAPSerial, countermeasureAPThreatIndex }
            ::= { countermeasureAPTable 1 }

        
        CountermeasureAPEntry ::=
            SEQUENCE { 
                countermeasureAPThreatIndex
                    Unsigned32,
                countermeasureAPSerial
                    DisplayString,
                countermeasureAPName
                    DisplayString,
                countermeasureAPThreatCategory
                    DisplayString,
                countermeasureAPCountermeasure
                    DisplayString,
                countermeasureAPTime
                    DisplayString
            }

            
        -- 1.3.6.1.4.1.4329.15.3.11.30.2.1.1
        countermeasureAPThreatIndex OBJECT-TYPE
            SYNTAX Unsigned32
            MAX-ACCESS not-accessible
            STATUS current
            DESCRIPTION
                "Internally generated index of the access point taking part in countermeasure."
            ::= { countermeasureAPEntry 1 }

        
        -- 1.3.6.1.4.1.4329.15.3.11.30.2.1.2
        countermeasureAPSerial OBJECT-TYPE
            SYNTAX DisplayString
            MAX-ACCESS read-only
            STATUS current
            DESCRIPTION
                "Serial number of the access point taking part in countermeasure."
            ::= { countermeasureAPEntry 2 }

        
        -- 1.3.6.1.4.1.4329.15.3.11.30.2.1.3
        countermeasureAPName OBJECT-TYPE
            SYNTAX DisplayString
            MAX-ACCESS read-only
            STATUS current
            DESCRIPTION
                "Name of the access point taking part in countermeasure."
            ::= { countermeasureAPEntry 3 }

        
        -- 1.3.6.1.4.1.4329.15.3.11.30.2.1.4
        countermeasureAPThreatCategory OBJECT-TYPE
            SYNTAX DisplayString
            MAX-ACCESS read-only
            STATUS current
            DESCRIPTION
                "Textual description of the threat category that countermeasure action 
                is aimed at."
            ::= { countermeasureAPEntry 4 }

        
        -- 1.3.6.1.4.1.4329.15.3.11.30.2.1.5
        countermeasureAPCountermeasure OBJECT-TYPE
            SYNTAX DisplayString
            MAX-ACCESS read-only
            STATUS current
            DESCRIPTION
                "Countermeasure has been taken to thwart the threat."
            ::= { countermeasureAPEntry 5 }

        
        -- 1.3.6.1.4.1.4329.15.3.11.30.2.1.6
        countermeasureAPTime OBJECT-TYPE
            SYNTAX DisplayString
            MAX-ACCESS read-only
            STATUS current
            DESCRIPTION
                "The time that the countermeasure has started."
            ::= { countermeasureAPEntry 6 }

        
        -- 1.3.6.1.4.1.4329.15.3.11.30.3
        blacklistedClientTable OBJECT-TYPE
            SYNTAX SEQUENCE OF BlacklistedClientEntry
            MAX-ACCESS not-accessible
            STATUS current
            DESCRIPTION
                "List of clients that have been blacklisted due to preceived threats they
                may pose to the safe functioning of the operating network."
            ::= { widsWipsReport 3 }

        
        -- 1.3.6.1.4.1.4329.15.3.11.30.3.1
        blacklistedClientEntry OBJECT-TYPE
            SYNTAX BlacklistedClientEntry
            MAX-ACCESS not-accessible
            STATUS current
            DESCRIPTION
                "An entry in this table pertaining information about the MU that has been
                blacklisted."
            INDEX { blacklistedClientMAC }
            ::= { blacklistedClientTable 1 }

        
        BlacklistedClientEntry ::=
            SEQUENCE { 
                blacklistedClientMAC
                    MacAddress,
                blacklistedClientStatTime
                    DisplayString,
                blacklistedClientEndTime
                    DisplayString,
                blacklistedClientReason
                    DisplayString
             }

        -- 1.3.6.1.4.1.4329.15.3.11.30.3.1.1
        blacklistedClientMAC OBJECT-TYPE
            SYNTAX MacAddress
            MAX-ACCESS read-only
            STATUS current
            DESCRIPTION
                "MAC address of the client."
            ::= { blacklistedClientEntry 1 }

        
        -- 1.3.6.1.4.1.4329.15.3.11.30.3.1.2
        blacklistedClientStatTime OBJECT-TYPE
            SYNTAX DisplayString
            MAX-ACCESS read-only
            STATUS current
            DESCRIPTION
                "The time blacklisting started."
            ::= { blacklistedClientEntry 2 }

        
        -- 1.3.6.1.4.1.4329.15.3.11.30.3.1.3
        blacklistedClientEndTime OBJECT-TYPE
            SYNTAX DisplayString
            MAX-ACCESS read-only
            STATUS current
            DESCRIPTION
                "The time blacklisting ends."
            ::= { blacklistedClientEntry 3 }

        
        -- 1.3.6.1.4.1.4329.15.3.11.30.3.1.4
        blacklistedClientReason OBJECT-TYPE
            SYNTAX DisplayString
            MAX-ACCESS read-only
            STATUS current
            DESCRIPTION
                "Reason for blacklisting the client."
            ::= { blacklistedClientEntry 4 }

        
        -- 1.3.6.1.4.1.4329.15.3.11.30.4
        threatSummaryTable OBJECT-TYPE
            SYNTAX SEQUENCE OF ThreatSummaryEntry
            MAX-ACCESS not-accessible
            STATUS current
            DESCRIPTION
                "Summary of all threats that have been detected in the network by wireless
                controller system."
            ::= { widsWipsReport 4 }

        
        -- 1.3.6.1.4.1.4329.15.3.11.30.4.1
        threatSummaryEntry OBJECT-TYPE
            SYNTAX ThreatSummaryEntry
            MAX-ACCESS not-accessible
            STATUS current
            DESCRIPTION
                "An entry summarizing statistics about a category of a threat."
            INDEX { threatSummaryIndex }
            ::= { threatSummaryTable 1 }

        
        ThreatSummaryEntry ::=
            SEQUENCE { 
                threatSummaryIndex
                    Unsigned32,
                threatSummaryCategory
                    DisplayString,
                threatSummaryActiveThreat
                    Unsigned32,
                threatSummaryHistoricalCounts
                    Unsigned32
             }

        -- 1.3.6.1.4.1.4329.15.3.11.30.4.1.1
        threatSummaryIndex OBJECT-TYPE
            SYNTAX Unsigned32
            MAX-ACCESS not-accessible
            STATUS current
            DESCRIPTION
                "Internally generated index."
            ::= { threatSummaryEntry 1 }

        
        -- 1.3.6.1.4.1.4329.15.3.11.30.4.1.2
        threatSummaryCategory OBJECT-TYPE
            SYNTAX DisplayString
            MAX-ACCESS read-only
            STATUS current
            DESCRIPTION
                "Textul description identifying the category of a threat."
            ::= { threatSummaryEntry 2 }

        
        -- 1.3.6.1.4.1.4329.15.3.11.30.4.1.3
        threatSummaryActiveThreat OBJECT-TYPE
            SYNTAX Unsigned32
            MAX-ACCESS read-only
            STATUS current
            DESCRIPTION
                "Counts of threats that are currently active."
            ::= { threatSummaryEntry 3 }

        
        -- 1.3.6.1.4.1.4329.15.3.11.30.4.1.4
        threatSummaryHistoricalCounts OBJECT-TYPE
            SYNTAX Unsigned32
            MAX-ACCESS read-only
            STATUS current
            DESCRIPTION
                "Historical counts of such threat that were detected in the past by the 
                wireless controller system."
            ::= { threatSummaryEntry 4 }

        
        -- 1.3.6.1.4.1.4329.15.3.19
        apNotifications OBJECT IDENTIFIER ::= { hiPathWirelessMgmt 19 }


        -- 1.3.6.1.4.1.4329.15.3.19.1
        apEventId OBJECT-TYPE
            SYNTAX INTEGER { 
                        apPollTimeout(1),
                        apRegister(2)
                        }
            MAX-ACCESS read-write
            STATUS current
            DESCRIPTION
                "Identifies event associated with AP or AP tunnel:
                apPollTimeout - an event triggered when the AP disconnects from the controller.
                apRegister - an event triggered when the AP connects to the controller."
            ::= { apNotifications 1 }


        -- 1.3.6.1.4.1.4329.15.3.19.2
        apEventDescription OBJECT-TYPE
            SYNTAX OCTET STRING
            MAX-ACCESS read-only
            STATUS current
            DESCRIPTION
                "Contains the description of the most recently triggered event."
            ::= { apNotifications 2 }

        
        -- 1.3.6.1.4.1.4329.15.3.19.3
        apEventAPSerialNumber OBJECT-TYPE
            SYNTAX OCTET STRING (SIZE (16))
            MAX-ACCESS read-only
            STATUS current
            DESCRIPTION
                "16-character serial number of the AP."
            ::= { apNotifications 3 }

        
        -- 1.3.6.1.4.1.4329.15.3.19.4
        apTunnelAlarm NOTIFICATION-TYPE
            OBJECTS { apEventId, apEventDescription, apEventAPSerialNumber }
            STATUS current
            DESCRIPTION 
                "alarm associated with AP and AP interface."
            ::= { apNotifications 4 }



        -- 1.3.6.1.4.1.4329.15.3.20
        stationSessionNotifications    OBJECT IDENTIFIER
            ::=  {  hiPathWirelessMgmt 20  }


        -- 1.3.6.1.4.1.4329.15.3.20.1
        stationEventType    OBJECT-TYPE    
            SYNTAX INTEGER
                {
                registration(0),
                deRegistration(1),
                stateChange(2),
                registrationFailed(3),
                roam(4),
                mbaTimeout(5),
                mbaAccepted(6),
                mbaRejected(7),
                authorizationChanged(8),
                authentication(9),
                authenticationFailed(10),
                locationUpdate(11),
                areaChange(12)
                }
            MAX-ACCESS read-only
            STATUS current
            DESCRIPTION        
                "station event type include:
                registration(0):   MU registration.
                deRegistration(1):  MU de-registration.
                stateChange(2): MU state changed.
                registrationFailed(3):  MU registration failure.
                roam(4):  MU roam.
                mbaTimeout(5):  MU MAC-Based-Authentication time out.
                mbaAccepted(6):  MU MAC-Based-Authentication accepted.
                mbaRejected(7):  MU MAC-Based-Authentication rejected.
                authorizationChanged(8):  MU authorization changed.
                authentication(9): MU authentication.
                authenticationFailed(10): MU authentication failure.
                locationUpdate(11):  MU location updated.
                areaChange(12): MU roamed to other area."
            ::=  {  stationSessionNotifications  1  }


        -- 1.3.6.1.4.1.4329.15.3.20.2
        stationMacAddress    OBJECT-TYPE    
            SYNTAX            MacAddress
            MAX-ACCESS        read-only
            STATUS            current
            DESCRIPTION        
                "MAC address of the station that is the subject of this event report."
            ::=  {  stationSessionNotifications  2  }

        -- 1.3.6.1.4.1.4329.15.3.20.3
        stationIPAddress    OBJECT-TYPE    
            SYNTAX            IpAddress
            MAX-ACCESS        read-only
            STATUS            current
            DESCRIPTION        
                "IP address of the station that is the subject of this event report."
            ::=  {  stationSessionNotifications  3  }


        -- 1.3.6.1.4.1.4329.15.3.20.4
        stationAPName    OBJECT-TYPE    
            SYNTAX            DisplayString
            MAX-ACCESS        read-only
            STATUS            current
            DESCRIPTION        
                "name of the AP  which station associated with"
            ::=  {  stationSessionNotifications  4  }


        -- 1.3.6.1.4.1.4329.15.3.20.5
        stationAPSSID    OBJECT-TYPE    
            SYNTAX            DisplayString
            MAX-ACCESS        read-only
            STATUS            current
            DESCRIPTION        
                "SSID broadcasted by the access point which station connected to"
            ::=  {  stationSessionNotifications  5  }

        -- 1.3.6.1.4.1.4329.15.3.20.6
        stationDetailEvent    OBJECT-TYPE    
            SYNTAX            DisplayString
            MAX-ACCESS        read-only
            STATUS            current
            DESCRIPTION        "detail description of the station event"
            ::=  {  stationSessionNotifications  6  }

        -- 1.3.6.1.4.1.4329.15.3.20.7
        stationRoamedAPName    OBJECT-TYPE    
            SYNTAX            DisplayString
            MAX-ACCESS        read-only
            STATUS            current
            DESCRIPTION        
                "name of the access point which station roamed from"
            ::=  {  stationSessionNotifications  7  }

        -- 1.3.6.1.4.1.4329.15.3.20.8
        stationName    OBJECT-TYPE    
            SYNTAX            DisplayString
            MAX-ACCESS        read-only
            STATUS            current
            DESCRIPTION        
                "name of station"
            ::=  {  stationSessionNotifications  8  }

        -- 1.3.6.1.4.1.4329.15.3.20.9
        stationBSSID    OBJECT-TYPE    
            SYNTAX            DisplayString
            MAX-ACCESS        read-only
            STATUS            current
            DESCRIPTION        
                "the Mac address of the radio which station connect to"
            ::=  {  stationSessionNotifications  9  }

        -- 1.3.6.1.4.1.4329.15.3.20.10
        stationEventTimeStamp    OBJECT-TYPE    
            SYNTAX            TimeTicks
            MAX-ACCESS        read-only
            STATUS            current
            DESCRIPTION        
                "The duration in hundredths of a second from the network agent start time
                to the time of generation of the station event."
            ::=  {  stationSessionNotifications  10  }
            
        -- 1.3.6.1.4.1.4329.15.3.20.11
        stationEventAlarm NOTIFICATION-TYPE
            OBJECTS { stationEventType, stationMacAddress, stationIPAddress, stationAPName,stationAPSSID,
                         stationDetailEvent, stationRoamedAPName, stationName,stationBSSID, stationEventTimeStamp,
                         stationIPv6Address1, stationIPv6Address2, stationIPv6Address3
            }
            STATUS current
            DESCRIPTION 
                "A trap describing a significant event that happened to a station during a session
                on the network. A controller can sees hundreds or even thousands of these events 
                every second."
            ::= { stationSessionNotifications 11 }

        -- 1.3.6.1.4.1.4329.15.3.20.12
        stationIPv6Address1    OBJECT-TYPE    
            SYNTAX            Ipv6Address
            MAX-ACCESS        read-only
            STATUS            current
            DESCRIPTION        
                "One of the IPv6 addresses of the station that is the subject of this event report."
            ::=  {  stationSessionNotifications  12  }

        -- 1.3.6.1.4.1.4329.15.3.20.13
        stationIPv6Address2    OBJECT-TYPE    
            SYNTAX            Ipv6Address
            MAX-ACCESS        read-only
            STATUS            current
            DESCRIPTION        
                "One of the IPv6 addresses of the station that is the subject of this event report."
            ::=  {  stationSessionNotifications  13  }


        -- 1.3.6.1.4.1.4329.15.3.20.14
        stationIPv6Address3    OBJECT-TYPE    
            SYNTAX            Ipv6Address
            MAX-ACCESS        read-only
            STATUS            current
            DESCRIPTION        
                "One of the IPv6 addresses of the station that is the subject of this event report."
            ::=  {  stationSessionNotifications  14  }


        -- 1.3.6.1.4.1.4329.15.3.30
        hiPathWirelessHWCConformance OBJECT IDENTIFIER ::= { hiPathWirelessMgmt 30 }

        
        -- 1.3.6.1.4.1.4329.15.3.30.1
        hiPathWirelessHWCModule MODULE-COMPLIANCE
            STATUS current
            DESCRIPTION 
                "Conformance definition for the EWC MIB."
            MODULE -- this module
                MANDATORY-GROUPS { hiPathWirelessHWCGroup, layerTwoPortGroup, muGroup, apStatsGroup, muACLGroup, 
                    siteGroup, sitePolicyGroup, siteCosGroup, siteAPGroup, siteWlanGroup, 
                    apGroup, wlanGroup, wlanStatsGroup, topologyGroup, topologyStatGroup,
                    loadGroup,  
                    outOfServiceScanGroup, widsWipsEngineGroup, widsWipsObjectsGroup,
                    scanGroupAPAssignmentGroup, inServiceScanGroup, 
                    wlanSecurityReportGroup, friendlyAPGroup, scanAPGroup, 
                     activeThreatGroup, muAccessListGroup, apAntennaGroup,
                    threatSummaryGroup, blaclistedClientGroup, countermeasureAPGroup,
                    apByChannelGroup, stationsByProtocolGroup, licensingInformationGroup ,
                    dedicatedScanGroup, prohibitedAPGroup, authorizedAPGroup, uncategorizedAPGroup,
                    radiusFastFailoverEventsGroup, dhcpRelayListenersGroup,
                    apRadioAntennaGroup, authenticationAdvancedGroup, radiusExtnsSettingGroup
                     }
            ::= { hiPathWirelessHWCConformance 1 }

        
        -- 1.3.6.1.4.1.4329.15.3.30.2
        hiPathWirelessHWCGroup OBJECT-GROUP
            OBJECTS { sysSoftwareVersion, sysCPUType,  sysLogLevel, logEventSeverityThreshold,
                        logEventSeverity, logEventComponent, 
                        apLogCollectionEnable, apLogFrequency, apLogDestination, apLogUserId, 
                        apLogServerIP, apLogDirectory, apLogPassword, apLogFTProtocol, select,
                        apLogQuickSelectedOption,
                        apLogFileCopyDestination, apLogFileCopyProtocol, apLogFileCopyServerIP, apLogFileCopyUserID, 
                        apLogFileCopyPassword, apLogFileCopyServerDirectory, apLogFileCopyOperation, apLogFileCopyOperationStatus,
                        apLogFileCopyRowStatus,  apLogFileUtilityLimit, apLogFileUtilityCurrent,
                        logEventDescription, apEventId, apEventDescription, apEventAPSerialNumber, assocTxPackets, 
                        assocRxPackets, assocTxOctets, assocRxOctets, assocDuration, assocCount, 
                        assocMUMacAddress, assocStartSysUpTime, mobileUnitCount, vnsIfIndex, radioVNSRowStatus, 
                        radioIfIndex, vnsFilterRulePortLow, vnsFilterRulePortHigh, cpURL, vnsDHCPRangeIndex, 
                        vns3rdPartyAP, vnsUseDHCPRelay, vnsMgmtTrafficEnable, vnsAuthModel, physicalPortCount, 
                        mgmtPortIfIndex, mgmtPortHostname, mgmtPortDomain, vnRole, vnIfIndex, 
                        vnHeartbeatInterval, ntpEnabled, ntpTimezone, ntpTimeServer1, ntpTimeServer2, 
                        ntpTimeServer3, tunnelCount, vnsCount, vnsDescription, vnsMUSessionTimeout, 
                        vnsAllowMulticast, vnsSSID, vnsDomain, vnsDNSServers, vnsWINSServers, 
                        vnsStatus, vnsDHCPRangeStart, vnsDHCPRangeEnd, vnsDHCPRangeType, vnsDHCPRangeStatus, 
                        vnsRadiusServerPort, vnsRadiusServerRetries, vnsRadiusServerTimeout, vnsRadiusServerSharedSecret, vnsRadiusServerNASIdentifier, 
                        vnsRadiusServerAuthType, vnsRadiusServerRowStatus, vnsFilterID, vnsFilterIDStatus, vnsFilterRuleOrder, 
                        vnsFilterRuleDirection, vnsFilterRuleAction, vnsFilterRuleIPAddress, vnsFilterRuleProtocol, vnsFilterRuleEtherType, 
                        vnsFilterRuleStatus, vnsPrivWEPKeyType, vnsPrivDynamicRekeyFrequency, vnsPrivWEPKeyLength, vnsPrivWPA1Enabled, 
                        vnsPrivUseSharedKey, vnsPrivWPASharedKey, vnsWEPKeyIndex, vnsWEPKeyValue, activeVNSSessionCount, 
                        apCount, cpReplaceGatewayWithFQDN, cpDefaultRedirectionURL, cpConnectionIP, cpConnectionPort, 
                        cpSharedSecret, cpLogOff, cpStatusCheck, cpType, apMacAddress, 
                        serviceLogFacility, sysLogServerIP, sysLogServerPort, sysLogServerRowStatus, sysLogServerIndex, 
                        apActiveCount, sysLogServerEnabled, assocVnsIfIndex, apRadioFrequency, includeAllServiceMessages, 
                        tunnelStartIP, tunnelStartHWC, tunnelEndIP, tunnelEndHWC, apBroadcastDisassociate, 
                        sysSerialNo, vnsPrivWPA2Enabled, tunnelStatus, hiPathWirelessAppLogFacility, vnsVlanID, 
                        vnsMgmIpAddress, maxVoiceBWforReassociation, maxVoiceBWforAssociation, maxVideoBWforReassociation, maxVideoBWforAssociation, 
                        maxBestEffortBWforReassociation, maxBestEffortBWforAssociation, maxBackgroundBWforReassociation, maxBackgroundBWforAssociation,
                        physicalPortsInternalVlanID, vnsMode, vnsQoSPriorityOverrideFlag, vnsQoSPriorityOverrideSC, vnsQoSPriorityOverrideDSCP, 
                        netflowDestinationIP, netflowInterval, mirrorFirstN, mirrorL2Ports,
                        vnsQoSClassificationServiceClass, vnsQoSWirelessLegacyFlag, vnsQoSWirelessWMMFlag, vnsQoSWireless80211eFlag, vnsQoSWirelessTurboVoiceFlag, 
                        vnsQoSWirelessEnableUAPSD, vnsQoSWirelessUseAdmControlVoice, vnsSuppressSSID, vnsEnable11hSupport, vnsApplyPowerBackOff, 
                        vnsProcessClientIEReq, vnsQoSWirelessUseAdmControlVideo, vnsInterfaceName, vnsQoSWirelessULPolicerAction, vnsQoSWirelessDLPolicerAction, 
                        vnsQoSWirelessUseAdmControlBestEffort, vnsQoSWirelessUseAdmControlBackground,
                        tspecMuMACAddress, tspecAC, tspecDirection, tspecApSerialNumber, tspecMuIPAddress, 
                        tspecBssMac, tspecSsid, tspecMDR, tspecNMS, tspecSBA, 
                        tspecDlRate, tspecUlRate, tspecDlViolations, tspecUlViolations, tspecProtocol, 
                        vnsDLSSupportEnable, vnsDLSAddress, vnsDLSPort, vnsSessionAvailabilityEnable, ntpServerEnabled, 
                        primaryDNS, secondaryDNS, tertiaryDNS, physicalFlash, jumboFrames, vnsRadiusServerName, 
                        vnsRadiusServerNasAddress, dasReplayInterval, dasPort, vnsEnabled, vnsAPFilterRuleOrder, 
                        vnsAPFilterRuleDirection, vnsAPFilterAction, vnsAPFilterIPAddress, vnsAPFilterMask, vnsAPFilterPortLow, 
                        vnsAPFilterPortHigh, vnsAPFilterProtocol, vnsAPFilterEtherType, vnsAPFilterRowStatus, vnsStrictSubnetAdherence, 
                        vnsSLPEnabled, imagePath36xx, imagePath26xx, tftpSever, imageVersionOfap26xx, 
                        imageVersionOfngap36xx, topoExceptionFiterName, topoExceptionStatPktsDenied, topoExceptionStatPktsAllowed, synchronizeSystemConfig, 
                        availabilityStatus, pairIPAddress, hwcAvailabilityRank, fastFailover, synchronizeGuestPort, 
                        tunnelStatsTxBytes, apRegistrationRequests, vnForeignClients, vnLocalClients, apStatsSessionDuration, 
                        detectLinkFailure, apRegUseClusterEncryption, apRegClusterSharedSecret, apRegDiscoveryRetries, apRegDiscoveryInterval, 
                        apRegTelnetPassword, apRegSSHPassword, apRegSecurityMode, vnTotalClients, tunnelStatsRxBytes, 
                        tunnelStatsTxRxBytes, tunnelsTxRxBytes, 
                        clearAccessRejectMsg, armCount, armReplyMessage, 
                        apLinkTimeout, apFastFailoverEnable, topoStatFrameTooLongErrors, 
                        topoStatFrameChkSeqErrors, vnsConfigWLANID, wlanVNSID, wlanPrivPrivacyType, wlanPrivWEPKeyIndex, 
                        wlanPrivWEPKeyLength, wlanPrivWEPKey, wlanPrivWPAv1EncryptionType, wlanPrivWPAv2EncryptionType, wlanPrivKeyManagement, 
                        wlanPrivBroadcastRekeying, wlanPrivRekeyInterval, wlanPrivGroupKPSR, wlanPrivWPAPSK, wlanPrivWPAversion, 
                        wlanPrivfastTransition, wlanPrivManagementFrameProtection, wlanAuthType, 
                        wlanAuthMacBasedAuth, wlanAuthMACBasedAuthOnRoam, wlanAuthAutoAuthAuthorizedUser, wlanAuthAllowUnauthorizedUser, wlanAuthRadiusIncludeAP, 
                        wlanAuthRadiusIncludeVNS, wlanAuthRadiusIncludeSSID, wlanAuthRadiusIncludePolicy, wlanAuthRadiusIncludeTopology, wlanAuthRadiusIncludeIngressRC, 
                        wlanAuthRadiusIncludeEgressRC, wlanAuthCollectAcctInformation, wlanAuthReplaceCalledStationIDWithZone,  wlanAuthRadiusAcctAfterMacBaseAuthorization,
                        wlanAuthRadiusTimeoutRole, wlanAuthRadiusOperatorNameSpace,  wlanAuthRadiusOperatorName, wlanAuthMACBasedAuthReAuthOnAreaRoam,   wlanRadiusName, 
                        wlanRadiusUsage, wlanRadiusPriority, wlanRadiusPort, wlanRadiusRetries, wlanRadiusTimeout, 
                        wlanRadiusNASUseVnsIP, wlanRadiusNASIP, wlanRadiusNASIDUseVNSName, wlanRadiusNASID, wlanRadiusAuthType, 
                        wlanCPAuthType, wlanCP802HttpRedirect, wlanCPExtConnection, wlanCPExtPort, wlanCPExtEnableHttps, 
                        wlanCPExtSharedSecret, wlanCPExtTosOverride, wlanCPExtTosValue, wlanCPGuestAccLifetime, wlanCPGuestSessionLifetime, 
                        loadGrpRadiosRadio1, loadGrpRadiosRadio2, loadGrpWlanAssigned, 
                        schedule, startHour, startMinute, duration, recurrenceDaily, recurrenceWeekly, recurrenceMonthly, apPlatforms,
                        wlanCPIntLogoffButton, wlanCPIntStatusCheckButton, 
                        wlanCPRedirectURL, apRadioProtocol, apRadioNumber, wlanCPReplaceIPwithFQDN, wlanCPSendLoginTo, 
                        wlanCPGuestAllowedLifetimeAcct, wlanCPGuestIDPrefix, wlanCPGuestMinPassLength, wlanCPGuestMaxConcurrentSession, 
                        wlanCPExtAddIPtoURL, wlanCPUseHTTPSforConnection,wlanCPIdentity, wlanCPCustomSpecificURL,
                        wlanCPSelectionOption, 
                        wlanCPExtEncryption, radiusStrictMode, advancedFilteringMode, weakCipherEnable,
                        stationEventType, stationMacAddress, stationIPAddress, stationAPName,
                        stationAPSSID, stationDetailEvent, stationRoamedAPName, stationName,
                        stationBSSID, stationEventTimeStamp, stationIPv6Address1, stationIPv6Address2, stationIPv6Address3,
                        clientAutologinOption, radiusMacAddressFormatOption,
                        wlanRadiusServerName, wlanRadiusServerUse, wlanRadiusServerUsage, 
                        wlanRadiusServerAuthNASIP, wlanRadiusServerAuthNASId, wlanRadiusServerAuthAuthType, wlanRadiusServerAcctNASIP, 
                        wlanRadiusServerAcctNASId,
                        wlanRadiusServerAcctSIAR,  wlanRadiusServerMacNASIP, wlanRadiusServerMacNASId,  wlanRadiusServerMacAuthType,
                        wlanRadiusServerMacPW, wlanRadiusServerAuthUseVNSIPAddr, wlanRadiusServerAuthUseVNSName,
                        wlanRadiusServerAcctUseVNSIPAddr, wlanRadiusServerAcctUseVNSName, 
                        wlanRadiusServerMacUseVNSIPAddr, wlanRadiusServerMacUseVNSName
                    }
            STATUS current
            DESCRIPTION 
                "Conformance groups."
            ::= { hiPathWirelessHWCConformance 2 }

        
        -- 1.3.6.1.4.1.4329.15.3.30.3
        hiPathWirelessHWCAlarms NOTIFICATION-GROUP
            NOTIFICATIONS { hiPathWirelessLogAlarm, stationEventAlarm, apTunnelAlarm }
            STATUS current
            DESCRIPTION 
                "Conformance information for the alarm groups."
            ::= { hiPathWirelessHWCConformance 3 }

        
        -- 1.3.6.1.4.1.4329.15.3.30.4
        hiPathWirelessHWCObsolete OBJECT-GROUP
            OBJECTS { vnsWDSRFAPName, vnsWDSRFbgService, vnsWDSRFaService, vnsWDSRFPreferredParent, vnsWDSRFBackupParent, 
                vnsWDSRFBridge, vnsRateControlProfInd, vnsRateControlProfName, vnsRateControlCIR, vnsRateControlCBS, 
                vnsExceptionFiterName, vnsExceptionStatPktsDenied, vnsExceptionStatPktsAllowed, vnsWDSStatAPName, vnsWDSStatAPRole, 
                vnsWDSStatAPRadio, vnsWDSStatAPParent, vnsWDSStatSSID, vnsWDSStatRxFrame, vnsWDSStatTxFrame, 
                vnsWDSStatRxError, vnsWDSStatTxError, vnsWDSStatRxRSSI, vnsWDSStatRxRate, vnsAssignmentMode, 
                vnsParentIfIndex, externalRadiusServerName, externalRadiusServerAddress, externalRadiusServerSharedSecret, externalRadiusServerRowStatus, 
                cpLoginLabel, cpPasswordLabel, cpHeaderURL, cpFooterURL, cpMessage, 
                cpURL, loadGroupLoadControl, vnsWDSStatTxRate, vnsRateControlProfile, vnsStatName, 
                vnsStatTxPkts, vnsStatRxPkts, vnsStatTxOctects, vnsStatRxOctects, vnsStatMulticastTxPkts, 
                vnsStatMulticastRxPkts, vnsStatBroadcastTxPkts, vnsStatBroadcastRxPkts, vnsStatRadiusTotRequests, vnsStatRadiusReqFailed, 
                vnsStatRadiusReqRejected }
            STATUS obsolete
            DESCRIPTION 
                "List of object that EWC does not anymore support."
            ::= { hiPathWirelessHWCConformance 4 }

        
        -- 1.3.6.1.4.1.4329.15.3.30.5
        wirelessEWCGroups OBJECT IDENTIFIER ::= { hiPathWirelessHWCConformance 5 }

        
        -- 1.3.6.1.4.1.4329.15.3.30.5.1
        physicalPortsGroup OBJECT-GROUP
            OBJECTS { portMgmtTrafficEnable, portDuplexMode, portFunction, portName, portIpAddress, 
                portMask, portVlanID, portDHCPEnable, portDHCPGateway, portDHCPDomain, 
                portDHCPDefaultLease, portDHCPMaxLease, portDHCPDnsServers, portDHCPWins, portEnabled, 
                portMacAddress }
            STATUS deprecated
            DESCRIPTION 
                "Physical ports and their attributes. "
            ::= { wirelessEWCGroups 1 }

        
        -- 1.3.6.1.4.1.4329.15.3.30.5.2
        phyDHCPRangeGroup OBJECT-GROUP
            OBJECTS { phyDHCPRangeIndex, phyDHCPRangeStart, phyDHCPRangeEnd, phyDHCPRangeType, phyDHCPRangeStatus
                 }
            STATUS deprecated
            DESCRIPTION 
                "DHCP objects and attributes associated to physical ports. "
            ::= { wirelessEWCGroups 2 }

        
        -- 1.3.6.1.4.1.4329.15.3.30.5.3
        layerTwoPortGroup OBJECT-GROUP
            OBJECTS { layerTwoPortName, layerTwoPortMacAddress, layerTwoPortMgmtState }
            STATUS current
            DESCRIPTION 
                "Collection of layer two ports objects."
            ::= { wirelessEWCGroups 3 }

        
        -- 1.3.6.1.4.1.4329.15.3.30.5.4
        muGroup OBJECT-GROUP
            OBJECTS { muMACAddress, muIPAddress, muUser, muState, muAPSerialNo, 
                muVnsSSID, muTxPackets, muRxPackets, muTxOctets, muRxOctets, 
                muDuration, muAPName, muWLANID, muConnectionProtocol, muTopologyName, 
                muPolicyName, muDefaultCoS, muConnectionCapability, muBSSIDMac, muDot11ConnectionCapability }
            STATUS current
            DESCRIPTION 
                "MU attributes associated to EWC."
            ::= { wirelessEWCGroups 4 }

        
        -- 1.3.6.1.4.1.4329.15.3.30.5.5
        apStatsGroup OBJECT-GROUP
            OBJECTS { apInUcastPkts, apInNUcastPkts, apInOctets, apInErrors, apInDiscards, 
                        apOutUcastPkts, apOutNUcastPkts, apOutOctets, apOutErrors, apOutDiscards, 
                        apUpTime, apCredentialType, apCertificateExpiry, apStatsMuCounts, 
                        apStatsSessionDuration, 
                        apTotalStationsA, apTotalStationsB, apTotalStationsG, apTotalStationsN50, apTotalStationsN24,
                        apInvalidPolicyCount, apInterfaceMTU, apEffectiveTunnelMTU, apTotalStationsAC,
                        apTotalStationsAInOctets, apTotalStationsAOutOctets, apTotalStationsBInOctets,
                        apTotalStationsBOutOctets, apTotalStationsGInOctets, apTotalStationsGOutOctets,
                        apTotalStationsN50InOctets, apTotalStationsN50OutOctets, apTotalStationsN24InOctets,
                        apTotalStationsN24OutOctets, apTotalStationsACInOctets, apTotalStationsACOutOctets,
                        apRadioStatusChannel, apRadioStatusChannelWidth, apRadioStatusChannelOffset,
                        apPerfRadioPrevPeakChannelUtilization, apPerfRadioCurPeakChannelUtilization, 
                        apPerfRadioAverageChannelUtilization, apPerfRadioCurrentChannelUtilization,
                        apPerfRadioPrevPeakRSS, apPerfRadioCurPeakRSS, apPerfRadioAverageRSS, 
                        apPerfRadioCurrentRSS,  apPerfRadioPrevPeakSNR,  apPerfRadioCurPeakSNR, 
                        apPerfRadioAverageSNR, apPerfRadioCurrentSNR, 
                        apPerfRadioPrevPeakPktRetx, apPerfRadioCurPeakPktRetx, apPerfRadioAveragePktRetx, 
                        apPerfRadioCurrentPktRetx, apPerfRadioPktRetx, apAccPrevPeakAssocReqRx,
                        apAccCurPeakAssocReqRx, apAccAverageAssocReqRx, 
                        apAccCurrentAssocReqRx, apAccAssocReqRx, apAccPrevPeakReassocReqRx,
                        apAccCurPeakReassocReqRx, apAccAverageReassocReqRx, 
                        apAccCurrentReassocReqRx, apAccReassocReqRx, apAccPrevPeakDisassocDeauthReqTx,
                        apAccCurPeakDisassocDeauthReqTx, apAccAverageDisassocDeauthReqTx, 
                        apAccCurrentDisassocDeauthReqTx, apAccDisassocDeauthReqTx, 
                        apAccPrevPeakDisassocDeauthReqRx, apAccCurPeakDisassocDeauthReqRx, 
                        apAccAverageDisassocDeauthReqRx, apAccCurrentDisassocDeauthReqRx, 
                        apAccDisassocDeauthReqRx, apPerfWlanPrevPeakClientsPerSec,
                        apPerfWlanCurPeakClientsPerSec, apPerfWlanAverageClientsPerSec, 
                        apPerfWlanCurrentClientsPerSec, apPerfWlanPrevPeakULOctetsPerSec, 
                        apPerfWlanCurPeakULOctetsPerSec, apPerfWlanAverageULOctetsPerSec, 
                        apPerfWlanCurrentULOctetsPerSec, apPerfWlanULOctets,
                        apPerfWlanPrevPeakULPktsPerSec, apPerfWlanCurPeakULPktsPerSec,
                        apPerfWlanAverageULPktsPerSec, apPerfWlanCurrentULPktsPerSec,
                        apPerfWlanULPkts, apPerfWlanPrevPeakDLOctetsPerSec,  apPerfWlanCurPeakDLOctetsPerSec,
                        apPerfWlanAverageDLOctetsPerSec, apPerfWlanCurrentDLOctetsPerSec, apPerfWlanDLOctets,
                        apPerfWlanPrevPeakDLPktsPerSec, apPerfWlanCurPeakDLPktsPerSec, 
                        apPerfWlanAverageDLPktsPerSec, apPerfWlanCurrentDLPktsPerSec,
                        apPerfWlanDLPkts, apChnlUtilPrevPeakUtilization,
                        apChnlUtilCurPeakUtilization, apChnlUtilAverageUtilization, apChnlUtilCurrentUtilization, 
                        nearbyApInfo, nearbyApBSSID, nearbyApChannel, nearbyApRSS
                 }
            STATUS current
            DESCRIPTION 
                "Collection of objects and attributes related to AP statistics."
            ::= { wirelessEWCGroups 5 }

        
        -- 1.3.6.1.4.1.4329.15.3.30.5.6
        muACLGroup OBJECT-GROUP
            OBJECTS { muACLRowStatus, muACLMACAddress, muACLType }
            STATUS current
            DESCRIPTION 
                "List of objects for creation of blacklist/whitelist."
            ::= { wirelessEWCGroups 6 }

        
        -- 1.3.6.1.4.1.4329.15.3.30.5.7
        siteGroup OBJECT-GROUP
            OBJECTS { siteID, siteName, siteLocalRadiusAuthentication, siteDefaultDNSServer, siteMaxEntries, 
                siteNumEntries, siteTableNextAvailableIndex, siteEnableSecureTunnel, siteReplaceStnIDwithSiteName, siteRowStatus, 
                siteEncryptCommAPtoController, siteEncryptCommBetweenAPs, siteBandPreferenceEnable, siteLoadControlEnableR1, siteLoadControlEnableR2, 
                siteMaxClientR1, siteMaxClientR2, siteStrictLimitEnableR1, siteStrictLimitEnableR2 }
            STATUS current
            DESCRIPTION 
                "A collection of objects providing Site creation and its attributes."
            ::= { wirelessEWCGroups 7 }

        
        -- 1.3.6.1.4.1.4329.15.3.30.5.8
        sitePolicyGroup OBJECT-GROUP
            OBJECTS { sitePolicyMember }
            STATUS current
            DESCRIPTION 
                "Objects defining the association of policies to sites."
            ::= { wirelessEWCGroups 8 }

        
        -- 1.3.6.1.4.1.4329.15.3.30.5.9
        siteCosGroup OBJECT-GROUP
            OBJECTS { siteCoSMember }
            STATUS current
            DESCRIPTION 
                "Objects defining the association of policies to sites."
            ::= { wirelessEWCGroups 9 }

        
        -- 1.3.6.1.4.1.4329.15.3.30.5.10
        siteAPGroup OBJECT-GROUP
            OBJECTS { siteAPMember }
            STATUS current
            DESCRIPTION 
                "Objects defining the association of policies to sites."
            ::= { wirelessEWCGroups 10 }

        
        -- 1.3.6.1.4.1.4329.15.3.30.5.11
        siteWlanGroup OBJECT-GROUP
            OBJECTS { siteWlanApRadioAssigned }
            STATUS current
            DESCRIPTION 
                "Objects defining the association of policies to sites."
            ::= { wirelessEWCGroups 11 }

        
        -- 1.3.6.1.4.1.4329.15.3.30.5.12
        apGroup OBJECT-GROUP
            OBJECTS { apIndex, apName, apDesc, apSerialNumber, apPortifIndex, 
                apWiredIfIndex, apSoftwareVersion, apSpecific, apBroadcastDisassociate, apRowStatus, 
                apVlanID, apIpAssignmentType, apIfMAC, apHwVersion, apSwVersion, 
                apEnvironment, apHome, apRole, apState, apStatus, 
                apPollTimeout, apPollInterval, apTelnetAccess, apMaintainClientSession, apRestartServiceContAbsent, 
                apHostname, apLocation, apStaticMTUsize, apSiteID, apZone, 
                apLLDP,  apLEDMode, apLocationbasedService, apSecureTunnel, 
                apEncryptCntTraffic, apIpAddress, apMICErrorWarning, apIPAddress, apSecureDataTunnelType,
                apIPMulticastAssembly, apSSHConnection}
            STATUS current
            DESCRIPTION 
                "List of objects defining configuration attributes of an AP."
            ::= { wirelessEWCGroups 12 }

        
        -- 1.3.6.1.4.1.4329.15.3.30.5.13
        wlanGroup OBJECT-GROUP
            OBJECTS { wlanID, wlanRowStatus, wlanServiceType, wlanName, wlanSSID, 
                wlanSynchronize, wlanEnabled, wlanDefaultTopologyID, wlanSessionTimeout, wlanIdleTimeoutPreAuth, 
                wlanIdleSessionPostAuth, wlanSupressSSID, wlanDot11hSupport, wlanDot11hClientPowerReduction, wlanProcessClientIE, 
                wlanEngerySaveMode, wlanBlockMuToMuTraffic, wlanRemoteable, wlanVNSID, wlanMaxEntries, 
                wlanRadioManagement11k, wlanBeaconReport, wlanQuietIE, wlanMirrorN, wlanNetFlow, wlanAppVisibility,
                wlanNumEntries, wlanTableNextAvailableIndex }
            STATUS current
            DESCRIPTION 
                "List of objects defining configuration attributes of a WLAN."
            ::= { wirelessEWCGroups 13 }

        
        -- 1.3.6.1.4.1.4329.15.3.30.5.14
        wlanStatsGroup OBJECT-GROUP
            OBJECTS { wlanStatsAssociatedClients, wlanStatsRadiusTotRequests, wlanStatsRadiusReqFailed, wlanStatsRadiusReqRejected, wlanStatsID
                 }
            STATUS current
            DESCRIPTION 
                "List of objects defining configuration attributes of a WLAN."
            ::= { wirelessEWCGroups 14 }

        
        -- 1.3.6.1.4.1.4329.15.3.30.5.15
        topologyGroup OBJECT-GROUP
            OBJECTS { topologyName, topologyMode, topologyTagged, topologyVlanID, topologyEgressPort, 
                topologyLayer3, topologyIPAddress, topologyIPMask, topologyMTUsize, topologyGateway, 
                topologyDHCPUsage, topologyAPRegistration, topologyManagementTraffic, topologySynchronize, topologySyncGateway, 
                topologySyncMask, topologySyncIPStart, topologySyncIPEnd, topologyStaticIPv6Address, topologyLinkLocalIPv6Address, 
                topologyPreFixLength, topologyIPv6Gateway, topologyDynamicEgress , topologyIsGroup, topologyGroupMembers,
                topologyMemberId}
            STATUS current
            DESCRIPTION 
                "List of objects defining configuration attributes of a WLAN."
            ::= { wirelessEWCGroups 15 }

        
        -- 1.3.6.1.4.1.4329.15.3.30.5.16
        topologyStatGroup OBJECT-GROUP
            OBJECTS { topologyName, topoStatName, topoStatTxPkts, topoStatRxPkts, topoStatTxOctets, 
                topoStatRxOctets, topoStatMulticastTxPkts, topoStatMulticastRxPkts, topoStatBroadcastTxPkts, topoStatBroadcastRxPkts, 
                topoStatFrameChkSeqErrors, topoStatFrameTooLongErrors,
                topoWireStatName, topoWireStatTxPkts, topoWireStatRxPkts, topoWireStatTxOctets, 
                topoWireStatRxOctets, topoWireStatMulticastTxPkts, topoWireStatMulticastRxPkts, 
                topoWireStatBroadcastTxPkts, topoWireStatBroadcastRxPkts, 
                topoWireStatFrameChkSeqErrors, topoWireStatFrameTooLongErrors,
                topoCompleteStatName,  topoCompleteStatTxPkts,topoCompleteStatRxPkts, topoCompleteStatTxOctets,
                topoCompleteStatRxOctets, topoCompleteStatMulticastTxPkts, topoCompleteStatMulticastRxPkts,
                topoCompleteStatBroadcastTxPkts, topoCompleteStatBroadcastRxPkts, topoCompleteStatFrameChkSeqErrors,
                topoCompleteStatFrameTooLongErrors
                }
            STATUS current
            DESCRIPTION 
                "List of objects for defining topology statics. "
            ::= { wirelessEWCGroups 16 }

        
        -- 1.3.6.1.4.1.4329.15.3.30.5.17
        loadGroup OBJECT-GROUP
            OBJECTS { loadGroupID, loadGroupName, loadGroupType, loadGroupBandPreference, loadGroupClientCountRadio1, 
                loadGroupClientCountRadio2, loadGroupLoadControlEnableR1, loadGroupLoadControlEnableR2, loadGroupLoadControlStrictLimitR1, loadGroupLoadControlStrictLimitR2
                 }
            STATUS current
            DESCRIPTION 
                "A collection of objects providing Load Group creation and its attributes."
            ::= { wirelessEWCGroups 17 }

        
        -- 1.3.6.1.4.1.4329.15.3.30.5.18
        widsWipsObjectsGroup OBJECT-GROUP
            OBJECTS { mitigatorAnalysisEngine, activeThreatsCounts, uncategorizedAPCounts, friendlyAPCounts, scanGroupMaxEntries, 
                scanGroupsCurrentEntries }
            STATUS current
            DESCRIPTION 
                "Objects defining the state of WIDS-WIPS for the controller."
            ::= { wirelessEWCGroups 18 }

        
        -- 1.3.6.1.4.1.4329.15.3.30.5.19
        widsWipsEngineGroup OBJECT-GROUP
            OBJECTS { widsWipsEngineRowStatus, widsWipsEngineControllerIPAddress, widsWipsEnginePollInterval, widsWipsEnginePollRetry }
            STATUS current
            DESCRIPTION 
                "Set of objects defining attributes of a WIDS-WIPS engine."
            ::= { wirelessEWCGroups 19 }

        
        -- 1.3.6.1.4.1.4329.15.3.30.5.20
        outOfServiceScanGroup OBJECT-GROUP
            OBJECTS { outOfSrvScanGrpName, outOfSrvScanGrpRadio, outOfSrvScanGrpChannelList, outOfSrvScanGrpScanType, outOfSrvScanGrpChannelDwellTime, 
                outOfSrvScanGrpScanTimeInterval, outOfSrvScanGrpSecurityScan, outOfSrvScanGrpScanActivity, outOfSrvScanGrpScanRowStatus }
            STATUS current
            DESCRIPTION 
                "List of objects for defining out-of-service scan group."
            ::= { wirelessEWCGroups 20 }

        
        -- 1.3.6.1.4.1.4329.15.3.30.5.21
        inServiceScanGroup OBJECT-GROUP
            OBJECTS { inSrvScanGrpName, inSrvScanGrpMaxConcurrentAttacksPerAP, inSrvScanGrpCounterMeasuresType, inSrvScanGrpScan2400MHzSelection, inSrvScanGrpScan5GHzSelection, 
                inSrvScanGrpRowStatus, inSrvScanGrpSecurityThreats, inSrvScanGrpblockAdHocClientsPeriod, inSrvScanGrpClassifySourceIF,
                inSrvScanGrpDetectRogueAP, inSrvScanGrpListeningPort}
            STATUS current
            DESCRIPTION 
                "List of objects for defining in-service scan group."
            ::= { wirelessEWCGroups 21 }

        
        -- 1.3.6.1.4.1.4329.15.3.30.5.22
        scanGroupAPAssignmentGroup OBJECT-GROUP
            OBJECTS { scanGroupAPAssignApSerial, scanGroupAPAssignName, scanGroupAPAssignRadio1, scanGroupAPAssignRadio2, scanGroupAPAssignInactiveAP, 
                scanGroupAPAssignAllowScanning,  scanGroupAPAssignGroupName, scanGroupAPAssignAllowSpectrumAnalysis, scanGroupAPAssignControllerIPAddress,
                scanGroupAPAssignFordwardingService
                                }
            STATUS current
            DESCRIPTION 
                "List of objects for assignment of AP to scan group."
            ::= { wirelessEWCGroups 22 }

        
        -- 1.3.6.1.4.1.4329.15.3.30.5.23
        scanAPGroup OBJECT-GROUP
            OBJECTS { scanAPSerialNumber, scanAPControllerIPAddress, scanAPRowStatus, scanAPAcessPointName,scanAPProfileName, scanAPProfileType }
            STATUS current
            DESCRIPTION 
                "List of objects for defining AP scan groups in EWC."
            ::= { wirelessEWCGroups 23 }

        
        -- 1.3.6.1.4.1.4329.15.3.30.5.24
        friendlyAPGroup OBJECT-GROUP
            OBJECTS { friendlyAPMacAddress, friendlyAPSSID, friendlyAPDescription, friendlyAPManufacturer }
            STATUS current
            DESCRIPTION 
                "List of objects defining friendly APs identified during scanning time."
            ::= { wirelessEWCGroups 24 }

        
        -- 1.3.6.1.4.1.4329.15.3.30.5.25
        wlanSecurityReportGroup OBJECT-GROUP
            OBJECTS { wlanSecurityReportFlag, wlanSecurityReportUnsecureType, wlanSecurityReportNotes, wlanUnsecuredWlanCounts }
            STATUS current
            DESCRIPTION 
                "Set of objects defining attributes of security group report."
            ::= { wirelessEWCGroups 25 }

        
        -- 1.3.6.1.4.1.4329.15.3.30.5.26
        apAntennaGroup OBJECT-GROUP
            OBJECTS { apAntennanName, apAntennaType }
            STATUS current
            DESCRIPTION 
                "A collection of objects defining an antenna attributes for an AP."
            ::= { wirelessEWCGroups 26 }

        
        -- 1.3.6.1.4.1.4329.15.3.30.5.27
        muAccessListGroup OBJECT-GROUP
            OBJECTS { muAccessListMACAddress, muAccessListBitmaskLength, muAccessListRowStatus }
            STATUS current
            DESCRIPTION 
                "List of objects for creation of MU access list to block MU access, case of black
                list, or allow access, case of white list to wireless controller resources."
            ::= { wirelessEWCGroups 27 }

        
        -- 1.3.6.1.4.1.4329.15.3.30.5.28
        activeThreatGroup OBJECT-GROUP
            OBJECTS { activeThreatCategory, activeThreatDeviceMAC, activeThreatDateTime, activeThreatCounterMeasure, activeThreatAPName, 
                activeThreatRSS, activeThreatExtraDetails, activeThreatThreat }
            STATUS current
            DESCRIPTION 
                "List of objects defining a discovered security threat."
            ::= { wirelessEWCGroups 28 }

        
        -- 1.3.6.1.4.1.4329.15.3.30.5.29
        countermeasureAPGroup OBJECT-GROUP
            OBJECTS { countermeasureAPName, countermeasureAPThreatCategory, countermeasureAPCountermeasure, countermeasureAPTime, countermeasureAPSerial
                 }
            STATUS current
            DESCRIPTION 
                "List of objects defining APs taking part in countermeasure activities to
                thwart incoming threats."
            ::= { wirelessEWCGroups 29 }

        
        -- 1.3.6.1.4.1.4329.15.3.30.5.30
        blaclistedClientGroup OBJECT-GROUP
            OBJECTS { blacklistedClientMAC, blacklistedClientStatTime, blacklistedClientEndTime, blacklistedClientReason }
            STATUS current
            DESCRIPTION 
                "List of objects identifying blacklisted clients."
            ::= { wirelessEWCGroups 30 }

        
        -- 1.3.6.1.4.1.4329.15.3.30.5.31
        threatSummaryGroup OBJECT-GROUP
            OBJECTS { threatSummaryCategory, threatSummaryActiveThreat, threatSummaryHistoricalCounts }
            STATUS current
            DESCRIPTION 
                "List of objects defining attributes of known discovered threat."
            ::= { wirelessEWCGroups 31 }

        
        -- 1.3.6.1.4.1.4329.15.3.30.5.32
        licensingInformationGroup OBJECT-GROUP
            OBJECTS { licenseRegulatoryDomain, licenseType, licenseDaysRemaining, licenseAvailableAP, licenseInServiceRadarAP,
                                licenseMode, licenseLocalAP, licenseForeignAP, licenseLocalRadarAP, licenseForeignRadarAP
            }
            STATUS current
            DESCRIPTION 
                "List of objects providing licensing information for the controller system."
            ::= { wirelessEWCGroups 32 }

        
        -- 1.3.6.1.4.1.4329.15.3.30.5.33
        stationsByProtocolGroup OBJECT-GROUP
            OBJECTS { stationsByProtocolA, stationsByProtocolB, stationsByProtocolG, stationsByProtocolN24, stationsByProtocolN5,
                                stationsByProtocolUnavailable, stationsByProtocolError, stationsByProtocolAC
                 }
            STATUS current
            DESCRIPTION 
                "List of objects for aggregated MUs on a specific wireless channel."
            ::= { wirelessEWCGroups 33 }

        
        -- 1.3.6.1.4.1.4329.15.3.30.5.34
        apByChannelGroup OBJECT-GROUP
            OBJECTS { apByChannelAPs }
            STATUS current
            DESCRIPTION 
                "List of objects for aggregated access points on a wireless channel."
            ::= { wirelessEWCGroups 34 }

        
        -- 1.3.6.1.4.1.4329.15.3.30.5.35
        uncategorizedAPGroup OBJECT-GROUP
            OBJECTS {  uncategorizedAPDescption, uncategorizedAPManufacturer, uncategorizedAPClassify,uncategorizedAPSSID }
            STATUS current
            DESCRIPTION 
                "Objects defining uncategorized access points discovered by Radar application."
            ::= { wirelessEWCGroups 35 }

        
        -- 1.3.6.1.4.1.4329.15.3.30.5.36
        authorizedAPGroup OBJECT-GROUP
            OBJECTS {  authorizedAPDescription, authorizedAPManufacturer, authorizedAPClassify, authorizedAPRowStatus }
            STATUS current
            DESCRIPTION 
                "Objects defining authorized access points discovered by Radar application."
            ::= { wirelessEWCGroups 36 }

        
        -- 1.3.6.1.4.1.4329.15.3.30.5.37
        prohibitedAPGroup OBJECT-GROUP
            OBJECTS {  prohibitedAPCategory, prohibitedAPDescription, prohibitedAPManufacturer, prohibitedAPClassify, prohibitedAPRowStatus
                 }
            STATUS current
            DESCRIPTION 
                "Objects defining prohibited access points discovered by Radar application."
            ::= { wirelessEWCGroups 37 }


        -- 1.3.6.1.4.1.4329.15.3.30.5.38
        dedicatedScanGroup OBJECT-GROUP
            OBJECTS { dedicatedScanGrpName, dedicatedScanGrpMaxConcurrentAttacksPerAP, 
                dedicatedScanGrpCounterMeasures, dedicatedScanGrpScan2400MHzFreq, 
                dedicatedScanGrpScan5GHzFreq, dedicatedScanGrpRowStatus, 
                dedicatedScanGrpSecurityThreats,dedicatedScanGrpBlockAdHocPeriod, 
                dedicatedScanGrpClassifySourceIF,
                dedicatedScanGrpDetectRogueAP, dedicatedScanGrpListeningPort
                }
            STATUS current
            DESCRIPTION 
                "List of objects for defining dedicated scan group."
            ::= { wirelessEWCGroups 38 }


        -- 1.3.6.1.4.1.4329.15.3.30.5.39
        apRadioAntennaGroup OBJECT-GROUP
            OBJECTS { apRadioAntennaType , apRadioAntennaModel, apRadioAttenuation}
            STATUS current
            DESCRIPTION 
                "A collection of objects defining an antenna attributes for an AP."
            ::= { wirelessEWCGroups 39 }
            
        -- 1.3.6.1.4.1.4329.15.3.30.5.40
        radiusFastFailoverEventsGroup OBJECT-GROUP
            OBJECTS { fastFailoverEvents }
            STATUS current
            DESCRIPTION 
                "List of objects for defining radius FastFailoverEvents."
            ::= { wirelessEWCGroups 40 }

        -- 1.3.6.1.4.1.4329.15.3.30.5.41
        dhcpRelayListenersGroup OBJECT-GROUP
            OBJECTS {  dhcpRelayListenersRowStatus, destinationName,destinationIP,dhcpRelayListenersMaxEntries,
                                 dhcpRelayListenersNextIndex,dhcpRelayListenersNumEntries 
                               }
            STATUS current
            DESCRIPTION 
                "List of objects for defining dhcpRelayListeners."
            ::= { wirelessEWCGroups 41 }

        -- 1.3.6.1.4.1.4329.15.3.30.5.42
        authenticationAdvancedGroup OBJECT-GROUP
            OBJECTS {  includeServiceType , clientMessageDelayTime ,radiusAccounting ,serverUsageModel,
                        radacctStartOnIPAddr, clientServiceTypeLogin, applyMacAddressFormat
                        }
            STATUS current
            DESCRIPTION 
                "List of objects for defining authenticationAdvanced."
            ::= { wirelessEWCGroups 42 }

        -- 1.3.6.1.4.1.4329.15.3.30.5.43
        radiusExtnsSettingGroup OBJECT-GROUP
            OBJECTS {pollingMechanism,  serverPollingInterval  }
            STATUS current
            DESCRIPTION 
                "List of objects for defining radiusExtnsSetting."
            ::= { wirelessEWCGroups 43 }




    
    END
