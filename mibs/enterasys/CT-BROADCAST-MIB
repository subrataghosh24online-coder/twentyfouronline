CT-BROADCAST-MIB DEFINITIONS ::= BEGIN

        --  ct-broadcast-mib.txt
        --  Revision: 01.00.02
        --  Part Number:
        --  Date: May 20, 1998

        --  Cabletron Systems, Inc.
        --  35 Industrial Way, P.O. Box 5005
        --  Rochester, NH 03867-0505
        --  (603) 332-9400
        --  support@ctron.com

        --  This module provides authoritative definitions for Cabletron's
        --  broadcast mib.
        --
        --  This module will be extended, as required.
        --

        --  Cabletron Systems reserves the right to make changes in
        --  specification and other information contained in this document
        --  without prior notice.  The reader should consult Cabletron 
        --  Systems to determine whether any such changes have been made.
        --
        --  In no event shall Cabletron Systems be liable for any 
        --  incidental, indirect, special, or consequential damages
        --  whatsoever (including but not limited to lost profits) arising 
        --  out of or related to this document or the information contained 
        --  in it, even if Cabletron Systems has been advised of, known, 
        --  or should have known, the possibility of such damages.
        --
        --  Cabletron grants vendors, end-users, and other interested 
        --  parties a non-exclusive license to use this Specification in 
        --  connection with the management of Cabletron products.
 
        --  Copyright (c)1998 Cabletron Systems
 
 IMPORTS

    OBJECT-TYPE
       FROM RFC-1212
 
    Counter, TimeTicks
       FROM RFC1155-SMI

    ctBroadcast
       FROM CTRON-MIB-NAMES;
 
--===============   Group Definitions   ===================
 
ctBroadcastCtl     OBJECT IDENTIFIER ::= { ctBroadcast 1 }


--===============   Broadcast Group Definitions   ===================

ctBroadcastCtlTable        OBJECT-TYPE
     SYNTAX     SEQUENCE OF CtBroadcastCtlEntry
     ACCESS     not-accessible
     STATUS     mandatory
     DESCRIPTION
        "Provides a list of definitions and control objects over  
         ports."
     ::= { ctBroadcastCtl 1 }
     
ctBroadcastCtlEntry        OBJECT-TYPE
     SYNTAX     CtBroadcastCtlEntry
     ACCESS     not-accessible
     STATUS     mandatory
     DESCRIPTION
        "Defines a particular entry containing objects pertaining to
         definition and control over ports."
     INDEX { ctBroadcastCtlSlotID, ctBroadcastCtlInterface}
     ::= { ctBroadcastCtlTable 1 }
     
CtBroadcastCtlEntry ::= 
            SEQUENCE {
                ctBroadcastCtlSlotID
                    INTEGER,
                ctBroadcastCtlInterface   
                    INTEGER,
                ctBroadcastTotalBroadcastFrames  
                    Counter,
                ctBroadcastPeakBroadcastRate 
                    INTEGER,
                ctBroadcastPeakBroadcastRateTime 
                    TimeTicks,
                ctBroadcastPeakBroadcastClear 
                    INTEGER,
                ctBroadcastDesiredBroadcastThreshold  
                    INTEGER
            }
         
ctBroadcastCtlSlotID  OBJECT-TYPE
     SYNTAX     INTEGER
     ACCESS     read-only
     STATUS     mandatory
     DESCRIPTION
        "The specific chassis slot to which this broadcast information 
         pertains."
     ::= { ctBroadcastCtlEntry 1 }
     
ctBroadcastCtlInterface     OBJECT-TYPE
     SYNTAX     INTEGER
     ACCESS     read-only
     STATUS     mandatory
     DESCRIPTION
        "The interface for which this broadcast information pertains."
     ::= { ctBroadcastCtlEntry 2 }
     
ctBroadcastTotalBroadcastFrames       OBJECT-TYPE
     SYNTAX      Counter
     ACCESS      read-only
     STATUS      mandatory
     DESCRIPTION
        "The returned value represents the total number of
         broadcast frames received on the interface since the
         device was initialized."
     ::= { ctBroadcastCtlEntry 3 }
     
ctBroadcastPeakBroadcastRate  OBJECT-TYPE
     SYNTAX      INTEGER
     ACCESS      read-only
     STATUS      mandatory
     DESCRIPTION
        "The peak rate of broadcast frames received on this
         interface represented in frames per second."
     ::= { ctBroadcastCtlEntry 4 }
     
ctBroadcastPeakBroadcastRateTime      OBJECT-TYPE
     SYNTAX      TimeTicks
     ACCESS      read-only
     STATUS      mandatory
     DESCRIPTION
        "The time at which the peak broadcast rate occurred. The value
         returned will represent system up time at which the peak 
         occurred."
     ::= { ctBroadcastCtlEntry 5 }
     
ctBroadcastPeakBroadcastClear         OBJECT-TYPE
     SYNTAX      INTEGER {
                           clear(1),
                           noClear(2)
                         }
     ACCESS      read-write
     STATUS      mandatory
     DESCRIPTION
        "This object is used to clear the values found in peakBroadcastRate
         and peakBroadcastRateTime.
     
         When set with a value of clear(1) the values will be cleared.
         When read, a value a value of noClear(2) will be returned.
         A set of a value of noClear(2) will have no effect."
     ::= { ctBroadcastCtlEntry 6 }
     
ctBroadcastDesiredBroadcastThreshold  OBJECT-TYPE
     SYNTAX      INTEGER (1..2147483647)
     ACCESS      read-write
     STATUS      mandatory
     DESCRIPTION
        "The allowable number of received broadcast frames per second
         this interface is allowed to forward to/out other interfaces
         in the device. Any number of broadcast frames per second above
         the desired vlaue will be dropped. The default value for the 
         interface is the theoretical maximum frames per second for the 
         interface. The acceptable range covers the theoretical maximum
         for all current media forms." 
     ::= { ctBroadcastCtlEntry 7 }
     
END
