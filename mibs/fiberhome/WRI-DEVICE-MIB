--
-- WRI-DEVICE-MIB.mib
-- MIB generated by MG-SOFT Visual MIB Builder Version 4.0 Build 349
-- Monday, November 16, 2015 at 16:55:37
--

	WRI-DEVICE-MIB DEFINITIONS ::= BEGIN
 
		IMPORTS
			TimeTicks, Unsigned32, Counter32, OBJECT-TYPE, NOTIFICATION-TYPE			
				FROM SNMPv2-SMI			
			PhysAddress, TEXTUAL-CONVENTION			
				FROM SNMPv2-TC			
			wriProducts, wriProtocol			
				FROM WRI-SMI;
	
	
--
-- Type definitions
--
	
		PortList ::= OCTET STRING (SIZE (0..1024))

--  Similarly, all representations of Bridge-Id in this MIB
-- Module use, as a textual convention (i.e. this
-- convention does not affect their encoding), the data
-- type:
		BridgeId ::= OCTET STRING (SIZE (8))

	
--
-- Textual conventions
--
	
		DisplayString ::= TEXTUAL-CONVENTION
			STATUS current
			DESCRIPTION 
				"8 bit octet."
			SYNTAX OCTET STRING

		RerRingDir ::= TEXTUAL-CONVENTION
			STATUS current
			DESCRIPTION 
				"Indicates the ringlet on which the OAM action
				request/response is sent/replied."
			SYNTAX INTEGER
				{
				west(0),
				east(1)
				}

		EntryStatus ::= TEXTUAL-CONVENTION
			STATUS current
			DESCRIPTION 
				"entry status."
			SYNTAX INTEGER
				{
				valid(1),
				createRequest(2),
				underCreation(3),
				invalid(4)
				}

		VlanIndex ::= TEXTUAL-CONVENTION
			STATUS current
			DESCRIPTION 
				"A value used to index per-VLAN tables: values of 0 and
				4095 are not permitted; if the value is between 1 and
				4094 inclusive, it represents an IEEE 802.1Q VLAN-ID with
				global scope within a given bridged domain (see VlanId
				textual convention).  If the value is greater than 4095
				then it represents a VLAN with scope local to the
				particular agent, i.e. one without a global VLAN-ID
				assigned to it. Such VLANs are outside the scope of
				IEEE 802.1Q but it is convenient to be able to manage them
				in the same way using this MIB."
			SYNTAX Unsigned32

		VlanId ::= TEXTUAL-CONVENTION
			STATUS current
			DESCRIPTION 
				"A 12-bit VLAN ID used in the VLAN Tag header."
			SYNTAX INTEGER (1..4094)

	
--
-- Node definitions
--
	
--  Multiple Services Ring (MSPP)
		mspp OBJECT IDENTIFIER ::= { wriProducts 8012 }

		
		msppChassis OBJECT IDENTIFIER ::= { mspp 1 }

		
		msppDev OBJECT IDENTIFIER ::= { mspp 2 }

		
--  the
-- Bridge-Identifier
-- as used in the
-- Spanning Tree
-- Protocol to uniquely identify a bridge.  Its first two
-- octets (in network byte order) contain a priority
-- value and its last 6 octets contain the MAC address
-- used to refer to a bridge in a unique fashion
-- (typically, the numerically smallest MAC address
-- of all ports on the bridge).
		msppDevGeneral OBJECT IDENTIFIER ::= { msppDev 1 }

		
		msppDevMac OBJECT-TYPE
			SYNTAX PhysAddress (SIZE (0..6))
			MAX-ACCESS read-only
			STATUS current
			DESCRIPTION
				"mac address."
			::= { msppDevGeneral 1 }

		
		msppDevDescr OBJECT-TYPE
			SYNTAX DisplayString (SIZE (0..64))
			MAX-ACCESS read-write
			STATUS current
			DESCRIPTION
				"Node desription."
			::= { msppDevGeneral 2 }

		
		msppDevHwVersion OBJECT-TYPE
			SYNTAX DisplayString (SIZE (0..64))
			MAX-ACCESS read-only
			STATUS current
			DESCRIPTION
				"Node desription."
			::= { msppDevGeneral 3 }

		
		msppDevSwVersion OBJECT-TYPE
			SYNTAX DisplayString (SIZE (0..64))
			MAX-ACCESS read-only
			STATUS current
			DESCRIPTION
				"Node desription."
			::= { msppDevGeneral 4 }

		
		msppDevCardBits OBJECT-TYPE
			SYNTAX Counter32
			MAX-ACCESS read-only
			STATUS current
			DESCRIPTION
				"Node card bitmap."
			::= { msppDevGeneral 5 }

		
		msppDevCardNum OBJECT-TYPE
			SYNTAX INTEGER
			MAX-ACCESS read-only
			STATUS current
			DESCRIPTION
				"Node index."
			::= { msppDevGeneral 6 }

		
		msppDevLastChange OBJECT-TYPE
			SYNTAX TimeTicks
			MAX-ACCESS read-only
			STATUS current
			DESCRIPTION
				"in seconds."
			::= { msppDevGeneral 7 }

		
		msppDevUpTime OBJECT-TYPE
			SYNTAX TimeTicks
			MAX-ACCESS read-only
			STATUS current
			DESCRIPTION
				"in seconds."
			::= { msppDevGeneral 8 }

		
		msppDevTime OBJECT-TYPE
			SYNTAX DisplayString (SIZE (0..32))
			MAX-ACCESS read-write
			STATUS current
			DESCRIPTION
				"set and get string format: 'yyyy/mm/dd hh:mm:ss'."
			::= { msppDevGeneral 9 }

		
		msppDevFlushMac OBJECT-TYPE
			SYNTAX INTEGER { reset(1) }
			MAX-ACCESS read-write
			STATUS current
			DESCRIPTION
				"counter value."
			::= { msppDevGeneral 10 }

		
		msppDevReboot OBJECT-TYPE
			SYNTAX INTEGER
				{
				reboot(1),
				writeconfigandreboot(2),
				writeconfigandrebootsys(3),
				eraseconfigandreboot(4),
				eraseconfigandrebootsys(5)
				}
			MAX-ACCESS read-write
			STATUS current
			DESCRIPTION
				"reboot"
			::= { msppDevGeneral 11 }

		
		msppDevCfgFile OBJECT-TYPE
			SYNTAX DisplayString (SIZE (0..64))
			MAX-ACCESS read-write
			STATUS current
			DESCRIPTION			" "
			::= { msppDevGeneral 12 }

		
		msppDevCfgAction OBJECT-TYPE
			SYNTAX INTEGER
				{
				write(1),
				erase(2),
				exec(3),
				upgrade(4),
				writestartup(5),
				erasestartup(6),
				execstartup(7),
				upgradestartup(8),
				writebackup(9),
				erasebackup(10),
				execbackup(11),
				upgradebackup(12),
				writeboth(13),
				eraseboth(14),
				upgradeboth(15),
				recoverconfig(16)
				}
			MAX-ACCESS read-write
			STATUS current
			DESCRIPTION			" "
			::= { msppDevGeneral 13 }

		
		msppDevOsFile OBJECT-TYPE
			SYNTAX DisplayString (SIZE (0..64))
			MAX-ACCESS read-write
			STATUS current
			DESCRIPTION			" "
			::= { msppDevGeneral 14 }

		
		msppDevOsAction OBJECT-TYPE
			SYNTAX INTEGER
				{
				upgradebootos(1),
				upgradebootosandreboot(2),
				upgrademainos(3),
				upgradebakos(4),
				upgradebothos(5),
				recoverbootos(6)
				}
			MAX-ACCESS read-write
			STATUS current
			DESCRIPTION			" "
			::= { msppDevGeneral 15 }

		
		msppDevVer OBJECT-TYPE
			SYNTAX INTEGER
				{
				mspp1(1),
				mspp2EO(2),
				mspp2O(3),
				mspp3(4)
				}
			MAX-ACCESS read-only
			STATUS current
			DESCRIPTION
				"counter value."
			::= { msppDevGeneral 16 }

		
		msppDevErrorBits OBJECT-TYPE
			SYNTAX Counter32
			MAX-ACCESS read-only
			STATUS current
			DESCRIPTION
				"counter value."
			::= { msppDevGeneral 17 }

		
		msppDevTemperatureLThreshold OBJECT-TYPE
			SYNTAX INTEGER
			MAX-ACCESS read-write
			STATUS current
			DESCRIPTION
				"current Temperature lowhest threshold."
			::= { msppDevGeneral 18 }

		
		msppDevTemperatureHThreshold OBJECT-TYPE
			SYNTAX INTEGER
			MAX-ACCESS read-write
			STATUS current
			DESCRIPTION
				"current Temperature lowhest threshold."
			::= { msppDevGeneral 19 }

		
		msppDevTemperature OBJECT-TYPE
			SYNTAX INTEGER
			MAX-ACCESS read-write
			STATUS current
			DESCRIPTION
				"current Temperature lowhest threshold."
			::= { msppDevGeneral 20 }

		
		msppDevTemperatureTrapEnable OBJECT-TYPE
			SYNTAX INTEGER
			MAX-ACCESS read-write
			STATUS current
			DESCRIPTION
				"current Temperature highhest threshold."
			::= { msppDevGeneral 21 }

		
		msppDevWRED OBJECT-TYPE
			SYNTAX INTEGER
				{
				disable(0),
				enable(1)
				}
			MAX-ACCESS read-write
			STATUS current
			DESCRIPTION
				"weighted random early discard.enable or disable"
			::= { msppDevGeneral 22 }

		
		msppDevMirrorToPort OBJECT-TYPE
			SYNTAX INTEGER
			MAX-ACCESS read-write
			STATUS current
			DESCRIPTION
				"NULL"
			::= { msppDevGeneral 23 }

		
		msppDevMirrorMode OBJECT-TYPE
			SYNTAX INTEGER
			MAX-ACCESS read-write
			STATUS current
			DESCRIPTION
				"NULL"
			::= { msppDevGeneral 24 }

		
		msppDevLcd OBJECT-TYPE
			SYNTAX INTEGER
			MAX-ACCESS read-write
			STATUS current
			DESCRIPTION
				"NULL"
			::= { msppDevGeneral 25 }

		
		msppDevTDMVlan OBJECT-TYPE
			SYNTAX INTEGER
			MAX-ACCESS read-write
			STATUS current
			DESCRIPTION
				"NULL"
			::= { msppDevGeneral 26 }

		
		msppDevFtpd OBJECT-TYPE
			SYNTAX INTEGER
			MAX-ACCESS read-write
			STATUS current
			DESCRIPTION
				"NULL"
			::= { msppDevGeneral 27 }

		
		msppDevTelnetd OBJECT-TYPE
			SYNTAX INTEGER
			MAX-ACCESS read-write
			STATUS current
			DESCRIPTION
				"NULL"
			::= { msppDevGeneral 28 }

		
		msppDevMirrorToRspanVid OBJECT-TYPE
			SYNTAX INTEGER
			MAX-ACCESS read-write
			STATUS current
			DESCRIPTION
				"NULL"
			::= { msppDevGeneral 29 }

		
		msppDevMirrorToTpid OBJECT-TYPE
			SYNTAX INTEGER
			MAX-ACCESS read-write
			STATUS current
			DESCRIPTION
				"NULL"
			::= { msppDevGeneral 30 }

		
		msppRebootFileMode OBJECT-TYPE
			SYNTAX INTEGER
				{
				master(0),
				backup(1)
				}
			MAX-ACCESS read-write
			STATUS current
			DESCRIPTION
				"reboot config file by master config file or backup config file. default:master."
			::= { msppDevGeneral 31 }

		
		msppFileExecMode OBJECT-TYPE
			SYNTAX INTEGER
				{
				master(0),
				backup(1)
				}
			MAX-ACCESS read-write
			STATUS current
			DESCRIPTION
				"exec config file by master config file or backup config file. default:master."
			::= { msppDevGeneral 32 }

		
		msppUpgradeBkOs OBJECT-TYPE
			SYNTAX INTEGER
				{
				master(0),
				backup(1)
				}
			MAX-ACCESS read-write
			STATUS current
			DESCRIPTION
				"upgrade master os or backup os. default:master."
			::= { msppDevGeneral 33 }

		
		msppInbandIp OBJECT-TYPE
			SYNTAX DisplayString (SIZE (0..8))
			MAX-ACCESS read-write
			STATUS current
			DESCRIPTION
				"inband ip address."
			::= { msppDevGeneral 34 }

		
		msppOutbandIp OBJECT-TYPE
			SYNTAX DisplayString (SIZE (0..8))
			MAX-ACCESS read-write
			STATUS current
			DESCRIPTION
				"outband ip address."
			::= { msppDevGeneral 35 }

		
		resetEraseCfg OBJECT-TYPE
			SYNTAX INTEGER
				{
				disable(0),
				enable(1)
				}
			MAX-ACCESS read-write
			STATUS current
			DESCRIPTION
				"erase config file when press reset button long. enable: erase."
			::= { msppDevGeneral 36 }

		
		msppDevLicenseEnable OBJECT-TYPE
			SYNTAX INTEGER
				{
				disable(0),
				enable(1)
				}
			MAX-ACCESS read-write
			STATUS current
			DESCRIPTION
				"enable or disable license key function. If you want to enable license key function, please designate 'msppDevLicenseKey' first "
			::= { msppDevGeneral 37 }

		
		msppDevLicenseKey OBJECT-TYPE
			SYNTAX DisplayString (SIZE (0..64))
			MAX-ACCESS read-write
			STATUS current
			DESCRIPTION
				"licnese key."
			::= { msppDevGeneral 38 }

		
		msppDevSerialNum OBJECT-TYPE
			SYNTAX DisplayString (SIZE (0..128))
			MAX-ACCESS read-only
			STATUS current
			DESCRIPTION
				"serial num."
			::= { msppDevGeneral 39 }

		
		msppDevMtu OBJECT-TYPE
			SYNTAX Unsigned32
			MAX-ACCESS read-write
			STATUS current
			DESCRIPTION
				"The size of the largest datagram which can be sent/received on the equipment."
			::= { msppDevGeneral 40 }

		
		msppDevFlushDynamicArp OBJECT-TYPE
			SYNTAX Unsigned32
			MAX-ACCESS read-write
			STATUS current
			DESCRIPTION
				"Flush all dynamic arp."
			::= { msppDevGeneral 41 }

		
		msppDevFlushStaticArp OBJECT-TYPE
			SYNTAX Unsigned32
			MAX-ACCESS read-write
			STATUS current
			DESCRIPTION
				"Flush all static arp."
			::= { msppDevGeneral 42 }

		
		msppDevFlushAllArp OBJECT-TYPE
			SYNTAX Unsigned32
			MAX-ACCESS read-write
			STATUS current
			DESCRIPTION
				"Flush all the arp."
			::= { msppDevGeneral 43 }

		
		msppDevBootOs OBJECT-TYPE
			SYNTAX INTEGER
				{
				main(0),
				backup(1)
				}
			MAX-ACCESS read-write
			STATUS current
			DESCRIPTION
				"Boot os imgage."
			::= { msppDevGeneral 44 }

		
		msppDevBootCfg OBJECT-TYPE
			SYNTAX INTEGER
				{
				main(0),
				backup(1)
				}
			MAX-ACCESS read-write
			STATUS current
			DESCRIPTION
				"Boot configuration."
			::= { msppDevGeneral 45 }

		
		msppl2HashMode OBJECT-TYPE
			SYNTAX INTEGER
				{
				crc32-upper(1),
				crc32-lower(2),
				lsb(3),
				crc16-lower(4),
				crc16-upper(5)
				}
			MAX-ACCESS read-write
			STATUS current
			DESCRIPTION
				"L2 hash mode configuration."
			::= { msppDevGeneral 46 }

		
		msppl3HashMode OBJECT-TYPE
			SYNTAX INTEGER
				{
				crc32-upper(1),
				crc32-lower(2),
				lsb(3),
				crc16-lower(4),
				crc16-upper(5)
				}
			MAX-ACCESS read-write
			STATUS current
			DESCRIPTION
				"L3 hash mode configuration."
			::= { msppDevGeneral 47 }

		
		msppl2AuxHashMode OBJECT-TYPE
			SYNTAX INTEGER
				{
				zero(0),
				crc32-upper(1),
				crc32-lower(2),
				lsb(3),
				crc16-lower(4),
				crc16-upper(5)
				}
			MAX-ACCESS read-write
			STATUS current
			DESCRIPTION
				"L2 aux-hash mode configuration."
			::= { msppDevGeneral 48 }

		
		msppIpv4AddrNum OBJECT-TYPE
			SYNTAX INTEGER
			MAX-ACCESS read-only
			STATUS current
			DESCRIPTION
				"The number of ipv4 address."
			::= { msppDevGeneral 49 }

		
		msppDevCode OBJECT-TYPE
			SYNTAX DisplayString (SIZE (0..128))
			MAX-ACCESS read-only
			STATUS current
			DESCRIPTION
				"Device code."
			::= { msppDevGeneral 50 }

		
		msppCmuState OBJECT-TYPE
			SYNTAX INTEGER
			MAX-ACCESS read-only
			STATUS current
			DESCRIPTION
				"Cmu State.whether cmu is insert"
			::= { msppDevGeneral 51 }

		
		msppDevTpid OBJECT-TYPE
			SYNTAX Unsigned32
			MAX-ACCESS read-write
			STATUS current
			DESCRIPTION
				"Protocol ID.0x8100 for 802.1q in 802.1q,0x9100 for none 802.1q in 802.1q"
			::= { msppDevGeneral 52 }

		
		msppDevLoggingInfo OBJECT-TYPE
			SYNTAX DisplayString (SIZE (0..1024))
			MAX-ACCESS read-only
			STATUS current
			DESCRIPTION
				"Logging info"
			::= { msppDevGeneral 53 }

		
		loggingTrapObjects OBJECT IDENTIFIER ::= { msppDevGeneral 54 }

		
		loggingTrap NOTIFICATION-TYPE
			OBJECTS { msppDevMac, msppDevDescr, msppDevLoggingInfo }
			STATUS current
			DESCRIPTION 
				"Logging trap."
			::= { loggingTrapObjects 1 }

		
		msppDevFileName OBJECT-TYPE
			SYNTAX DisplayString (SIZE (0..128))
			MAX-ACCESS read-write
			STATUS current
			DESCRIPTION			" "
			::= { msppDevGeneral 55 }

		
		msppDevFileAction OBJECT-TYPE
			SYNTAX INTEGER { delet(1) }
			MAX-ACCESS read-write
			STATUS current
			DESCRIPTION			" "
			::= { msppDevGeneral 56 }

		
		msppShareVlanEn OBJECT-TYPE
			SYNTAX INTEGER
				{
				enable(1),
				disable(2)
				}
			MAX-ACCESS read-write
			STATUS current
			DESCRIPTION			" "
			::= { msppDevGeneral 57 }

		
		msppUpgradeStatus OBJECT-TYPE
			SYNTAX INTEGER
			MAX-ACCESS read-only
			STATUS current
			DESCRIPTION			" "
			::= { msppDevGeneral 58 }

		
		msppCliVersion OBJECT-TYPE
			SYNTAX OCTET STRING
			MAX-ACCESS read-only
			STATUS current
			DESCRIPTION
				"Description."
			::= { msppDevGeneral 59 }

		
		msppSnmpVersion OBJECT-TYPE
			SYNTAX OCTET STRING
			MAX-ACCESS read-only
			STATUS current
			DESCRIPTION
				"Description."
			::= { msppDevGeneral 60 }

		
		msppHttpVersion OBJECT-TYPE
			SYNTAX OCTET STRING
			MAX-ACCESS read-only
			STATUS current
			DESCRIPTION
				"Description."
			::= { msppDevGeneral 61 }

		
	
	END

--
-- WRI-DEVICE-MIB.mib
--
