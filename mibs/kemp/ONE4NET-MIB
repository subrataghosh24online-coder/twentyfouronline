ONE4NET-MIB DEFINITIONS ::= BEGIN
IMPORTS
    OBJECT-TYPE, MODULE-IDENTITY, enterprises FROM SNMPv2-SMI;
 

one4net MODULE-IDENTITY
    LAST-UPDATED "200201120000Z"
    ORGANIZATION "One4net GmbH"
    CONTACT-INFO
        "email:      support@one4net.com"
    DESCRIPTION
	"one4net MIB."
    REVISION	 "200201120000Z"
    DESCRIPTION
	"initial version"
    ::= { enterprises 12196 }
END
