--
-- sle-network6-mib.mib
-- MIB generated by MG-SOFT Visual MIB Builder Version 6.0  Build 88
-- Tuesday, July 28, 2015 at 10:44:38
--

	SLE-Network6-MIB DEFINITIONS ::= BEGIN
 
		IMPORTS
			sleMgmt			
				FROM DASAN-SMI			
			InetAddressIPv6, InetAddressPrefixLength			
				FROM INET-ADDRESS-MIB			
			sleIpVRFIndex			
				FROM SLE-NETWORK-MIB			
			SleControlStatusType, SleControlRequestResultType			
				FROM SLE-TC-MIB			
			OBJECT-GROUP, NOTIFICATION-GROUP			
				FROM SNMPv2-CONF			
			TimeTicks, Integer32, Gauge32, BITS, OBJECT-TYPE, 
			MODULE-IDENTITY, NOTIFICATION-TYPE			
				FROM SNMPv2-SMI;
	
	
		-- 1.3.6.1.4.1.6296.101.26
		sleNetwork6 MODULE-IDENTITY 
			LAST-UPDATED "201501060917Z"		-- January 06, 2015 at 09:17 GMT
			ORGANIZATION 
				"HANASOFT"
			CONTACT-INFO 
				" "
			DESCRIPTION 
				"This MIB contains information about Network6."
			REVISION "201501070901Z"		-- January 07, 2015 at 09:01 GMT
			DESCRIPTION 
				"sleNetwork6 MIB"
			::= { sleMgmt 26 }

		
	
	
--
-- Node definitions
--
	
		-- 1.3.6.1.4.1.6296.101.26.1
		sleNetInterface6 OBJECT IDENTIFIER ::= { sleNetwork6 1 }

		
		-- 1.3.6.1.4.1.6296.101.26.1.1
		sleNetIf6Table OBJECT-TYPE
			SYNTAX SEQUENCE OF SleNetIf6Entry
			MAX-ACCESS not-accessible
			STATUS current
			DESCRIPTION
				"Description."
			::= { sleNetInterface6 1 }

		
		-- 1.3.6.1.4.1.6296.101.26.1.1.1
		sleNetIf6Entry OBJECT-TYPE
			SYNTAX SleNetIf6Entry
			MAX-ACCESS not-accessible
			STATUS current
			DESCRIPTION
				"Description."
			INDEX { sleNetIf6Index }
			::= { sleNetIf6Table 1 }

		
		SleNetIf6Entry ::=
			SEQUENCE { 
				sleNetIf6Index
					INTEGER,
				sleNetIf6Name
					OCTET STRING,
				sleNetIf6Ipv6State
					INTEGER,
				sleNetIf6Mode
					INTEGER,
				sleNetIf6RouteMap
					OCTET STRING,
				sleNetIf6AddrAutoConf
					INTEGER,
				sleNetIf6AddrAutoConfDefault
					INTEGER,
				sleNetIf6NdRouterPref
					INTEGER,
				sleNetIf6SuppressRA
					INTEGER,
				sleNetIf6NdRaMaxInterval
					INTEGER,
				sleNetIf6NdRaMinInterval
					INTEGER,
				sleNetIf6NdRaLifeTime
					INTEGER,
				sleNetIf6NdRaReachTime
					INTEGER,
				sleNetIf6NdRaHopLimit
					INTEGER,
				sleNetIf6NdRetransTime
					Gauge32,
				sleNetIf6NdMFlag
					INTEGER,
				sleNetIf6NdOFlag
					INTEGER,
				sleNetIf6NdProxy
					INTEGER,
				sleNetIf6NdDadAttempt
					INTEGER,
				sleNetIf6Identifier
					OCTET STRING,
				sleNetIf6Ip6MartianFilter
					INTEGER
			 }

		-- 1.3.6.1.4.1.6296.101.26.1.1.1.1
		sleNetIf6Index OBJECT-TYPE
			SYNTAX INTEGER (0..65535)
			MAX-ACCESS read-write
			STATUS current
			DESCRIPTION
				"Description."
			::= { sleNetIf6Entry 1 }

		
		-- 1.3.6.1.4.1.6296.101.26.1.1.1.2
		sleNetIf6Name OBJECT-TYPE
			SYNTAX OCTET STRING
			MAX-ACCESS read-write
			STATUS current
			DESCRIPTION
				"Description."
			::= { sleNetIf6Entry 2 }

		
		-- 1.3.6.1.4.1.6296.101.26.1.1.1.3
		sleNetIf6Ipv6State OBJECT-TYPE
			SYNTAX INTEGER
				{
				disable(0),
				enable(1)
				}
			MAX-ACCESS read-write
			STATUS current
			DESCRIPTION
				"Description."
			::= { sleNetIf6Entry 3 }

		
		-- 1.3.6.1.4.1.6296.101.26.1.1.1.4
		sleNetIf6Mode OBJECT-TYPE
			SYNTAX INTEGER
				{
				host(1),
				router(2)
				}
			MAX-ACCESS read-write
			STATUS current
			DESCRIPTION
				"Description."
			::= { sleNetIf6Entry 4 }

		
		-- 1.3.6.1.4.1.6296.101.26.1.1.1.5
		sleNetIf6RouteMap OBJECT-TYPE
			SYNTAX OCTET STRING
			MAX-ACCESS read-write
			STATUS current
			DESCRIPTION
				"Description."
			::= { sleNetIf6Entry 5 }

		
		-- 1.3.6.1.4.1.6296.101.26.1.1.1.6
		sleNetIf6AddrAutoConf OBJECT-TYPE
			SYNTAX INTEGER
				{
				disable(0),
				enable(1)
				}
			MAX-ACCESS read-write
			STATUS current
			DESCRIPTION
				"Description."
			::= { sleNetIf6Entry 6 }

		
		-- 1.3.6.1.4.1.6296.101.26.1.1.1.7
		sleNetIf6AddrAutoConfDefault OBJECT-TYPE
			SYNTAX INTEGER
				{
				disable(0),
				enable(1)
				}
			MAX-ACCESS read-write
			STATUS current
			DESCRIPTION
				"Description."
			::= { sleNetIf6Entry 7 }

		
		-- 1.3.6.1.4.1.6296.101.26.1.1.1.8
		sleNetIf6NdRouterPref OBJECT-TYPE
			SYNTAX INTEGER
				{
				high(1),
				low(2),
				medium(3)
				}
			MAX-ACCESS read-write
			STATUS current
			DESCRIPTION
				"Description."
			::= { sleNetIf6Entry 8 }

		
		-- 1.3.6.1.4.1.6296.101.26.1.1.1.9
		sleNetIf6SuppressRA OBJECT-TYPE
			SYNTAX INTEGER
				{
				unset(0),
				set(1)
				}
			MAX-ACCESS read-write
			STATUS current
			DESCRIPTION
				"Description."
			::= { sleNetIf6Entry 9 }

		
		-- 1.3.6.1.4.1.6296.101.26.1.1.1.10
		sleNetIf6NdRaMaxInterval OBJECT-TYPE
			SYNTAX INTEGER (-1 | 3..1800)
			MAX-ACCESS read-write
			STATUS current
			DESCRIPTION
				"Description."
			::= { sleNetIf6Entry 10 }

		
		-- 1.3.6.1.4.1.6296.101.26.1.1.1.11
		sleNetIf6NdRaMinInterval OBJECT-TYPE
			SYNTAX INTEGER (-1 | 3..1350)
			MAX-ACCESS read-write
			STATUS current
			DESCRIPTION
				"Description."
			::= { sleNetIf6Entry 11 }

		
		-- 1.3.6.1.4.1.6296.101.26.1.1.1.12
		sleNetIf6NdRaLifeTime OBJECT-TYPE
			SYNTAX INTEGER (-1 | 0..9000)
			MAX-ACCESS read-write
			STATUS current
			DESCRIPTION
				"Description."
			::= { sleNetIf6Entry 12 }

		
		-- 1.3.6.1.4.1.6296.101.26.1.1.1.13
		sleNetIf6NdRaReachTime OBJECT-TYPE
			SYNTAX INTEGER (-1 | 0..3600000)
			MAX-ACCESS read-write
			STATUS current
			DESCRIPTION
				"Description."
			::= { sleNetIf6Entry 13 }

		
		-- 1.3.6.1.4.1.6296.101.26.1.1.1.14
		sleNetIf6NdRaHopLimit OBJECT-TYPE
			SYNTAX INTEGER (-1 | 0..255)
			MAX-ACCESS read-write
			STATUS current
			DESCRIPTION
				"Description."
			::= { sleNetIf6Entry 14 }

		
		-- 1.3.6.1.4.1.6296.101.26.1.1.1.15
		sleNetIf6NdRetransTime OBJECT-TYPE
			SYNTAX Gauge32 (0..4294967295)
			MAX-ACCESS read-write
			STATUS current
			DESCRIPTION
				"Description."
			::= { sleNetIf6Entry 15 }

		
		-- 1.3.6.1.4.1.6296.101.26.1.1.1.16
		sleNetIf6NdMFlag OBJECT-TYPE
			SYNTAX INTEGER
				{
				unset(0),
				set(1)
				}
			MAX-ACCESS read-write
			STATUS current
			DESCRIPTION
				"Description."
			::= { sleNetIf6Entry 16 }

		
		-- 1.3.6.1.4.1.6296.101.26.1.1.1.17
		sleNetIf6NdOFlag OBJECT-TYPE
			SYNTAX INTEGER
				{
				unset(0),
				set(1)
				}
			MAX-ACCESS read-write
			STATUS current
			DESCRIPTION
				"Description."
			::= { sleNetIf6Entry 17 }

		
		-- 1.3.6.1.4.1.6296.101.26.1.1.1.18
		sleNetIf6NdProxy OBJECT-TYPE
			SYNTAX INTEGER
				{
				disable(0),
				enable(1)
				}
			MAX-ACCESS read-write
			STATUS current
			DESCRIPTION
				"Description."
			::= { sleNetIf6Entry 18 }

		
		-- 1.3.6.1.4.1.6296.101.26.1.1.1.19
		sleNetIf6NdDadAttempt OBJECT-TYPE
			SYNTAX INTEGER (0..600)
			MAX-ACCESS read-write
			STATUS current
			DESCRIPTION
				"Description."
			::= { sleNetIf6Entry 19 }

		
		-- 1.3.6.1.4.1.6296.101.26.1.1.1.20
		sleNetIf6Identifier OBJECT-TYPE
			SYNTAX OCTET STRING
			MAX-ACCESS read-only
			STATUS current
			DESCRIPTION
				"Set interface identifier on interface"
			::= { sleNetIf6Entry 20 }

		
		-- 1.3.6.1.4.1.6296.101.26.1.1.1.21
		sleNetIf6Ip6MartianFilter OBJECT-TYPE
			SYNTAX INTEGER
				{
				disable(0),
				enable(1)
				}
			MAX-ACCESS read-only
			STATUS current
			DESCRIPTION
				"IPv6 Martian Filter configuration"
			::= { sleNetIf6Entry 21 }

		
		-- 1.3.6.1.4.1.6296.101.26.1.2
		sleNetIf6Control OBJECT IDENTIFIER ::= { sleNetInterface6 2 }

		
		-- 1.3.6.1.4.1.6296.101.26.1.2.1
		sleNetIf6ControlRequest OBJECT-TYPE
			SYNTAX INTEGER
				{
				setIPv6State(1),
				setMode(2),
				setAddrAutoConf(3),
				setNdProfile(4),
				setRouteMap(5),
				unsetRouteMap(6),
				setIdentifier(7),
				setIp6MartianFilter(8)
				}
			MAX-ACCESS read-write
			STATUS current
			DESCRIPTION
				"Description."
			::= { sleNetIf6Control 1 }

		
		-- 1.3.6.1.4.1.6296.101.26.1.2.2
		sleNetIf6ControlStatus OBJECT-TYPE
			SYNTAX SleControlStatusType
			MAX-ACCESS read-write
			STATUS current
			DESCRIPTION
				"Description."
			::= { sleNetIf6Control 2 }

		
		-- 1.3.6.1.4.1.6296.101.26.1.2.3
		sleNetIf6ControlTimer OBJECT-TYPE
			SYNTAX Gauge32
			MAX-ACCESS read-write
			STATUS current
			DESCRIPTION
				"Description."
			::= { sleNetIf6Control 3 }

		
		-- 1.3.6.1.4.1.6296.101.26.1.2.4
		sleNetIf6ControlTimeStamp OBJECT-TYPE
			SYNTAX TimeTicks
			MAX-ACCESS read-write
			STATUS current
			DESCRIPTION
				"Description."
			::= { sleNetIf6Control 4 }

		
		-- 1.3.6.1.4.1.6296.101.26.1.2.5
		sleNetIf6ControlReqResult OBJECT-TYPE
			SYNTAX SleControlRequestResultType
			MAX-ACCESS read-write
			STATUS current
			DESCRIPTION
				"Description."
			::= { sleNetIf6Control 5 }

		
		-- 1.3.6.1.4.1.6296.101.26.1.2.6
		sleNetIf6ControlIndex OBJECT-TYPE
			SYNTAX INTEGER
			MAX-ACCESS read-write
			STATUS current
			DESCRIPTION
				"Description."
			::= { sleNetIf6Control 6 }

		
		-- 1.3.6.1.4.1.6296.101.26.1.2.7
		sleNetIf6ControlIpv6State OBJECT-TYPE
			SYNTAX INTEGER
				{
				disable(0),
				enable(1)
				}
			MAX-ACCESS read-write
			STATUS current
			DESCRIPTION
				"Description."
			::= { sleNetIf6Control 7 }

		
		-- 1.3.6.1.4.1.6296.101.26.1.2.8
		sleNetIf6ControlMode OBJECT-TYPE
			SYNTAX INTEGER
				{
				host(1),
				router(2)
				}
			MAX-ACCESS read-write
			STATUS current
			DESCRIPTION
				"Description."
			::= { sleNetIf6Control 8 }

		
		-- 1.3.6.1.4.1.6296.101.26.1.2.9
		sleNetIf6ControlRouteMap OBJECT-TYPE
			SYNTAX OCTET STRING
			MAX-ACCESS read-write
			STATUS current
			DESCRIPTION
				"Description."
			::= { sleNetIf6Control 9 }

		
		-- 1.3.6.1.4.1.6296.101.26.1.2.10
		sleNetIf6ControlAutoConf OBJECT-TYPE
			SYNTAX INTEGER
				{
				disable(0),
				enable(1)
				}
			MAX-ACCESS read-write
			STATUS current
			DESCRIPTION
				"Description."
			::= { sleNetIf6Control 10 }

		
		-- 1.3.6.1.4.1.6296.101.26.1.2.11
		sleNetIf6ControlAutoConfDefault OBJECT-TYPE
			SYNTAX INTEGER
				{
				disable(0),
				enable(1)
				}
			MAX-ACCESS read-write
			STATUS current
			DESCRIPTION
				"Description."
			::= { sleNetIf6Control 11 }

		
		-- 1.3.6.1.4.1.6296.101.26.1.2.12
		sleNetIf6ControlNdRouterPref OBJECT-TYPE
			SYNTAX INTEGER
				{
				high(1),
				row(2),
				medium(3)
				}
			MAX-ACCESS read-write
			STATUS current
			DESCRIPTION
				"Description."
			::= { sleNetIf6Control 12 }

		
		-- 1.3.6.1.4.1.6296.101.26.1.2.13
		sleNetIf6ControlNdSuppressRA OBJECT-TYPE
			SYNTAX INTEGER
				{
				unset(0),
				set(1)
				}
			MAX-ACCESS read-write
			STATUS current
			DESCRIPTION
				"Description."
			::= { sleNetIf6Control 13 }

		
		-- 1.3.6.1.4.1.6296.101.26.1.2.14
		sleNetIf6ControlNdMaxInterval OBJECT-TYPE
			SYNTAX INTEGER (-1 | 3..1800)
			MAX-ACCESS read-write
			STATUS current
			DESCRIPTION
				"Description."
			::= { sleNetIf6Control 14 }

		
		-- 1.3.6.1.4.1.6296.101.26.1.2.15
		sleNetIf6ControlNdMinInterval OBJECT-TYPE
			SYNTAX INTEGER (-1 | 3..1350)
			MAX-ACCESS read-write
			STATUS current
			DESCRIPTION
				"Description."
			::= { sleNetIf6Control 15 }

		
		-- 1.3.6.1.4.1.6296.101.26.1.2.16
		sleNetIf6ControlNdRaLifeTime OBJECT-TYPE
			SYNTAX INTEGER (-1 | 0..9000)
			MAX-ACCESS read-write
			STATUS current
			DESCRIPTION
				"Description."
			::= { sleNetIf6Control 16 }

		
		-- 1.3.6.1.4.1.6296.101.26.1.2.17
		sleNetIf6ControlNdRaReachTime OBJECT-TYPE
			SYNTAX INTEGER (-1 | 0..3600000)
			MAX-ACCESS read-write
			STATUS current
			DESCRIPTION
				"Description."
			::= { sleNetIf6Control 17 }

		
		-- 1.3.6.1.4.1.6296.101.26.1.2.18
		sleNetIf6ControlNdRaHopLimit OBJECT-TYPE
			SYNTAX INTEGER (-1 | 0..255)
			MAX-ACCESS read-write
			STATUS current
			DESCRIPTION
				"Description."
			::= { sleNetIf6Control 18 }

		
		-- 1.3.6.1.4.1.6296.101.26.1.2.19
		sleNetIf6ControlNdRetransTime OBJECT-TYPE
			SYNTAX Gauge32 (0..4294967295)
			MAX-ACCESS read-write
			STATUS current
			DESCRIPTION
				"Description."
			::= { sleNetIf6Control 19 }

		
		-- 1.3.6.1.4.1.6296.101.26.1.2.20
		sleNetIf6ControlNdMFlag OBJECT-TYPE
			SYNTAX INTEGER
				{
				unset(0),
				set(1)
				}
			MAX-ACCESS read-write
			STATUS current
			DESCRIPTION
				"Description."
			::= { sleNetIf6Control 20 }

		
		-- 1.3.6.1.4.1.6296.101.26.1.2.21
		sleNetIf6ControlNdOFlag OBJECT-TYPE
			SYNTAX INTEGER
				{
				unset(0),
				set(1)
				}
			MAX-ACCESS read-write
			STATUS current
			DESCRIPTION
				"Description."
			::= { sleNetIf6Control 21 }

		
		-- 1.3.6.1.4.1.6296.101.26.1.2.22
		sleNetIf6ControlNdProxy OBJECT-TYPE
			SYNTAX INTEGER
				{
				disable(0),
				enable(1)
				}
			MAX-ACCESS read-write
			STATUS current
			DESCRIPTION
				"Description."
			::= { sleNetIf6Control 22 }

		
		-- 1.3.6.1.4.1.6296.101.26.1.2.23
		sleNetIf6ControlNdDadAttempt OBJECT-TYPE
			SYNTAX INTEGER (0..600)
			MAX-ACCESS read-write
			STATUS current
			DESCRIPTION
				"Description."
			::= { sleNetIf6Control 23 }

		
		-- 1.3.6.1.4.1.6296.101.26.1.2.24
		sleNetIf6ControlIdentifier OBJECT-TYPE
			SYNTAX OCTET STRING
			MAX-ACCESS read-write
			STATUS current
			DESCRIPTION
				"Set interface identifier on interface"
			::= { sleNetIf6Control 24 }

		
		-- 1.3.6.1.4.1.6296.101.26.1.2.25
		sleNetIf6ControlIp6MartianFilter OBJECT-TYPE
			SYNTAX INTEGER
				{
				disable(0),
				enable(1)
				}
			MAX-ACCESS read-write
			STATUS current
			DESCRIPTION
				"IPv6 Martian Filter configuration"
			::= { sleNetIf6Control 25 }

		
		-- 1.3.6.1.4.1.6296.101.26.1.3
		sleNetIf6Notification OBJECT IDENTIFIER ::= { sleNetInterface6 3 }

		
		-- 1.3.6.1.4.1.6296.101.26.1.3.1
		sleIp6StateChanged NOTIFICATION-TYPE
			OBJECTS { sleNetIf6ControlRequest, sleNetIf6ControlTimeStamp, sleNetIf6ControlReqResult, sleNetIf6Index, sleNetIf6Ipv6State
				 }
			STATUS current
			DESCRIPTION 
				"Description."
			::= { sleNetIf6Notification 1 }

		
		-- 1.3.6.1.4.1.6296.101.26.1.3.2
		sleIfModeChanged NOTIFICATION-TYPE
			OBJECTS { sleNetIf6ControlRequest, sleNetIf6ControlTimeStamp, sleNetIf6ControlReqResult, sleNetIf6Index, sleNetIf6Mode
				 }
			STATUS current
			DESCRIPTION 
				"Description."
			::= { sleNetIf6Notification 2 }

		
		-- 1.3.6.1.4.1.6296.101.26.1.3.3
		sleAddrAutoConfChanged NOTIFICATION-TYPE
			OBJECTS { sleNetIf6ControlRequest, sleNetIf6ControlTimeStamp, sleNetIf6ControlReqResult, sleNetIf6Index, sleNetIf6AddrAutoConf, 
				sleNetIf6AddrAutoConfDefault }
			STATUS current
			DESCRIPTION 
				"Description."
			::= { sleNetIf6Notification 3 }

		
		-- 1.3.6.1.4.1.6296.101.26.1.3.4
		sleNdProfileChanged NOTIFICATION-TYPE
			OBJECTS { sleNetIf6ControlRequest, sleNetIf6ControlTimeStamp, sleNetIf6ControlReqResult, sleNetIf6Index, sleNetIf6NdRouterPref, 
				sleNetIf6SuppressRA, sleNetIf6NdRaMaxInterval, sleNetIf6NdRaMinInterval, sleNetIf6NdRaLifeTime, sleNetIf6NdRaReachTime, 
				sleNetIf6NdRaHopLimit, sleNetIf6NdRetransTime, sleNetIf6NdMFlag, sleNetIf6NdOFlag, sleNetIf6NdProxy, 
				sleNetIf6NdDadAttempt }
			STATUS current
			DESCRIPTION 
				"Description."
			::= { sleNetIf6Notification 4 }

		
		-- 1.3.6.1.4.1.6296.101.26.1.3.5
		sleRouteMapSet NOTIFICATION-TYPE
			OBJECTS { sleNetIf6ControlRequest, sleNetIf6ControlTimeStamp, sleNetIf6ControlReqResult }
			STATUS current
			DESCRIPTION 
				"Description."
			::= { sleNetIf6Notification 5 }

		
		-- 1.3.6.1.4.1.6296.101.26.1.3.6
		sleRouteMapUnset NOTIFICATION-TYPE
			OBJECTS { sleNetIf6ControlRequest, sleNetIf6ControlTimeStamp, sleNetIf6ControlReqResult }
			STATUS current
			DESCRIPTION 
				"Description."
			::= { sleNetIf6Notification 6 }

		
		-- 1.3.6.1.4.1.6296.101.26.1.3.7
		sleIdentifierChanged NOTIFICATION-TYPE
			OBJECTS { sleNetIf6ControlRequest, sleNetIf6ControlTimeStamp, sleNetIf6ControlReqResult, sleNetIf6ControlIndex, sleNetIf6ControlIdentifier
				 }
			STATUS current
			DESCRIPTION 
				"setIdentifier"
			::= { sleNetIf6Notification 7 }

		
		-- 1.3.6.1.4.1.6296.101.26.1.3.8
		sleIp6MartianFilterChanged NOTIFICATION-TYPE
			OBJECTS { sleNetIf6ControlRequest, sleNetIf6ControlTimeStamp, sleNetIf6ControlReqResult, sleNetIf6ControlIndex, sleNetIf6ControlIp6MartianFilter
				 }
			STATUS current
			DESCRIPTION 
				"setIp6MartianFilter"
			::= { sleNetIf6Notification 8 }

		
		-- 1.3.6.1.4.1.6296.101.26.2
		sleIpAddress6 OBJECT IDENTIFIER ::= { sleNetwork6 2 }

		
		-- 1.3.6.1.4.1.6296.101.26.2.1
		sleIpAddr6Table OBJECT-TYPE
			SYNTAX SEQUENCE OF SleIpAddr6Entry
			MAX-ACCESS not-accessible
			STATUS current
			DESCRIPTION
				"Description."
			::= { sleIpAddress6 1 }

		
		-- 1.3.6.1.4.1.6296.101.26.2.1.1
		sleIpAddr6Entry OBJECT-TYPE
			SYNTAX SleIpAddr6Entry
			MAX-ACCESS not-accessible
			STATUS current
			DESCRIPTION
				"Description."
			INDEX { sleNetIf6Index, sleIpAddr6Value }
			::= { sleIpAddr6Table 1 }

		
		SleIpAddr6Entry ::=
			SEQUENCE { 
				sleIpAddr6Value
					InetAddressIPv6,
				sleIpAddr6Mask
					InetAddressPrefixLength,
				sleIpAddr6Score
					INTEGER,
				sleIpAddr6Type
					INTEGER,
				sleIpAddr6Status
					INTEGER,
				sleIpAddr6ValidTime
					Integer32,
				sleIpAddr6UsedTime
					Integer32
			 }

		-- 1.3.6.1.4.1.6296.101.26.2.1.1.1
		sleIpAddr6Value OBJECT-TYPE
			SYNTAX InetAddressIPv6
			MAX-ACCESS read-only
			STATUS current
			DESCRIPTION
				"IP address of a Interface"
			::= { sleIpAddr6Entry 1 }

		
		-- 1.3.6.1.4.1.6296.101.26.2.1.1.2
		sleIpAddr6Mask OBJECT-TYPE
			SYNTAX InetAddressPrefixLength
			MAX-ACCESS read-only
			STATUS current
			DESCRIPTION
				"IP mask of a Interface"
			::= { sleIpAddr6Entry 2 }

		
		-- 1.3.6.1.4.1.6296.101.26.2.1.1.3
		sleIpAddr6Score OBJECT-TYPE
			SYNTAX INTEGER
				{
				linklocal(1),
				global(2),
				anycast(3),
				host(4)
				}
			MAX-ACCESS read-only
			STATUS current
			DESCRIPTION
				"Score of IP address"
			::= { sleIpAddr6Entry 3 }

		
		-- 1.3.6.1.4.1.6296.101.26.2.1.1.4
		sleIpAddr6Type OBJECT-TYPE
			SYNTAX INTEGER
				{
				auto(1),
				manual(2)
				}
			MAX-ACCESS read-only
			STATUS current
			DESCRIPTION
				"Type of IP address"
			::= { sleIpAddr6Entry 4 }

		
		-- 1.3.6.1.4.1.6296.101.26.2.1.1.5
		sleIpAddr6Status OBJECT-TYPE
			SYNTAX INTEGER
				{
				active(1),
				dadfailed(2),
				tentative(3),
				deprecated(4)
				}
			MAX-ACCESS read-only
			STATUS current
			DESCRIPTION
				"Status of IP address"
			::= { sleIpAddr6Entry 5 }

		
		-- 1.3.6.1.4.1.6296.101.26.2.1.1.6
		sleIpAddr6ValidTime OBJECT-TYPE
			SYNTAX Integer32
			MAX-ACCESS read-only
			STATUS current
			DESCRIPTION
				"Valid Time of IP address"
			::= { sleIpAddr6Entry 6 }

		
		-- 1.3.6.1.4.1.6296.101.26.2.1.1.7
		sleIpAddr6UsedTime OBJECT-TYPE
			SYNTAX Integer32
			MAX-ACCESS read-only
			STATUS current
			DESCRIPTION
				"Used Time of IP address"
			::= { sleIpAddr6Entry 7 }

		
		-- 1.3.6.1.4.1.6296.101.26.2.2
		sleIpAddr6Control OBJECT IDENTIFIER ::= { sleIpAddress6 2 }

		
		-- 1.3.6.1.4.1.6296.101.26.2.2.1
		sleIpAddr6ControlRequest OBJECT-TYPE
			SYNTAX INTEGER
				{
				createIP6Addr(1),
				deleteIP6Addr(2),
				deleteIP6AddrAll(3)
				}
			MAX-ACCESS read-write
			STATUS current
			DESCRIPTION
				"Description."
			::= { sleIpAddr6Control 1 }

		
		-- 1.3.6.1.4.1.6296.101.26.2.2.2
		sleIpAddr6ControlStatus OBJECT-TYPE
			SYNTAX SleControlStatusType
			MAX-ACCESS read-only
			STATUS current
			DESCRIPTION
				"Description."
			::= { sleIpAddr6Control 2 }

		
		-- 1.3.6.1.4.1.6296.101.26.2.2.3
		sleIpAddr6ControlTimer OBJECT-TYPE
			SYNTAX Gauge32
			MAX-ACCESS read-write
			STATUS current
			DESCRIPTION
				"Description."
			::= { sleIpAddr6Control 3 }

		
		-- 1.3.6.1.4.1.6296.101.26.2.2.4
		sleIpAddr6ControlTimeStamp OBJECT-TYPE
			SYNTAX TimeTicks
			MAX-ACCESS read-only
			STATUS current
			DESCRIPTION
				"Description."
			::= { sleIpAddr6Control 4 }

		
		-- 1.3.6.1.4.1.6296.101.26.2.2.5
		sleIpAddr6ControlReqResult OBJECT-TYPE
			SYNTAX SleControlRequestResultType
			MAX-ACCESS read-only
			STATUS current
			DESCRIPTION
				"Description."
			::= { sleIpAddr6Control 5 }

		
		-- 1.3.6.1.4.1.6296.101.26.2.2.6
		sleIPAddr6ControlIfIndex OBJECT-TYPE
			SYNTAX INTEGER (0..65535)
			MAX-ACCESS read-write
			STATUS current
			DESCRIPTION
				"Description."
			::= { sleIpAddr6Control 6 }

		
		-- 1.3.6.1.4.1.6296.101.26.2.2.7
		sleIPAddr6ControlValue OBJECT-TYPE
			SYNTAX InetAddressIPv6
			MAX-ACCESS read-write
			STATUS current
			DESCRIPTION
				"Description."
			::= { sleIpAddr6Control 7 }

		
		-- 1.3.6.1.4.1.6296.101.26.2.2.8
		sleIPAddr6ControlMask OBJECT-TYPE
			SYNTAX InetAddressPrefixLength
			MAX-ACCESS read-write
			STATUS current
			DESCRIPTION
				"Description."
			::= { sleIpAddr6Control 8 }

		
		-- 1.3.6.1.4.1.6296.101.26.2.2.9
		sleIPAddr6ControlScore OBJECT-TYPE
			SYNTAX INTEGER
				{
				linklocal(1),
				global(2),
				anycast(3),
				host(4)
				}
			MAX-ACCESS read-write
			STATUS current
			DESCRIPTION
				"Description."
			::= { sleIpAddr6Control 9 }

		
		-- 1.3.6.1.4.1.6296.101.26.2.2.10
		sleIPAddr6ControlType OBJECT-TYPE
			SYNTAX INTEGER
				{
				auto(1),
				manual(2)
				}
			MAX-ACCESS read-write
			STATUS current
			DESCRIPTION
				"Description."
			::= { sleIpAddr6Control 10 }

		
		-- 1.3.6.1.4.1.6296.101.26.2.2.11
		sleIPAddr6ControlStatus OBJECT-TYPE
			SYNTAX INTEGER
				{
				active(1),
				dadfailed(2),
				tentative(3),
				deprecated(4)
				}
			MAX-ACCESS read-write
			STATUS current
			DESCRIPTION
				"Description."
			::= { sleIpAddr6Control 11 }

		
		-- 1.3.6.1.4.1.6296.101.26.2.2.12
		sleIPAddr6ControlValidTime OBJECT-TYPE
			SYNTAX INTEGER (0..65535000)
			MAX-ACCESS read-write
			STATUS current
			DESCRIPTION
				"Description."
			::= { sleIpAddr6Control 12 }

		
		-- 1.3.6.1.4.1.6296.101.26.2.2.13
		sleIPAddr6ControlUsedTime OBJECT-TYPE
			SYNTAX INTEGER (0..65535000)
			MAX-ACCESS read-write
			STATUS current
			DESCRIPTION
				"Description."
			::= { sleIpAddr6Control 13 }

		
		-- 1.3.6.1.4.1.6296.101.26.2.3
		sleIpAddr6Notification OBJECT IDENTIFIER ::= { sleIpAddress6 3 }

		
		-- 1.3.6.1.4.1.6296.101.26.2.3.1
		sleIPAddr6Created NOTIFICATION-TYPE
			OBJECTS { sleIpAddr6Score, sleIpAddr6Type }
			STATUS current
			DESCRIPTION 
				"Description."
			::= { sleIpAddr6Notification 1 }

		
		-- 1.3.6.1.4.1.6296.101.26.2.3.2
		sleIPAddr6Deleted NOTIFICATION-TYPE
			OBJECTS { sleIPAddr6ControlIfIndex, sleIPAddr6ControlValue, sleIPAddr6ControlMask, sleIPAddr6ControlScore, sleIPAddr6ControlType
				 }
			STATUS current
			DESCRIPTION 
				"Description."
			::= { sleIpAddr6Notification 2 }

		
		-- 1.3.6.1.4.1.6296.101.26.2.3.3
		sleIPAddr6AllDeleted NOTIFICATION-TYPE
			OBJECTS { sleIPAddr6ControlIfIndex }
			STATUS current
			DESCRIPTION 
				"Description."
			::= { sleIpAddr6Notification 3 }

		
		-- 1.3.6.1.4.1.6296.101.26.3
		sleNdPrefix OBJECT IDENTIFIER ::= { sleNetwork6 3 }

		
		-- 1.3.6.1.4.1.6296.101.26.3.1
		sleNdPrefixTable OBJECT-TYPE
			SYNTAX SEQUENCE OF SleNdPrefixEntry
			MAX-ACCESS not-accessible
			STATUS current
			DESCRIPTION
				"Description."
			::= { sleNdPrefix 1 }

		
		-- 1.3.6.1.4.1.6296.101.26.3.1.1
		sleNdPrefixEntry OBJECT-TYPE
			SYNTAX SleNdPrefixEntry
			MAX-ACCESS not-accessible
			STATUS current
			DESCRIPTION
				"Description."
			INDEX { sleNetIf6Index, sleNdPrefixDefault, sleNdPrefixValue, sleNdPrefixMask }
			::= { sleNdPrefixTable 1 }

		
		SleNdPrefixEntry ::=
			SEQUENCE { 
				sleNdPrefixDefault
					INTEGER,
				sleNdPrefixValue
					InetAddressIPv6,
				sleNdPrefixMask
					InetAddressPrefixLength,
				sleNdPrefixValTime
					Gauge32,
				sleNdPrefixPreTime
					Gauge32,
				sleNdPrefixOffLink
					INTEGER,
				sleNdPrefixNoAutoconfig
					INTEGER
			 }

		-- 1.3.6.1.4.1.6296.101.26.3.1.1.1
		sleNdPrefixDefault OBJECT-TYPE
			SYNTAX INTEGER
				{
				no(0),
				yes(1)
				}
			MAX-ACCESS read-write
			STATUS current
			DESCRIPTION
				"If default flag is set, prefix value and mask have no mean."
			::= { sleNdPrefixEntry 1 }

		
		-- 1.3.6.1.4.1.6296.101.26.3.1.1.2
		sleNdPrefixValue OBJECT-TYPE
			SYNTAX InetAddressIPv6
			MAX-ACCESS read-write
			STATUS current
			DESCRIPTION
				"ND prefix value (X:X::X:X)"
			::= { sleNdPrefixEntry 2 }

		
		-- 1.3.6.1.4.1.6296.101.26.3.1.1.3
		sleNdPrefixMask OBJECT-TYPE
			SYNTAX InetAddressPrefixLength (0..65535)
			MAX-ACCESS read-write
			STATUS current
			DESCRIPTION
				"ND prefix mask"
			::= { sleNdPrefixEntry 3 }

		
		-- 1.3.6.1.4.1.6296.101.26.3.1.1.4
		sleNdPrefixValTime OBJECT-TYPE
			SYNTAX Gauge32 (0..4294967295)
			MAX-ACCESS read-write
			STATUS current
			DESCRIPTION
				"Valid lifetime of prefix (second)"
			::= { sleNdPrefixEntry 4 }

		
		-- 1.3.6.1.4.1.6296.101.26.3.1.1.5
		sleNdPrefixPreTime OBJECT-TYPE
			SYNTAX Gauge32 (0..4294967295)
			MAX-ACCESS read-write
			STATUS current
			DESCRIPTION
				"Preferred lifetime of prefix (second)"
			::= { sleNdPrefixEntry 5 }

		
		-- 1.3.6.1.4.1.6296.101.26.3.1.1.6
		sleNdPrefixOffLink OBJECT-TYPE
			SYNTAX INTEGER
				{
				disable(0),
				enable(1)
				}
			MAX-ACCESS read-write
			STATUS current
			DESCRIPTION
				"Use or do not use prefix for onlink determination"
			::= { sleNdPrefixEntry 6 }

		
		-- 1.3.6.1.4.1.6296.101.26.3.1.1.7
		sleNdPrefixNoAutoconfig OBJECT-TYPE
			SYNTAX INTEGER
				{
				disable(0),
				enable(1)
				}
			MAX-ACCESS read-write
			STATUS current
			DESCRIPTION
				"Use or do not use prefix for autoconfiguration"
			::= { sleNdPrefixEntry 7 }

		
		-- 1.3.6.1.4.1.6296.101.26.3.2
		sleNdPrefixControl OBJECT IDENTIFIER ::= { sleNdPrefix 2 }

		
		-- 1.3.6.1.4.1.6296.101.26.3.2.1
		sleNdPrefixControlRequest OBJECT-TYPE
			SYNTAX INTEGER
				{
				createNdPrefix(1),
				deleteNdPrefix(2)
				}
			MAX-ACCESS read-write
			STATUS current
			DESCRIPTION
				"Description."
			::= { sleNdPrefixControl 1 }

		
		-- 1.3.6.1.4.1.6296.101.26.3.2.2
		sleNdPrefixControlStatus OBJECT-TYPE
			SYNTAX SleControlStatusType
			MAX-ACCESS read-write
			STATUS current
			DESCRIPTION
				"Description."
			::= { sleNdPrefixControl 2 }

		
		-- 1.3.6.1.4.1.6296.101.26.3.2.3
		sleNdPrefixControlTimer OBJECT-TYPE
			SYNTAX Gauge32
			MAX-ACCESS read-write
			STATUS current
			DESCRIPTION
				"Description."
			::= { sleNdPrefixControl 3 }

		
		-- 1.3.6.1.4.1.6296.101.26.3.2.4
		sleNdPrefixControlTimeStamp OBJECT-TYPE
			SYNTAX TimeTicks
			MAX-ACCESS read-write
			STATUS current
			DESCRIPTION
				"Description."
			::= { sleNdPrefixControl 4 }

		
		-- 1.3.6.1.4.1.6296.101.26.3.2.5
		sleNdPrefixControlReqResult OBJECT-TYPE
			SYNTAX SleControlRequestResultType
			MAX-ACCESS read-write
			STATUS current
			DESCRIPTION
				"Description."
			::= { sleNdPrefixControl 5 }

		
		-- 1.3.6.1.4.1.6296.101.26.3.2.6
		sleNdPrefixControlIfIndex OBJECT-TYPE
			SYNTAX INTEGER (0..65535)
			MAX-ACCESS read-write
			STATUS current
			DESCRIPTION
				"Description."
			::= { sleNdPrefixControl 6 }

		
		-- 1.3.6.1.4.1.6296.101.26.3.2.7
		sleNdPrefixControlDefault OBJECT-TYPE
			SYNTAX INTEGER
				{
				no(0),
				yes(1)
				}
			MAX-ACCESS read-write
			STATUS current
			DESCRIPTION
				"Description."
			::= { sleNdPrefixControl 7 }

		
		-- 1.3.6.1.4.1.6296.101.26.3.2.8
		sleNdPrefixControlValue OBJECT-TYPE
			SYNTAX InetAddressIPv6
			MAX-ACCESS read-write
			STATUS current
			DESCRIPTION
				"Description."
			::= { sleNdPrefixControl 8 }

		
		-- 1.3.6.1.4.1.6296.101.26.3.2.9
		sleNdPrefixControlMask OBJECT-TYPE
			SYNTAX InetAddressPrefixLength
			MAX-ACCESS read-write
			STATUS current
			DESCRIPTION
				"Description."
			::= { sleNdPrefixControl 9 }

		
		-- 1.3.6.1.4.1.6296.101.26.3.2.10
		sleNdPrefixControlValTime OBJECT-TYPE
			SYNTAX Gauge32 (0..4294967295)
			MAX-ACCESS read-write
			STATUS current
			DESCRIPTION
				"Description."
			::= { sleNdPrefixControl 10 }

		
		-- 1.3.6.1.4.1.6296.101.26.3.2.11
		sleNdPrefixControlPreTime OBJECT-TYPE
			SYNTAX Gauge32 (0..4294967295)
			MAX-ACCESS read-write
			STATUS current
			DESCRIPTION
				"Description."
			::= { sleNdPrefixControl 11 }

		
		-- 1.3.6.1.4.1.6296.101.26.3.2.12
		sleNdPrefixControlOffLink OBJECT-TYPE
			SYNTAX INTEGER
				{
				disable(0),
				enable(1)
				}
			MAX-ACCESS read-write
			STATUS current
			DESCRIPTION
				"Description."
			::= { sleNdPrefixControl 12 }

		
		-- 1.3.6.1.4.1.6296.101.26.3.2.13
		sleNdPrefixControlNoAutoconfig OBJECT-TYPE
			SYNTAX INTEGER
				{
				disable(0),
				enable(1)
				}
			MAX-ACCESS read-write
			STATUS current
			DESCRIPTION
				"Description."
			::= { sleNdPrefixControl 13 }

		
		-- 1.3.6.1.4.1.6296.101.26.3.3
		sleNdPrefixNotification OBJECT IDENTIFIER ::= { sleNdPrefix 3 }

		
		-- 1.3.6.1.4.1.6296.101.26.3.3.1
		sleNdPrefixCreated NOTIFICATION-TYPE
			OBJECTS { sleNdPrefixControlRequest, sleNdPrefixControlTimeStamp, sleNdPrefixControlReqResult, sleNdPrefixControlIfIndex, sleNdPrefixDefault, 
				sleNdPrefixValue, sleNdPrefixMask, sleNdPrefixValTime, sleNdPrefixPreTime, sleNdPrefixOffLink, 
				sleNdPrefixNoAutoconfig }
			STATUS current
			DESCRIPTION 
				"Description."
			::= { sleNdPrefixNotification 1 }

		
		-- 1.3.6.1.4.1.6296.101.26.3.3.2
		sleNdPrefixDeleted NOTIFICATION-TYPE
			OBJECTS { sleNdPrefixControlRequest, sleNdPrefixControlTimeStamp, sleNdPrefixControlReqResult, sleNdPrefixControlIfIndex, sleNdPrefixControlDefault, 
				sleNdPrefixControlValue, sleNdPrefixControlMask }
			STATUS current
			DESCRIPTION 
				"Description."
			::= { sleNdPrefixNotification 2 }

		
		-- 1.3.6.1.4.1.6296.101.26.4
		sleNeighbour6 OBJECT IDENTIFIER ::= { sleNetwork6 4 }

		
		-- 1.3.6.1.4.1.6296.101.26.4.1
		sleNeighbour6Table OBJECT-TYPE
			SYNTAX SEQUENCE OF SleNeighbour6Entry
			MAX-ACCESS not-accessible
			STATUS current
			DESCRIPTION
				"Description."
			::= { sleNeighbour6 1 }

		
		-- 1.3.6.1.4.1.6296.101.26.4.1.1
		sleNeighbour6Entry OBJECT-TYPE
			SYNTAX SleNeighbour6Entry
			MAX-ACCESS not-accessible
			STATUS current
			DESCRIPTION
				"Description."
			INDEX { sleNetIf6Index, sleNeighbour6Address }
			::= { sleNeighbour6Table 1 }

		
		SleNeighbour6Entry ::=
			SEQUENCE { 
				sleNeighbour6Address
					InetAddressIPv6,
				sleNeighbour6PhyAddress
					OCTET STRING,
				sleNeighbour6PortIndex
					INTEGER,
				sleNeighbour6State
					INTEGER,
				sleNeighbour6HwType
					INTEGER,
				sleNeighbour6HwUsed
					INTEGER
			 }

		-- 1.3.6.1.4.1.6296.101.26.4.1.1.1
		sleNeighbour6Address OBJECT-TYPE
			SYNTAX InetAddressIPv6
			MAX-ACCESS read-write
			STATUS current
			DESCRIPTION
				"The IP6Address corresponding to the media-dependent `physical' address."
			::= { sleNeighbour6Entry 1 }

		
		-- 1.3.6.1.4.1.6296.101.26.4.1.1.2
		sleNeighbour6PhyAddress OBJECT-TYPE
			SYNTAX OCTET STRING
			MAX-ACCESS read-write
			STATUS current
			DESCRIPTION
				"The media-dependent `physical' address."
			::= { sleNeighbour6Entry 2 }

		
		-- 1.3.6.1.4.1.6296.101.26.4.1.1.3
		sleNeighbour6PortIndex OBJECT-TYPE
			SYNTAX INTEGER (0..255)
			MAX-ACCESS read-write
			STATUS current
			DESCRIPTION
				"The interface on which this entry's equivalence is effective.
				0: for any ports. (if sleNeighbour6HwUsed is 0, always 0)"
			::= { sleNeighbour6Entry 3 }

		
		-- 1.3.6.1.4.1.6296.101.26.4.1.1.4
		sleNeighbour6State OBJECT-TYPE
			SYNTAX INTEGER
				{
				static(0),
				dynamic(1)
				}
			MAX-ACCESS read-write
			STATUS current
			DESCRIPTION
				"Neighbour6 entry's currently status."
			::= { sleNeighbour6Entry 4 }

		
		-- 1.3.6.1.4.1.6296.101.26.4.1.1.5
		sleNeighbour6HwType OBJECT-TYPE
			SYNTAX INTEGER { ethernet(1) }
			MAX-ACCESS read-write
			STATUS current
			DESCRIPTION
				"Hardware Type of media"
			::= { sleNeighbour6Entry 5 }

		
		-- 1.3.6.1.4.1.6296.101.26.4.1.1.6
		sleNeighbour6HwUsed OBJECT-TYPE
			SYNTAX INTEGER
				{
				nonused(0),
				used(1)
				}
			MAX-ACCESS read-write
			STATUS current
			DESCRIPTION
				"Neighbour6 entry’s currently chip usage state."
			::= { sleNeighbour6Entry 6 }

		
		-- 1.3.6.1.4.1.6296.101.26.4.2
		sleNeighbour6Control OBJECT IDENTIFIER ::= { sleNeighbour6 2 }

		
		-- 1.3.6.1.4.1.6296.101.26.4.2.1
		sleNeighbour6ControlRequest OBJECT-TYPE
			SYNTAX INTEGER
				{
				createNeighbour6(1),
				deleteNeighbour6(2),
				clearNeighbour6(3),
				clearNeighbour6ByAddr(4)
				}
			MAX-ACCESS read-write
			STATUS current
			DESCRIPTION
				"Description."
			::= { sleNeighbour6Control 1 }

		
		-- 1.3.6.1.4.1.6296.101.26.4.2.2
		sleNeighbour6ControlStatus OBJECT-TYPE
			SYNTAX SleControlStatusType
			MAX-ACCESS read-write
			STATUS current
			DESCRIPTION
				"Description."
			::= { sleNeighbour6Control 2 }

		
		-- 1.3.6.1.4.1.6296.101.26.4.2.3
		sleNeighbour6ControlTimer OBJECT-TYPE
			SYNTAX Gauge32
			MAX-ACCESS read-write
			STATUS current
			DESCRIPTION
				"Description."
			::= { sleNeighbour6Control 3 }

		
		-- 1.3.6.1.4.1.6296.101.26.4.2.4
		sleNeighbour6ControlTimeStamp OBJECT-TYPE
			SYNTAX TimeTicks
			MAX-ACCESS read-write
			STATUS current
			DESCRIPTION
				"Description."
			::= { sleNeighbour6Control 4 }

		
		-- 1.3.6.1.4.1.6296.101.26.4.2.5
		sleNeighbour6ControlReqResult OBJECT-TYPE
			SYNTAX SleControlRequestResultType
			MAX-ACCESS read-write
			STATUS current
			DESCRIPTION
				"Description."
			::= { sleNeighbour6Control 5 }

		
		-- 1.3.6.1.4.1.6296.101.26.4.2.6
		sleNeighbour6ControlIfIndex OBJECT-TYPE
			SYNTAX INTEGER (0..65535)
			MAX-ACCESS read-write
			STATUS current
			DESCRIPTION
				"Description."
			::= { sleNeighbour6Control 6 }

		
		-- 1.3.6.1.4.1.6296.101.26.4.2.7
		sleNeighbour6ControlAddress OBJECT-TYPE
			SYNTAX InetAddressIPv6
			MAX-ACCESS read-write
			STATUS current
			DESCRIPTION
				"Description."
			::= { sleNeighbour6Control 7 }

		
		-- 1.3.6.1.4.1.6296.101.26.4.2.8
		sleNeighbour6ControlPhyAddress OBJECT-TYPE
			SYNTAX OCTET STRING
			MAX-ACCESS read-write
			STATUS current
			DESCRIPTION
				"Description."
			::= { sleNeighbour6Control 8 }

		
		-- 1.3.6.1.4.1.6296.101.26.4.2.9
		sleNeighbour6ControlMask OBJECT-TYPE
			SYNTAX INTEGER (0..128)
			MAX-ACCESS read-write
			STATUS current
			DESCRIPTION
				"Description."
			::= { sleNeighbour6Control 9 }

		
		-- 1.3.6.1.4.1.6296.101.26.4.3
		sleNeighbour6Notification OBJECT IDENTIFIER ::= { sleNeighbour6 3 }

		
		-- 1.3.6.1.4.1.6296.101.26.4.3.1
		sleNeighbour6Created NOTIFICATION-TYPE
			OBJECTS { sleNeighbour6ControlRequest, sleNeighbour6ControlTimeStamp, sleNeighbour6ControlReqResult, sleNeighbour6PhyAddress }
			STATUS current
			DESCRIPTION 
				"Description."
			::= { sleNeighbour6Notification 1 }

		
		-- 1.3.6.1.4.1.6296.101.26.4.3.2
		sleNeighbour6Deleted NOTIFICATION-TYPE
			OBJECTS { sleNeighbour6ControlRequest, sleNeighbour6ControlTimeStamp, sleNeighbour6ControlReqResult, sleNeighbour6ControlAddress, sleNeighbour6ControlMask, 
				sleNeighbour6ControlIfIndex }
			STATUS current
			DESCRIPTION 
				"Description."
			::= { sleNeighbour6Notification 2 }

		
		-- 1.3.6.1.4.1.6296.101.26.4.3.3
		sleNeighbour6Cleared NOTIFICATION-TYPE
			OBJECTS { sleNeighbour6ControlRequest, sleNeighbour6ControlTimeStamp, sleNeighbour6ControlReqResult, sleNeighbour6ControlIfIndex, sleNeighbour6ControlAddress, 
				sleNeighbour6ControlMask }
			STATUS current
			DESCRIPTION 
				"Description."
			::= { sleNeighbour6Notification 3 }

		
		-- 1.3.6.1.4.1.6296.101.26.5
		sleRoute6 OBJECT IDENTIFIER ::= { sleNetwork6 5 }

		
		-- 1.3.6.1.4.1.6296.101.26.5.1
		sleRoute6Table OBJECT-TYPE
			SYNTAX SEQUENCE OF SleRoute6Entry
			MAX-ACCESS not-accessible
			STATUS current
			DESCRIPTION
				"Description."
			::= { sleRoute6 1 }

		
		-- 1.3.6.1.4.1.6296.101.26.5.1.1
		sleRoute6Entry OBJECT-TYPE
			SYNTAX SleRoute6Entry
			MAX-ACCESS not-accessible
			STATUS current
			DESCRIPTION
				"Description."
			INDEX { sleIpVRFIndex, sleRoute6DstAddress, sleRoute6DstMask, sleRoute6Gateway, sleRoute6Proto, 
				sleNetIf6Index }
			::= { sleRoute6Table 1 }

		
		SleRoute6Entry ::=
			SEQUENCE { 
				sleRoute6DstAddress
					InetAddressIPv6,
				sleRoute6DstMask
					InetAddressPrefixLength,
				sleRoute6Proto
					INTEGER,
				sleRoute6Gateway
					InetAddressIPv6,
				sleRoute6Type
					INTEGER,
				sleRoute6Subtype
					INTEGER,
				sleRoute6Distance
					Integer32,
				sleRoute6Metric
					Integer32,
				sleRoute6Active
					INTEGER,
				sleRoute6NexthopStatus
					BITS,
				sleRoute6RibStatus
					BITS,
				sleRoute6BfdState
					INTEGER
			 }

		-- 1.3.6.1.4.1.6296.101.26.5.1.1.1
		sleRoute6DstAddress OBJECT-TYPE
			SYNTAX InetAddressIPv6
			MAX-ACCESS read-write
			STATUS current
			DESCRIPTION
				"The destination IP6 address of this route. Multiple routes to a single destination can appear in the table, but access to such multiple entries is dependent on the table-access mechanisms defined by the network management protocol in use."
			::= { sleRoute6Entry 1 }

		
		-- 1.3.6.1.4.1.6296.101.26.5.1.1.2
		sleRoute6DstMask OBJECT-TYPE
			SYNTAX InetAddressPrefixLength (0..65535)
			MAX-ACCESS read-write
			STATUS current
			DESCRIPTION
				"Indicate the mask to be logical-ANDed with the destination address before being compared to the value in the sleRoute6DstAddress field. "
			::= { sleRoute6Entry 2 }

		
		-- 1.3.6.1.4.1.6296.101.26.5.1.1.3
		sleRoute6Proto OBJECT-TYPE
			SYNTAX INTEGER
				{
				other(1),
				local(2),
				netmgmt(3),
				icmp(4),
				egp(5),
				ggp(6),
				hello(7),
				rip(8),
				isis(9),
				esis(10),
				ciscoIgrp(11),
				bbnSpfIgp(12),
				ospf(13),
				bgp(14),
				idpr(15),
				ciscoEigrp(16),
				dhcp(17)
				}
			MAX-ACCESS read-write
			STATUS current
			DESCRIPTION
				"The routing mechanism via which this route was learned. Inclusion of values for gateway routing protocols is not intended to imply that hosts should support those protocols.
				other - not specified
				local - local interface
				netmgmt - static route
				icmp - result of ICMP Redirect
				egp - Exterior Gateway Protocol
				ggp - Gateway-Gateway Protocol
				hello - FuzzBall HelloSpeak
				rip - Berkeley RIP or RIP-II
				is-is - Dual IS-IS
				es-is - ISO 9542
				ciscoIgrp - Cisco IGRP
				bbnSpfIgp - BBN SPF IGP
				ospf - Open Shortest Path First
				bgp - Border Gateway Protocol
				idpr - InterDomain Policy Routing
				ciscoEigrp - Cisco EIGRP
				"
			::= { sleRoute6Entry 3 }

		
		-- 1.3.6.1.4.1.6296.101.26.5.1.1.4
		sleRoute6Gateway OBJECT-TYPE
			SYNTAX InetAddressIPv6
			MAX-ACCESS read-write
			STATUS current
			DESCRIPTION
				"The Gateway IP 6 Address. 
				::0 : indicate invalid
				"
			::= { sleRoute6Entry 4 }

		
		-- 1.3.6.1.4.1.6296.101.26.5.1.1.5
		sleRoute6Type OBJECT-TYPE
			SYNTAX INTEGER
				{
				other(1),
				invalid(2),
				direct(3),
				indirect(4)
				}
			MAX-ACCESS read-write
			STATUS current
			DESCRIPTION
				"The type of route. Note that the values direct and indirect refer to the notion of direct and indirect routing in the IP architecture."
			::= { sleRoute6Entry 5 }

		
		-- 1.3.6.1.4.1.6296.101.26.5.1.1.6
		sleRoute6Subtype OBJECT-TYPE
			SYNTAX INTEGER
				{
				unknown(0),
				ospfIa(1),
				ospfNssa1(2),
				ospfNssa2(3),
				ospfExternal1(4),
				ospfExternal2(5),
				isisL1(8),
				isisL2(9),
				isisIa(10),
				bgpMpls(11)
				}
			MAX-ACCESS read-write
			STATUS current
			DESCRIPTION
				"The subtype of this route."
			::= { sleRoute6Entry 6 }

		
		-- 1.3.6.1.4.1.6296.101.26.5.1.1.7
		sleRoute6Distance OBJECT-TYPE
			SYNTAX Integer32 (1..255)
			MAX-ACCESS read-write
			STATUS current
			DESCRIPTION
				"The Distance value for this route."
			::= { sleRoute6Entry 7 }

		
		-- 1.3.6.1.4.1.6296.101.26.5.1.1.8
		sleRoute6Metric OBJECT-TYPE
			SYNTAX Integer32 (0..255)
			MAX-ACCESS read-write
			STATUS current
			DESCRIPTION
				"The primary routing metric for this route. The semantics of this metric are determined by the routing-protocol specified in the route's sleRoute6Proto value. If this metric is not used, its value should be set to -1."
			::= { sleRoute6Entry 8 }

		
		-- 1.3.6.1.4.1.6296.101.26.5.1.1.9
		sleRoute6Active OBJECT-TYPE
			SYNTAX INTEGER
				{
				inactive(0),
				active(1)
				}
			MAX-ACCESS read-write
			STATUS current
			DESCRIPTION
				"The active status for this routing entry."
			::= { sleRoute6Entry 9 }

		
		-- 1.3.6.1.4.1.6296.101.26.5.1.1.10
		sleRoute6NexthopStatus OBJECT-TYPE
			SYNTAX BITS
				{
				active(0),
				fib(1),
				recursive(2)
				}
			MAX-ACCESS read-write
			STATUS current
			DESCRIPTION
				"The nexthop status of this route."
			::= { sleRoute6Entry 10 }

		
		-- 1.3.6.1.4.1.6296.101.26.5.1.1.11
		sleRoute6RibStatus OBJECT-TYPE
			SYNTAX BITS
				{
				internal(0),
				selfroute(1),
				blackhole(2),
				nonfib(3),
				selected(4),
				changed(5),
				static(6),
				stale(7)
				}
			MAX-ACCESS read-write
			STATUS current
			DESCRIPTION
				"The rib status for this route."
			::= { sleRoute6Entry 11 }

		
		-- 1.3.6.1.4.1.6296.101.26.5.1.1.12
		sleRoute6BfdState OBJECT-TYPE
			SYNTAX INTEGER
				{
				inactive(0),
				active(1)
				}
			MAX-ACCESS read-write
			STATUS current
			DESCRIPTION
				"Static route entry’s BFD state."
			::= { sleRoute6Entry 12 }

		
		-- 1.3.6.1.4.1.6296.101.26.5.2
		sleRoute6Control OBJECT IDENTIFIER ::= { sleRoute6 2 }

		
		-- 1.3.6.1.4.1.6296.101.26.5.2.1
		sleRoute6ControlRequest OBJECT-TYPE
			SYNTAX INTEGER
				{
				createStaticRoute6(1),
				deleteStaticRoute6(2)
				}
			MAX-ACCESS read-write
			STATUS current
			DESCRIPTION
				"Description."
			::= { sleRoute6Control 1 }

		
		-- 1.3.6.1.4.1.6296.101.26.5.2.2
		sleRoute6ControlStatus OBJECT-TYPE
			SYNTAX SleControlStatusType
			MAX-ACCESS read-write
			STATUS current
			DESCRIPTION
				"Description."
			::= { sleRoute6Control 2 }

		
		-- 1.3.6.1.4.1.6296.101.26.5.2.3
		sleRoute6ControlTimer OBJECT-TYPE
			SYNTAX Gauge32
			MAX-ACCESS read-write
			STATUS current
			DESCRIPTION
				"Description."
			::= { sleRoute6Control 3 }

		
		-- 1.3.6.1.4.1.6296.101.26.5.2.4
		sleRoute6ControlTimeStamp OBJECT-TYPE
			SYNTAX TimeTicks
			MAX-ACCESS read-write
			STATUS current
			DESCRIPTION
				"Description."
			::= { sleRoute6Control 4 }

		
		-- 1.3.6.1.4.1.6296.101.26.5.2.5
		sleRoute6ControlReqResult OBJECT-TYPE
			SYNTAX SleControlRequestResultType
			MAX-ACCESS read-write
			STATUS current
			DESCRIPTION
				"Description."
			::= { sleRoute6Control 5 }

		
		-- 1.3.6.1.4.1.6296.101.26.5.2.6
		sleRoute6ControlVRFIndex OBJECT-TYPE
			SYNTAX Integer32 (0..2147483647)
			MAX-ACCESS read-write
			STATUS current
			DESCRIPTION
				"Description."
			::= { sleRoute6Control 6 }

		
		-- 1.3.6.1.4.1.6296.101.26.5.2.7
		sleRoute6ControlDstAddress OBJECT-TYPE
			SYNTAX InetAddressIPv6
			MAX-ACCESS read-write
			STATUS current
			DESCRIPTION
				"Description."
			::= { sleRoute6Control 7 }

		
		-- 1.3.6.1.4.1.6296.101.26.5.2.8
		sleRoute6ControlDstMask OBJECT-TYPE
			SYNTAX InetAddressPrefixLength
			MAX-ACCESS read-write
			STATUS current
			DESCRIPTION
				"Description."
			::= { sleRoute6Control 8 }

		
		-- 1.3.6.1.4.1.6296.101.26.5.2.9
		sleRoute6ControlGateway OBJECT-TYPE
			SYNTAX InetAddressIPv6
			MAX-ACCESS read-write
			STATUS current
			DESCRIPTION
				"Description."
			::= { sleRoute6Control 9 }

		
		-- 1.3.6.1.4.1.6296.101.26.5.2.10
		sleRoute6ControlInterface OBJECT-TYPE
			SYNTAX Integer32 (0..11023)
			MAX-ACCESS read-write
			STATUS current
			DESCRIPTION
				"Description."
			::= { sleRoute6Control 10 }

		
		-- 1.3.6.1.4.1.6296.101.26.5.2.11
		sleRoute6ControlDistance OBJECT-TYPE
			SYNTAX Integer32 (1..255)
			MAX-ACCESS read-write
			STATUS current
			DESCRIPTION
				"Description."
			::= { sleRoute6Control 11 }

		
		-- 1.3.6.1.4.1.6296.101.26.5.3
		sleRoute6Notification OBJECT IDENTIFIER ::= { sleRoute6 3 }

		
		-- 1.3.6.1.4.1.6296.101.26.5.3.1
		sleRoute6Created NOTIFICATION-TYPE
			OBJECTS { sleRoute6ControlRequest, sleRoute6ControlTimeStamp, sleRoute6ControlReqResult, sleRoute6DstAddress, sleRoute6DstMask, 
				sleRoute6Proto, sleRoute6Gateway, sleRoute6Distance }
			STATUS current
			DESCRIPTION 
				"Description."
			::= { sleRoute6Notification 1 }

		
		-- 1.3.6.1.4.1.6296.101.26.5.3.2
		sleRoute6Deleted NOTIFICATION-TYPE
			OBJECTS { sleRoute6ControlRequest, sleRoute6ControlTimeStamp, sleRoute6ControlReqResult, sleRoute6ControlVRFIndex, sleRoute6ControlDstAddress, 
				sleRoute6ControlDstMask, sleRoute6ControlGateway, sleRoute6ControlInterface }
			STATUS current
			DESCRIPTION 
				"Description."
			::= { sleRoute6Notification 2 }

		
		-- 1.3.6.1.4.1.6296.101.26.6
		sleNetworkBase6 OBJECT IDENTIFIER ::= { sleNetwork6 6 }

		
		-- 1.3.6.1.4.1.6296.101.26.6.1
		sleNetworkBase6Info OBJECT IDENTIFIER ::= { sleNetworkBase6 1 }

		
		-- 1.3.6.1.4.1.6296.101.26.6.1.1
		sleNetwork6DADinterval OBJECT-TYPE
			SYNTAX Integer32 (100..50000)
			MAX-ACCESS read-write
			STATUS current
			DESCRIPTION
				"Description."
			::= { sleNetworkBase6Info 1 }

		
		-- 1.3.6.1.4.1.6296.101.26.6.2
		sleNetworkBase6Control OBJECT IDENTIFIER ::= { sleNetworkBase6 2 }

		
		-- 1.3.6.1.4.1.6296.101.26.6.2.1
		sleNetworkBase6ControlRequest OBJECT-TYPE
			SYNTAX INTEGER { setDADInterval(1) }
			MAX-ACCESS read-write
			STATUS current
			DESCRIPTION
				"Description."
			::= { sleNetworkBase6Control 1 }

		
		-- 1.3.6.1.4.1.6296.101.26.6.2.2
		sleNetworkBase6ControlStatus OBJECT-TYPE
			SYNTAX SleControlStatusType
			MAX-ACCESS read-write
			STATUS current
			DESCRIPTION
				"Description."
			::= { sleNetworkBase6Control 2 }

		
		-- 1.3.6.1.4.1.6296.101.26.6.2.3
		sleNetworkBase6ControlTimer OBJECT-TYPE
			SYNTAX Gauge32
			MAX-ACCESS read-write
			STATUS current
			DESCRIPTION
				"Description."
			::= { sleNetworkBase6Control 3 }

		
		-- 1.3.6.1.4.1.6296.101.26.6.2.4
		sleNetworkBase6ControlTimeStamp OBJECT-TYPE
			SYNTAX TimeTicks
			MAX-ACCESS read-write
			STATUS current
			DESCRIPTION
				"Description."
			::= { sleNetworkBase6Control 4 }

		
		-- 1.3.6.1.4.1.6296.101.26.6.2.5
		sleNetworkBase6ControlReqResult OBJECT-TYPE
			SYNTAX SleControlRequestResultType
			MAX-ACCESS read-write
			STATUS current
			DESCRIPTION
				"Description."
			::= { sleNetworkBase6Control 5 }

		
		-- 1.3.6.1.4.1.6296.101.26.6.2.6
		sleNetworkBase6ControlDADinterval OBJECT-TYPE
			SYNTAX Integer32 (100..50000)
			MAX-ACCESS read-write
			STATUS current
			DESCRIPTION
				"Description."
			::= { sleNetworkBase6Control 6 }

		
		-- 1.3.6.1.4.1.6296.101.26.6.3
		sleNetworkBase6Notification OBJECT IDENTIFIER ::= { sleNetworkBase6 3 }

		
		-- 1.3.6.1.4.1.6296.101.26.6.3.1
		sleNetworkBase6DADIntervalChanged NOTIFICATION-TYPE
			OBJECTS { sleNetworkBase6ControlRequest, sleNetworkBase6ControlTimeStamp, sleNetworkBase6ControlReqResult, sleNetworkBase6ControlDADinterval }
			STATUS current
			DESCRIPTION 
				"Description."
			::= { sleNetworkBase6Notification 1 }

		
		-- 1.3.6.1.4.1.6296.101.26.7
		sleIpVRF6 OBJECT IDENTIFIER ::= { sleNetwork6 7 }

		
		-- 1.3.6.1.4.1.6296.101.26.7.1
		sleIpVRF6SelectionSourceTable OBJECT-TYPE
			SYNTAX SEQUENCE OF SleIpVRF6SelectionSourceEntry
			MAX-ACCESS not-accessible
			STATUS current
			DESCRIPTION
				"Description."
			::= { sleIpVRF6 1 }

		
		-- 1.3.6.1.4.1.6296.101.26.7.1.1
		sleIpVRF6SelectionSourceEntry OBJECT-TYPE
			SYNTAX SleIpVRF6SelectionSourceEntry
			MAX-ACCESS not-accessible
			STATUS current
			DESCRIPTION
				"Description."
			INDEX { sleIpVRF6SelectionSourceAddr, sleIpVRF6SelectionSourceMask }
			::= { sleIpVRF6SelectionSourceTable 1 }

		
		SleIpVRF6SelectionSourceEntry ::=
			SEQUENCE { 
				sleIpVRF6SelectionSourceAddr
					InetAddressIPv6,
				sleIpVRF6SelectionSourceMask
					InetAddressPrefixLength,
				sleIpVRF6SelectionSourceVRFIndex
					INTEGER
			 }

		-- 1.3.6.1.4.1.6296.101.26.7.1.1.1
		sleIpVRF6SelectionSourceAddr OBJECT-TYPE
			SYNTAX InetAddressIPv6
			MAX-ACCESS read-write
			STATUS current
			DESCRIPTION
				"IP6 Address of selection source"
			::= { sleIpVRF6SelectionSourceEntry 1 }

		
		-- 1.3.6.1.4.1.6296.101.26.7.1.1.2
		sleIpVRF6SelectionSourceMask OBJECT-TYPE
			SYNTAX InetAddressPrefixLength (0..128)
			MAX-ACCESS read-write
			STATUS current
			DESCRIPTION
				"Address mask of selection source"
			::= { sleIpVRF6SelectionSourceEntry 2 }

		
		-- 1.3.6.1.4.1.6296.101.26.7.1.1.3
		sleIpVRF6SelectionSourceVRFIndex OBJECT-TYPE
			SYNTAX INTEGER (0..2147483647)
			MAX-ACCESS read-write
			STATUS current
			DESCRIPTION
				"sleIpVRFIndex in sleIpVRF"
			::= { sleIpVRF6SelectionSourceEntry 3 }

		
		-- 1.3.6.1.4.1.6296.101.26.7.2
		sleIpVRF6SelectionSourceControl OBJECT IDENTIFIER ::= { sleIpVRF6 2 }

		
		-- 1.3.6.1.4.1.6296.101.26.7.2.1
		sleIpVRF6SelectionSourceControlRequest OBJECT-TYPE
			SYNTAX INTEGER
				{
				createVRF6SelectionSource(1),
				deleteVRF6SelectionSource(2)
				}
			MAX-ACCESS read-write
			STATUS current
			DESCRIPTION
				"Description."
			::= { sleIpVRF6SelectionSourceControl 1 }

		
		-- 1.3.6.1.4.1.6296.101.26.7.2.2
		sleIpVRF6SelectionSourceControlStatus OBJECT-TYPE
			SYNTAX SleControlStatusType
			MAX-ACCESS read-write
			STATUS current
			DESCRIPTION
				"Description."
			::= { sleIpVRF6SelectionSourceControl 2 }

		
		-- 1.3.6.1.4.1.6296.101.26.7.2.3
		sleIpVRF6SelectionSourceControlTimer OBJECT-TYPE
			SYNTAX Gauge32
			MAX-ACCESS read-write
			STATUS current
			DESCRIPTION
				"Description."
			::= { sleIpVRF6SelectionSourceControl 3 }

		
		-- 1.3.6.1.4.1.6296.101.26.7.2.4
		sleIpVRF6SelectionSourceControlTimeStamp OBJECT-TYPE
			SYNTAX TimeTicks
			MAX-ACCESS read-write
			STATUS current
			DESCRIPTION
				"Description."
			::= { sleIpVRF6SelectionSourceControl 4 }

		
		-- 1.3.6.1.4.1.6296.101.26.7.2.5
		sleIpVRF6SelectionSourceControlReqResult OBJECT-TYPE
			SYNTAX SleControlRequestResultType
			MAX-ACCESS read-write
			STATUS current
			DESCRIPTION
				"Description."
			::= { sleIpVRF6SelectionSourceControl 5 }

		
		-- 1.3.6.1.4.1.6296.101.26.7.2.6
		sleIpVRF6SelectionSourceControlAddr OBJECT-TYPE
			SYNTAX InetAddressIPv6
			MAX-ACCESS read-write
			STATUS current
			DESCRIPTION
				"IP6 Address of selection source"
			::= { sleIpVRF6SelectionSourceControl 6 }

		
		-- 1.3.6.1.4.1.6296.101.26.7.2.7
		sleIpVRF6SelectionSourceControlMask OBJECT-TYPE
			SYNTAX InetAddressPrefixLength
			MAX-ACCESS read-write
			STATUS current
			DESCRIPTION
				"Address mask of selection source"
			::= { sleIpVRF6SelectionSourceControl 7 }

		
		-- 1.3.6.1.4.1.6296.101.26.7.2.8
		sleIpVRF6SelectionSourceControlVRFIndex OBJECT-TYPE
			SYNTAX INTEGER (0..2147483647)
			MAX-ACCESS read-write
			STATUS current
			DESCRIPTION
				"sleIpVRFIndex in sleIpVRF"
			::= { sleIpVRF6SelectionSourceControl 8 }

		
		-- 1.3.6.1.4.1.6296.101.26.7.3
		sleIpVRF6SelectionSourceNotification OBJECT IDENTIFIER ::= { sleIpVRF6 3 }

		
		-- 1.3.6.1.4.1.6296.101.26.7.3.1
		sleIpVRF6SelectionSourceCreated NOTIFICATION-TYPE
			OBJECTS { sleIpVRF6SelectionSourceControlRequest, sleIpVRF6SelectionSourceControlTimeStamp, sleIpVRF6SelectionSourceControlReqResult, sleIpVRF6SelectionSourceVRFIndex }
			STATUS current
			DESCRIPTION 
				"Description."
			::= { sleIpVRF6SelectionSourceNotification 1 }

		
		-- 1.3.6.1.4.1.6296.101.26.7.3.2
		sleIpVRF6SelectionSourceDeleted NOTIFICATION-TYPE
			OBJECTS { sleIpVRF6SelectionSourceControlRequest, sleIpVRF6SelectionSourceControlTimeStamp, sleIpVRF6SelectionSourceControlMask, sleIpVRF6SelectionSourceControlAddr, sleIpVRF6SelectionSourceControlReqResult
				 }
			STATUS current
			DESCRIPTION 
				"Description."
			::= { sleIpVRF6SelectionSourceNotification 2 }

		
		-- 1.3.6.1.4.1.6296.101.26.9
		sleNetwork6Group OBJECT-GROUP
			OBJECTS { sleIPAddr6ControlIfIndex, sleIPAddr6ControlValue, sleIPAddr6ControlMask, sleIPAddr6ControlScore, sleIPAddr6ControlType, 
				sleIPAddr6ControlValidTime, sleIPAddr6ControlUsedTime, sleIpAddr6Mask, sleIpAddr6Score, sleIpAddr6Status, 
				sleIpAddr6ValidTime, sleIpAddr6UsedTime, sleIpAddr6ControlRequest, sleIpAddr6ControlTimer, sleIpAddr6ControlTimeStamp, 
				sleIpAddr6ControlReqResult, sleNetIf6Index, sleNetIf6Name, sleNetIf6Ipv6State, sleNetIf6Mode, 
				sleNetIf6RouteMap, sleNetIf6AddrAutoConf, sleNetIf6AddrAutoConfDefault, sleNetIf6NdRouterPref, sleNetIf6SuppressRA, 
				sleNetIf6NdRaMaxInterval, sleNetIf6NdRaMinInterval, sleNetIf6NdRaLifeTime, sleNetIf6NdRaReachTime, sleNetIf6NdRaHopLimit, 
				sleNetIf6NdRetransTime, sleNetIf6NdMFlag, sleNetIf6NdOFlag, sleNetIf6ControlRequest, sleNetIf6ControlStatus, 
				sleNetIf6ControlTimer, sleNetIf6ControlTimeStamp, sleNetIf6ControlReqResult, sleNetIf6ControlIndex, sleNetIf6ControlIpv6State, 
				sleNetIf6ControlMode, sleNetIf6ControlRouteMap, sleNetIf6ControlAutoConf, sleNetIf6ControlAutoConfDefault, sleNetIf6ControlNdRouterPref, 
				sleNetIf6ControlNdSuppressRA, sleNetIf6ControlNdMaxInterval, sleNetIf6ControlNdMinInterval, sleNetIf6ControlNdRaLifeTime, sleNetIf6ControlNdRaReachTime, 
				sleNetIf6ControlNdRaHopLimit, sleNetIf6ControlNdRetransTime, sleNetIf6ControlNdMFlag, sleNetIf6ControlNdOFlag, sleNdPrefixValue, 
				sleNdPrefixValTime, sleNdPrefixPreTime, sleNdPrefixOffLink, sleNdPrefixNoAutoconfig, sleNdPrefixControlRequest, 
				sleNdPrefixControlStatus, sleNdPrefixControlTimer, sleNdPrefixControlTimeStamp, sleNdPrefixControlReqResult, sleNdPrefixControlIfIndex, 
				sleNdPrefixControlValue, sleNdPrefixControlValTime, sleNdPrefixControlPreTime, sleNdPrefixControlOffLink, sleNdPrefixControlNoAutoconfig, 
				sleNetIf6NdProxy, sleNetIf6ControlNdProxy, sleNetIf6NdDadAttempt, sleNetIf6ControlNdDadAttempt, sleNeighbour6HwUsed, 
				sleNeighbour6ControlIfIndex, sleNeighbour6ControlAddress, sleNeighbour6ControlPhyAddress, sleNeighbour6ControlMask, sleNeighbour6ControlRequest, 
				sleNeighbour6ControlStatus, sleNeighbour6ControlTimer, sleNeighbour6ControlTimeStamp, sleNeighbour6ControlReqResult, sleNeighbour6Address, 
				sleNeighbour6PhyAddress, sleNeighbour6PortIndex, sleNeighbour6State, sleNeighbour6HwType, sleNdPrefixMask, 
				sleNdPrefixControlMask, sleNdPrefixDefault, sleNdPrefixControlDefault, sleRoute6DstAddress, sleRoute6DstMask, 
				sleRoute6Proto, sleRoute6Gateway, sleRoute6Type, sleRoute6Subtype, sleRoute6Distance, 
				sleRoute6Metric, sleRoute6Active, sleRoute6NexthopStatus, sleRoute6RibStatus, sleRoute6BfdState, 
				sleRoute6ControlRequest, sleRoute6ControlStatus, sleRoute6ControlTimer, sleRoute6ControlTimeStamp, sleRoute6ControlReqResult, 
				sleRoute6ControlVRFIndex, sleRoute6ControlDstAddress, sleRoute6ControlDstMask, sleRoute6ControlGateway, sleRoute6ControlInterface, 
				sleRoute6ControlDistance, sleNetwork6DADinterval, sleNetworkBase6ControlRequest, sleNetworkBase6ControlStatus, sleNetworkBase6ControlTimer, 
				sleNetworkBase6ControlTimeStamp, sleNetworkBase6ControlReqResult, sleNetworkBase6ControlDADinterval, sleIpAddr6Value, sleIpAddr6Type, 
				sleIpVRF6SelectionSourceControlVRFIndex, sleIpVRF6SelectionSourceControlMask, sleIpVRF6SelectionSourceControlAddr, sleIpVRF6SelectionSourceControlReqResult, sleIpVRF6SelectionSourceControlTimeStamp, 
				sleIpVRF6SelectionSourceControlTimer, sleIpVRF6SelectionSourceControlStatus, sleIpVRF6SelectionSourceControlRequest, sleIpVRF6SelectionSourceVRFIndex, sleIpVRF6SelectionSourceMask, 
				sleIpVRF6SelectionSourceAddr, sleIpAddr6ControlStatus, sleIpVRFIndex, sleNetIf6Identifier, sleNetIf6Ip6MartianFilter, 
				sleNetIf6ControlIdentifier, sleNetIf6ControlIp6MartianFilter, sleIPAddr6ControlStatus }
			STATUS current
			DESCRIPTION 
				"Description."
			::= { sleNetwork6 9 }

		
		-- 1.3.6.1.4.1.6296.101.26.10
		sleNetwork6NotificationGroup NOTIFICATION-GROUP
			NOTIFICATIONS { sleIPAddr6Created, sleNdPrefixCreated, sleNdPrefixDeleted, sleIPAddr6AllDeleted, sleNeighbour6Created, 
				sleNeighbour6Deleted, sleNeighbour6Cleared, sleIpVRF6SelectionSourceDeleted, sleIpVRF6SelectionSourceCreated, sleIdentifierChanged, 
				sleIp6MartianFilterChanged, sleIPAddr6Deleted, sleIp6StateChanged, sleIfModeChanged, sleAddrAutoConfChanged, 
				sleNdProfileChanged, sleRouteMapSet, sleRouteMapUnset, sleRoute6Created, sleRoute6Deleted, 
				sleNetworkBase6DADIntervalChanged }
			STATUS current
			DESCRIPTION 
				"Description."
			::= { sleNetwork6 10 }

		
	
	END

--
-- sle-network6-mib.mib
--
