--
-- sle-ripng-mib.mib
-- MIB generated by MG-SOFT Visual MIB Builder Version 6.0  Build 88
-- Monday, March 23, 2015 at 15:00:56
--

	SLE-RIPng-MIB DEFINITIONS ::= BEGIN
 
		IMPORTS
			sleMgmt			
				FROM DASAN-SMI			
			InetAddress			
				FROM INET-ADDRESS-MIB			
			SleControlStatusType, SleControlRequestResultType			
				FROM SLE-TC-MIB			
			OBJECT-GROUP, NOTIFICATION-GROUP			
				FROM SNMPv2-CONF			
			TimeTicks, IpAddress, Gauge32, OBJECT-TYPE, MODULE-IDENTITY, 
			NOTIFICATION-TYPE			
				FROM SNMPv2-SMI;
	
	
		-- 1.3.6.1.4.1.6296.101.55
		sleRIPng MODULE-IDENTITY 
			LAST-UPDATED "200412291441Z"		-- December 29, 2004 at 14:41 GMT
			ORGANIZATION 
				"HANASOFT"
			CONTACT-INFO 
				" "
			DESCRIPTION 
				"This MIB contains information about RIPng version 2."
			REVISION "201003211954Z"		-- March 21, 2010 at 19:54 GMT
			DESCRIPTION 
				"OSFPv2"
			::= { sleMgmt 55 }

		
	
	
--
-- Node definitions
--
	
		-- 1.3.6.1.4.1.6296.101.55.1
		sleRIPngBase OBJECT IDENTIFIER ::= { sleRIPng 1 }

		
		-- 1.3.6.1.4.1.6296.101.55.1.1
		sleRIPngBaseInfo OBJECT IDENTIFIER ::= { sleRIPngBase 1 }

		
		-- 1.3.6.1.4.1.6296.101.55.1.1.1
		sleRIPngDefaultMetric OBJECT-TYPE
			SYNTAX INTEGER (1..16)
			MAX-ACCESS read-only
			STATUS current
			DESCRIPTION
				"Description."
			DEFVAL { 1 }
			::= { sleRIPngBaseInfo 1 }

		
		-- 1.3.6.1.4.1.6296.101.55.1.1.2
		sleRIPngDefaultInformationOrg OBJECT-TYPE
			SYNTAX INTEGER
				{
				disable(0),
				enable(1)
				}
			MAX-ACCESS read-only
			STATUS current
			DESCRIPTION
				"Description."
			DEFVAL { 0 }
			::= { sleRIPngBaseInfo 2 }

		
		-- 1.3.6.1.4.1.6296.101.55.1.1.3
		sleRIPngDefaultDistance OBJECT-TYPE
			SYNTAX INTEGER (1..255)
			MAX-ACCESS read-only
			STATUS current
			DESCRIPTION
				"Description."
			::= { sleRIPngBaseInfo 3 }

		
		-- 1.3.6.1.4.1.6296.101.55.1.1.4
		sleRIPngRecvBufferSize OBJECT-TYPE
			SYNTAX INTEGER (8192..2147483647)
			MAX-ACCESS read-only
			STATUS current
			DESCRIPTION
				"Description."
			DEFVAL { 215040 }
			::= { sleRIPngBaseInfo 4 }

		
		-- 1.3.6.1.4.1.6296.101.55.1.1.5
		sleRIPngMaximumPaths OBJECT-TYPE
			SYNTAX INTEGER (1..8)
			MAX-ACCESS read-only
			STATUS current
			DESCRIPTION
				"Description."
			DEFVAL { 1 }
			::= { sleRIPngBaseInfo 5 }

		
		-- 1.3.6.1.4.1.6296.101.55.1.1.6
		sleRIPngMaximumPrefixRoute OBJECT-TYPE
			SYNTAX INTEGER (0..65535)
			MAX-ACCESS read-only
			STATUS current
			DESCRIPTION
				"Description."
			DEFVAL { 1 }
			::= { sleRIPngBaseInfo 6 }

		
		-- 1.3.6.1.4.1.6296.101.55.1.1.7
		sleRIPngMaximumPrefixRoutePercent OBJECT-TYPE
			SYNTAX INTEGER (1..100)
			MAX-ACCESS read-only
			STATUS current
			DESCRIPTION
				"Description."
			DEFVAL { 75 }
			::= { sleRIPngBaseInfo 7 }

		
		-- 1.3.6.1.4.1.6296.101.55.1.1.8
		sleRIPngMetricSumApply OBJECT-TYPE
			SYNTAX INTEGER
				{
				disable(0),
				enable(1)
				}
			MAX-ACCESS read-only
			STATUS current
			DESCRIPTION
				"Description."
			DEFVAL { 0 }
			::= { sleRIPngBaseInfo 8 }

		
		-- 1.3.6.1.4.1.6296.101.55.1.1.9
		sleRIPngBasicUpdateTimer OBJECT-TYPE
			SYNTAX INTEGER (5..2147483647)
			MAX-ACCESS read-only
			STATUS current
			DESCRIPTION
				"Description."
			DEFVAL { 30 }
			::= { sleRIPngBaseInfo 9 }

		
		-- 1.3.6.1.4.1.6296.101.55.1.1.10
		sleRIPngBasicTimeoutTimer OBJECT-TYPE
			SYNTAX INTEGER (5..2147483647)
			MAX-ACCESS read-only
			STATUS current
			DESCRIPTION
				"Description."
			DEFVAL { 180 }
			::= { sleRIPngBaseInfo 10 }

		
		-- 1.3.6.1.4.1.6296.101.55.1.1.11
		sleRIPngBasicGarbageTimer OBJECT-TYPE
			SYNTAX INTEGER (5..2147483647)
			MAX-ACCESS read-only
			STATUS current
			DESCRIPTION
				"Description."
			DEFVAL { 120 }
			::= { sleRIPngBaseInfo 11 }

		
		-- 1.3.6.1.4.1.6296.101.55.1.2
		sleRIPngBaseControl OBJECT IDENTIFIER ::= { sleRIPngBase 2 }

		
		-- 1.3.6.1.4.1.6296.101.55.1.2.1
		sleRIPngControlRequest OBJECT-TYPE
			SYNTAX INTEGER
				{
				createRIPngMode(1),
				deleteRIPngMode(2),
				setRIPngDefaultMetric(3),
				setRIPngDefaultInformationOrg(4),
				setRIPngDefaultDistance(5),
				setRIPngRecvBufferSize(6),
				setRIPngMaximumPaths(7),
				setRIPngMaximumPrefixRouteProfile(8),
				setRIPngMetricSumApply(9),
				setRIPngBasicTimersProfile(10),
				clearRIPngAll(11),
				clearRIPngRoute(12),
				clearRIPngProtoType(13)
				}
			MAX-ACCESS read-write
			STATUS current
			DESCRIPTION
				"Description."
			::= { sleRIPngBaseControl 1 }

		
		-- 1.3.6.1.4.1.6296.101.55.1.2.2
		sleRIPngControlStatus OBJECT-TYPE
			SYNTAX SleControlStatusType
			MAX-ACCESS read-only
			STATUS current
			DESCRIPTION
				"1.3.6.1.4.1.6296.101.61.1.2.2"
			::= { sleRIPngBaseControl 2 }

		
		-- 1.3.6.1.4.1.6296.101.55.1.2.3
		sleRIPngControlTimer OBJECT-TYPE
			SYNTAX Gauge32
			MAX-ACCESS read-write
			STATUS current
			DESCRIPTION
				"1.3.6.1.4.1.6296.101.61.1.2.3"
			::= { sleRIPngBaseControl 3 }

		
		-- 1.3.6.1.4.1.6296.101.55.1.2.4
		sleRIPngControlTimeStamp OBJECT-TYPE
			SYNTAX TimeTicks
			MAX-ACCESS read-only
			STATUS current
			DESCRIPTION
				"1.3.6.1.4.1.6296.101.61.1.2.4"
			::= { sleRIPngBaseControl 4 }

		
		-- 1.3.6.1.4.1.6296.101.55.1.2.5
		sleRIPngControlReqResult OBJECT-TYPE
			SYNTAX SleControlRequestResultType
			MAX-ACCESS read-only
			STATUS current
			DESCRIPTION
				"1.3.6.1.4.1.6296.101.61.1.2.5"
			::= { sleRIPngBaseControl 5 }

		
		-- 1.3.6.1.4.1.6296.101.55.1.2.6
		sleRIPngControlDefaultMetric OBJECT-TYPE
			SYNTAX INTEGER (1..16)
			MAX-ACCESS read-only
			STATUS current
			DESCRIPTION
				"1.3.6.1.4.1.6296.101.61.1.2.7"
			DEFVAL { 1 }
			::= { sleRIPngBaseControl 6 }

		
		-- 1.3.6.1.4.1.6296.101.55.1.2.7
		sleRIPngControlDefaultInformationOrg OBJECT-TYPE
			SYNTAX INTEGER
				{
				disable(0),
				enable(1)
				}
			MAX-ACCESS read-only
			STATUS current
			DESCRIPTION
				"1.3.6.1.4.1.6296.101.61.1.2.8"
			DEFVAL { 0 }
			::= { sleRIPngBaseControl 7 }

		
		-- 1.3.6.1.4.1.6296.101.55.1.2.8
		sleRIPngControlDefaultDistance OBJECT-TYPE
			SYNTAX INTEGER (1..255)
			MAX-ACCESS read-only
			STATUS current
			DESCRIPTION
				"Description."
			::= { sleRIPngBaseControl 8 }

		
		-- 1.3.6.1.4.1.6296.101.55.1.2.9
		sleRIPngControlRecvBufferSize OBJECT-TYPE
			SYNTAX INTEGER (8192..2147483647)
			MAX-ACCESS read-only
			STATUS current
			DESCRIPTION
				"1.3.6.1.4.1.6296.101.61.1.2.9"
			DEFVAL { 215040 }
			::= { sleRIPngBaseControl 9 }

		
		-- 1.3.6.1.4.1.6296.101.55.1.2.10
		sleRIPngControlMaximumPaths OBJECT-TYPE
			SYNTAX INTEGER (1..8)
			MAX-ACCESS read-only
			STATUS current
			DESCRIPTION
				"1.3.6.1.4.1.6296.101.61.1.2.10"
			DEFVAL { 1 }
			::= { sleRIPngBaseControl 10 }

		
		-- 1.3.6.1.4.1.6296.101.55.1.2.11
		sleRIPngControlMaximumPrefixRoute OBJECT-TYPE
			SYNTAX INTEGER (0..65535)
			MAX-ACCESS read-only
			STATUS current
			DESCRIPTION
				"1.3.6.1.4.1.6296.101.61.1.2.11"
			DEFVAL { 1 }
			::= { sleRIPngBaseControl 11 }

		
		-- 1.3.6.1.4.1.6296.101.55.1.2.12
		sleRIPngControlMaximumPrefixRoutePercent OBJECT-TYPE
			SYNTAX INTEGER (1..100)
			MAX-ACCESS read-only
			STATUS current
			DESCRIPTION
				"1.3.6.1.4.1.6296.101.61.1.2.12"
			DEFVAL { 75 }
			::= { sleRIPngBaseControl 12 }

		
		-- 1.3.6.1.4.1.6296.101.55.1.2.13
		sleRIPngControlMetricSumApply OBJECT-TYPE
			SYNTAX INTEGER
				{
				disable(0),
				enable(1)
				}
			MAX-ACCESS read-only
			STATUS current
			DESCRIPTION
				"1.3.6.1.4.1.6296.101.61.1.2.13"
			DEFVAL { 0 }
			::= { sleRIPngBaseControl 13 }

		
		-- 1.3.6.1.4.1.6296.101.55.1.2.14
		sleRIPngControlBasicUpdateTimer OBJECT-TYPE
			SYNTAX INTEGER (5..2147483647)
			MAX-ACCESS read-only
			STATUS current
			DESCRIPTION
				"1.3.6.1.4.1.6296.101.61.1.2.14"
			DEFVAL { 30 }
			::= { sleRIPngBaseControl 14 }

		
		-- 1.3.6.1.4.1.6296.101.55.1.2.15
		sleRIPngControlBasicTimeoutTimer OBJECT-TYPE
			SYNTAX INTEGER (5..2147483647)
			MAX-ACCESS read-only
			STATUS current
			DESCRIPTION
				"1.3.6.1.4.1.6296.101.61.1.2.15"
			DEFVAL { 180 }
			::= { sleRIPngBaseControl 15 }

		
		-- 1.3.6.1.4.1.6296.101.55.1.2.16
		sleRIPngControlBasicGarbageTimer OBJECT-TYPE
			SYNTAX INTEGER (5..2147483647)
			MAX-ACCESS read-only
			STATUS current
			DESCRIPTION
				"1.3.6.1.4.1.6296.101.61.1.2.16"
			DEFVAL { 180 }
			::= { sleRIPngBaseControl 16 }

		
		-- 1.3.6.1.4.1.6296.101.55.1.2.17
		sleRIPngControlClearRoutePrefix OBJECT-TYPE
			SYNTAX InetAddress
			MAX-ACCESS read-only
			STATUS current
			DESCRIPTION
				"1.3.6.1.4.1.6296.101.61.1.2.13"
			::= { sleRIPngBaseControl 17 }

		
		-- 1.3.6.1.4.1.6296.101.55.1.2.18
		sleRIPngControlClearRouteMask OBJECT-TYPE
			SYNTAX INTEGER (0..128)
			MAX-ACCESS read-only
			STATUS current
			DESCRIPTION
				"1.3.6.1.4.1.6296.101.61.1.2.13"
			::= { sleRIPngBaseControl 18 }

		
		-- 1.3.6.1.4.1.6296.101.55.1.2.19
		sleRIPngControlClearProtoTpye OBJECT-TYPE
			SYNTAX INTEGER
				{
				kernel(1),
				connected(2),
				static(3),
				bgp(4),
				ospf(5),
				rip(6)
				}
			MAX-ACCESS read-only
			STATUS current
			DESCRIPTION
				"1.3.6.1.4.1.6296.101.61.1.2.13"
			DEFVAL { 0 }
			::= { sleRIPngBaseControl 19 }

		
		-- 1.3.6.1.4.1.6296.101.55.1.3
		sleRIPngBaseNotification OBJECT IDENTIFIER ::= { sleRIPngBase 3 }

		
		-- 1.3.6.1.4.1.6296.101.55.1.3.1
		sleRIPngModeCreated NOTIFICATION-TYPE
			OBJECTS { sleRIPngControlRequest, sleRIPngControlTimeStamp, sleRIPngControlReqResult }
			STATUS current
			DESCRIPTION 
				"Description."
			::= { sleRIPngBaseNotification 1 }

		
		-- 1.3.6.1.4.1.6296.101.55.1.3.2
		sleRIPngModeDeleted NOTIFICATION-TYPE
			OBJECTS { sleRIPngControlRequest, sleRIPngControlTimeStamp, sleRIPngControlReqResult }
			STATUS current
			DESCRIPTION 
				"Description."
			::= { sleRIPngBaseNotification 2 }

		
		-- 1.3.6.1.4.1.6296.101.55.1.3.3
		sleRIPngDefaultMetricChanged NOTIFICATION-TYPE
			OBJECTS { sleRIPngControlRequest, sleRIPngControlTimeStamp, sleRIPngControlReqResult, sleRIPngDefaultMetric }
			STATUS current
			DESCRIPTION 
				"Description."
			::= { sleRIPngBaseNotification 3 }

		
		-- 1.3.6.1.4.1.6296.101.55.1.3.4
		sleRIPngDefaultInformationOrgChanged NOTIFICATION-TYPE
			OBJECTS { sleRIPngControlRequest, sleRIPngControlTimeStamp, sleRIPngControlReqResult, sleRIPngDefaultInformationOrg }
			STATUS current
			DESCRIPTION 
				"Description."
			::= { sleRIPngBaseNotification 4 }

		
		-- 1.3.6.1.4.1.6296.101.55.1.3.5
		sleRIPngDefaultDistanceChanged NOTIFICATION-TYPE
			OBJECTS { sleRIPngControlRequest, sleRIPngControlTimeStamp, sleRIPngControlReqResult, sleRIPngDefaultDistance }
			STATUS current
			DESCRIPTION 
				"Description."
			::= { sleRIPngBaseNotification 5 }

		
		-- 1.3.6.1.4.1.6296.101.55.1.3.6
		sleRIPngRecvBufferSizeChanged NOTIFICATION-TYPE
			OBJECTS { sleRIPngControlRequest, sleRIPngControlTimeStamp, sleRIPngControlReqResult, sleRIPngRecvBufferSize }
			STATUS current
			DESCRIPTION 
				"Description."
			::= { sleRIPngBaseNotification 6 }

		
		-- 1.3.6.1.4.1.6296.101.55.1.3.7
		sleRIPngMaximumPathsChanged NOTIFICATION-TYPE
			OBJECTS { sleRIPngControlRequest, sleRIPngControlTimeStamp, sleRIPngControlReqResult, sleRIPngMaximumPaths }
			STATUS current
			DESCRIPTION 
				"Description."
			::= { sleRIPngBaseNotification 7 }

		
		-- 1.3.6.1.4.1.6296.101.55.1.3.8
		sleRIPngMaximumPrefixProfileChanged NOTIFICATION-TYPE
			OBJECTS { sleRIPngControlRequest, sleRIPngControlTimeStamp, sleRIPngControlReqResult, sleRIPngMaximumPrefixRoute, sleRIPngMaximumPrefixRoutePercent
				 }
			STATUS current
			DESCRIPTION 
				"Description."
			::= { sleRIPngBaseNotification 8 }

		
		-- 1.3.6.1.4.1.6296.101.55.1.3.9
		sleRIPngMetricSumApplyChanged NOTIFICATION-TYPE
			OBJECTS { sleRIPngControlRequest, sleRIPngControlTimeStamp, sleRIPngControlReqResult, sleRIPngMetricSumApply }
			STATUS current
			DESCRIPTION 
				"Description."
			::= { sleRIPngBaseNotification 9 }

		
		-- 1.3.6.1.4.1.6296.101.55.1.3.10
		sleRIPngTimersChanged NOTIFICATION-TYPE
			OBJECTS { sleRIPngControlRequest, sleRIPngControlTimeStamp, sleRIPngControlReqResult, sleRIPngBasicUpdateTimer, sleRIPngBasicTimeoutTimer, 
				sleRIPngBasicGarbageTimer }
			STATUS current
			DESCRIPTION 
				"Description."
			::= { sleRIPngBaseNotification 10 }

		
		-- 1.3.6.1.4.1.6296.101.55.1.3.11
		sleRIPngAllCleared NOTIFICATION-TYPE
			OBJECTS { sleRIPngControlRequest, sleRIPngControlTimeStamp, sleRIPngControlReqResult }
			STATUS current
			DESCRIPTION 
				"Description."
			::= { sleRIPngBaseNotification 11 }

		
		-- 1.3.6.1.4.1.6296.101.55.1.3.12
		sleRIPngRouteCleared NOTIFICATION-TYPE
			OBJECTS { sleRIPngControlRequest, sleRIPngControlTimeStamp, sleRIPngControlReqResult, sleRIPngControlClearRoutePrefix, sleRIPngControlClearRouteMask
				 }
			STATUS current
			DESCRIPTION 
				"Description."
			::= { sleRIPngBaseNotification 12 }

		
		-- 1.3.6.1.4.1.6296.101.55.1.3.13
		sleRIPngProtoTypeCleared NOTIFICATION-TYPE
			OBJECTS { sleRIPngControlRequest, sleRIPngControlTimeStamp, sleRIPngControlReqResult, sleRIPngControlClearProtoTpye }
			STATUS current
			DESCRIPTION 
				"Description."
			::= { sleRIPngBaseNotification 13 }

		
		-- 1.3.6.1.4.1.6296.101.55.2
		sleRIPngAggregate OBJECT IDENTIFIER ::= { sleRIPng 2 }

		
		-- 1.3.6.1.4.1.6296.101.55.2.1
		sleRIPngAggregateTable OBJECT-TYPE
			SYNTAX SEQUENCE OF SleRIPngAggregateEntry
			MAX-ACCESS not-accessible
			STATUS current
			DESCRIPTION
				"Description."
			::= { sleRIPngAggregate 1 }

		
		-- 1.3.6.1.4.1.6296.101.55.2.1.1
		sleRIPngAggregateEntry OBJECT-TYPE
			SYNTAX SleRIPngAggregateEntry
			MAX-ACCESS not-accessible
			STATUS current
			DESCRIPTION
				"Description."
			INDEX { sleRIPngAggregateAddr, sleRIPngAggregateMask }
			::= { sleRIPngAggregateTable 1 }

		
		SleRIPngAggregateEntry ::=
			SEQUENCE { 
				sleRIPngAggregateAddr
					InetAddress,
				sleRIPngAggregateMask
					INTEGER
			 }

		-- 1.3.6.1.4.1.6296.101.55.2.1.1.1
		sleRIPngAggregateAddr OBJECT-TYPE
			SYNTAX InetAddress
			MAX-ACCESS read-only
			STATUS current
			DESCRIPTION
				"Description."
			::= { sleRIPngAggregateEntry 1 }

		
		-- 1.3.6.1.4.1.6296.101.55.2.1.1.2
		sleRIPngAggregateMask OBJECT-TYPE
			SYNTAX INTEGER (0..128)
			MAX-ACCESS read-only
			STATUS current
			DESCRIPTION
				"Description."
			::= { sleRIPngAggregateEntry 2 }

		
		-- 1.3.6.1.4.1.6296.101.55.2.2
		sleRIPngAggregateControl OBJECT IDENTIFIER ::= { sleRIPngAggregate 2 }

		
		-- 1.3.6.1.4.1.6296.101.55.2.2.1
		sleRIPngAggregateControlRequest OBJECT-TYPE
			SYNTAX INTEGER
				{
				createRIPngAggregateAddr(1),
				deleteRIPngAggregateAddr(2)
				}
			MAX-ACCESS read-write
			STATUS current
			DESCRIPTION
				"Description."
			::= { sleRIPngAggregateControl 1 }

		
		-- 1.3.6.1.4.1.6296.101.55.2.2.2
		sleRIPngAggregateControlStatus OBJECT-TYPE
			SYNTAX SleControlStatusType
			MAX-ACCESS read-only
			STATUS current
			DESCRIPTION
				"Description."
			::= { sleRIPngAggregateControl 2 }

		
		-- 1.3.6.1.4.1.6296.101.55.2.2.3
		sleRIPngAggregateControlTimer OBJECT-TYPE
			SYNTAX Gauge32
			MAX-ACCESS read-write
			STATUS current
			DESCRIPTION
				"Description."
			::= { sleRIPngAggregateControl 3 }

		
		-- 1.3.6.1.4.1.6296.101.55.2.2.4
		sleRIPngAggregateControlTimeStamp OBJECT-TYPE
			SYNTAX TimeTicks
			MAX-ACCESS read-only
			STATUS current
			DESCRIPTION
				"Description."
			::= { sleRIPngAggregateControl 4 }

		
		-- 1.3.6.1.4.1.6296.101.55.2.2.5
		sleRIPngAggregateControlReqResult OBJECT-TYPE
			SYNTAX SleControlRequestResultType
			MAX-ACCESS read-only
			STATUS current
			DESCRIPTION
				"Description."
			::= { sleRIPngAggregateControl 5 }

		
		-- 1.3.6.1.4.1.6296.101.55.2.2.6
		sleRIPngAggregateControlAddr OBJECT-TYPE
			SYNTAX InetAddress
			MAX-ACCESS read-write
			STATUS current
			DESCRIPTION
				"Description."
			::= { sleRIPngAggregateControl 6 }

		
		-- 1.3.6.1.4.1.6296.101.55.2.2.7
		sleRIPngAggregateControlMask OBJECT-TYPE
			SYNTAX INTEGER (0..128)
			MAX-ACCESS read-write
			STATUS current
			DESCRIPTION
				"Description."
			::= { sleRIPngAggregateControl 7 }

		
		-- 1.3.6.1.4.1.6296.101.55.2.3
		sleRIPngAggregateNotification OBJECT IDENTIFIER ::= { sleRIPngAggregate 3 }

		
		-- 1.3.6.1.4.1.6296.101.55.2.3.1
		sleRIPngAggregateAddrCreated NOTIFICATION-TYPE
			OBJECTS { sleRIPngAggregateControlRequest, sleRIPngAggregateControlTimeStamp, sleRIPngAggregateControlReqResult, sleRIPngAggregateAddr, sleRIPngAggregateMask
				 }
			STATUS current
			DESCRIPTION 
				"Description."
			::= { sleRIPngAggregateNotification 1 }

		
		-- 1.3.6.1.4.1.6296.101.55.2.3.2
		sleRIPngAggregateAddrDeleted NOTIFICATION-TYPE
			OBJECTS { sleRIPngAggregateControlRequest, sleRIPngAggregateControlTimeStamp, sleRIPngAggregateControlReqResult, sleRIPngAggregateControlAddr, sleRIPngAggregateControlMask
				 }
			STATUS current
			DESCRIPTION 
				"Description."
			::= { sleRIPngAggregateNotification 2 }

		
		-- 1.3.6.1.4.1.6296.101.55.3
		sleRIPngNeighbor OBJECT IDENTIFIER ::= { sleRIPng 3 }

		
		-- 1.3.6.1.4.1.6296.101.55.3.1
		sleRIPngNeighborTable OBJECT-TYPE
			SYNTAX SEQUENCE OF SleRIPNeighborEntry
			MAX-ACCESS not-accessible
			STATUS current
			DESCRIPTION
				"Description."
			::= { sleRIPngNeighbor 1 }

		
		-- 1.3.6.1.4.1.6296.101.55.3.1.1
		sleRIPngNeighborEntry OBJECT-TYPE
			SYNTAX SleRIPNeighborEntry
			MAX-ACCESS not-accessible
			STATUS current
			DESCRIPTION
				"Description."
			INDEX { sleRIPngNeighborAddr }
			::= { sleRIPngNeighborTable 1 }

		
		SleRIPNeighborEntry ::=
			SEQUENCE { 
				sleRIPngNeighborAddr
					InetAddress,
				sleRIPngNeighborIfName
					OCTET STRING
			 }

		-- 1.3.6.1.4.1.6296.101.55.3.1.1.1
		sleRIPngNeighborAddr OBJECT-TYPE
			SYNTAX InetAddress
			MAX-ACCESS read-only
			STATUS current
			DESCRIPTION
				"Description."
			::= { sleRIPngNeighborEntry 1 }

		
		-- 1.3.6.1.4.1.6296.101.55.3.1.1.2
		sleRIPngNeighborIfName OBJECT-TYPE
			SYNTAX OCTET STRING (SIZE (0..512))
			MAX-ACCESS read-only
			STATUS current
			DESCRIPTION
				"Description."
			::= { sleRIPngNeighborEntry 2 }

		
		-- 1.3.6.1.4.1.6296.101.55.3.2
		sleRIPngNeighborControl OBJECT IDENTIFIER ::= { sleRIPngNeighbor 2 }

		
		-- 1.3.6.1.4.1.6296.101.55.3.2.1
		sleRIPngNeighborControlRequest OBJECT-TYPE
			SYNTAX INTEGER
				{
				createRIPngNeighbor(1),
				deleteRIPngNeighbor(2)
				}
			MAX-ACCESS read-write
			STATUS current
			DESCRIPTION
				"Description."
			::= { sleRIPngNeighborControl 1 }

		
		-- 1.3.6.1.4.1.6296.101.55.3.2.2
		sleRIPngNeighborControlStatus OBJECT-TYPE
			SYNTAX SleControlStatusType
			MAX-ACCESS read-only
			STATUS current
			DESCRIPTION
				"Description."
			::= { sleRIPngNeighborControl 2 }

		
		-- 1.3.6.1.4.1.6296.101.55.3.2.3
		sleRIPngNeighborControlTimer OBJECT-TYPE
			SYNTAX Gauge32
			MAX-ACCESS read-write
			STATUS current
			DESCRIPTION
				"Description."
			::= { sleRIPngNeighborControl 3 }

		
		-- 1.3.6.1.4.1.6296.101.55.3.2.4
		sleRIPngNeighborControlTimeStamp OBJECT-TYPE
			SYNTAX TimeTicks
			MAX-ACCESS read-only
			STATUS current
			DESCRIPTION
				"Description."
			::= { sleRIPngNeighborControl 4 }

		
		-- 1.3.6.1.4.1.6296.101.55.3.2.5
		sleRIPngNeighborControlReqResult OBJECT-TYPE
			SYNTAX SleControlRequestResultType
			MAX-ACCESS read-only
			STATUS current
			DESCRIPTION
				"Description."
			::= { sleRIPngNeighborControl 5 }

		
		-- 1.3.6.1.4.1.6296.101.55.3.2.6
		sleRIPngNeighborControlAddr OBJECT-TYPE
			SYNTAX InetAddress
			MAX-ACCESS read-write
			STATUS current
			DESCRIPTION
				"Description."
			::= { sleRIPngNeighborControl 6 }

		
		-- 1.3.6.1.4.1.6296.101.55.3.2.7
		sleRIPngNeighborControlIfName OBJECT-TYPE
			SYNTAX OCTET STRING (SIZE (0..512))
			MAX-ACCESS read-write
			STATUS current
			DESCRIPTION
				"Description."
			::= { sleRIPngNeighborControl 7 }

		
		-- 1.3.6.1.4.1.6296.101.55.3.3
		sleRIPngNeighborNotification OBJECT IDENTIFIER ::= { sleRIPngNeighbor 3 }

		
		-- 1.3.6.1.4.1.6296.101.55.3.3.1
		sleRIPngNeighborCreated NOTIFICATION-TYPE
			OBJECTS { sleRIPngNeighborControlRequest, sleRIPngNeighborControlTimeStamp, sleRIPngNeighborControlReqResult, sleRIPngNeighborAddr, sleRIPngNeighborIfName
				 }
			STATUS current
			DESCRIPTION 
				"Description."
			::= { sleRIPngNeighborNotification 1 }

		
		-- 1.3.6.1.4.1.6296.101.55.3.3.2
		sleRIPngNeighborDeleted NOTIFICATION-TYPE
			OBJECTS { sleRIPngNeighborControlRequest, sleRIPngNeighborControlTimeStamp, sleRIPngNeighborControlReqResult, sleRIPngNeighborControlAddr, sleRIPngNeighborControlIfName
				 }
			STATUS current
			DESCRIPTION 
				"Description."
			::= { sleRIPngNeighborNotification 2 }

		
		-- 1.3.6.1.4.1.6296.101.55.4
		sleRIPngStaticRoute OBJECT IDENTIFIER ::= { sleRIPng 4 }

		
		-- 1.3.6.1.4.1.6296.101.55.4.1
		sleRIPngStaticRouteTable OBJECT-TYPE
			SYNTAX SEQUENCE OF SleRIPStaticRouteEntry
			MAX-ACCESS not-accessible
			STATUS current
			DESCRIPTION
				"Description."
			::= { sleRIPngStaticRoute 1 }

		
		-- 1.3.6.1.4.1.6296.101.55.4.1.1
		sleRIPngStaticRouteEntry OBJECT-TYPE
			SYNTAX SleRIPStaticRouteEntry
			MAX-ACCESS not-accessible
			STATUS current
			DESCRIPTION
				"Description."
			INDEX { sleRIPngStaticRouteAddr, sleRIPngStaticRouteMask }
			::= { sleRIPngStaticRouteTable 1 }

		
		SleRIPStaticRouteEntry ::=
			SEQUENCE { 
				sleRIPngStaticRouteAddr
					InetAddress,
				sleRIPngStaticRouteMask
					INTEGER
			 }

		-- 1.3.6.1.4.1.6296.101.55.4.1.1.1
		sleRIPngStaticRouteAddr OBJECT-TYPE
			SYNTAX InetAddress
			MAX-ACCESS read-only
			STATUS current
			DESCRIPTION
				"Description."
			::= { sleRIPngStaticRouteEntry 1 }

		
		-- 1.3.6.1.4.1.6296.101.55.4.1.1.2
		sleRIPngStaticRouteMask OBJECT-TYPE
			SYNTAX INTEGER (0..128)
			MAX-ACCESS read-only
			STATUS current
			DESCRIPTION
				"Description."
			::= { sleRIPngStaticRouteEntry 2 }

		
		-- 1.3.6.1.4.1.6296.101.55.4.2
		sleRIPngStaticRouteControl OBJECT IDENTIFIER ::= { sleRIPngStaticRoute 2 }

		
		-- 1.3.6.1.4.1.6296.101.55.4.2.1
		sleRIPngStaticRouteControlRequest OBJECT-TYPE
			SYNTAX INTEGER
				{
				createRIPngStaticRoute(1),
				deleteRIPngStaticRoute(2)
				}
			MAX-ACCESS read-write
			STATUS current
			DESCRIPTION
				"Description."
			::= { sleRIPngStaticRouteControl 1 }

		
		-- 1.3.6.1.4.1.6296.101.55.4.2.2
		sleRIPngStaticRouteControlStatus OBJECT-TYPE
			SYNTAX SleControlStatusType
			MAX-ACCESS read-only
			STATUS current
			DESCRIPTION
				"Description."
			::= { sleRIPngStaticRouteControl 2 }

		
		-- 1.3.6.1.4.1.6296.101.55.4.2.3
		sleRIPngStaticRouteControlTimer OBJECT-TYPE
			SYNTAX Gauge32
			MAX-ACCESS read-write
			STATUS current
			DESCRIPTION
				"Description."
			::= { sleRIPngStaticRouteControl 3 }

		
		-- 1.3.6.1.4.1.6296.101.55.4.2.4
		sleRIPngStaticRouteControlTimeStamp OBJECT-TYPE
			SYNTAX TimeTicks
			MAX-ACCESS read-only
			STATUS current
			DESCRIPTION
				"Description."
			::= { sleRIPngStaticRouteControl 4 }

		
		-- 1.3.6.1.4.1.6296.101.55.4.2.5
		sleRIPngStaticRouteControlReqResult OBJECT-TYPE
			SYNTAX SleControlRequestResultType
			MAX-ACCESS read-only
			STATUS current
			DESCRIPTION
				"Description."
			::= { sleRIPngStaticRouteControl 5 }

		
		-- 1.3.6.1.4.1.6296.101.55.4.2.6
		sleRIPngStaticRouteControlAddr OBJECT-TYPE
			SYNTAX InetAddress
			MAX-ACCESS read-write
			STATUS current
			DESCRIPTION
				"Description."
			::= { sleRIPngStaticRouteControl 6 }

		
		-- 1.3.6.1.4.1.6296.101.55.4.2.7
		sleRIPngStaticRouteControlMask OBJECT-TYPE
			SYNTAX INTEGER (0..128)
			MAX-ACCESS read-write
			STATUS current
			DESCRIPTION
				"Description."
			::= { sleRIPngStaticRouteControl 7 }

		
		-- 1.3.6.1.4.1.6296.101.55.4.3
		sleRIPngStaticRouteNotification OBJECT IDENTIFIER ::= { sleRIPngStaticRoute 3 }

		
		-- 1.3.6.1.4.1.6296.101.55.4.3.1
		sleRIPngStaticRouteCreated NOTIFICATION-TYPE
			OBJECTS { sleRIPngStaticRouteControlRequest, sleRIPngStaticRouteControlTimeStamp, sleRIPngStaticRouteControlReqResult, sleRIPngStaticRouteAddr, sleRIPngStaticRouteMask
				 }
			STATUS current
			DESCRIPTION 
				"Description."
			::= { sleRIPngStaticRouteNotification 1 }

		
		-- 1.3.6.1.4.1.6296.101.55.4.3.2
		sleRIPngStaticRouteDeleted NOTIFICATION-TYPE
			OBJECTS { sleRIPngStaticRouteControlRequest, sleRIPngStaticRouteControlTimeStamp, sleRIPngStaticRouteControlReqResult, sleRIPngStaticRouteControlAddr, sleRIPngStaticRouteControlMask
				 }
			STATUS current
			DESCRIPTION 
				"Description."
			::= { sleRIPngStaticRouteNotification 2 }

		
		-- 1.3.6.1.4.1.6296.101.55.5
		sleRIPngAdminDistance OBJECT IDENTIFIER ::= { sleRIPng 5 }

		
		-- 1.3.6.1.4.1.6296.101.55.5.1
		sleRIPngAdminDistanceTable OBJECT-TYPE
			SYNTAX SEQUENCE OF SleRIPAdminDistanceEntry
			MAX-ACCESS not-accessible
			STATUS current
			DESCRIPTION
				"Description."
			::= { sleRIPngAdminDistance 1 }

		
		-- 1.3.6.1.4.1.6296.101.55.5.1.1
		sleRIPngAdminDistanceEntry OBJECT-TYPE
			SYNTAX SleRIPAdminDistanceEntry
			MAX-ACCESS not-accessible
			STATUS current
			DESCRIPTION
				"Description."
			INDEX { sleRIPngAdminDistanceValue, sleRIPngAdminDistanceAddr, sleRIPngAdminDistanceMask }
			::= { sleRIPngAdminDistanceTable 1 }

		
		SleRIPAdminDistanceEntry ::=
			SEQUENCE { 
				sleRIPngAdminDistanceValue
					INTEGER,
				sleRIPngAdminDistanceAddr
					InetAddress,
				sleRIPngAdminDistanceMask
					INTEGER,
				sleRIPngAdminDistanceAccessName
					OCTET STRING
			 }

		-- 1.3.6.1.4.1.6296.101.55.5.1.1.1
		sleRIPngAdminDistanceValue OBJECT-TYPE
			SYNTAX INTEGER (1..255)
			MAX-ACCESS read-only
			STATUS current
			DESCRIPTION
				"Description."
			::= { sleRIPngAdminDistanceEntry 1 }

		
		-- 1.3.6.1.4.1.6296.101.55.5.1.1.2
		sleRIPngAdminDistanceAddr OBJECT-TYPE
			SYNTAX InetAddress
			MAX-ACCESS read-only
			STATUS current
			DESCRIPTION
				"Description."
			::= { sleRIPngAdminDistanceEntry 2 }

		
		-- 1.3.6.1.4.1.6296.101.55.5.1.1.3
		sleRIPngAdminDistanceMask OBJECT-TYPE
			SYNTAX INTEGER (0..128)
			MAX-ACCESS read-only
			STATUS current
			DESCRIPTION
				"Description."
			::= { sleRIPngAdminDistanceEntry 3 }

		
		-- 1.3.6.1.4.1.6296.101.55.5.1.1.4
		sleRIPngAdminDistanceAccessName OBJECT-TYPE
			SYNTAX OCTET STRING (SIZE (0..512))
			MAX-ACCESS read-only
			STATUS current
			DESCRIPTION
				"Description."
			::= { sleRIPngAdminDistanceEntry 4 }

		
		-- 1.3.6.1.4.1.6296.101.55.5.2
		sleRIPngAdminDistanceControl OBJECT IDENTIFIER ::= { sleRIPngAdminDistance 2 }

		
		-- 1.3.6.1.4.1.6296.101.55.5.2.1
		sleRIPngAdminDistanceControlRequest OBJECT-TYPE
			SYNTAX INTEGER
				{
				createRIPngAdminDistance(1),
				deleteRIPngAdminDistance(2)
				}
			MAX-ACCESS read-write
			STATUS current
			DESCRIPTION
				"Description."
			::= { sleRIPngAdminDistanceControl 1 }

		
		-- 1.3.6.1.4.1.6296.101.55.5.2.2
		sleRIPngAdminDistanceControlStatus OBJECT-TYPE
			SYNTAX SleControlStatusType
			MAX-ACCESS read-only
			STATUS current
			DESCRIPTION
				"Description."
			::= { sleRIPngAdminDistanceControl 2 }

		
		-- 1.3.6.1.4.1.6296.101.55.5.2.3
		sleRIPngAdminDistanceControlTimer OBJECT-TYPE
			SYNTAX Gauge32
			MAX-ACCESS read-write
			STATUS current
			DESCRIPTION
				"Description."
			::= { sleRIPngAdminDistanceControl 3 }

		
		-- 1.3.6.1.4.1.6296.101.55.5.2.4
		sleRIPngAdminDistanceControlTimeStamp OBJECT-TYPE
			SYNTAX TimeTicks
			MAX-ACCESS read-only
			STATUS current
			DESCRIPTION
				"Description."
			::= { sleRIPngAdminDistanceControl 4 }

		
		-- 1.3.6.1.4.1.6296.101.55.5.2.5
		sleRIPngAdminDistanceControlReqResult OBJECT-TYPE
			SYNTAX SleControlRequestResultType
			MAX-ACCESS read-only
			STATUS current
			DESCRIPTION
				"Description."
			::= { sleRIPngAdminDistanceControl 5 }

		
		-- 1.3.6.1.4.1.6296.101.55.5.2.6
		sleRIPngAdminDistanceControlValue OBJECT-TYPE
			SYNTAX INTEGER (1..255)
			MAX-ACCESS read-write
			STATUS current
			DESCRIPTION
				"Description."
			::= { sleRIPngAdminDistanceControl 6 }

		
		-- 1.3.6.1.4.1.6296.101.55.5.2.7
		sleRIPngAdminDistanceControlAddr OBJECT-TYPE
			SYNTAX InetAddress
			MAX-ACCESS read-write
			STATUS current
			DESCRIPTION
				"Description."
			::= { sleRIPngAdminDistanceControl 7 }

		
		-- 1.3.6.1.4.1.6296.101.55.5.2.8
		sleRIPngAdminDistanceControlMask OBJECT-TYPE
			SYNTAX INTEGER (0..128)
			MAX-ACCESS read-write
			STATUS current
			DESCRIPTION
				"Description."
			::= { sleRIPngAdminDistanceControl 8 }

		
		-- 1.3.6.1.4.1.6296.101.55.5.2.9
		sleRIPngAdminDistanceControlAccessName OBJECT-TYPE
			SYNTAX OCTET STRING (SIZE (0..512))
			MAX-ACCESS read-write
			STATUS current
			DESCRIPTION
				"Description."
			::= { sleRIPngAdminDistanceControl 9 }

		
		-- 1.3.6.1.4.1.6296.101.55.5.3
		sleRIPngAdminDistanceNotification OBJECT IDENTIFIER ::= { sleRIPngAdminDistance 3 }

		
		-- 1.3.6.1.4.1.6296.101.55.5.3.1
		sleRIPngAdminDistanceCreated NOTIFICATION-TYPE
			OBJECTS { sleRIPngAdminDistanceControlRequest, sleRIPngAdminDistanceControlTimeStamp, sleRIPngAdminDistanceControlReqResult, sleRIPngAdminDistanceValue, sleRIPngAdminDistanceAddr, 
				sleRIPngAdminDistanceMask, sleRIPngAdminDistanceAccessName }
			STATUS current
			DESCRIPTION 
				"Description."
			::= { sleRIPngAdminDistanceNotification 1 }

		
		-- 1.3.6.1.4.1.6296.101.55.5.3.2
		sleRIPngAdminDistanceDeleted NOTIFICATION-TYPE
			OBJECTS { sleRIPngAdminDistanceControlRequest, sleRIPngAdminDistanceControlTimeStamp, sleRIPngAdminDistanceControlReqResult, sleRIPngAdminDistanceControlValue, sleRIPngAdminDistanceControlAddr, 
				sleRIPngAdminDistanceControlMask, sleRIPngAdminDistanceControlAccessName }
			STATUS current
			DESCRIPTION 
				"Description."
			::= { sleRIPngAdminDistanceNotification 2 }

		
		-- 1.3.6.1.4.1.6296.101.55.6
		sleRIPngDistribute OBJECT IDENTIFIER ::= { sleRIPng 6 }

		
		-- 1.3.6.1.4.1.6296.101.55.6.1
		sleRIPngDistributeTable OBJECT-TYPE
			SYNTAX SEQUENCE OF SleRIPngDistributeEntry
			MAX-ACCESS not-accessible
			STATUS current
			DESCRIPTION
				"Description."
			::= { sleRIPngDistribute 1 }

		
		-- 1.3.6.1.4.1.6296.101.55.6.1.1
		sleRIPngDistributeEntry OBJECT-TYPE
			SYNTAX SleRIPngDistributeEntry
			MAX-ACCESS not-accessible
			STATUS current
			DESCRIPTION
				"Description."
			INDEX { sleRIPngDistributeIfName }
			::= { sleRIPngDistributeTable 1 }

		
		SleRIPngDistributeEntry ::=
			SEQUENCE { 
				sleRIPngDistributeIfName
					OCTET STRING,
				sleRIPngDistributeInAccessName
					OCTET STRING,
				sleRIPngDistributeOutAccessName
					OCTET STRING,
				sleRIPngDistributeInPrefixName
					OCTET STRING,
				sleRIPngDistributeOutPrefixName
					OCTET STRING
			 }

		-- 1.3.6.1.4.1.6296.101.55.6.1.1.1
		sleRIPngDistributeIfName OBJECT-TYPE
			SYNTAX OCTET STRING (SIZE (0..512))
			MAX-ACCESS read-only
			STATUS current
			DESCRIPTION
				"Description."
			::= { sleRIPngDistributeEntry 1 }

		
		-- 1.3.6.1.4.1.6296.101.55.6.1.1.2
		sleRIPngDistributeInAccessName OBJECT-TYPE
			SYNTAX OCTET STRING (SIZE (0..512))
			MAX-ACCESS read-only
			STATUS current
			DESCRIPTION
				"Description."
			::= { sleRIPngDistributeEntry 2 }

		
		-- 1.3.6.1.4.1.6296.101.55.6.1.1.3
		sleRIPngDistributeOutAccessName OBJECT-TYPE
			SYNTAX OCTET STRING (SIZE (0..512))
			MAX-ACCESS read-only
			STATUS current
			DESCRIPTION
				"Description."
			::= { sleRIPngDistributeEntry 3 }

		
		-- 1.3.6.1.4.1.6296.101.55.6.1.1.4
		sleRIPngDistributeInPrefixName OBJECT-TYPE
			SYNTAX OCTET STRING (SIZE (0..512))
			MAX-ACCESS read-only
			STATUS current
			DESCRIPTION
				"Description."
			::= { sleRIPngDistributeEntry 4 }

		
		-- 1.3.6.1.4.1.6296.101.55.6.1.1.5
		sleRIPngDistributeOutPrefixName OBJECT-TYPE
			SYNTAX OCTET STRING (SIZE (0..512))
			MAX-ACCESS read-only
			STATUS current
			DESCRIPTION
				"Description."
			::= { sleRIPngDistributeEntry 5 }

		
		-- 1.3.6.1.4.1.6296.101.55.6.2
		sleRIPngDistributeControl OBJECT IDENTIFIER ::= { sleRIPngDistribute 2 }

		
		-- 1.3.6.1.4.1.6296.101.55.6.2.1
		sleRIPngDistributeControlRequest OBJECT-TYPE
			SYNTAX INTEGER
				{
				createRIPngDistributeInAccess(1),
				deleteRIPngDistributeInAccess(2),
				createRIPngDistributeOutAccess(3),
				deleteRIPngDistributeOutAccess(4),
				createRIPngDistributeInPrefix(5),
				deleteRIPngDistributeInPrefix(6),
				createRIPngDistributeOutPrefix(7),
				deleteRIPngDistributeOutPrefix(8)
				}
			MAX-ACCESS read-write
			STATUS current
			DESCRIPTION
				"Description."
			::= { sleRIPngDistributeControl 1 }

		
		-- 1.3.6.1.4.1.6296.101.55.6.2.2
		sleRIPngDistributeControlStatus OBJECT-TYPE
			SYNTAX SleControlStatusType
			MAX-ACCESS read-only
			STATUS current
			DESCRIPTION
				"Description."
			::= { sleRIPngDistributeControl 2 }

		
		-- 1.3.6.1.4.1.6296.101.55.6.2.3
		sleRIPngDistributeControlTimer OBJECT-TYPE
			SYNTAX Gauge32
			MAX-ACCESS read-write
			STATUS current
			DESCRIPTION
				"Description."
			::= { sleRIPngDistributeControl 3 }

		
		-- 1.3.6.1.4.1.6296.101.55.6.2.4
		sleRIPngDistributeControlTimeStamp OBJECT-TYPE
			SYNTAX TimeTicks
			MAX-ACCESS read-only
			STATUS current
			DESCRIPTION
				"Description."
			::= { sleRIPngDistributeControl 4 }

		
		-- 1.3.6.1.4.1.6296.101.55.6.2.5
		sleRIPngDistributeControlReqResult OBJECT-TYPE
			SYNTAX SleControlRequestResultType
			MAX-ACCESS read-only
			STATUS current
			DESCRIPTION
				"Description."
			::= { sleRIPngDistributeControl 5 }

		
		-- 1.3.6.1.4.1.6296.101.55.6.2.6
		sleRIPngDistributeControlIfName OBJECT-TYPE
			SYNTAX OCTET STRING (SIZE (0..512))
			MAX-ACCESS read-write
			STATUS current
			DESCRIPTION
				"Description."
			::= { sleRIPngDistributeControl 6 }

		
		-- 1.3.6.1.4.1.6296.101.55.6.2.7
		sleRIPngDistributeControlInAccessName OBJECT-TYPE
			SYNTAX OCTET STRING (SIZE (0..512))
			MAX-ACCESS read-write
			STATUS current
			DESCRIPTION
				"Description."
			::= { sleRIPngDistributeControl 7 }

		
		-- 1.3.6.1.4.1.6296.101.55.6.2.8
		sleRIPngDistributeControlOutAccessName OBJECT-TYPE
			SYNTAX OCTET STRING (SIZE (0..512))
			MAX-ACCESS read-write
			STATUS current
			DESCRIPTION
				"Description."
			::= { sleRIPngDistributeControl 8 }

		
		-- 1.3.6.1.4.1.6296.101.55.6.2.9
		sleRIPngDistributeControlInPrefixName OBJECT-TYPE
			SYNTAX OCTET STRING (SIZE (0..512))
			MAX-ACCESS read-write
			STATUS current
			DESCRIPTION
				"Description."
			::= { sleRIPngDistributeControl 9 }

		
		-- 1.3.6.1.4.1.6296.101.55.6.2.10
		sleRIPngDistributeControlOutPrefixName OBJECT-TYPE
			SYNTAX OCTET STRING (SIZE (0..512))
			MAX-ACCESS read-write
			STATUS current
			DESCRIPTION
				"Description."
			::= { sleRIPngDistributeControl 10 }

		
		-- 1.3.6.1.4.1.6296.101.55.6.3
		sleRIPngDistributeNotification OBJECT IDENTIFIER ::= { sleRIPngDistribute 3 }

		
		-- 1.3.6.1.4.1.6296.101.55.6.3.1
		sleRIPngDistributeInAccessCreated NOTIFICATION-TYPE
			OBJECTS { sleRIPngDistributeControlRequest, sleRIPngDistributeControlTimeStamp, sleRIPngDistributeControlReqResult, sleRIPngDistributeIfName, sleRIPngDistributeInAccessName
				 }
			STATUS current
			DESCRIPTION 
				"Description."
			::= { sleRIPngDistributeNotification 1 }

		
		-- 1.3.6.1.4.1.6296.101.55.6.3.2
		sleRIPngDistributeInAccessDeleted NOTIFICATION-TYPE
			OBJECTS { sleRIPngDistributeControlRequest, sleRIPngDistributeControlTimeStamp, sleRIPngDistributeControlReqResult, sleRIPngDistributeControlIfName, sleRIPngDistributeControlInAccessName
				 }
			STATUS current
			DESCRIPTION 
				"Description."
			::= { sleRIPngDistributeNotification 2 }

		
		-- 1.3.6.1.4.1.6296.101.55.6.3.3
		sleRIPngDistributeOutAccessCreated NOTIFICATION-TYPE
			OBJECTS { sleRIPngDistributeControlRequest, sleRIPngDistributeControlTimeStamp, sleRIPngDistributeControlReqResult, sleRIPngDistributeIfName, sleRIPngDistributeOutAccessName
				 }
			STATUS current
			DESCRIPTION 
				"Description."
			::= { sleRIPngDistributeNotification 3 }

		
		-- 1.3.6.1.4.1.6296.101.55.6.3.4
		sleRIPngDistributeOutAccessDeleted NOTIFICATION-TYPE
			OBJECTS { sleRIPngDistributeControlRequest, sleRIPngDistributeControlTimeStamp, sleRIPngDistributeControlReqResult, sleRIPngDistributeControlIfName, sleRIPngDistributeControlOutAccessName
				 }
			STATUS current
			DESCRIPTION 
				"Description."
			::= { sleRIPngDistributeNotification 4 }

		
		-- 1.3.6.1.4.1.6296.101.55.6.3.5
		sleRIPngDistributeInPrefixCreated NOTIFICATION-TYPE
			OBJECTS { sleRIPngDistributeControlRequest, sleRIPngDistributeControlTimeStamp, sleRIPngDistributeControlReqResult, sleRIPngDistributeIfName, sleRIPngDistributeInPrefixName
				 }
			STATUS current
			DESCRIPTION 
				"Description."
			::= { sleRIPngDistributeNotification 5 }

		
		-- 1.3.6.1.4.1.6296.101.55.6.3.6
		sleRIPngDistributeInPrefixDeleted NOTIFICATION-TYPE
			OBJECTS { sleRIPngDistributeControlRequest, sleRIPngDistributeControlTimeStamp, sleRIPngDistributeControlReqResult, sleRIPngDistributeControlIfName, sleRIPngDistributeControlInPrefixName
				 }
			STATUS current
			DESCRIPTION 
				"Description."
			::= { sleRIPngDistributeNotification 6 }

		
		-- 1.3.6.1.4.1.6296.101.55.6.3.7
		sleRIPngDistributeOutPrefixCreated NOTIFICATION-TYPE
			OBJECTS { sleRIPngDistributeControlRequest, sleRIPngDistributeControlTimeStamp, sleRIPngDistributeControlReqResult, sleRIPngDistributeIfName, sleRIPngDistributeOutPrefixName
				 }
			STATUS current
			DESCRIPTION 
				"Description."
			::= { sleRIPngDistributeNotification 7 }

		
		-- 1.3.6.1.4.1.6296.101.55.6.3.8
		sleRIPngDistributeOutPrefixDeleted NOTIFICATION-TYPE
			OBJECTS { sleRIPngDistributeControlRequest, sleRIPngDistributeControlTimeStamp, sleRIPngDistributeControlReqResult, sleRIPngDistributeControlIfName, sleRIPngDistributeControlOutPrefixName
				 }
			STATUS current
			DESCRIPTION 
				"Description."
			::= { sleRIPngDistributeNotification 8 }

		
		-- 1.3.6.1.4.1.6296.101.55.7
		sleRIPngOffsetList OBJECT IDENTIFIER ::= { sleRIPng 7 }

		
		-- 1.3.6.1.4.1.6296.101.55.7.1
		sleRIPngOffsetListTable OBJECT-TYPE
			SYNTAX SEQUENCE OF SleRIPOffsetListEntry
			MAX-ACCESS not-accessible
			STATUS current
			DESCRIPTION
				"Description."
			::= { sleRIPngOffsetList 1 }

		
		-- 1.3.6.1.4.1.6296.101.55.7.1.1
		sleRIPngOffsetListEntry OBJECT-TYPE
			SYNTAX SleRIPOffsetListEntry
			MAX-ACCESS not-accessible
			STATUS current
			DESCRIPTION
				"Description."
			INDEX { sleRIPngOffsetListIfname }
			::= { sleRIPngOffsetListTable 1 }

		
		SleRIPOffsetListEntry ::=
			SEQUENCE { 
				sleRIPngOffsetListIfname
					OCTET STRING,
				sleRIPngOffsetListInAccName
					OCTET STRING,
				sleRIPngOffsetListInMetric
					INTEGER,
				sleRIPngOffsetListOutAccName
					OCTET STRING,
				sleRIPngOffsetListOutMetric
					INTEGER
			 }

		-- 1.3.6.1.4.1.6296.101.55.7.1.1.1
		sleRIPngOffsetListIfname OBJECT-TYPE
			SYNTAX OCTET STRING (SIZE (0..512))
			MAX-ACCESS read-only
			STATUS current
			DESCRIPTION
				"Description."
			::= { sleRIPngOffsetListEntry 1 }

		
		-- 1.3.6.1.4.1.6296.101.55.7.1.1.2
		sleRIPngOffsetListInAccName OBJECT-TYPE
			SYNTAX OCTET STRING (SIZE (0..512))
			MAX-ACCESS read-only
			STATUS current
			DESCRIPTION
				"Description."
			::= { sleRIPngOffsetListEntry 2 }

		
		-- 1.3.6.1.4.1.6296.101.55.7.1.1.3
		sleRIPngOffsetListInMetric OBJECT-TYPE
			SYNTAX INTEGER (0..16)
			MAX-ACCESS read-only
			STATUS current
			DESCRIPTION
				"Description."
			::= { sleRIPngOffsetListEntry 3 }

		
		-- 1.3.6.1.4.1.6296.101.55.7.1.1.4
		sleRIPngOffsetListOutAccName OBJECT-TYPE
			SYNTAX OCTET STRING (SIZE (0..512))
			MAX-ACCESS read-only
			STATUS current
			DESCRIPTION
				"Description."
			::= { sleRIPngOffsetListEntry 4 }

		
		-- 1.3.6.1.4.1.6296.101.55.7.1.1.5
		sleRIPngOffsetListOutMetric OBJECT-TYPE
			SYNTAX INTEGER (0..16)
			MAX-ACCESS read-only
			STATUS current
			DESCRIPTION
				"Description."
			::= { sleRIPngOffsetListEntry 5 }

		
		-- 1.3.6.1.4.1.6296.101.55.7.2
		sleRIPngOffsetListControl OBJECT IDENTIFIER ::= { sleRIPngOffsetList 2 }

		
		-- 1.3.6.1.4.1.6296.101.55.7.2.1
		sleRIPngOffsetListControlRequest OBJECT-TYPE
			SYNTAX INTEGER
				{
				createRIPngOffsetListIn(1),
				deleteRIPngOffsetListIn(2),
				createRIPngOffsetListOut(3),
				deleteRIPngOffsetListOut(4)
				}
			MAX-ACCESS read-write
			STATUS current
			DESCRIPTION
				"Description."
			::= { sleRIPngOffsetListControl 1 }

		
		-- 1.3.6.1.4.1.6296.101.55.7.2.2
		sleRIPngOffsetListControlStatus OBJECT-TYPE
			SYNTAX SleControlStatusType
			MAX-ACCESS read-only
			STATUS current
			DESCRIPTION
				"Description."
			::= { sleRIPngOffsetListControl 2 }

		
		-- 1.3.6.1.4.1.6296.101.55.7.2.3
		sleRIPngOffsetListControlTimer OBJECT-TYPE
			SYNTAX Gauge32
			MAX-ACCESS read-write
			STATUS current
			DESCRIPTION
				"Description."
			::= { sleRIPngOffsetListControl 3 }

		
		-- 1.3.6.1.4.1.6296.101.55.7.2.4
		sleRIPngOffsetListControlTimeStamp OBJECT-TYPE
			SYNTAX TimeTicks
			MAX-ACCESS read-only
			STATUS current
			DESCRIPTION
				"Description."
			::= { sleRIPngOffsetListControl 4 }

		
		-- 1.3.6.1.4.1.6296.101.55.7.2.5
		sleRIPngOffsetListControlReqResult OBJECT-TYPE
			SYNTAX SleControlRequestResultType
			MAX-ACCESS read-only
			STATUS current
			DESCRIPTION
				"Description."
			::= { sleRIPngOffsetListControl 5 }

		
		-- 1.3.6.1.4.1.6296.101.55.7.2.6
		sleRIPngOffsetListControlIfname OBJECT-TYPE
			SYNTAX OCTET STRING (SIZE (0..512))
			MAX-ACCESS read-write
			STATUS current
			DESCRIPTION
				"Description."
			::= { sleRIPngOffsetListControl 6 }

		
		-- 1.3.6.1.4.1.6296.101.55.7.2.7
		sleRIPngOffsetListControlInAccName OBJECT-TYPE
			SYNTAX OCTET STRING (SIZE (0..512))
			MAX-ACCESS read-write
			STATUS current
			DESCRIPTION
				"Description."
			::= { sleRIPngOffsetListControl 7 }

		
		-- 1.3.6.1.4.1.6296.101.55.7.2.8
		sleRIPngOffsetListControlInMetric OBJECT-TYPE
			SYNTAX INTEGER (0..16)
			MAX-ACCESS read-write
			STATUS current
			DESCRIPTION
				"Description."
			::= { sleRIPngOffsetListControl 8 }

		
		-- 1.3.6.1.4.1.6296.101.55.7.2.9
		sleRIPngOffsetListControlOutAccName OBJECT-TYPE
			SYNTAX OCTET STRING (SIZE (0..512))
			MAX-ACCESS read-write
			STATUS current
			DESCRIPTION
				"Description."
			::= { sleRIPngOffsetListControl 9 }

		
		-- 1.3.6.1.4.1.6296.101.55.7.2.10
		sleRIPngOffsetListControlOutMetric OBJECT-TYPE
			SYNTAX INTEGER (0..16)
			MAX-ACCESS read-write
			STATUS current
			DESCRIPTION
				"Description."
			::= { sleRIPngOffsetListControl 10 }

		
		-- 1.3.6.1.4.1.6296.101.55.7.3
		sleRIPngOffsetListNotification OBJECT IDENTIFIER ::= { sleRIPngOffsetList 3 }

		
		-- 1.3.6.1.4.1.6296.101.55.7.3.1
		sleRIPngOffsetListInCreated NOTIFICATION-TYPE
			OBJECTS { sleRIPngOffsetListControlRequest, sleRIPngOffsetListControlTimeStamp, sleRIPngOffsetListControlReqResult, sleRIPngOffsetListIfname, sleRIPngOffsetListInAccName, 
				sleRIPngOffsetListInMetric }
			STATUS current
			DESCRIPTION 
				"Description."
			::= { sleRIPngOffsetListNotification 1 }

		
		-- 1.3.6.1.4.1.6296.101.55.7.3.2
		sleRIPngOffsetListInDeleted NOTIFICATION-TYPE
			OBJECTS { sleRIPngOffsetListControlRequest, sleRIPngOffsetListControlTimeStamp, sleRIPngOffsetListControlReqResult, sleRIPngOffsetListControlIfname, sleRIPngOffsetListControlInAccName, 
				sleRIPngOffsetListControlInMetric }
			STATUS current
			DESCRIPTION 
				"Description."
			::= { sleRIPngOffsetListNotification 2 }

		
		-- 1.3.6.1.4.1.6296.101.55.7.3.3
		sleRIPngOffsetListOutCreated NOTIFICATION-TYPE
			OBJECTS { sleRIPngOffsetListControlRequest, sleRIPngOffsetListControlTimeStamp, sleRIPngOffsetListControlReqResult, sleRIPngOffsetListIfname, sleRIPngOffsetListOutAccName, 
				sleRIPngOffsetListOutMetric }
			STATUS current
			DESCRIPTION 
				"Description."
			::= { sleRIPngOffsetListNotification 3 }

		
		-- 1.3.6.1.4.1.6296.101.55.7.3.4
		sleRIPngOffsetListOutDeleted NOTIFICATION-TYPE
			OBJECTS { sleRIPngOffsetListControlRequest, sleRIPngOffsetListControlTimeStamp, sleRIPngOffsetListControlReqResult, sleRIPngOffsetListControlIfname, sleRIPngOffsetListControlOutAccName, 
				sleRIPngOffsetListControlOutMetric }
			STATUS current
			DESCRIPTION 
				"Description."
			::= { sleRIPngOffsetListNotification 4 }

		
		-- 1.3.6.1.4.1.6296.101.55.8
		sleRIPngRedistribute OBJECT IDENTIFIER ::= { sleRIPng 8 }

		
		-- 1.3.6.1.4.1.6296.101.55.8.1
		sleRIPngRedistributeTable OBJECT-TYPE
			SYNTAX SEQUENCE OF SleRIPRedistributeEntry
			MAX-ACCESS not-accessible
			STATUS current
			DESCRIPTION
				"Description."
			::= { sleRIPngRedistribute 1 }

		
		-- 1.3.6.1.4.1.6296.101.55.8.1.1
		sleRIPngRedistributeEntry OBJECT-TYPE
			SYNTAX SleRIPRedistributeEntry
			MAX-ACCESS not-accessible
			STATUS current
			DESCRIPTION
				"Description."
			INDEX { sleRIPngRedistType }
			::= { sleRIPngRedistributeTable 1 }

		
		SleRIPRedistributeEntry ::=
			SEQUENCE { 
				sleRIPngRedistType
					INTEGER,
				sleRIPngRedistMetric
					INTEGER,
				sleRIPngRedistRouteMapName
					OCTET STRING
			 }

		-- 1.3.6.1.4.1.6296.101.55.8.1.1.1
		sleRIPngRedistType OBJECT-TYPE
			SYNTAX INTEGER
				{
				kernel(1),
				connected(2),
				static(3),
				bgp(4),
				ospf(5)
				}
			MAX-ACCESS read-only
			STATUS current
			DESCRIPTION
				"Description."
			::= { sleRIPngRedistributeEntry 1 }

		
		-- 1.3.6.1.4.1.6296.101.55.8.1.1.2
		sleRIPngRedistMetric OBJECT-TYPE
			SYNTAX INTEGER (1..16777214)
			MAX-ACCESS read-only
			STATUS current
			DESCRIPTION
				"Description."
			::= { sleRIPngRedistributeEntry 2 }

		
		-- 1.3.6.1.4.1.6296.101.55.8.1.1.3
		sleRIPngRedistRouteMapName OBJECT-TYPE
			SYNTAX OCTET STRING (SIZE (0..512))
			MAX-ACCESS read-only
			STATUS current
			DESCRIPTION
				"Description."
			::= { sleRIPngRedistributeEntry 3 }

		
		-- 1.3.6.1.4.1.6296.101.55.8.2
		sleRIPngRedistributeControl OBJECT IDENTIFIER ::= { sleRIPngRedistribute 2 }

		
		-- 1.3.6.1.4.1.6296.101.55.8.2.1
		sleRIPngRedistControlRequest OBJECT-TYPE
			SYNTAX INTEGER
				{
				createRIPngRedistribute(1),
				deleteRIPngRedistribute(2),
				setRIPngRedistribute(3)
				}
			MAX-ACCESS read-write
			STATUS current
			DESCRIPTION
				"Description."
			::= { sleRIPngRedistributeControl 1 }

		
		-- 1.3.6.1.4.1.6296.101.55.8.2.2
		sleRIPngRedistControlStatus OBJECT-TYPE
			SYNTAX SleControlStatusType
			MAX-ACCESS read-only
			STATUS current
			DESCRIPTION
				"Description."
			::= { sleRIPngRedistributeControl 2 }

		
		-- 1.3.6.1.4.1.6296.101.55.8.2.3
		sleRIPngRedistControlTimer OBJECT-TYPE
			SYNTAX Gauge32
			MAX-ACCESS read-write
			STATUS current
			DESCRIPTION
				"Description."
			::= { sleRIPngRedistributeControl 3 }

		
		-- 1.3.6.1.4.1.6296.101.55.8.2.4
		sleRIPngRedistControlTimeStamp OBJECT-TYPE
			SYNTAX TimeTicks
			MAX-ACCESS read-only
			STATUS current
			DESCRIPTION
				"Description."
			::= { sleRIPngRedistributeControl 4 }

		
		-- 1.3.6.1.4.1.6296.101.55.8.2.5
		sleRIPngRedistControlReqResult OBJECT-TYPE
			SYNTAX SleControlRequestResultType
			MAX-ACCESS read-only
			STATUS current
			DESCRIPTION
				"Description."
			::= { sleRIPngRedistributeControl 5 }

		
		-- 1.3.6.1.4.1.6296.101.55.8.2.6
		sleRIPngRedistControlType OBJECT-TYPE
			SYNTAX INTEGER
				{
				kernel(1),
				connected(2),
				static(3),
				bgp(4),
				ospf(5)
				}
			MAX-ACCESS read-write
			STATUS current
			DESCRIPTION
				"Description."
			::= { sleRIPngRedistributeControl 6 }

		
		-- 1.3.6.1.4.1.6296.101.55.8.2.7
		sleRIPngRedistControlMetric OBJECT-TYPE
			SYNTAX INTEGER (1..16777214)
			MAX-ACCESS read-write
			STATUS current
			DESCRIPTION
				"Description."
			::= { sleRIPngRedistributeControl 7 }

		
		-- 1.3.6.1.4.1.6296.101.55.8.2.8
		sleRIPngRedistControlRouteMapName OBJECT-TYPE
			SYNTAX OCTET STRING (SIZE (0..512))
			MAX-ACCESS read-write
			STATUS current
			DESCRIPTION
				"Description."
			::= { sleRIPngRedistributeControl 8 }

		
		-- 1.3.6.1.4.1.6296.101.55.8.3
		sleRIPngRedistributeNotification OBJECT IDENTIFIER ::= { sleRIPngRedistribute 3 }

		
		-- 1.3.6.1.4.1.6296.101.55.8.3.1
		sleRIPngRedistributeCreated NOTIFICATION-TYPE
			OBJECTS { sleRIPngRedistControlRequest, sleRIPngRedistControlTimeStamp, sleRIPngRedistControlReqResult, sleRIPngRedistType, sleRIPngRedistMetric, 
				sleRIPngRedistRouteMapName }
			STATUS current
			DESCRIPTION 
				"Description."
			::= { sleRIPngRedistributeNotification 1 }

		
		-- 1.3.6.1.4.1.6296.101.55.8.3.2
		sleRIPngRedistributeDeleted NOTIFICATION-TYPE
			OBJECTS { sleRIPngRedistControlRequest, sleRIPngRedistControlTimeStamp, sleRIPngRedistControlReqResult, sleRIPngRedistControlType }
			STATUS current
			DESCRIPTION 
				"Description."
			::= { sleRIPngRedistributeNotification 2 }

		
		-- 1.3.6.1.4.1.6296.101.55.8.3.3
		sleRIPngRedistributeChanged NOTIFICATION-TYPE
			OBJECTS { sleRIPngRedistControlRequest, sleRIPngRedistControlTimeStamp, sleRIPngRedistControlReqResult, sleRIPngRedistType, sleRIPngRedistMetric, 
				sleRIPngRedistRouteMapName }
			STATUS current
			DESCRIPTION 
				"Description."
			::= { sleRIPngRedistributeNotification 3 }

		
		-- 1.3.6.1.4.1.6296.101.55.9
		sleRIPngRoutemap OBJECT IDENTIFIER ::= { sleRIPng 9 }

		
		-- 1.3.6.1.4.1.6296.101.55.9.1
		sleRIPngRoutemapTable OBJECT-TYPE
			SYNTAX SEQUENCE OF SleRIPngRoutemapEntry
			MAX-ACCESS not-accessible
			STATUS current
			DESCRIPTION
				"Description."
			::= { sleRIPngRoutemap 1 }

		
		-- 1.3.6.1.4.1.6296.101.55.9.1.1
		sleRIPngRoutemapEntry OBJECT-TYPE
			SYNTAX SleRIPngRoutemapEntry
			MAX-ACCESS not-accessible
			STATUS current
			DESCRIPTION
				"Description."
			INDEX { sleRIPngRoutemapName, sleRIPngRoutemapType, sleRIPngRoutemapIfname }
			::= { sleRIPngRoutemapTable 1 }

		
		SleRIPngRoutemapEntry ::=
			SEQUENCE { 
				sleRIPngRoutemapName
					OCTET STRING,
				sleRIPngRoutemapType
					INTEGER,
				sleRIPngRoutemapIfname
					OCTET STRING
			 }

		-- 1.3.6.1.4.1.6296.101.55.9.1.1.1
		sleRIPngRoutemapName OBJECT-TYPE
			SYNTAX OCTET STRING (SIZE (0..512))
			MAX-ACCESS read-only
			STATUS current
			DESCRIPTION
				"Description."
			::= { sleRIPngRoutemapEntry 1 }

		
		-- 1.3.6.1.4.1.6296.101.55.9.1.1.2
		sleRIPngRoutemapType OBJECT-TYPE
			SYNTAX INTEGER
				{
				in(0),
				out(1)
				}
			MAX-ACCESS read-only
			STATUS current
			DESCRIPTION
				"Description."
			::= { sleRIPngRoutemapEntry 2 }

		
		-- 1.3.6.1.4.1.6296.101.55.9.1.1.3
		sleRIPngRoutemapIfname OBJECT-TYPE
			SYNTAX OCTET STRING (SIZE (0..512))
			MAX-ACCESS read-only
			STATUS current
			DESCRIPTION
				"Description."
			::= { sleRIPngRoutemapEntry 3 }

		
		-- 1.3.6.1.4.1.6296.101.55.9.2
		sleRIPngRoutemapControl OBJECT IDENTIFIER ::= { sleRIPngRoutemap 2 }

		
		-- 1.3.6.1.4.1.6296.101.55.9.2.1
		sleRIPngRoutemapControlRequest OBJECT-TYPE
			SYNTAX INTEGER
				{
				createRIPngRoutemap(1),
				deleteRIPngRoutemap(2)
				}
			MAX-ACCESS read-write
			STATUS current
			DESCRIPTION
				"Description."
			::= { sleRIPngRoutemapControl 1 }

		
		-- 1.3.6.1.4.1.6296.101.55.9.2.2
		sleRIPngRoutemapControlStatus OBJECT-TYPE
			SYNTAX SleControlStatusType
			MAX-ACCESS read-only
			STATUS current
			DESCRIPTION
				"Description."
			::= { sleRIPngRoutemapControl 2 }

		
		-- 1.3.6.1.4.1.6296.101.55.9.2.3
		sleRIPngRoutemapControlTimer OBJECT-TYPE
			SYNTAX Gauge32
			MAX-ACCESS read-write
			STATUS current
			DESCRIPTION
				"Description."
			::= { sleRIPngRoutemapControl 3 }

		
		-- 1.3.6.1.4.1.6296.101.55.9.2.4
		sleRIPngRoutemapControlTimeStamp OBJECT-TYPE
			SYNTAX TimeTicks
			MAX-ACCESS read-only
			STATUS current
			DESCRIPTION
				"Description."
			::= { sleRIPngRoutemapControl 4 }

		
		-- 1.3.6.1.4.1.6296.101.55.9.2.5
		sleRIPngRoutemapControlReqResult OBJECT-TYPE
			SYNTAX SleControlRequestResultType
			MAX-ACCESS read-only
			STATUS current
			DESCRIPTION
				"Description."
			::= { sleRIPngRoutemapControl 5 }

		
		-- 1.3.6.1.4.1.6296.101.55.9.2.6
		sleRIPngRoutemapControlName OBJECT-TYPE
			SYNTAX OCTET STRING (SIZE (0..512))
			MAX-ACCESS read-write
			STATUS current
			DESCRIPTION
				"Description."
			::= { sleRIPngRoutemapControl 6 }

		
		-- 1.3.6.1.4.1.6296.101.55.9.2.7
		sleRIPngRoutemapControlType OBJECT-TYPE
			SYNTAX INTEGER
				{
				in(0),
				out(1)
				}
			MAX-ACCESS read-write
			STATUS current
			DESCRIPTION
				"Description."
			::= { sleRIPngRoutemapControl 7 }

		
		-- 1.3.6.1.4.1.6296.101.55.9.2.8
		sleRIPngRoutemapControlIfname OBJECT-TYPE
			SYNTAX OCTET STRING (SIZE (0..512))
			MAX-ACCESS read-write
			STATUS current
			DESCRIPTION
				"Description."
			::= { sleRIPngRoutemapControl 8 }

		
		-- 1.3.6.1.4.1.6296.101.55.9.3
		sleRIPngRoutemapNotification OBJECT IDENTIFIER ::= { sleRIPngRoutemap 3 }

		
		-- 1.3.6.1.4.1.6296.101.55.9.3.1
		sleRIPngRoutemapCreated NOTIFICATION-TYPE
			OBJECTS { sleRIPngRoutemapControlRequest, sleRIPngRoutemapControlTimeStamp, sleRIPngRoutemapControlReqResult, sleRIPngRoutemapName, sleRIPngRoutemapType, 
				sleRIPngRoutemapIfname }
			STATUS current
			DESCRIPTION 
				"Description."
			::= { sleRIPngRoutemapNotification 1 }

		
		-- 1.3.6.1.4.1.6296.101.55.9.3.2
		sleRIPngRoutemapDeleted NOTIFICATION-TYPE
			OBJECTS { sleRIPngRoutemapControlRequest, sleRIPngRoutemapControlTimeStamp, sleRIPngRoutemapControlReqResult, sleRIPngRoutemapControlName, sleRIPngRoutemapControlType, 
				sleRIPngRoutemapControlIfname }
			STATUS current
			DESCRIPTION 
				"Description."
			::= { sleRIPngRoutemapNotification 2 }

		
		-- 1.3.6.1.4.1.6296.101.55.10
		sleRIPngPassInterface OBJECT IDENTIFIER ::= { sleRIPng 10 }

		
		-- 1.3.6.1.4.1.6296.101.55.10.1
		sleRIPngPassInterfaceTable OBJECT-TYPE
			SYNTAX SEQUENCE OF SleRIPPassInterfaceEntry
			MAX-ACCESS not-accessible
			STATUS current
			DESCRIPTION
				"Description."
			::= { sleRIPngPassInterface 1 }

		
		-- 1.3.6.1.4.1.6296.101.55.10.1.1
		sleRIPngPassInterfaceEntry OBJECT-TYPE
			SYNTAX SleRIPPassInterfaceEntry
			MAX-ACCESS not-accessible
			STATUS current
			DESCRIPTION
				"Description."
			INDEX { sleRIPngPassInterfaceName }
			::= { sleRIPngPassInterfaceTable 1 }

		
		SleRIPPassInterfaceEntry ::=
			SEQUENCE { 
				sleRIPngPassInterfaceName
					OCTET STRING
			 }

		-- 1.3.6.1.4.1.6296.101.55.10.1.1.1
		sleRIPngPassInterfaceName OBJECT-TYPE
			SYNTAX OCTET STRING (SIZE (0..512))
			MAX-ACCESS read-only
			STATUS current
			DESCRIPTION
				"Description."
			::= { sleRIPngPassInterfaceEntry 1 }

		
		-- 1.3.6.1.4.1.6296.101.55.10.2
		sleRIPngPassInterfaceControl OBJECT IDENTIFIER ::= { sleRIPngPassInterface 2 }

		
		-- 1.3.6.1.4.1.6296.101.55.10.2.1
		sleRIPngPassInterfaceControlRequest OBJECT-TYPE
			SYNTAX INTEGER
				{
				createRIPngPassInterface(1),
				deleteRIPngPassInterface(2)
				}
			MAX-ACCESS read-write
			STATUS current
			DESCRIPTION
				"Description."
			::= { sleRIPngPassInterfaceControl 1 }

		
		-- 1.3.6.1.4.1.6296.101.55.10.2.2
		sleRIPngPassInterfaceControlStatus OBJECT-TYPE
			SYNTAX SleControlStatusType
			MAX-ACCESS read-only
			STATUS current
			DESCRIPTION
				"Description."
			::= { sleRIPngPassInterfaceControl 2 }

		
		-- 1.3.6.1.4.1.6296.101.55.10.2.3
		sleRIPngPassInterfaceControlTimer OBJECT-TYPE
			SYNTAX Gauge32
			MAX-ACCESS read-write
			STATUS current
			DESCRIPTION
				"Description."
			::= { sleRIPngPassInterfaceControl 3 }

		
		-- 1.3.6.1.4.1.6296.101.55.10.2.4
		sleRIPngPassInterfaceControlTimeStamp OBJECT-TYPE
			SYNTAX TimeTicks
			MAX-ACCESS read-only
			STATUS current
			DESCRIPTION
				"Description."
			::= { sleRIPngPassInterfaceControl 4 }

		
		-- 1.3.6.1.4.1.6296.101.55.10.2.5
		sleRIPngPassInterfaceControlReqResult OBJECT-TYPE
			SYNTAX SleControlRequestResultType
			MAX-ACCESS read-only
			STATUS current
			DESCRIPTION
				"Description."
			::= { sleRIPngPassInterfaceControl 5 }

		
		-- 1.3.6.1.4.1.6296.101.55.10.2.6
		sleRIPngPassInterfaceControlName OBJECT-TYPE
			SYNTAX OCTET STRING (SIZE (0..512))
			MAX-ACCESS read-write
			STATUS current
			DESCRIPTION
				"Description."
			::= { sleRIPngPassInterfaceControl 6 }

		
		-- 1.3.6.1.4.1.6296.101.55.10.3
		sleRIPngPassInterfaceNotification OBJECT IDENTIFIER ::= { sleRIPngPassInterface 3 }

		
		-- 1.3.6.1.4.1.6296.101.55.10.3.1
		sleRIPngPassInterfaceCreated NOTIFICATION-TYPE
			OBJECTS { sleRIPngPassInterfaceControlRequest, sleRIPngPassInterfaceControlTimeStamp, sleRIPngPassInterfaceControlReqResult, sleRIPngPassInterfaceName }
			STATUS current
			DESCRIPTION 
				"Description."
			::= { sleRIPngPassInterfaceNotification 1 }

		
		-- 1.3.6.1.4.1.6296.101.55.10.3.2
		sleRIPngPassInterfaceDeleted NOTIFICATION-TYPE
			OBJECTS { sleRIPngPassInterfaceControlRequest, sleRIPngPassInterfaceControlTimeStamp, sleRIPngPassInterfaceControlReqResult, sleRIPngPassInterfaceControlName }
			STATUS current
			DESCRIPTION 
				"Description."
			::= { sleRIPngPassInterfaceNotification 2 }

		
		-- 1.3.6.1.4.1.6296.101.55.11
		sleRIPngInterface OBJECT IDENTIFIER ::= { sleRIPng 11 }

		
		-- 1.3.6.1.4.1.6296.101.55.11.1
		sleRIPngInterfaceTable OBJECT-TYPE
			SYNTAX SEQUENCE OF SleRIPInterfaceEntry
			MAX-ACCESS not-accessible
			STATUS current
			DESCRIPTION
				"Description."
			::= { sleRIPngInterface 1 }

		
		-- 1.3.6.1.4.1.6296.101.55.11.1.1
		sleRIPngInterfaceEntry OBJECT-TYPE
			SYNTAX SleRIPInterfaceEntry
			MAX-ACCESS not-accessible
			STATUS current
			DESCRIPTION
				"Description."
			INDEX { sleRIPngInterfaceIndex }
			::= { sleRIPngInterfaceTable 1 }

		
		SleRIPInterfaceEntry ::=
			SEQUENCE { 
				sleRIPngInterfaceIndex
					INTEGER,
				sleRIPngInterfaceRouterMode
					INTEGER,
				sleRIPngInterfaceRecvPacket
					INTEGER,
				sleRIPngInterfaceSendPacket
					INTEGER,
				sleRIPngInterfaceSplitHorizonMode
					INTEGER
			 }

		-- 1.3.6.1.4.1.6296.101.55.11.1.1.1
		sleRIPngInterfaceIndex OBJECT-TYPE
			SYNTAX INTEGER (0..4097)
			MAX-ACCESS read-only
			STATUS current
			DESCRIPTION
				"Description."
			::= { sleRIPngInterfaceEntry 1 }

		
		-- 1.3.6.1.4.1.6296.101.55.11.1.1.2
		sleRIPngInterfaceRouterMode OBJECT-TYPE
			SYNTAX INTEGER
				{
				disable(0),
				enable(1)
				}
			MAX-ACCESS read-only
			STATUS current
			DESCRIPTION
				"Description."
			::= { sleRIPngInterfaceEntry 2 }

		
		-- 1.3.6.1.4.1.6296.101.55.11.1.1.3
		sleRIPngInterfaceRecvPacket OBJECT-TYPE
			SYNTAX INTEGER
				{
				disable(0),
				enable(1)
				}
			MAX-ACCESS read-only
			STATUS current
			DESCRIPTION
				"Description."
			::= { sleRIPngInterfaceEntry 3 }

		
		-- 1.3.6.1.4.1.6296.101.55.11.1.1.4
		sleRIPngInterfaceSendPacket OBJECT-TYPE
			SYNTAX INTEGER
				{
				disable(0),
				enable(1)
				}
			MAX-ACCESS read-only
			STATUS current
			DESCRIPTION
				"Description."
			::= { sleRIPngInterfaceEntry 4 }

		
		-- 1.3.6.1.4.1.6296.101.55.11.1.1.5
		sleRIPngInterfaceSplitHorizonMode OBJECT-TYPE
			SYNTAX INTEGER
				{
				disable(0),
				withoutPoisonedReverse(1),
				withPoisonedReverse(2)
				}
			MAX-ACCESS read-only
			STATUS current
			DESCRIPTION
				"Description."
			::= { sleRIPngInterfaceEntry 5 }

		
		-- 1.3.6.1.4.1.6296.101.55.11.2
		sleRIPngInterfaceControl OBJECT IDENTIFIER ::= { sleRIPngInterface 2 }

		
		-- 1.3.6.1.4.1.6296.101.55.11.2.1
		sleRIPngInterfaceControlRequest OBJECT-TYPE
			SYNTAX INTEGER
				{
				createRIPngInterfaceRouterMode(1),
				deleteRIPngInterfaceRouterMode(2),
				setRIPngInterfaceRecvPacketEnable(3),
				setRIPngInterfaceSendPacketEnable(4),
				setRIPngInterfaceSplitHorizonMode(5)
				}
			MAX-ACCESS read-write
			STATUS current
			DESCRIPTION
				"Description."
			::= { sleRIPngInterfaceControl 1 }

		
		-- 1.3.6.1.4.1.6296.101.55.11.2.2
		sleRIPngInterfaceControlStatus OBJECT-TYPE
			SYNTAX SleControlStatusType
			MAX-ACCESS read-only
			STATUS current
			DESCRIPTION
				"Description."
			::= { sleRIPngInterfaceControl 2 }

		
		-- 1.3.6.1.4.1.6296.101.55.11.2.3
		sleRIPngInterfaceControlTimer OBJECT-TYPE
			SYNTAX Gauge32
			MAX-ACCESS read-write
			STATUS current
			DESCRIPTION
				"Description."
			::= { sleRIPngInterfaceControl 3 }

		
		-- 1.3.6.1.4.1.6296.101.55.11.2.4
		sleRIPngInterfaceControlTimeStamp OBJECT-TYPE
			SYNTAX TimeTicks
			MAX-ACCESS read-only
			STATUS current
			DESCRIPTION
				"Description."
			::= { sleRIPngInterfaceControl 4 }

		
		-- 1.3.6.1.4.1.6296.101.55.11.2.5
		sleRIPngInterfaceControlReqResult OBJECT-TYPE
			SYNTAX SleControlRequestResultType
			MAX-ACCESS read-only
			STATUS current
			DESCRIPTION
				"Description."
			::= { sleRIPngInterfaceControl 5 }

		
		-- 1.3.6.1.4.1.6296.101.55.11.2.6
		sleRIPngInterfaceControlIndex OBJECT-TYPE
			SYNTAX INTEGER (0..4097)
			MAX-ACCESS read-write
			STATUS current
			DESCRIPTION
				"Description."
			::= { sleRIPngInterfaceControl 6 }

		
		-- 1.3.6.1.4.1.6296.101.55.11.2.7
		sleRIPngInterfaceControlRouterMode OBJECT-TYPE
			SYNTAX SleControlRequestResultType
				{
				disable(0),
				enable(1)
				}
			MAX-ACCESS read-only
			STATUS current
			DESCRIPTION
				"Description."
			::= { sleRIPngInterfaceControl 7 }

		
		-- 1.3.6.1.4.1.6296.101.55.11.2.8
		sleRIPngInterfaceControlRecvPacket OBJECT-TYPE
			SYNTAX INTEGER
				{
				disable(0),
				enable(1)
				}
			MAX-ACCESS read-write
			STATUS current
			DESCRIPTION
				"Description."
			::= { sleRIPngInterfaceControl 8 }

		
		-- 1.3.6.1.4.1.6296.101.55.11.2.9
		sleRIPngInterfaceControlSendPacket OBJECT-TYPE
			SYNTAX INTEGER
				{
				disable(0),
				enable(1)
				}
			MAX-ACCESS read-write
			STATUS current
			DESCRIPTION
				"Description."
			::= { sleRIPngInterfaceControl 9 }

		
		-- 1.3.6.1.4.1.6296.101.55.11.2.10
		sleRIPngInterfaceControlSplitHorizonMode OBJECT-TYPE
			SYNTAX INTEGER
				{
				disable(0),
				withoutPoisonedReverse(1),
				withPoisonedReverse(2)
				}
			MAX-ACCESS read-write
			STATUS current
			DESCRIPTION
				"Description."
			::= { sleRIPngInterfaceControl 10 }

		
		-- 1.3.6.1.4.1.6296.101.55.11.3
		sleRIPngInterfaceNotification OBJECT IDENTIFIER ::= { sleRIPngInterface 3 }

		
		-- 1.3.6.1.4.1.6296.101.55.11.3.1
		sleRIPngInterfaceRouterModeCreated NOTIFICATION-TYPE
			OBJECTS { sleRIPngInterfaceControlRequest, sleRIPngInterfaceControlTimeStamp, sleRIPngInterfaceControlReqResult, sleRIPngInterfaceIndex }
			STATUS current
			DESCRIPTION 
				"Description."
			::= { sleRIPngInterfaceNotification 1 }

		
		-- 1.3.6.1.4.1.6296.101.55.11.3.2
		sleRIPngInterfaceRouterModeDeleted NOTIFICATION-TYPE
			OBJECTS { sleRIPngInterfaceControlRequest, sleRIPngInterfaceControlTimeStamp, sleRIPngInterfaceControlReqResult, sleRIPngInterfaceIndex }
			STATUS current
			DESCRIPTION 
				"Description."
			::= { sleRIPngInterfaceNotification 2 }

		
		-- 1.3.6.1.4.1.6296.101.55.11.3.3
		sleRIPngInterfaceRecvPacketChanged NOTIFICATION-TYPE
			OBJECTS { sleRIPngInterfaceControlRequest, sleRIPngInterfaceControlTimeStamp, sleRIPngInterfaceControlReqResult, sleRIPngInterfaceIndex, sleRIPngInterfaceRecvPacket
				 }
			STATUS current
			DESCRIPTION 
				"Description."
			::= { sleRIPngInterfaceNotification 3 }

		
		-- 1.3.6.1.4.1.6296.101.55.11.3.4
		sleRIPngInterfaceSendPacketChanged NOTIFICATION-TYPE
			OBJECTS { sleRIPngInterfaceControlRequest, sleRIPngInterfaceControlTimeStamp, sleRIPngInterfaceControlReqResult, sleRIPngInterfaceIndex, sleRIPngInterfaceSendPacket
				 }
			STATUS current
			DESCRIPTION 
				"Description."
			::= { sleRIPngInterfaceNotification 4 }

		
		-- 1.3.6.1.4.1.6296.101.55.11.3.5
		sleRIPngInterfaceSplitHorizonModeChanged NOTIFICATION-TYPE
			OBJECTS { sleRIPngInterfaceControlRequest, sleRIPngInterfaceControlTimeStamp, sleRIPngInterfaceControlReqResult, sleRIPngInterfaceIndex, sleRIPngInterfaceSplitHorizonMode
				 }
			STATUS current
			DESCRIPTION 
				"Description."
			::= { sleRIPngInterfaceNotification 5 }

		
		-- 1.3.6.1.4.1.6296.101.55.12
		sleRIPngRoutes OBJECT IDENTIFIER ::= { sleRIPng 12 }

		
		-- 1.3.6.1.4.1.6296.101.55.12.1
		sleRIPngRoutesTable OBJECT-TYPE
			SYNTAX SEQUENCE OF SleRIPRoutesEntry
			MAX-ACCESS not-accessible
			STATUS current
			DESCRIPTION
				"Description."
			::= { sleRIPngRoutes 1 }

		
		-- 1.3.6.1.4.1.6296.101.55.12.1.1
		sleRIPngRoutesEntry OBJECT-TYPE
			SYNTAX SleRIPRoutesEntry
			MAX-ACCESS not-accessible
			STATUS current
			DESCRIPTION
				"Description."
			INDEX { sleRIPngRoutesType, sleRIPngRoutesPrefix, sleRIPngRoutesMask, sleRIPngRoutesNextHop }
			::= { sleRIPngRoutesTable 1 }

		
		SleRIPRoutesEntry ::=
			SEQUENCE { 
				sleRIPngRoutesType
					INTEGER,
				sleRIPngRoutesPrefix
					IpAddress,
				sleRIPngRoutesMask
					INTEGER,
				sleRIPngRoutesNextHop
					IpAddress,
				sleRIPngRoutesSelected
					INTEGER,
				sleRIPngRoutesIfName
					OCTET STRING,
				sleRIPngRoutesMetric
					INTEGER,
				sleRIPngRoutesTag
					INTEGER,
				sleRIPngRoutesUpTime
					TimeTicks
			 }

		-- 1.3.6.1.4.1.6296.101.55.12.1.1.1
		sleRIPngRoutesType OBJECT-TYPE
			SYNTAX INTEGER
				{
				rip(1),
				kernel(2),
				connected(3),
				static(4),
				ospf(5),
				isis(6),
				bgp(7)
				}
			MAX-ACCESS read-only
			STATUS current
			DESCRIPTION
				"Description."
			::= { sleRIPngRoutesEntry 1 }

		
		-- 1.3.6.1.4.1.6296.101.55.12.1.1.2
		sleRIPngRoutesPrefix OBJECT-TYPE
			SYNTAX IpAddress
			MAX-ACCESS read-only
			STATUS current
			DESCRIPTION
				"Description."
			::= { sleRIPngRoutesEntry 2 }

		
		-- 1.3.6.1.4.1.6296.101.55.12.1.1.3
		sleRIPngRoutesMask OBJECT-TYPE
			SYNTAX INTEGER (0..32)
			MAX-ACCESS read-only
			STATUS current
			DESCRIPTION
				"Description."
			::= { sleRIPngRoutesEntry 3 }

		
		-- 1.3.6.1.4.1.6296.101.55.12.1.1.4
		sleRIPngRoutesNextHop OBJECT-TYPE
			SYNTAX IpAddress
			MAX-ACCESS read-only
			STATUS current
			DESCRIPTION
				"Description."
			::= { sleRIPngRoutesEntry 4 }

		
		-- 1.3.6.1.4.1.6296.101.55.12.1.1.5
		sleRIPngRoutesSelected OBJECT-TYPE
			SYNTAX INTEGER
				{
				deselected(0),
				selected(1)
				}
			MAX-ACCESS read-only
			STATUS current
			DESCRIPTION
				"Description."
			::= { sleRIPngRoutesEntry 5 }

		
		-- 1.3.6.1.4.1.6296.101.55.12.1.1.6
		sleRIPngRoutesIfName OBJECT-TYPE
			SYNTAX OCTET STRING
			MAX-ACCESS read-only
			STATUS current
			DESCRIPTION
				"Description."
			::= { sleRIPngRoutesEntry 6 }

		
		-- 1.3.6.1.4.1.6296.101.55.12.1.1.7
		sleRIPngRoutesMetric OBJECT-TYPE
			SYNTAX INTEGER (0..255)
			MAX-ACCESS read-only
			STATUS current
			DESCRIPTION
				"Description."
			::= { sleRIPngRoutesEntry 7 }

		
		-- 1.3.6.1.4.1.6296.101.55.12.1.1.8
		sleRIPngRoutesTag OBJECT-TYPE
			SYNTAX INTEGER (0..255)
			MAX-ACCESS read-only
			STATUS current
			DESCRIPTION
				"Description."
			::= { sleRIPngRoutesEntry 8 }

		
		-- 1.3.6.1.4.1.6296.101.55.12.1.1.9
		sleRIPngRoutesUpTime OBJECT-TYPE
			SYNTAX TimeTicks
			MAX-ACCESS read-only
			STATUS current
			DESCRIPTION
				"Description."
			::= { sleRIPngRoutesEntry 9 }

		
		-- 1.3.6.1.4.1.6296.101.55.13
		sleRIPngGroup OBJECT-GROUP
			OBJECTS { sleRIPngDefaultMetric, sleRIPngDefaultInformationOrg, sleRIPngDefaultDistance, sleRIPngRecvBufferSize, sleRIPngMaximumPaths, 
				sleRIPngMaximumPrefixRoute, sleRIPngMaximumPrefixRoutePercent, sleRIPngMetricSumApply, sleRIPngBasicUpdateTimer, sleRIPngBasicTimeoutTimer, 
				sleRIPngBasicGarbageTimer, sleRIPngControlRequest, sleRIPngControlStatus, sleRIPngControlTimer, sleRIPngControlTimeStamp, 
				sleRIPngControlReqResult, sleRIPngControlDefaultMetric, sleRIPngControlDefaultInformationOrg, sleRIPngControlDefaultDistance, sleRIPngControlRecvBufferSize, 
				sleRIPngControlMaximumPaths, sleRIPngControlMaximumPrefixRoute, sleRIPngControlMaximumPrefixRoutePercent, sleRIPngControlMetricSumApply, sleRIPngControlBasicUpdateTimer, 
				sleRIPngControlBasicTimeoutTimer, sleRIPngControlBasicGarbageTimer, sleRIPngControlClearRoutePrefix, sleRIPngControlClearRouteMask, sleRIPngControlClearProtoTpye, 
				sleRIPngAggregateAddr, sleRIPngAggregateMask, sleRIPngAggregateControlRequest, sleRIPngAggregateControlStatus, sleRIPngAggregateControlTimer, 
				sleRIPngAggregateControlTimeStamp, sleRIPngAggregateControlReqResult, sleRIPngAggregateControlAddr, sleRIPngAggregateControlMask, sleRIPngNeighborAddr, 
				sleRIPngNeighborIfName, sleRIPngNeighborControlRequest, sleRIPngNeighborControlStatus, sleRIPngNeighborControlTimer, sleRIPngNeighborControlTimeStamp, 
				sleRIPngNeighborControlReqResult, sleRIPngNeighborControlAddr, sleRIPngNeighborControlIfName, sleRIPngStaticRouteAddr, sleRIPngStaticRouteMask, 
				sleRIPngStaticRouteControlRequest, sleRIPngStaticRouteControlStatus, sleRIPngStaticRouteControlTimer, sleRIPngStaticRouteControlTimeStamp, sleRIPngStaticRouteControlReqResult, 
				sleRIPngStaticRouteControlAddr, sleRIPngStaticRouteControlMask, sleRIPngAdminDistanceValue, sleRIPngAdminDistanceAddr, sleRIPngAdminDistanceMask, 
				sleRIPngAdminDistanceAccessName, sleRIPngAdminDistanceControlRequest, sleRIPngAdminDistanceControlStatus, sleRIPngAdminDistanceControlTimer, sleRIPngAdminDistanceControlTimeStamp, 
				sleRIPngAdminDistanceControlReqResult, sleRIPngAdminDistanceControlValue, sleRIPngAdminDistanceControlAddr, sleRIPngAdminDistanceControlMask, sleRIPngAdminDistanceControlAccessName, 
				sleRIPngDistributeIfName, sleRIPngDistributeInAccessName, sleRIPngDistributeOutAccessName, sleRIPngDistributeInPrefixName, sleRIPngDistributeOutPrefixName, 
				sleRIPngDistributeControlRequest, sleRIPngDistributeControlStatus, sleRIPngDistributeControlTimer, sleRIPngDistributeControlTimeStamp, sleRIPngDistributeControlReqResult, 
				sleRIPngDistributeControlIfName, sleRIPngDistributeControlInAccessName, sleRIPngDistributeControlOutAccessName, sleRIPngDistributeControlInPrefixName, sleRIPngDistributeControlOutPrefixName, 
				sleRIPngOffsetListIfname, sleRIPngOffsetListInAccName, sleRIPngOffsetListInMetric, sleRIPngOffsetListOutAccName, sleRIPngOffsetListOutMetric, 
				sleRIPngOffsetListControlRequest, sleRIPngOffsetListControlStatus, sleRIPngOffsetListControlTimer, sleRIPngOffsetListControlTimeStamp, sleRIPngOffsetListControlReqResult, 
				sleRIPngOffsetListControlIfname, sleRIPngOffsetListControlInAccName, sleRIPngOffsetListControlInMetric, sleRIPngOffsetListControlOutAccName, sleRIPngOffsetListControlOutMetric, 
				sleRIPngRedistType, sleRIPngRedistMetric, sleRIPngRedistRouteMapName, sleRIPngRedistControlRequest, sleRIPngRedistControlStatus, 
				sleRIPngRedistControlTimer, sleRIPngRedistControlTimeStamp, sleRIPngRedistControlReqResult, sleRIPngRedistControlType, sleRIPngRedistControlMetric, 
				sleRIPngRedistControlRouteMapName, sleRIPngRoutemapName, sleRIPngRoutemapType, sleRIPngRoutemapIfname, sleRIPngRoutemapControlRequest, 
				sleRIPngRoutemapControlStatus, sleRIPngRoutemapControlTimer, sleRIPngRoutemapControlTimeStamp, sleRIPngRoutemapControlReqResult, sleRIPngRoutemapControlName, 
				sleRIPngRoutemapControlType, sleRIPngRoutemapControlIfname, sleRIPngPassInterfaceName, sleRIPngPassInterfaceControlRequest, sleRIPngPassInterfaceControlStatus, 
				sleRIPngPassInterfaceControlTimer, sleRIPngPassInterfaceControlTimeStamp, sleRIPngPassInterfaceControlReqResult, sleRIPngPassInterfaceControlName, sleRIPngInterfaceIndex, 
				sleRIPngInterfaceRouterMode, sleRIPngInterfaceRecvPacket, sleRIPngInterfaceSendPacket, sleRIPngInterfaceSplitHorizonMode, sleRIPngInterfaceControlRequest, 
				sleRIPngInterfaceControlStatus, sleRIPngInterfaceControlTimer, sleRIPngInterfaceControlTimeStamp, sleRIPngInterfaceControlReqResult, sleRIPngInterfaceControlIndex, 
				sleRIPngInterfaceControlRouterMode, sleRIPngInterfaceControlRecvPacket, sleRIPngInterfaceControlSendPacket, sleRIPngInterfaceControlSplitHorizonMode, sleRIPngRoutesType, 
				sleRIPngRoutesPrefix, sleRIPngRoutesMask, sleRIPngRoutesNextHop, sleRIPngRoutesSelected, sleRIPngRoutesIfName, 
				sleRIPngRoutesMetric, sleRIPngRoutesTag, sleRIPngRoutesUpTime }
			STATUS current
			DESCRIPTION 
				"Description."
			::= { sleRIPng 13 }

		
		-- 1.3.6.1.4.1.6296.101.55.14
		sleRIPngNotificationGroup NOTIFICATION-GROUP
			NOTIFICATIONS { sleRIPngModeCreated, sleRIPngModeDeleted, sleRIPngDefaultMetricChanged, sleRIPngDefaultInformationOrgChanged, sleRIPngDefaultDistanceChanged, 
				sleRIPngRecvBufferSizeChanged, sleRIPngMaximumPathsChanged, sleRIPngMaximumPrefixProfileChanged, sleRIPngMetricSumApplyChanged, sleRIPngTimersChanged, 
				sleRIPngAllCleared, sleRIPngRouteCleared, sleRIPngProtoTypeCleared, sleRIPngAggregateAddrCreated, sleRIPngAggregateAddrDeleted, 
				sleRIPngNeighborCreated, sleRIPngNeighborDeleted, sleRIPngStaticRouteCreated, sleRIPngStaticRouteDeleted, sleRIPngAdminDistanceCreated, 
				sleRIPngAdminDistanceDeleted, sleRIPngDistributeInAccessCreated, sleRIPngDistributeInAccessDeleted, sleRIPngDistributeOutAccessCreated, sleRIPngDistributeOutAccessDeleted, 
				sleRIPngDistributeInPrefixCreated, sleRIPngDistributeInPrefixDeleted, sleRIPngDistributeOutPrefixCreated, sleRIPngDistributeOutPrefixDeleted, sleRIPngOffsetListInCreated, 
				sleRIPngOffsetListInDeleted, sleRIPngOffsetListOutCreated, sleRIPngOffsetListOutDeleted, sleRIPngRedistributeCreated, sleRIPngRedistributeDeleted, 
				sleRIPngRedistributeChanged, sleRIPngRoutemapCreated, sleRIPngRoutemapDeleted, sleRIPngPassInterfaceCreated, sleRIPngPassInterfaceDeleted, 
				sleRIPngInterfaceRouterModeCreated, sleRIPngInterfaceRouterModeDeleted, sleRIPngInterfaceRecvPacketChanged, sleRIPngInterfaceSendPacketChanged, sleRIPngInterfaceSplitHorizonModeChanged
				 }
			STATUS current
			DESCRIPTION 
				"Description."
			::= { sleRIPng 14 }

		
	
	END

--
-- sle-ripng-mib.mib
--
