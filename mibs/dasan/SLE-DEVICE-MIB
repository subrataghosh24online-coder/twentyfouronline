--
-- SLE-DEVICE-MIB.my
-- MIB generated by MG-SOFT Visual MIB Builder Version 6.0  Build 88
-- Friday, March 18, 2016 at 15:23:50
--

	SLE-DEVICE-MIB DEFINITIONS ::= BEGIN
 
		IMPORTS
			sleMgmt			
				FROM DASAN-SMI			
			SleControlStatusType, SleControlRequestResultType			
				FROM SLE-TC-MIB			
			OBJECT-GROUP, NOTIFICATION-GROUP			
				FROM SNMPv2-CONF			
			TimeTicks, IpAddress, Integer32, Unsigned32, Gauge32, 
			BITS, OBJECT-TYPE, MODULE-IDENTITY, NOTIFICATION-TYPE			
				FROM SNMPv2-SMI;
	
	
		sleDevice MODULE-IDENTITY 
			LAST-UPDATED "200412100852Z"		-- December 10, 2004 at 08:52 GMT
			ORGANIZATION 
				"Organization."
			CONTACT-INFO 
				"Contact-info."
			DESCRIPTION 
				"Description."
			::= { sleMgmt 2 }

		
	
	
--
-- Node definitions
--
	
		sleDeviceBase OBJECT IDENTIFIER ::= { sleDevice 1 }

		
		sleDeviceBaseInfo OBJECT IDENTIFIER ::= { sleDeviceBase 1 }

		
		sleDeviceEthernetPortNum OBJECT-TYPE
			SYNTAX Integer32
			MAX-ACCESS read-only
			STATUS current
			DESCRIPTION
				"The number of ethernet port."
			::= { sleDeviceBaseInfo 1 }

		
		sleDevicePowerNum OBJECT-TYPE
			SYNTAX Integer32
			MAX-ACCESS read-only
			STATUS current
			DESCRIPTION
				"The number of power module"
			::= { sleDeviceBaseInfo 2 }

		
		sleDeviceFanModuleNum OBJECT-TYPE
			SYNTAX Integer32
			MAX-ACCESS read-only
			STATUS current
			DESCRIPTION
				"The number of FAN module"
			::= { sleDeviceBaseInfo 3 }

		
		sleDeviceTemperatureNum OBJECT-TYPE
			SYNTAX Integer32
			MAX-ACCESS read-only
			STATUS current
			DESCRIPTION
				"The number of temperature sensor"
			::= { sleDeviceBaseInfo 4 }

		
		sleDeviceFanStartTemperature OBJECT-TYPE
			SYNTAX Integer32
			MAX-ACCESS read-only
			STATUS current
			DESCRIPTION
				"The temperature value which begins to turn fan."
			::= { sleDeviceBaseInfo 5 }

		
		sleDeviceFanStopTemperature OBJECT-TYPE
			SYNTAX Integer32
			MAX-ACCESS read-only
			STATUS current
			DESCRIPTION
				"The temperature value which stops fan."
			::= { sleDeviceBaseInfo 6 }

		
		sleDeviceJumboFrameStatus OBJECT-TYPE
			SYNTAX INTEGER
				{
				enable(1),
				disable(2)
				}
			MAX-ACCESS read-only
			STATUS current
			DESCRIPTION
				"The global jumbo-frame status.
				2011/01/20 V5924CR only support this."
			::= { sleDeviceBaseInfo 7 }

		
		sleDeviceEnvironmentMonitoringStatus OBJECT-TYPE
			SYNTAX INTEGER
				{
				notInstallAIU(0),
				normalOpen(1),
				normalClose(2)
				}
			MAX-ACCESS read-only
			STATUS current
			DESCRIPTION
				"The alarm input mode of environment monitoring for AIU"
			::= { sleDeviceBaseInfo 8 }

		
		sleDeviceBaseControl OBJECT IDENTIFIER ::= { sleDeviceBase 2 }

		
		sleDeviceControlRequest OBJECT-TYPE
			SYNTAX INTEGER
				{
				setDeviceTemperatureThreshold(1),
				setDeviceJumboFrameStatus(2),
				setDeviceLEDTest(3),
				setEnvironmentMonitoringStatus(4)
				}
			MAX-ACCESS read-write
			STATUS current
			DESCRIPTION
				"set an administrative state of FAN module"
			::= { sleDeviceBaseControl 1 }

		
		sleDeviceControlStatus OBJECT-TYPE
			SYNTAX SleControlStatusType
			MAX-ACCESS read-only
			STATUS current
			DESCRIPTION
				"Description."
			::= { sleDeviceBaseControl 2 }

		
		sleDeviceControlTimer OBJECT-TYPE
			SYNTAX Gauge32
			MAX-ACCESS read-write
			STATUS current
			DESCRIPTION
				"Description."
			::= { sleDeviceBaseControl 3 }

		
		sleDeviceControlTimeStamp OBJECT-TYPE
			SYNTAX TimeTicks
			MAX-ACCESS read-only
			STATUS current
			DESCRIPTION
				"Description."
			::= { sleDeviceBaseControl 4 }

		
		sleDeviceControlReqResult OBJECT-TYPE
			SYNTAX SleControlRequestResultType
			MAX-ACCESS read-only
			STATUS current
			DESCRIPTION
				"Description."
			::= { sleDeviceBaseControl 5 }

		
		sleDeviceControlFanStartTemperature OBJECT-TYPE
			SYNTAX Integer32
			MAX-ACCESS read-write
			STATUS current
			DESCRIPTION
				"Description."
			::= { sleDeviceBaseControl 6 }

		
		sleDeviceControlFanStopTemperature OBJECT-TYPE
			SYNTAX Integer32
			MAX-ACCESS read-write
			STATUS current
			DESCRIPTION
				"Description."
			::= { sleDeviceBaseControl 7 }

		
		sleDeviceControlJumboFrameStatus OBJECT-TYPE
			SYNTAX INTEGER
				{
				enable(1),
				disable(2)
				}
			MAX-ACCESS read-write
			STATUS current
			DESCRIPTION
				"The global jumbo-frame status.
				2011/01/20 V5924CR only support this."
			::= { sleDeviceBaseControl 8 }

		
		sleDeviceControlEnvironmentMonitoringStatus OBJECT-TYPE
			SYNTAX INTEGER
				{
				normalOpen(1),
				normalClose(2)
				}
			MAX-ACCESS read-only
			STATUS current
			DESCRIPTION
				"The alarm input mode of environment monitoring for AIU"
			::= { sleDeviceBaseControl 9 }

		
		sleDeviceBaseNotification OBJECT IDENTIFIER ::= { sleDeviceBase 3 }

		
		sleDeviceTemperatureThresholdChanged NOTIFICATION-TYPE
			OBJECTS { sleDeviceFanStartTemperature, sleDeviceFanStopTemperature, sleDeviceControlRequest, sleDeviceControlTimeStamp, sleDeviceControlReqResult
				 }
			STATUS current
			DESCRIPTION 
				"Description."
			::= { sleDeviceBaseNotification 1 }

		
		sleDeviceJumboFrameChanged NOTIFICATION-TYPE
			OBJECTS { sleDeviceControlRequest, sleDeviceControlTimeStamp, sleDeviceControlReqResult, sleDeviceControlJumboFrameStatus }
			STATUS current
			DESCRIPTION 
				"Description."
			::= { sleDeviceBaseNotification 2 }

		
		sleDeviceLEDTestChanged NOTIFICATION-TYPE
			OBJECTS { sleDeviceControlRequest, sleDeviceControlTimeStamp, sleDeviceControlReqResult }
			STATUS current
			DESCRIPTION 
				"Description."
			::= { sleDeviceBaseNotification 3 }

		
		sleDeviceEnvironmentMonitoringStatusChanged NOTIFICATION-TYPE
			OBJECTS { sleDeviceControlRequest, sleDeviceControlTimeStamp, sleDeviceControlReqResult, sleDeviceEnvironmentMonitoringStatus }
			STATUS current
			DESCRIPTION 
				"setEnvironmentMonitoringStatus "
			::= { sleDeviceBaseNotification 4 }

		
		sleEthernetPort OBJECT IDENTIFIER ::= { sleDevice 2 }

		
		sleEthernetPortTable OBJECT-TYPE
			SYNTAX SEQUENCE OF SleEthernetPortEntry
			MAX-ACCESS not-accessible
			STATUS current
			DESCRIPTION
				"Description."
			::= { sleEthernetPort 1 }

		
		sleEthernetPortEntry OBJECT-TYPE
			SYNTAX SleEthernetPortEntry
			MAX-ACCESS not-accessible
			STATUS current
			DESCRIPTION
				"Description."
			INDEX { sleEthernetPortIndex }
			::= { sleEthernetPortTable 1 }

		
		SleEthernetPortEntry ::=
			SEQUENCE { 
				sleEthernetPortIndex
					INTEGER,
				sleEthernetPortPhyIndex
					Integer32,
				sleEthernetPortType
					INTEGER,
				sleEthernetPortAdminStatus
					INTEGER,
				sleEthernetPortOperStatus
					INTEGER,
				sleEthernetPortTransmissionRate
					Integer32,
				sleEthernetPortDuplexMode
					INTEGER,
				sleEthernetPortFlowControl
					INTEGER,
				sleEthernetPortNegotiationMode
					INTEGER,
				sleEthernetPortJumboFrameSize
					Integer32,
				sleEthernetPortSfpTransceiver
					INTEGER,
				sleEthernetPortSfpVendorName
					OCTET STRING,
				sleEthernetPortSfpVendorPartNumber
					OCTET STRING,
				sleEthernetPortSfpVendorRevision
					OCTET STRING,
				sleEthernetPortSfpVendorSerialNumber
					OCTET STRING,
				sleEthernetPortSfpDateCode
					OCTET STRING,
				sleEthernetPortPhysicalRemoteChassis
					OCTET STRING,
				sleEthernetPortPhysicalRemoteSlot
					Integer32,
				sleEthernetPortPhysicalRemotePort
					Integer32,
				sleEthernetPortPhysicalLinkDiscoveryMode
					INTEGER,
				sleEthernetPortSfpTransceiverType
					INTEGER,
				sleEthernetPortSfpTransceiverDetailType
					INTEGER,
				sleEthernetPortSlotIndex
					Integer32,
				sleEthernetPortSlotPortIndex
					Integer32,
				sleEthernetPortAdminTransmissionRate
					Integer32,
				sleEthernetPortAdminDuplexMode
					INTEGER,
				sleEthernetPortAdminFlowControl
					INTEGER,
				sleEthernetPortAdminNegotiationMode
					INTEGER,
				sleEthernetPortAdminReason
					INTEGER,
				sleEthernetPortLinkCheckTimer
					Integer32,
				sleEthernetPortLinkDebounceTime
					Integer32,
				sleEthernetPortCpuStatisticsLimitUnicast
					Integer32,
				sleEthernetPortCpuStatisticsLimitMulticast
					Integer32,
				sleEthernetPortCpuStatisticsLimitBroadcast
					Integer32,
				sleEthernetPortFloodBlockBroadcastState
					INTEGER,
				sleEthernetPortFloodBlockDlfState
					INTEGER
			 }

		sleEthernetPortIndex OBJECT-TYPE
			SYNTAX INTEGER (1..255)
			MAX-ACCESS read-only
			STATUS current
			DESCRIPTION
				"The port index."
			::= { sleEthernetPortEntry 1 }

		
		sleEthernetPortPhyIndex OBJECT-TYPE
			SYNTAX Integer32
			MAX-ACCESS read-only
			STATUS current
			DESCRIPTION
				"The physical index of entity mib."
			::= { sleEthernetPortEntry 2 }

		
		sleEthernetPortType OBJECT-TYPE
			SYNTAX INTEGER
				{
				unknown(0),
				electrical(1),
				optical(2)
				}
			MAX-ACCESS read-only
			STATUS current
			DESCRIPTION
				"The type of port.
				It is not planed to made a automatic switchover between optical and electrical interfaces."
			::= { sleEthernetPortEntry 3 }

		
		sleEthernetPortAdminStatus OBJECT-TYPE
			SYNTAX INTEGER
				{
				up(1),
				down(2),
				notAvailable(3)
				}
			MAX-ACCESS read-only
			STATUS current
			DESCRIPTION
				"The admin status of port."
			::= { sleEthernetPortEntry 4 }

		
		sleEthernetPortOperStatus OBJECT-TYPE
			SYNTAX INTEGER
				{
				up(1),
				down(2),
				notAvailable(3)
				}
			MAX-ACCESS read-only
			STATUS current
			DESCRIPTION
				"The oper status of port"
			::= { sleEthernetPortEntry 5 }

		
		sleEthernetPortTransmissionRate OBJECT-TYPE
			SYNTAX Integer32 (10 | 100 | 1000 | 2500 | 10000)
			MAX-ACCESS read-only
			STATUS current
			DESCRIPTION
				"The speed of port. Unit is Mbit/s.
				This configurations are only useful for electrical interfaces.
				Optical - interfaces will always support 1000 MBIT/s"
			::= { sleEthernetPortEntry 6 }

		
		sleEthernetPortDuplexMode OBJECT-TYPE
			SYNTAX INTEGER
				{
				full(1),
				half(2),
				notAvailable(3)
				}
			MAX-ACCESS read-only
			STATUS current
			DESCRIPTION
				"The duplex status of port."
			::= { sleEthernetPortEntry 7 }

		
		sleEthernetPortFlowControl OBJECT-TYPE
			SYNTAX INTEGER
				{
				disabled(1),
				enabledSymetrical(2),
				enabledAsymetrical(3),
				enabledBoth(4),
				notAvailable(5)
				}
			MAX-ACCESS read-only
			STATUS current
			DESCRIPTION
				"The flow-control mode of port."
			::= { sleEthernetPortEntry 8 }

		
		sleEthernetPortNegotiationMode OBJECT-TYPE
			SYNTAX INTEGER
				{
				auto(1),
				force(2),
				notAvailable(3)
				}
			MAX-ACCESS read-only
			STATUS current
			DESCRIPTION
				"The Auto Negotiation mode of port. "
			::= { sleEthernetPortEntry 9 }

		
		sleEthernetPortJumboFrameSize OBJECT-TYPE
			SYNTAX Integer32 (0 | 1518..12288)
			MAX-ACCESS read-only
			STATUS current
			DESCRIPTION
				"The jumbo frame's size of port.
				If the value is zero, it means that it is not set up."
			::= { sleEthernetPortEntry 10 }

		
		sleEthernetPortSfpTransceiver OBJECT-TYPE
			SYNTAX INTEGER
				{
				unknown(0),
				electrical(1),
				electricalCoaxial(2),
				opticalLongHaul(3),
				opticalShortHaul(4),
				optical10G(5),
				opticalGpon(6)
				}
			MAX-ACCESS read-only
			STATUS current
			DESCRIPTION
				"Description."
			::= { sleEthernetPortEntry 11 }

		
		sleEthernetPortSfpVendorName OBJECT-TYPE
			SYNTAX OCTET STRING
			MAX-ACCESS read-only
			STATUS current
			DESCRIPTION
				"Description."
			::= { sleEthernetPortEntry 12 }

		
		sleEthernetPortSfpVendorPartNumber OBJECT-TYPE
			SYNTAX OCTET STRING
			MAX-ACCESS read-only
			STATUS current
			DESCRIPTION
				"Description."
			::= { sleEthernetPortEntry 13 }

		
		sleEthernetPortSfpVendorRevision OBJECT-TYPE
			SYNTAX OCTET STRING
			MAX-ACCESS read-only
			STATUS current
			DESCRIPTION
				"Description."
			::= { sleEthernetPortEntry 14 }

		
		sleEthernetPortSfpVendorSerialNumber OBJECT-TYPE
			SYNTAX OCTET STRING
			MAX-ACCESS read-only
			STATUS current
			DESCRIPTION
				"Description."
			::= { sleEthernetPortEntry 15 }

		
		sleEthernetPortSfpDateCode OBJECT-TYPE
			SYNTAX OCTET STRING
			MAX-ACCESS read-only
			STATUS current
			DESCRIPTION
				"Description."
			::= { sleEthernetPortEntry 16 }

		
		sleEthernetPortPhysicalRemoteChassis OBJECT-TYPE
			SYNTAX OCTET STRING
			MAX-ACCESS read-only
			STATUS current
			DESCRIPTION
				"Description."
			::= { sleEthernetPortEntry 17 }

		
		sleEthernetPortPhysicalRemoteSlot OBJECT-TYPE
			SYNTAX Integer32
			MAX-ACCESS read-only
			STATUS current
			DESCRIPTION
				"Description."
			::= { sleEthernetPortEntry 18 }

		
		sleEthernetPortPhysicalRemotePort OBJECT-TYPE
			SYNTAX Integer32
			MAX-ACCESS read-only
			STATUS current
			DESCRIPTION
				"Description."
			::= { sleEthernetPortEntry 19 }

		
		sleEthernetPortPhysicalLinkDiscoveryMode OBJECT-TYPE
			SYNTAX INTEGER
				{
				none(1),
				manual(2),
				automatic(3)
				}
			MAX-ACCESS read-only
			STATUS current
			DESCRIPTION
				"Description."
			::= { sleEthernetPortEntry 20 }

		
		sleEthernetPortSfpTransceiverType OBJECT-TYPE
			SYNTAX INTEGER
				{
				sfp(1),
				gbit(2),
				xfp(3),
				unknown(255)
				}
			MAX-ACCESS read-only
			STATUS current
			DESCRIPTION
				"The type of SFP transceiver."
			::= { sleEthernetPortEntry 21 }

		
		sleEthernetPortSfpTransceiverDetailType OBJECT-TYPE
			SYNTAX INTEGER
				{
				fiber1000Sx(1),
				fiber1000Lx(2),
				fiber1000Cx(3),
				fiber1000T(4),
				fiber100lLxLx10(5),
				fiber100Fx(6),
				fiberBx10(7),
				fiberPx(8),
				fiberOc3MmSr(9),
				fiberOc3SmIr(10),
				fiberOc3SmLr(11),
				fiber1000Zx(12),
				unknown(255)
				}
			MAX-ACCESS read-write
			STATUS current
			DESCRIPTION
				"The detailed-type of SFP transceiver."
			::= { sleEthernetPortEntry 22 }

		
		sleEthernetPortSlotIndex OBJECT-TYPE
			SYNTAX Integer32
			MAX-ACCESS read-only
			STATUS current
			DESCRIPTION
				"The slot index."
			::= { sleEthernetPortEntry 23 }

		
		sleEthernetPortSlotPortIndex OBJECT-TYPE
			SYNTAX Integer32
			MAX-ACCESS read-only
			STATUS current
			DESCRIPTION
				"The slot's port index."
			::= { sleEthernetPortEntry 24 }

		
		sleEthernetPortAdminTransmissionRate OBJECT-TYPE
			SYNTAX Integer32 (10 | 100 | 1000 | 10000)
			MAX-ACCESS read-only
			STATUS current
			DESCRIPTION
				"The speed of port. Unit is Mbit/s.
				This configurations are only useful for electrical interfaces.
				Optical - interfaces will always support 1000 MBIT/s"
			::= { sleEthernetPortEntry 25 }

		
		sleEthernetPortAdminDuplexMode OBJECT-TYPE
			SYNTAX INTEGER
				{
				full(1),
				half(2),
				notAvailable(255)
				}
			MAX-ACCESS read-only
			STATUS current
			DESCRIPTION
				"The duplex status of port."
			::= { sleEthernetPortEntry 26 }

		
		sleEthernetPortAdminFlowControl OBJECT-TYPE
			SYNTAX INTEGER
				{
				disabled(1),
				enableSend(2),
				enableReceive(3),
				enabledBoth(4)
				}
			MAX-ACCESS read-only
			STATUS current
			DESCRIPTION
				"The flow-control mode of port."
			::= { sleEthernetPortEntry 27 }

		
		sleEthernetPortAdminNegotiationMode OBJECT-TYPE
			SYNTAX INTEGER
				{
				auto(1),
				force(2),
				notAvailable(255)
				}
			MAX-ACCESS read-only
			STATUS current
			DESCRIPTION
				"The Auto Negotiation mode of port. "
			::= { sleEthernetPortEntry 28 }

		
		sleEthernetPortAdminReason OBJECT-TYPE
			SYNTAX INTEGER
				{
				none(0),
				user(1),
				xllcf(2),
				all(3)
				}
			MAX-ACCESS read-only
			STATUS current
			DESCRIPTION
				"The admin down reason of the interface. 
				user : by user-configuration 
				xllcf : by xllcf protocol 
				all : both user and xllcf 
				"
			::= { sleEthernetPortEntry 29 }

		
		sleEthernetPortLinkCheckTimer OBJECT-TYPE
			SYNTAX Integer32 (20..1000)
			MAX-ACCESS read-only
			STATUS current
			DESCRIPTION
				"The Link check internval of the interface "
			::= { sleEthernetPortEntry 30 }

		
		sleEthernetPortLinkDebounceTime OBJECT-TYPE
			SYNTAX Integer32 (0 | 10..5000)
			MAX-ACCESS read-only
			STATUS current
			DESCRIPTION
				"The  link debounce time of the interface"
			::= { sleEthernetPortEntry 31 }

		
		sleEthernetPortCpuStatisticsLimitUnicast OBJECT-TYPE
			SYNTAX Integer32 (0 | 10..100)
			MAX-ACCESS read-only
			STATUS current
			DESCRIPTION
				"The CPU statistics-limit Unicast Count
				( the standard unit : 1000,  10 = 1000 )
				"
			::= { sleEthernetPortEntry 32 }

		
		sleEthernetPortCpuStatisticsLimitMulticast OBJECT-TYPE
			SYNTAX Integer32 (0 | 10..100)
			MAX-ACCESS read-only
			STATUS current
			DESCRIPTION
				"et CPU statistics-limit Multicast Count
				( the standard unit : 1000,  10 = 1000 )
				"
			::= { sleEthernetPortEntry 33 }

		
		sleEthernetPortCpuStatisticsLimitBroadcast OBJECT-TYPE
			SYNTAX Integer32 (0 | 10..100)
			MAX-ACCESS read-only
			STATUS current
			DESCRIPTION
				"Set CPU statistics-limit Broadcast Count
				( the standard unit : 1000,  10 = 1000 )
				
				"
			::= { sleEthernetPortEntry 34 }

		
		sleEthernetPortFloodBlockBroadcastState OBJECT-TYPE
			SYNTAX INTEGER
				{
				disable(0),
				enable(1)
				}
			MAX-ACCESS read-only
			STATUS current
			DESCRIPTION
				"The Flood Block Broadcast State of the interface"
			::= { sleEthernetPortEntry 35 }

		
		sleEthernetPortFloodBlockDlfState OBJECT-TYPE
			SYNTAX INTEGER
				{
				disable(0),
				enable(1)
				}
			MAX-ACCESS read-only
			STATUS current
			DESCRIPTION
				"The Flood Block DLF State of the interface"
			::= { sleEthernetPortEntry 36 }

		
		sleEthernetPortControl OBJECT IDENTIFIER ::= { sleEthernetPort 2 }

		
		sleEthernetPortControlRequest OBJECT-TYPE
			SYNTAX INTEGER
				{
				setEthernetPortProfile(1),
				setEthernetPortLinkProfile(2),
				setEhternetPortCpuStatisticsLimitProfile(3),
				setEthernetPortFloodBlockStateProfile(4)
				}
			MAX-ACCESS read-write
			STATUS current
			DESCRIPTION
				"Description."
			::= { sleEthernetPortControl 1 }

		
		sleEthernetPortControlStatus OBJECT-TYPE
			SYNTAX SleControlStatusType
			MAX-ACCESS read-only
			STATUS current
			DESCRIPTION
				"Description."
			::= { sleEthernetPortControl 2 }

		
		sleEthernetPortControlTimer OBJECT-TYPE
			SYNTAX Gauge32
			MAX-ACCESS read-write
			STATUS current
			DESCRIPTION
				"Description."
			::= { sleEthernetPortControl 3 }

		
		sleEthernetPortControlTimeStamp OBJECT-TYPE
			SYNTAX TimeTicks
			MAX-ACCESS read-only
			STATUS current
			DESCRIPTION
				"Description."
			::= { sleEthernetPortControl 4 }

		
		sleEthernetPortControlReqResult OBJECT-TYPE
			SYNTAX SleControlRequestResultType
			MAX-ACCESS read-only
			STATUS current
			DESCRIPTION
				"Description."
			::= { sleEthernetPortControl 5 }

		
		sleEthernetPortControlIndex OBJECT-TYPE
			SYNTAX Integer32
			MAX-ACCESS read-write
			STATUS current
			DESCRIPTION
				"Description."
			::= { sleEthernetPortControl 6 }

		
		sleEthernetPortControlType OBJECT-TYPE
			SYNTAX INTEGER
				{
				unknown(0),
				electrical(1),
				optical(2)
				}
			MAX-ACCESS read-write
			STATUS current
			DESCRIPTION
				"Description."
			::= { sleEthernetPortControl 7 }

		
		sleEthernetPortControlAdminStatus OBJECT-TYPE
			SYNTAX INTEGER
				{
				up(1),
				down(2),
				notAvailable(3)
				}
			MAX-ACCESS read-write
			STATUS current
			DESCRIPTION
				"Description."
			::= { sleEthernetPortControl 8 }

		
		sleEthernetPortControlTransmissionRate OBJECT-TYPE
			SYNTAX Integer32 (10 | 100 | 1000 | 2500 | 10000)
			MAX-ACCESS read-write
			STATUS current
			DESCRIPTION
				"Description.The speed of port. Unit is Mbit/s.
				This configurations are only useful for electrical interfaces.
				Optical - interfaces will always support 1000 MBIT/s"
			::= { sleEthernetPortControl 9 }

		
		sleEthernetPortControlDuplexMode OBJECT-TYPE
			SYNTAX INTEGER
				{
				full(1),
				half(2),
				notAvailable(3)
				}
			MAX-ACCESS read-write
			STATUS current
			DESCRIPTION
				"Description."
			::= { sleEthernetPortControl 10 }

		
		sleEthernetPortControlFlowControl OBJECT-TYPE
			SYNTAX INTEGER
				{
				disabled(1),
				enabledSymetrical(2),
				enabledAsymetrical(3),
				enabledBoth(4),
				notAvailable(5)
				}
			MAX-ACCESS read-write
			STATUS current
			DESCRIPTION
				"Description."
			::= { sleEthernetPortControl 11 }

		
		sleEthernetPortControlNegotiationMode OBJECT-TYPE
			SYNTAX INTEGER
				{
				auto(1),
				force(2),
				notAvailable(3)
				}
			MAX-ACCESS read-write
			STATUS current
			DESCRIPTION
				"Description."
			::= { sleEthernetPortControl 12 }

		
		sleEthernetPortControlJumboFrameSize OBJECT-TYPE
			SYNTAX Integer32 (0 | 1518..12288)
			MAX-ACCESS read-write
			STATUS current
			DESCRIPTION
				"Description. If the value is zero, it means erasing the set-up value.
				"
			::= { sleEthernetPortControl 13 }

		
		sleEthernetPortControlPhysicalRemoteChassis OBJECT-TYPE
			SYNTAX OCTET STRING
			MAX-ACCESS read-write
			STATUS current
			DESCRIPTION
				"Description."
			::= { sleEthernetPortControl 14 }

		
		sleEthernetPortControlPhysicalRemoteSlot OBJECT-TYPE
			SYNTAX Integer32
			MAX-ACCESS read-write
			STATUS current
			DESCRIPTION
				"Description."
			::= { sleEthernetPortControl 15 }

		
		sleEthernetPortControlPhysicalRemotePort OBJECT-TYPE
			SYNTAX Integer32
			MAX-ACCESS read-write
			STATUS current
			DESCRIPTION
				"Description."
			::= { sleEthernetPortControl 16 }

		
		sleEthernetPortControlPhysicalLinkDiscoveryMode OBJECT-TYPE
			SYNTAX INTEGER
				{
				none(1),
				manual(2),
				automatic(3)
				}
			MAX-ACCESS read-write
			STATUS current
			DESCRIPTION
				"Description."
			::= { sleEthernetPortControl 17 }

		
		sleEthernetPortControlLinkCheckTimer OBJECT-TYPE
			SYNTAX Integer32 (20..1000)
			MAX-ACCESS read-write
			STATUS current
			DESCRIPTION
				"The Link check internval of the interface "
			::= { sleEthernetPortControl 18 }

		
		sleEthernetPortControlLinkDebounceTime OBJECT-TYPE
			SYNTAX Integer32 (0 | 10..5000)
			MAX-ACCESS read-write
			STATUS current
			DESCRIPTION
				"The  link debounce time of the interface"
			::= { sleEthernetPortControl 19 }

		
		sleEthernetPortControlCpuStatisticsLimitUnicast OBJECT-TYPE
			SYNTAX Integer32 (0 | 10..100)
			MAX-ACCESS read-write
			STATUS current
			DESCRIPTION
				"The CPU statistics-limit Unicast Count
				( the standard unit : 1000,  10 = 1000 )
				"
			::= { sleEthernetPortControl 20 }

		
		sleEthernetPortControlCpuStatisticsLimitMulticast OBJECT-TYPE
			SYNTAX Integer32 (0 | 10..100)
			MAX-ACCESS read-write
			STATUS current
			DESCRIPTION
				"et CPU statistics-limit Multicast Count
				( the standard unit : 1000,  10 = 1000 )
				"
			::= { sleEthernetPortControl 21 }

		
		sleEthernetPortControlCpuStatisticsLimitBroadcast OBJECT-TYPE
			SYNTAX Integer32 (0 | 10..100)
			MAX-ACCESS read-write
			STATUS current
			DESCRIPTION
				"Set CPU statistics-limit Broadcast Count
				( the standard unit : 1000,  10 = 1000 )
				"
			::= { sleEthernetPortControl 22 }

		
		sleEthernetPortControlFloodBlockBroadcastState OBJECT-TYPE
			SYNTAX INTEGER
				{
				disable(0),
				enable(1)
				}
			MAX-ACCESS read-write
			STATUS current
			DESCRIPTION
				"The Flood Block Broadcast State of the interface"
			::= { sleEthernetPortControl 23 }

		
		sleEthernetPortControlFloodBlockDlfState OBJECT-TYPE
			SYNTAX INTEGER
				{
				disable(0),
				enable(1)
				}
			MAX-ACCESS read-write
			STATUS current
			DESCRIPTION
				"The Flood Block DLF State of the interface"
			::= { sleEthernetPortControl 24 }

		
		sleEthernetPortNotification OBJECT IDENTIFIER ::= { sleEthernetPort 3 }

		
		sleEthernetPortChanged NOTIFICATION-TYPE
			OBJECTS { sleEthernetPortType, sleEthernetPortAdminStatus, sleEthernetPortTransmissionRate, sleEthernetPortDuplexMode, sleEthernetPortFlowControl, 
				sleEthernetPortNegotiationMode, sleEthernetPortJumboFrameSize, sleEthernetPortSfpVendorName, sleEthernetPortSfpVendorPartNumber, sleEthernetPortSfpVendorRevision, 
				sleEthernetPortSfpVendorSerialNumber, sleEthernetPortSfpDateCode, sleEthernetPortPhysicalRemoteChassis, sleEthernetPortPhysicalRemoteSlot, sleEthernetPortPhysicalRemotePort, 
				sleEthernetPortPhysicalLinkDiscoveryMode, sleEthernetPortControlRequest, sleEthernetPortControlTimeStamp, sleEthernetPortControlReqResult }
			STATUS current
			DESCRIPTION 
				"Description."
			::= { sleEthernetPortNotification 1 }

		
		sleEthernetPortLinkChanged NOTIFICATION-TYPE
			OBJECTS { sleEthernetPortControlRequest, sleEthernetPortControlTimeStamp, sleEthernetPortControlReqResult, sleEthernetPortControlIndex, sleEthernetPortControlLinkCheckTimer, 
				sleEthernetPortControlLinkDebounceTime }
			STATUS current
			DESCRIPTION 
				"setEthernetPortLinkProfile"
			::= { sleEthernetPortNotification 2 }

		
		sleEthernetPortCpuStatisticsLimitChanged NOTIFICATION-TYPE
			OBJECTS { sleEthernetPortControlRequest, sleEthernetPortControlTimeStamp, sleEthernetPortControlReqResult, sleEthernetPortControlIndex, sleEthernetPortControlCpuStatisticsLimitUnicast, 
				sleEthernetPortControlCpuStatisticsLimitMulticast, sleEthernetPortControlCpuStatisticsLimitBroadcast }
			STATUS current
			DESCRIPTION 
				"setEhternetPortCpuStatisticsLimitProfile"
			::= { sleEthernetPortNotification 3 }

		
		sleEthernetPortFloodBlockStateChanged NOTIFICATION-TYPE
			OBJECTS { sleEthernetPortControlRequest, sleEthernetPortControlTimeStamp, sleEthernetPortControlReqResult, sleEthernetPortControlIndex, sleEthernetPortControlFloodBlockBroadcastState, 
				sleEthernetPortControlFloodBlockDlfState }
			STATUS current
			DESCRIPTION 
				"setEthernetPortFloodBlockStateProfile"
			::= { sleEthernetPortNotification 4 }

		
		sleEthernetPortDMITable OBJECT-TYPE
			SYNTAX SEQUENCE OF SleEthernetPortDMIEntry
			MAX-ACCESS not-accessible
			STATUS current
			DESCRIPTION
				"Description."
			::= { sleEthernetPort 4 }

		
		sleEthernetPortDMIEntry OBJECT-TYPE
			SYNTAX SleEthernetPortDMIEntry
			MAX-ACCESS not-accessible
			STATUS current
			DESCRIPTION
				"Description."
			INDEX { sleEthernetPortDMIIndex }
			::= { sleEthernetPortDMITable 1 }

		
		SleEthernetPortDMIEntry ::=
			SEQUENCE { 
				sleEthernetPortDMIIndex
					INTEGER,
				sleEthernetPortDMITemper
					OCTET STRING,
				sleEthernetPortDMIVoltage
					OCTET STRING,
				sleEthernetPortDMITxBias
					OCTET STRING,
				sleEthernetPortDMITxPower
					OCTET STRING,
				sleEthernetPortDMIRxPower
					OCTET STRING
			 }

		sleEthernetPortDMIIndex OBJECT-TYPE
			SYNTAX INTEGER (1..255)
			MAX-ACCESS read-only
			STATUS current
			DESCRIPTION
				"Port Index."
			::= { sleEthernetPortDMIEntry 1 }

		
		sleEthernetPortDMITemper OBJECT-TYPE
			SYNTAX OCTET STRING
			MAX-ACCESS read-only
			STATUS current
			DESCRIPTION
				"Internally measured module temperature."
			::= { sleEthernetPortDMIEntry 2 }

		
		sleEthernetPortDMIVoltage OBJECT-TYPE
			SYNTAX OCTET STRING
			MAX-ACCESS read-only
			STATUS current
			DESCRIPTION
				"Internally measured supply voltage in transceiver."
			::= { sleEthernetPortDMIEntry 3 }

		
		sleEthernetPortDMITxBias OBJECT-TYPE
			SYNTAX OCTET STRING
			MAX-ACCESS read-only
			STATUS current
			DESCRIPTION
				"Internally measured TX Bias Current."
			::= { sleEthernetPortDMIEntry 4 }

		
		sleEthernetPortDMITxPower OBJECT-TYPE
			SYNTAX OCTET STRING
			MAX-ACCESS read-only
			STATUS current
			DESCRIPTION
				"Measured TX output power."
			::= { sleEthernetPortDMIEntry 5 }

		
		sleEthernetPortDMIRxPower OBJECT-TYPE
			SYNTAX OCTET STRING
			MAX-ACCESS read-only
			STATUS current
			DESCRIPTION
				"Measured RX input power."
			::= { sleEthernetPortDMIEntry 6 }

		
		sleEthernetSFPTable OBJECT-TYPE
			SYNTAX SEQUENCE OF SleEthernetSFPEntry
			MAX-ACCESS not-accessible
			STATUS current
			DESCRIPTION
				"Description."
			::= { sleEthernetPort 5 }

		
		sleEthernetSFPEntry OBJECT-TYPE
			SYNTAX SleEthernetSFPEntry
			MAX-ACCESS not-accessible
			STATUS current
			DESCRIPTION
				"Description."
			INDEX { sleEthernetSfpIndex }
			::= { sleEthernetSFPTable 1 }

		
		SleEthernetSFPEntry ::=
			SEQUENCE { 
				sleEthernetSfpIndex
					Integer32,
				sleEthernetSfpTransceiver
					INTEGER,
				sleEthernetSfpVendorName
					OCTET STRING,
				sleEthernetSfpVendorPartNumber
					OCTET STRING,
				sleEthernetSfpVendorRevision
					OCTET STRING,
				sleEthernetSfpVendorSerialNumber
					OCTET STRING,
				sleEthernetSfpDateCode
					OCTET STRING,
				sleEthernetSfpTransceiverType
					INTEGER,
				sleEthernetSfpTransceiverDetailType
					INTEGER,
				sleEthernetSfpTransceiverCodes
					OCTET STRING,
				sleEthernetSfpSpeed
					OCTET STRING,
				sleEthernetSfpLength
					Integer32,
				sleEthernetSfpWaveLength
					Integer32,
				sleEthernetSfpMultimodeLengthOm1
					Integer32,
				sleEthernetSfpMultimodeLengthOm2
					Integer32,
				sleEthernetSfpMultimodeLengthOm3
					Integer32,
				sleEthernetSfpTransceiverDetailTypeStr
					OCTET STRING,
				sleEthernetSfpTransceiverLengthStr
					OCTET STRING,
				sleEthernetSfpWaveLengthStr
					OCTET STRING,
				sleEthernetSfpConnectorType
					OCTET STRING,
				sleEthernetSfpDdmState
					INTEGER,
				sleEthernetSfpNegoState
					INTEGER
			 }

		sleEthernetSfpIndex OBJECT-TYPE
			SYNTAX Integer32 (1..65556)
			MAX-ACCESS read-only
			STATUS current
			DESCRIPTION
				"The SFP index."
			::= { sleEthernetSFPEntry 1 }

		
		sleEthernetSfpTransceiver OBJECT-TYPE
			SYNTAX INTEGER
				{
				unknown(0),
				electrical(1),
				electricalCoaxial(2),
				opticalLongHaul(3),
				opticalShortHaul(4),
				optical10G(5),
				opticalGpon(6)
				}
			MAX-ACCESS read-only
			STATUS current
			DESCRIPTION
				"The type of SFP"
			::= { sleEthernetSFPEntry 2 }

		
		sleEthernetSfpVendorName OBJECT-TYPE
			SYNTAX OCTET STRING
			MAX-ACCESS read-only
			STATUS current
			DESCRIPTION
				"The vendor name of SFP"
			::= { sleEthernetSFPEntry 3 }

		
		sleEthernetSfpVendorPartNumber OBJECT-TYPE
			SYNTAX OCTET STRING
			MAX-ACCESS read-only
			STATUS current
			DESCRIPTION
				"The part number of SFP"
			::= { sleEthernetSFPEntry 4 }

		
		sleEthernetSfpVendorRevision OBJECT-TYPE
			SYNTAX OCTET STRING
			MAX-ACCESS read-only
			STATUS current
			DESCRIPTION
				"The revision of SFP"
			::= { sleEthernetSFPEntry 5 }

		
		sleEthernetSfpVendorSerialNumber OBJECT-TYPE
			SYNTAX OCTET STRING
			MAX-ACCESS read-only
			STATUS current
			DESCRIPTION
				"The serial number of SFP"
			::= { sleEthernetSFPEntry 6 }

		
		sleEthernetSfpDateCode OBJECT-TYPE
			SYNTAX OCTET STRING
			MAX-ACCESS read-only
			STATUS current
			DESCRIPTION
				"The manufacturing date of SFP"
			::= { sleEthernetSFPEntry 7 }

		
		sleEthernetSfpTransceiverType OBJECT-TYPE
			SYNTAX INTEGER
				{
				sfp(1),
				gbic(2),
				xfp(3),
				unknown(255)
				}
			MAX-ACCESS read-only
			STATUS current
			DESCRIPTION
				"The type of SFP transceiver."
			::= { sleEthernetSFPEntry 8 }

		
		sleEthernetSfpTransceiverDetailType OBJECT-TYPE
			SYNTAX INTEGER
				{
				fiber1000Sx(1),
				fiber1000Lx(2),
				fiber1000Cx(3),
				fiber1000T(4),
				fiber100lLxLx10(5),
				fiber100Fx(6),
				fiberBx10(7),
				fiberPx(8),
				fiberOc3MmSr(9),
				fiberOc3SmIr(10),
				fiberOc3SmLr(11),
				fiber1000Zx(12),
				base10GSR(64),
				base10GLR(65),
				base10GER(66),
				base10GLRM(67),
				base10GSW(68),
				base10GLW(69),
				base10GEW(70),
				base10GEWorZW(71),
				unknown(255)
				}
			MAX-ACCESS read-write
			STATUS current
			DESCRIPTION
				"The detailed-type of SFP transceiver."
			::= { sleEthernetSFPEntry 9 }

		
		sleEthernetSfpTransceiverCodes OBJECT-TYPE
			SYNTAX OCTET STRING (SIZE (1..8))
			MAX-ACCESS read-only
			STATUS current
			DESCRIPTION
				"The transceiver codes.
				In case of SFP, reference SFP-8472 Rev 11.0
				  - Table 3.5: Transceiver codes (Address A0h)
				  - Table 3.5a: SONET Compliance Specifiers (A0h)
				In case of XFP, reference XFP Specification Revision 4.5 (August 31,2005)
				  - Table 40 Transceiver codes
				"
			::= { sleEthernetSFPEntry 10 }

		
		sleEthernetSfpSpeed OBJECT-TYPE
			SYNTAX OCTET STRING
			MAX-ACCESS read-only
			STATUS current
			DESCRIPTION
				"The speed of SFP"
			::= { sleEthernetSFPEntry 11 }

		
		sleEthernetSfpLength OBJECT-TYPE
			SYNTAX Integer32
			MAX-ACCESS read-only
			STATUS current
			DESCRIPTION
				"The length of SFP"
			::= { sleEthernetSFPEntry 12 }

		
		sleEthernetSfpWaveLength OBJECT-TYPE
			SYNTAX Integer32
			MAX-ACCESS read-only
			STATUS current
			DESCRIPTION
				"The wavelength of SFP"
			::= { sleEthernetSFPEntry 13 }

		
		sleEthernetSfpMultimodeLengthOm1 OBJECT-TYPE
			SYNTAX Integer32
			MAX-ACCESS read-only
			STATUS current
			DESCRIPTION
				"The Flame rating is 62.5um(OM1). This is used only for 10G SFP module with multi-mode.
				ref) 50/125 Multimode Fiber Optic 
				50/125 is one of the most commonly used multimode optical fiber, the other commonly used is 62.5/125 types. 
				There is a special kind 50/125 multimode fibers, which is called OM3 50/125. People usually refer 62.5/125 as the OM1 MMF, 
				common type 50/125 MMF as OM2, OM3 is also 50/125, but it is different from OM2 because it support 10Gig data transmission. 
				The OM3 50/125 fiber optic cable is also called laser optimized fiber cable. 
				Both OM1 and OM2 multimode cables use the orange color jacket (standard practice for commonly used indoor multimode), 
				OM3 use a special color, which is called Aqua."
			::= { sleEthernetSFPEntry 14 }

		
		sleEthernetSfpMultimodeLengthOm2 OBJECT-TYPE
			SYNTAX Integer32
			MAX-ACCESS read-only
			STATUS current
			DESCRIPTION
				"The Flame rating is 50um(OM2). This is used only for 10G SFP module with multi-mode.
				ref) 50/125 Multimode Fiber Optic 
				50/125 is one of the most commonly used multimode optical fiber, the other commonly used is 62.5/125 types. 
				There is a special kind 50/125 multimode fibers, which is called OM3 50/125. People usually refer 62.5/125 as the OM1 MMF, 
				common type 50/125 MMF as OM2, OM3 is also 50/125, but it is different from OM2 because it support 10Gig data transmission. 
				The OM3 50/125 fiber optic cable is also called laser optimized fiber cable. 
				Both OM1 and OM2 multimode cables use the orange color jacket (standard practice for commonly used indoor multimode), 
				OM3 use a special color, which is called Aqua."
			::= { sleEthernetSFPEntry 15 }

		
		sleEthernetSfpMultimodeLengthOm3 OBJECT-TYPE
			SYNTAX Integer32
			MAX-ACCESS read-only
			STATUS current
			DESCRIPTION
				"The Flame rating is 50um(OM3). This is used only for 10G SFP module with multi-mode.
				ref) 50/125 Multimode Fiber Optic 
				50/125 is one of the most commonly used multimode optical fiber, the other commonly used is 62.5/125 types. 
				There is a special kind 50/125 multimode fibers, which is called OM3 50/125. People usually refer 62.5/125 as the OM1 MMF, 
				common type 50/125 MMF as OM2, OM3 is also 50/125, but it is different from OM2 because it support 10Gig data transmission. 
				The OM3 50/125 fiber optic cable is also called laser optimized fiber cable. 
				Both OM1 and OM2 multimode cables use the orange color jacket (standard practice for commonly used indoor multimode), 
				OM3 use a special color, which is called Aqua."
			::= { sleEthernetSFPEntry 16 }

		
		sleEthernetSfpTransceiverDetailTypeStr OBJECT-TYPE
			SYNTAX OCTET STRING
			MAX-ACCESS read-only
			STATUS current
			DESCRIPTION
				"Description."
			::= { sleEthernetSFPEntry 17 }

		
		sleEthernetSfpTransceiverLengthStr OBJECT-TYPE
			SYNTAX OCTET STRING
			MAX-ACCESS read-only
			STATUS current
			DESCRIPTION
				"Description."
			::= { sleEthernetSFPEntry 18 }

		
		sleEthernetSfpWaveLengthStr OBJECT-TYPE
			SYNTAX OCTET STRING
			MAX-ACCESS read-only
			STATUS current
			DESCRIPTION
				"Description."
			::= { sleEthernetSFPEntry 19 }

		
		sleEthernetSfpConnectorType OBJECT-TYPE
			SYNTAX OCTET STRING
			MAX-ACCESS read-only
			STATUS current
			DESCRIPTION
				"Description."
			::= { sleEthernetSFPEntry 20 }

		
		sleEthernetSfpDdmState OBJECT-TYPE
			SYNTAX INTEGER
				{
				disable(0),
				enable(1)
				}
			MAX-ACCESS read-only
			STATUS current
			DESCRIPTION
				"The DDM state"
			::= { sleEthernetSFPEntry 21 }

		
		sleEthernetSfpNegoState OBJECT-TYPE
			SYNTAX INTEGER
				{
				off(0),
				on(1)
				}
			MAX-ACCESS read-only
			STATUS current
			DESCRIPTION
				"The Nego state"
			::= { sleEthernetSFPEntry 22 }

		
		sleEthernetSFPControl OBJECT IDENTIFIER ::= { sleEthernetPort 6 }

		
		sleEthernetSFPControlRequest OBJECT-TYPE
			SYNTAX INTEGER
				{
				setSFPRemoteReset(1),
				setSFPDdmState(2)
				}
			MAX-ACCESS read-write
			STATUS current
			DESCRIPTION
				"Description."
			::= { sleEthernetSFPControl 1 }

		
		sleEthernetSFPControlStatus OBJECT-TYPE
			SYNTAX SleControlStatusType
			MAX-ACCESS read-only
			STATUS current
			DESCRIPTION
				"Description."
			::= { sleEthernetSFPControl 2 }

		
		sleEthernetSFPControlTimer OBJECT-TYPE
			SYNTAX Gauge32
			MAX-ACCESS read-write
			STATUS current
			DESCRIPTION
				"Description."
			::= { sleEthernetSFPControl 3 }

		
		sleEthernetSFPControlTimeStamp OBJECT-TYPE
			SYNTAX TimeTicks
			MAX-ACCESS read-only
			STATUS current
			DESCRIPTION
				"Description."
			::= { sleEthernetSFPControl 4 }

		
		sleEthernetSFPControlReqResult OBJECT-TYPE
			SYNTAX SleControlRequestResultType
			MAX-ACCESS read-only
			STATUS current
			DESCRIPTION
				"Description."
			::= { sleEthernetSFPControl 5 }

		
		sleEthernetSFPControlIndex OBJECT-TYPE
			SYNTAX Integer32
			MAX-ACCESS read-write
			STATUS current
			DESCRIPTION
				"Description."
			::= { sleEthernetSFPControl 6 }

		
		sleEthernetSfpControlDdmState OBJECT-TYPE
			SYNTAX INTEGER
				{
				disable(0),
				enable(1)
				}
			MAX-ACCESS read-write
			STATUS current
			DESCRIPTION
				"Description."
			::= { sleEthernetSFPControl 7 }

		
		sleEthernetSFPNotification OBJECT IDENTIFIER ::= { sleEthernetPort 7 }

		
		sleEthernetSFPRemoteReset NOTIFICATION-TYPE
			OBJECTS { sleEthernetSFPControlRequest, sleEthernetSFPControlTimeStamp, sleEthernetSFPControlReqResult, sleEthernetSFPControlIndex }
			STATUS current
			DESCRIPTION 
				"setSFPRemoteReset"
			::= { sleEthernetSFPNotification 1 }

		
		sleEthernetSFPDdmState NOTIFICATION-TYPE
			OBJECTS { sleEthernetSFPControlRequest, sleEthernetSFPControlTimeStamp, sleEthernetSFPControlReqResult, sleEthernetSFPControlIndex, sleEthernetSfpControlDdmState
				 }
			STATUS current
			DESCRIPTION 
				"setSFPDdmState"
			::= { sleEthernetSFPNotification 2 }

		
		sleEthernetSFPThresholdTable OBJECT-TYPE
			SYNTAX SEQUENCE OF SleEthernetSFPThresholdEntry
			MAX-ACCESS not-accessible
			STATUS current
			DESCRIPTION
				"Description."
			::= { sleEthernetPort 8 }

		
		sleEthernetSFPThresholdEntry OBJECT-TYPE
			SYNTAX SleEthernetSFPThresholdEntry
			MAX-ACCESS not-accessible
			STATUS current
			DESCRIPTION
				"Description."
			INDEX { sleEthernetSFPThresholdIfIndex, sleEthernetSFPThresholdType }
			::= { sleEthernetSFPThresholdTable 1 }

		
		SleEthernetSFPThresholdEntry ::=
			SEQUENCE { 
				sleEthernetSFPThresholdIfIndex
					Integer32,
				sleEthernetSFPThresholdType
					INTEGER,
				sleEthernetSFPThresholdSfpLow
					OCTET STRING,
				sleEthernetSFPThresholdSfpHigh
					OCTET STRING,
				sleEthernetSFPThresholdSystemLow
					OCTET STRING,
				sleEthernetSFPThresholdSystemHigh
					OCTET STRING
			 }

		sleEthernetSFPThresholdIfIndex OBJECT-TYPE
			SYNTAX Integer32 (1..65535)
			MAX-ACCESS read-only
			STATUS current
			DESCRIPTION
				"The index of the interface"
			::= { sleEthernetSFPThresholdEntry 1 }

		
		sleEthernetSFPThresholdType OBJECT-TYPE
			SYNTAX INTEGER
				{
				temperWarning(1),
				temperAlarm(2),
				voltageWarning(3),
				voltageAlarm(4),
				txbiasWarning(5),
				txbiasAlarm(6),
				txpowerWarning(7),
				txpowerAlarm(8),
				rxpowerWarning(9),
				rxpowerAlarm(10)
				}
			MAX-ACCESS read-only
			STATUS current
			DESCRIPTION
				"The Type of Threshold"
			::= { sleEthernetSFPThresholdEntry 2 }

		
		sleEthernetSFPThresholdSfpLow OBJECT-TYPE
			SYNTAX OCTET STRING
			MAX-ACCESS read-only
			STATUS current
			DESCRIPTION
				"The Threshold Low Value of Sfp"
			::= { sleEthernetSFPThresholdEntry 3 }

		
		sleEthernetSFPThresholdSfpHigh OBJECT-TYPE
			SYNTAX OCTET STRING
			MAX-ACCESS read-only
			STATUS current
			DESCRIPTION
				"The Threshold High Value of Sfp"
			::= { sleEthernetSFPThresholdEntry 4 }

		
		sleEthernetSFPThresholdSystemLow OBJECT-TYPE
			SYNTAX OCTET STRING
			MAX-ACCESS read-only
			STATUS current
			DESCRIPTION
				"The Threshold Low Value of System"
			::= { sleEthernetSFPThresholdEntry 5 }

		
		sleEthernetSFPThresholdSystemHigh OBJECT-TYPE
			SYNTAX OCTET STRING
			MAX-ACCESS read-only
			STATUS current
			DESCRIPTION
				"The Threshold High Value of System"
			::= { sleEthernetSFPThresholdEntry 6 }

		
		sleEthernetSFPThresholdControl OBJECT IDENTIFIER ::= { sleEthernetPort 9 }

		
		sleEthernetSFPThresholdControlRequest OBJECT-TYPE
			SYNTAX INTEGER
				{
				setSfpThresholdModule(1),
				setSystemThresholdModule(2),
				delThresholdModule(3)
				}
			MAX-ACCESS read-write
			STATUS current
			DESCRIPTION
				"Description."
			::= { sleEthernetSFPThresholdControl 1 }

		
		sleEthernetSFPThresholdControlStatus OBJECT-TYPE
			SYNTAX SleControlStatusType
			MAX-ACCESS read-only
			STATUS current
			DESCRIPTION
				"Description."
			::= { sleEthernetSFPThresholdControl 2 }

		
		sleEthernetSFPThresholdControlTimer OBJECT-TYPE
			SYNTAX Gauge32
			MAX-ACCESS read-write
			STATUS current
			DESCRIPTION
				"Description."
			::= { sleEthernetSFPThresholdControl 3 }

		
		sleEthernetSFPThresholdControlTimeStamp OBJECT-TYPE
			SYNTAX TimeTicks
			MAX-ACCESS read-only
			STATUS current
			DESCRIPTION
				"Description."
			::= { sleEthernetSFPThresholdControl 4 }

		
		sleEthernetSFPThresholdControlReqResult OBJECT-TYPE
			SYNTAX SleControlRequestResultType
			MAX-ACCESS read-only
			STATUS current
			DESCRIPTION
				"Description."
			::= { sleEthernetSFPThresholdControl 5 }

		
		sleEthernetSFPThresholdControlIfIndex OBJECT-TYPE
			SYNTAX Integer32
			MAX-ACCESS read-write
			STATUS current
			DESCRIPTION
				"The index of the interface"
			::= { sleEthernetSFPThresholdControl 6 }

		
		sleEthernetSFPThresholdControlType OBJECT-TYPE
			SYNTAX INTEGER
				{
				temperWarning(1),
				temperAlarm(2),
				voltageWarning(3),
				voltageAlarm(4),
				txbiasWarning(5),
				txbiasAlarm(6),
				txpowerWarning(7),
				txpowerAlarm(8),
				rxpowerWarning(9),
				rxpowerAlarm(10)
				}
			MAX-ACCESS read-write
			STATUS current
			DESCRIPTION
				"The Type of Threshold"
			::= { sleEthernetSFPThresholdControl 7 }

		
		sleEthernetSFPThresholdControlSfpLow OBJECT-TYPE
			SYNTAX OCTET STRING
			MAX-ACCESS read-write
			STATUS current
			DESCRIPTION
				"The Threshold Low Value of Sfp"
			::= { sleEthernetSFPThresholdControl 8 }

		
		sleEthernetSFPThresholdControlSfpHigh OBJECT-TYPE
			SYNTAX OCTET STRING
			MAX-ACCESS read-write
			STATUS current
			DESCRIPTION
				"The Threshold High Value of Sfp"
			::= { sleEthernetSFPThresholdControl 9 }

		
		sleEthernetSFPThresholdControlSystemLow OBJECT-TYPE
			SYNTAX OCTET STRING
			MAX-ACCESS read-write
			STATUS current
			DESCRIPTION
				"The Threshold Low Value of System"
			::= { sleEthernetSFPThresholdControl 10 }

		
		sleEthernetSFPThresholdControlSystemHigh OBJECT-TYPE
			SYNTAX OCTET STRING
			MAX-ACCESS read-write
			STATUS current
			DESCRIPTION
				"The Threshold High Value of System"
			::= { sleEthernetSFPThresholdControl 11 }

		
		sleEthernetSFPThresholdNotification OBJECT IDENTIFIER ::= { sleEthernetPort 10 }

		
		sleEthernetSFPThresholdSfpChanged NOTIFICATION-TYPE
			OBJECTS { sleEthernetSFPThresholdControlRequest, sleEthernetSFPThresholdControlTimeStamp, sleEthernetSFPThresholdControlReqResult, sleEthernetSFPThresholdControlIfIndex, sleEthernetSFPThresholdControlType, 
				sleEthernetSFPThresholdControlSfpLow, sleEthernetSFPThresholdControlSfpHigh }
			STATUS current
			DESCRIPTION 
				"setSfpThresholdModule "
			::= { sleEthernetSFPThresholdNotification 1 }

		
		sleEthernetSFPThresholdSystemChanged NOTIFICATION-TYPE
			OBJECTS { sleEthernetSFPThresholdControlRequest, sleEthernetSFPThresholdControlTimeStamp, sleEthernetSFPThresholdControlReqResult, sleEthernetSFPThresholdControlIfIndex, sleEthernetSFPThresholdControlType, 
				sleEthernetSFPThresholdControlSystemLow, sleEthernetSFPThresholdControlSystemHigh }
			STATUS current
			DESCRIPTION 
				"setSystemThresholdModule "
			::= { sleEthernetSFPThresholdNotification 2 }

		
		sleEthernetSFPThresholdDestroyed NOTIFICATION-TYPE
			OBJECTS { sleEthernetSFPThresholdControlRequest, sleEthernetSFPThresholdControlTimeStamp, sleEthernetSFPThresholdControlReqResult, sleEthernetSFPThresholdControlIfIndex, sleEthernetSFPThresholdControlType
				 }
			STATUS current
			DESCRIPTION 
				"delThresholdModule "
			::= { sleEthernetSFPThresholdNotification 3 }

		
		slePower OBJECT IDENTIFIER ::= { sleDevice 3 }

		
		slePowerTable OBJECT-TYPE
			SYNTAX SEQUENCE OF SlePowerEntry
			MAX-ACCESS not-accessible
			STATUS current
			DESCRIPTION
				"Description."
			::= { slePower 1 }

		
		slePowerEntry OBJECT-TYPE
			SYNTAX SlePowerEntry
			MAX-ACCESS not-accessible
			STATUS current
			DESCRIPTION
				"Description."
			INDEX { slePowerIndex }
			::= { slePowerTable 1 }

		
		SlePowerEntry ::=
			SEQUENCE { 
				slePowerIndex
					INTEGER,
				slePowerPhyIndex
					Integer32,
				slePowerState
					INTEGER,
				slePowerType
					INTEGER,
				slePowerPSUType
					INTEGER
			 }

		slePowerIndex OBJECT-TYPE
			SYNTAX INTEGER (1..255)
			MAX-ACCESS read-only
			STATUS current
			DESCRIPTION
				"A unique value, greater than zero, for each module. It is recommended that values are assigned contiguously starting from 1. The value for each interface sub-layer must remain constant at least from one re-initialization of the entity's network management system to the next re-initialization."
			::= { slePowerEntry 1 }

		
		slePowerPhyIndex OBJECT-TYPE
			SYNTAX Integer32
			MAX-ACCESS read-only
			STATUS current
			DESCRIPTION
				"entPhysicalIndex of Power Modules (0: Internal, -1: uninstalled)"
			::= { slePowerEntry 2 }

		
		slePowerState OBJECT-TYPE
			SYNTAX INTEGER
				{
				failure(0),
				ok(1)
				}
			MAX-ACCESS read-only
			STATUS current
			DESCRIPTION
				"Power status information."
			::= { slePowerEntry 3 }

		
		slePowerType OBJECT-TYPE
			SYNTAX INTEGER
				{
				ac(1),
				dc(2),
				unknown(3),
				psu(4)
				}
			MAX-ACCESS read-only
			STATUS current
			DESCRIPTION
				"Power type information."
			::= { slePowerEntry 4 }

		
		slePowerPSUType OBJECT-TYPE
			SYNTAX INTEGER
				{
				psuA(1),
				psuS(2),
				unknown(255)
				}
			MAX-ACCESS read-only
			STATUS current
			DESCRIPTION
				"The type of Power Supply Unit.(DC)"
			::= { slePowerEntry 5 }

		
		sleFanModule OBJECT IDENTIFIER ::= { sleDevice 4 }

		
		sleFanModuleTable OBJECT-TYPE
			SYNTAX SEQUENCE OF SleFanModuleEntry
			MAX-ACCESS not-accessible
			STATUS current
			DESCRIPTION
				"Description."
			::= { sleFanModule 1 }

		
		sleFanModuleEntry OBJECT-TYPE
			SYNTAX SleFanModuleEntry
			MAX-ACCESS not-accessible
			STATUS current
			DESCRIPTION
				"Description."
			INDEX { sleFanModuleIndex }
			::= { sleFanModuleTable 1 }

		
		SleFanModuleEntry ::=
			SEQUENCE { 
				sleFanModuleIndex
					INTEGER,
				sleFanModulePhyIndex
					Integer32,
				sleFanModuleUnitNum
					Integer32,
				sleFanModuleAdminState
					INTEGER,
				sleFanModuleSpeedThreshold
					Integer32
			 }

		sleFanModuleIndex OBJECT-TYPE
			SYNTAX INTEGER (1..255)
			MAX-ACCESS read-only
			STATUS current
			DESCRIPTION
				"A unique value, greater than zero, for each module. It is recommended that values are assigned contiguously starting from 1."
			::= { sleFanModuleEntry 1 }

		
		sleFanModulePhyIndex OBJECT-TYPE
			SYNTAX Integer32
			MAX-ACCESS read-only
			STATUS current
			DESCRIPTION
				"entPhysicalIndex of FAN Modules. (0: Internal, -1: uninstalled)"
			::= { sleFanModuleEntry 2 }

		
		sleFanModuleUnitNum OBJECT-TYPE
			SYNTAX Integer32
			MAX-ACCESS read-only
			STATUS current
			DESCRIPTION
				"The number of unit in FAN module"
			::= { sleFanModuleEntry 3 }

		
		sleFanModuleAdminState OBJECT-TYPE
			SYNTAX INTEGER
				{
				off(0),
				on(1),
				auto(2)
				}
			MAX-ACCESS read-only
			STATUS current
			DESCRIPTION
				"An administrative state of FAN module"
			::= { sleFanModuleEntry 4 }

		
		sleFanModuleSpeedThreshold OBJECT-TYPE
			SYNTAX Integer32
			MAX-ACCESS read-only
			STATUS current
			DESCRIPTION
				"Fan-speed threshold"
			::= { sleFanModuleEntry 5 }

		
		sleFanModuleControl OBJECT IDENTIFIER ::= { sleFanModule 2 }

		
		sleFanModuleControlRequest OBJECT-TYPE
			SYNTAX INTEGER
				{
				setFanAdminState(1),
				setFanSpeedThreshold(2)
				}
			MAX-ACCESS read-write
			STATUS current
			DESCRIPTION
				"set an administrative state of FAN module"
			::= { sleFanModuleControl 1 }

		
		sleFanModuleControlStatus OBJECT-TYPE
			SYNTAX SleControlStatusType
			MAX-ACCESS read-only
			STATUS current
			DESCRIPTION
				"Description."
			::= { sleFanModuleControl 2 }

		
		sleFanModuleControlTimer OBJECT-TYPE
			SYNTAX Gauge32
			MAX-ACCESS read-write
			STATUS current
			DESCRIPTION
				"Description."
			::= { sleFanModuleControl 3 }

		
		sleFanModuleControlTimeStamp OBJECT-TYPE
			SYNTAX TimeTicks
			MAX-ACCESS read-only
			STATUS current
			DESCRIPTION
				"Description."
			::= { sleFanModuleControl 4 }

		
		sleFanModuleControlReqResult OBJECT-TYPE
			SYNTAX SleControlRequestResultType
			MAX-ACCESS read-only
			STATUS current
			DESCRIPTION
				"Description."
			::= { sleFanModuleControl 5 }

		
		sleFanModuleControlIndex OBJECT-TYPE
			SYNTAX Integer32
			MAX-ACCESS read-write
			STATUS current
			DESCRIPTION
				"Description."
			::= { sleFanModuleControl 6 }

		
		sleFanModuleControlAdminState OBJECT-TYPE
			SYNTAX INTEGER
				{
				off(0),
				on(1),
				auto(2)
				}
			MAX-ACCESS read-write
			STATUS current
			DESCRIPTION
				"An administrative state of FAN module"
			::= { sleFanModuleControl 7 }

		
		sleFanModuleControlSpeedThreshold OBJECT-TYPE
			SYNTAX Integer32
			MAX-ACCESS read-write
			STATUS current
			DESCRIPTION
				"Fan-speed threshold"
			::= { sleFanModuleControl 8 }

		
		sleFanModuleNotification OBJECT IDENTIFIER ::= { sleFanModule 3 }

		
		sleFanAdminStateChanged NOTIFICATION-TYPE
			OBJECTS { sleFanModuleAdminState, sleFanModuleControlRequest, sleFanModuleControlTimeStamp, sleFanModuleControlReqResult }
			STATUS current
			DESCRIPTION 
				"Description."
			::= { sleFanModuleNotification 1 }

		
		sleFanSpeedThresholdChanged NOTIFICATION-TYPE
			OBJECTS { sleFanModuleControlRequest, sleFanModuleControlTimeStamp, sleFanModuleControlReqResult, sleFanModuleControlIndex, sleFanModuleControlSpeedThreshold
				 }
			STATUS current
			DESCRIPTION 
				"Description."
			::= { sleFanModuleNotification 2 }

		
		sleFanUnit OBJECT IDENTIFIER ::= { sleDevice 5 }

		
		sleFanUnitTable OBJECT-TYPE
			SYNTAX SEQUENCE OF SleFanUnitEntry
			MAX-ACCESS not-accessible
			STATUS current
			DESCRIPTION
				"Description."
			::= { sleFanUnit 1 }

		
		sleFanUnitEntry OBJECT-TYPE
			SYNTAX SleFanUnitEntry
			MAX-ACCESS not-accessible
			STATUS current
			DESCRIPTION
				"Description."
			INDEX { sleFanModuleIndex, sleFanUnitIndex }
			::= { sleFanUnitTable 1 }

		
		SleFanUnitEntry ::=
			SEQUENCE { 
				sleFanUnitIndex
					INTEGER,
				sleFanUnitOperState
					INTEGER,
				sleFanUnitSpeed
					Integer32
			 }

		sleFanUnitIndex OBJECT-TYPE
			SYNTAX INTEGER (1..255)
			MAX-ACCESS read-only
			STATUS current
			DESCRIPTION
				"A unique number in FAN module"
			::= { sleFanUnitEntry 1 }

		
		sleFanUnitOperState OBJECT-TYPE
			SYNTAX INTEGER
				{
				failure(0),
				ok(1),
				stop(2)
				}
			MAX-ACCESS read-only
			STATUS current
			DESCRIPTION
				"An operational state of FAN unit"
			::= { sleFanUnitEntry 2 }

		
		sleFanUnitSpeed OBJECT-TYPE
			SYNTAX Integer32
			MAX-ACCESS read-only
			STATUS current
			DESCRIPTION
				"Speed of FAN unit"
			::= { sleFanUnitEntry 3 }

		
		sleTemperature OBJECT IDENTIFIER ::= { sleDevice 6 }

		
		sleTemperatureTable OBJECT-TYPE
			SYNTAX SEQUENCE OF SleTemperatureEntry
			MAX-ACCESS not-accessible
			STATUS current
			DESCRIPTION
				"Description."
			::= { sleTemperature 1 }

		
		sleTemperatureEntry OBJECT-TYPE
			SYNTAX SleTemperatureEntry
			MAX-ACCESS not-accessible
			STATUS current
			DESCRIPTION
				"Description."
			INDEX { sleTemperatureIndex }
			::= { sleTemperatureTable 1 }

		
		SleTemperatureEntry ::=
			SEQUENCE { 
				sleTemperatureIndex
					INTEGER,
				sleTemperatureState
					INTEGER,
				sleTemperatureValue
					Integer32,
				sleTemperatureHighThreshold
					Integer32,
				sleTemperatureLowThreshold
					Integer32,
				sleTemperatureWarnHighThreshold
					Integer32,
				sleTemperatureWarnLowThreshold
					Integer32,
				sleTemperatureWarnDuration
					Integer32,
				sleTemperatureAlarmHighThreshold
					Integer32,
				sleTemperatureAlarmLowThreshold
					Integer32,
				sleTemperatureAlarmDuration
					Integer32
			 }

		sleTemperatureIndex OBJECT-TYPE
			SYNTAX INTEGER (1..255)
			MAX-ACCESS read-only
			STATUS current
			DESCRIPTION
				"A unique value, greater than zero, for each module. It is recommended that values are assigned contiguously starting from 1."
			::= { sleTemperatureEntry 1 }

		
		sleTemperatureState OBJECT-TYPE
			SYNTAX INTEGER
				{
				failure(0),
				ok(1),
				others(2)
				}
			MAX-ACCESS read-only
			STATUS current
			DESCRIPTION
				"Temperature status information"
			::= { sleTemperatureEntry 2 }

		
		sleTemperatureValue OBJECT-TYPE
			SYNTAX Integer32
			MAX-ACCESS read-only
			STATUS current
			DESCRIPTION
				"The value of temperature sensor. (unit: C)"
			::= { sleTemperatureEntry 3 }

		
		sleTemperatureHighThreshold OBJECT-TYPE
			SYNTAX Integer32
			MAX-ACCESS read-only
			STATUS current
			DESCRIPTION
				"The High threshold of temperature."
			::= { sleTemperatureEntry 4 }

		
		sleTemperatureLowThreshold OBJECT-TYPE
			SYNTAX Integer32
			MAX-ACCESS read-only
			STATUS current
			DESCRIPTION
				"The Low threshold of temperature."
			::= { sleTemperatureEntry 5 }

		
		sleTemperatureWarnHighThreshold OBJECT-TYPE
			SYNTAX Integer32 (-40..100)
			MAX-ACCESS read-only
			STATUS current
			DESCRIPTION
				"The High threshold of temperature."
			::= { sleTemperatureEntry 6 }

		
		sleTemperatureWarnLowThreshold OBJECT-TYPE
			SYNTAX Integer32 (-40..100)
			MAX-ACCESS read-only
			STATUS current
			DESCRIPTION
				"The Low threshold of temperature."
			::= { sleTemperatureEntry 7 }

		
		sleTemperatureWarnDuration OBJECT-TYPE
			SYNTAX Integer32 (0..300)
			MAX-ACCESS read-only
			STATUS current
			DESCRIPTION
				"Duration-time units by the 5 sec.
				0: Clear threshold."
			::= { sleTemperatureEntry 8 }

		
		sleTemperatureAlarmHighThreshold OBJECT-TYPE
			SYNTAX Integer32 (-40..100)
			MAX-ACCESS read-only
			STATUS current
			DESCRIPTION
				"The High threshold of temperature."
			::= { sleTemperatureEntry 9 }

		
		sleTemperatureAlarmLowThreshold OBJECT-TYPE
			SYNTAX Integer32 (-40..100)
			MAX-ACCESS read-only
			STATUS current
			DESCRIPTION
				"The Low threshold of temperature."
			::= { sleTemperatureEntry 10 }

		
		sleTemperatureAlarmDuration OBJECT-TYPE
			SYNTAX Integer32 (0..300)
			MAX-ACCESS read-only
			STATUS current
			DESCRIPTION
				"Duration-time units by the 5 sec.
				0: Clear threshold."
			::= { sleTemperatureEntry 11 }

		
		sleTemperatureControl OBJECT IDENTIFIER ::= { sleTemperature 2 }

		
		sleTemperatureControlRequest OBJECT-TYPE
			SYNTAX INTEGER
				{
				setTempThreshold(1),
				setTempAlarmThreshold(2),
				setTempWarnThreshold(3)
				}
			MAX-ACCESS read-write
			STATUS current
			DESCRIPTION
				"set an administrative state of FAN module"
			::= { sleTemperatureControl 1 }

		
		sleTemperatureControlStatus OBJECT-TYPE
			SYNTAX SleControlStatusType
			MAX-ACCESS read-only
			STATUS current
			DESCRIPTION
				"Description."
			::= { sleTemperatureControl 2 }

		
		sleTemperatureControlTimer OBJECT-TYPE
			SYNTAX Gauge32
			MAX-ACCESS read-write
			STATUS current
			DESCRIPTION
				"Description."
			::= { sleTemperatureControl 3 }

		
		sleTemperatureControlTimeStamp OBJECT-TYPE
			SYNTAX TimeTicks
			MAX-ACCESS read-only
			STATUS current
			DESCRIPTION
				"Description."
			::= { sleTemperatureControl 4 }

		
		sleTemperatureControlReqResult OBJECT-TYPE
			SYNTAX SleControlRequestResultType
			MAX-ACCESS read-only
			STATUS current
			DESCRIPTION
				"Description."
			::= { sleTemperatureControl 5 }

		
		sleTemperatureControlIndex OBJECT-TYPE
			SYNTAX Integer32
			MAX-ACCESS read-write
			STATUS current
			DESCRIPTION
				"The Temperature index"
			::= { sleTemperatureControl 6 }

		
		sleTemperatureControlHighThreshold OBJECT-TYPE
			SYNTAX Integer32
			MAX-ACCESS read-write
			STATUS current
			DESCRIPTION
				"The High threshold of temperature."
			::= { sleTemperatureControl 7 }

		
		sleTemperatureControlLowThreshold OBJECT-TYPE
			SYNTAX Integer32
			MAX-ACCESS read-write
			STATUS current
			DESCRIPTION
				"The Low threshold of temperature."
			::= { sleTemperatureControl 8 }

		
		sleTemperatureControlDuration OBJECT-TYPE
			SYNTAX Integer32 (0..300)
			MAX-ACCESS read-write
			STATUS current
			DESCRIPTION
				"Duration-time units by the 5 sec.
				0: Clear threshold."
			::= { sleTemperatureControl 9 }

		
		sleTemperatureNotification OBJECT IDENTIFIER ::= { sleTemperature 3 }

		
		sleTemperatureThresholdChanged NOTIFICATION-TYPE
			OBJECTS { sleTemperatureControlRequest, sleTemperatureControlTimeStamp, sleTemperatureControlReqResult, sleTemperatureIndex, sleTemperatureWarnHighThreshold, 
				sleTemperatureWarnLowThreshold, sleTemperatureWarnDuration, sleTemperatureAlarmHighThreshold, sleTemperatureAlarmLowThreshold, sleTemperatureLowThreshold, 
				sleTemperatureAlarmDuration, sleTemperatureHighThreshold }
			STATUS current
			DESCRIPTION 
				"Description."
			::= { sleTemperatureNotification 1 }

		
		sleBattery OBJECT IDENTIFIER ::= { sleDevice 7 }

		
		sleBatteryTable OBJECT-TYPE
			SYNTAX SEQUENCE OF SleBatteryEntry
			MAX-ACCESS not-accessible
			STATUS current
			DESCRIPTION
				"Description."
			::= { sleBattery 1 }

		
		sleBatteryEntry OBJECT-TYPE
			SYNTAX SleBatteryEntry
			MAX-ACCESS not-accessible
			STATUS current
			DESCRIPTION
				"Description."
			INDEX { sleBatteryIndex }
			::= { sleBatteryTable 1 }

		
		SleBatteryEntry ::=
			SEQUENCE { 
				sleBatteryIndex
					INTEGER,
				sleOperationPowerType
					INTEGER,
				sleOperationPowerInfo
					OCTET STRING,
				slePSUACPowerState
					INTEGER,
				slePSUTemperture
					Integer32,
				slePSUTempThreshold
					Integer32,
				slePSUOutVoltage
					OCTET STRING,
				slePSUOverTemp
					INTEGER,
				slePSUFirmwareVer
					Integer32,
				sleRBUEquipState
					INTEGER,
				sleRBUModeStaus
					OCTET STRING,
				sleRBUTemperature1
					Integer32,
				sleRBUTemperature2
					Integer32,
				sleRBUTempLowThreshold
					Integer32,
				sleRBUOutVoltage
					OCTET STRING,
				sleRBUChargeCurrent
					Integer32,
				sleRBURemainCapacity
					Integer32,
				sleRBUOverTemp
					INTEGER,
				sleBatteryLow
					INTEGER,
				sleRBUTempHighThreshold
					Integer32,
				sleRBUBTStatus
					INTEGER,
				sleRBUBTThreshold
					Integer32,
				sleRBURechargeVoltage
					Integer32,
				sleBatteryCellStatus
					INTEGER,
				sleBPSUACHardwareVer
					Integer32
			 }

		sleBatteryIndex OBJECT-TYPE
			SYNTAX INTEGER (1..256)
			MAX-ACCESS read-only
			STATUS current
			DESCRIPTION
				"The index of battery charger."
			::= { sleBatteryEntry 1 }

		
		sleOperationPowerType OBJECT-TYPE
			SYNTAX INTEGER
				{
				ac(0),
				rbu(1)
				}
			MAX-ACCESS read-only
			STATUS current
			DESCRIPTION
				"Power Type."
			::= { sleBatteryEntry 2 }

		
		sleOperationPowerInfo OBJECT-TYPE
			SYNTAX OCTET STRING
			MAX-ACCESS read-only
			STATUS current
			DESCRIPTION
				"Operation Power Info."
			::= { sleBatteryEntry 3 }

		
		slePSUACPowerState OBJECT-TYPE
			SYNTAX INTEGER
				{
				ok(0),
				fault(1)
				}
			MAX-ACCESS read-only
			STATUS current
			DESCRIPTION
				"Power State."
			::= { sleBatteryEntry 4 }

		
		slePSUTemperture OBJECT-TYPE
			SYNTAX Integer32
			MAX-ACCESS read-only
			STATUS current
			DESCRIPTION
				"Temperture."
			::= { sleBatteryEntry 5 }

		
		slePSUTempThreshold OBJECT-TYPE
			SYNTAX Integer32
			MAX-ACCESS read-only
			STATUS current
			DESCRIPTION
				"Temperture Threshold."
			::= { sleBatteryEntry 6 }

		
		slePSUOutVoltage OBJECT-TYPE
			SYNTAX OCTET STRING
			MAX-ACCESS read-only
			STATUS current
			DESCRIPTION
				"Voltage."
			::= { sleBatteryEntry 7 }

		
		slePSUOverTemp OBJECT-TYPE
			SYNTAX INTEGER
				{
				normal(0),
				over(1)
				}
			MAX-ACCESS read-only
			STATUS current
			DESCRIPTION
				"Description."
			::= { sleBatteryEntry 8 }

		
		slePSUFirmwareVer OBJECT-TYPE
			SYNTAX Integer32
			MAX-ACCESS read-only
			STATUS current
			DESCRIPTION
				"The firmware version of battery charger for communication to system."
			::= { sleBatteryEntry 9 }

		
		sleRBUEquipState OBJECT-TYPE
			SYNTAX INTEGER
				{
				equipped(0),
				empty(1)
				}
			MAX-ACCESS read-only
			STATUS current
			DESCRIPTION
				"Equipment State."
			::= { sleBatteryEntry 10 }

		
		sleRBUModeStaus OBJECT-TYPE
			SYNTAX OCTET STRING
			MAX-ACCESS read-only
			STATUS current
			DESCRIPTION
				"Description."
			::= { sleBatteryEntry 11 }

		
		sleRBUTemperature1 OBJECT-TYPE
			SYNTAX Integer32
			MAX-ACCESS read-only
			STATUS current
			DESCRIPTION
				"Description."
			::= { sleBatteryEntry 12 }

		
		sleRBUTemperature2 OBJECT-TYPE
			SYNTAX Integer32
			MAX-ACCESS read-only
			STATUS current
			DESCRIPTION
				"."
			::= { sleBatteryEntry 13 }

		
		sleRBUTempLowThreshold OBJECT-TYPE
			SYNTAX Integer32
			MAX-ACCESS read-only
			STATUS current
			DESCRIPTION
				"RBU Low Temperature Threshold."
			::= { sleBatteryEntry 14 }

		
		sleRBUOutVoltage OBJECT-TYPE
			SYNTAX OCTET STRING
			MAX-ACCESS read-only
			STATUS current
			DESCRIPTION
				"RBU Out Voltage."
			::= { sleBatteryEntry 15 }

		
		sleRBUChargeCurrent OBJECT-TYPE
			SYNTAX Integer32
			MAX-ACCESS read-only
			STATUS current
			DESCRIPTION
				"Current Charge."
			::= { sleBatteryEntry 16 }

		
		sleRBURemainCapacity OBJECT-TYPE
			SYNTAX Integer32
			MAX-ACCESS read-only
			STATUS current
			DESCRIPTION
				"Remain Capacity."
			::= { sleBatteryEntry 17 }

		
		sleRBUOverTemp OBJECT-TYPE
			SYNTAX INTEGER
				{
				normal(0),
				over(1),
				under(2)
				}
			MAX-ACCESS read-only
			STATUS current
			DESCRIPTION
				"The  state of Temperature over."
			::= { sleBatteryEntry 18 }

		
		sleBatteryLow OBJECT-TYPE
			SYNTAX INTEGER
				{
				normal(0),
				low(1),
				notAvailable(2)
				}
			MAX-ACCESS read-only
			STATUS current
			DESCRIPTION
				"Battery state."
			::= { sleBatteryEntry 19 }

		
		sleRBUTempHighThreshold OBJECT-TYPE
			SYNTAX Integer32
			MAX-ACCESS read-only
			STATUS current
			DESCRIPTION
				"RBU High Temperature Threshold."
			::= { sleBatteryEntry 20 }

		
		sleRBUBTStatus OBJECT-TYPE
			SYNTAX INTEGER
				{
				enable(1),
				disable(2)
				}
			MAX-ACCESS read-only
			STATUS current
			DESCRIPTION
				"Description."
			::= { sleBatteryEntry 21 }

		
		sleRBUBTThreshold OBJECT-TYPE
			SYNTAX Integer32
			MAX-ACCESS read-only
			STATUS current
			DESCRIPTION
				"Description."
			::= { sleBatteryEntry 22 }

		
		sleRBURechargeVoltage OBJECT-TYPE
			SYNTAX Integer32
			MAX-ACCESS read-only
			STATUS current
			DESCRIPTION
				"Description."
			::= { sleBatteryEntry 23 }

		
		sleBatteryCellStatus OBJECT-TYPE
			SYNTAX INTEGER
				{
				ok(1),
				failure(2)
				}
			MAX-ACCESS read-only
			STATUS current
			DESCRIPTION
				"Description."
			::= { sleBatteryEntry 24 }

		
		sleBPSUACHardwareVer OBJECT-TYPE
			SYNTAX Integer32
			MAX-ACCESS read-only
			STATUS current
			DESCRIPTION
				"Description."
			::= { sleBatteryEntry 25 }

		
		sleBatteryControl OBJECT IDENTIFIER ::= { sleBattery 2 }

		
		sleBatteryControlRequest OBJECT-TYPE
			SYNTAX INTEGER
				{
				setBatteryForceCharge(1),
				setBatteryChargingStart(2),
				setBatteryForceChargeNonStop(3),
				setBatteryBootingTimeStatus(4),
				setBatteryBootingTime(5),
				setBatteryRechargeVoltage(6),
				setPsuAcTemperature(7),
				setBatteryTemperature(8)
				}
			MAX-ACCESS read-write
			STATUS current
			DESCRIPTION
				"Description."
			::= { sleBatteryControl 1 }

		
		sleBatteryControlStatus OBJECT-TYPE
			SYNTAX Integer32
			MAX-ACCESS read-write
			STATUS current
			DESCRIPTION
				"Description."
			::= { sleBatteryControl 2 }

		
		sleBatteryControlTimer OBJECT-TYPE
			SYNTAX Integer32
			MAX-ACCESS read-write
			STATUS current
			DESCRIPTION
				"Description."
			::= { sleBatteryControl 3 }

		
		sleBatteryControlTimeStamp OBJECT-TYPE
			SYNTAX Integer32
			MAX-ACCESS read-write
			STATUS current
			DESCRIPTION
				"Description."
			::= { sleBatteryControl 4 }

		
		sleBatteryControlReqResult OBJECT-TYPE
			SYNTAX Integer32
			MAX-ACCESS read-write
			STATUS current
			DESCRIPTION
				"Description."
			::= { sleBatteryControl 5 }

		
		sleBatteryControlRBUBTStatus OBJECT-TYPE
			SYNTAX INTEGER
				{
				enable(1),
				disable(2)
				}
			MAX-ACCESS read-write
			STATUS current
			DESCRIPTION
				"Description."
			::= { sleBatteryControl 6 }

		
		sleBatteryControlRBUBTThreshold OBJECT-TYPE
			SYNTAX Integer32
			MAX-ACCESS read-write
			STATUS current
			DESCRIPTION
				"Description."
			::= { sleBatteryControl 7 }

		
		sleBatteryControlRBURechargeVoltage OBJECT-TYPE
			SYNTAX Integer32
			MAX-ACCESS read-write
			STATUS current
			DESCRIPTION
				"Description."
			::= { sleBatteryControl 8 }

		
		sleBatteryControlTemperThresh1 OBJECT-TYPE
			SYNTAX Integer32
			MAX-ACCESS read-write
			STATUS current
			DESCRIPTION
				"Description."
			::= { sleBatteryControl 9 }

		
		sleBatteryControlTemperThresh2 OBJECT-TYPE
			SYNTAX Integer32
			MAX-ACCESS read-write
			STATUS current
			DESCRIPTION
				"Description."
			::= { sleBatteryControl 10 }

		
		sleBatteryNotification OBJECT IDENTIFIER ::= { sleBattery 3 }

		
		sleBatteryForceChargeChanged NOTIFICATION-TYPE
			OBJECTS { sleBatteryControlRequest, sleBatteryControlTimeStamp, sleBatteryControlReqResult }
			STATUS current
			DESCRIPTION 
				"Description."
			::= { sleBatteryNotification 1 }

		
		sleBatteryChargingStartChanged NOTIFICATION-TYPE
			OBJECTS { sleBatteryControlRequest, sleBatteryControlTimeStamp, sleBatteryControlReqResult }
			STATUS current
			DESCRIPTION 
				"Description."
			::= { sleBatteryNotification 2 }

		
		sleBatteryForceChargeNonStopChanged NOTIFICATION-TYPE
			OBJECTS { sleBatteryControlRequest, sleBatteryControlTimeStamp, sleBatteryControlReqResult }
			STATUS current
			DESCRIPTION 
				"Description."
			::= { sleBatteryNotification 3 }

		
		sleBatteryRBUBTStatusChanged NOTIFICATION-TYPE
			OBJECTS { sleBatteryControlRequest, sleBatteryControlTimeStamp, sleBatteryControlReqResult, sleRBUBTStatus }
			STATUS current
			DESCRIPTION 
				"Description."
			::= { sleBatteryNotification 4 }

		
		sleBatteryRBUBTThresholdChanged NOTIFICATION-TYPE
			OBJECTS { sleBatteryControlRequest, sleBatteryControlTimeStamp, sleBatteryControlReqResult, sleRBUBTThreshold }
			STATUS current
			DESCRIPTION 
				"Description."
			::= { sleBatteryNotification 5 }

		
		sleBatteryRBURechargeVoltageChanged NOTIFICATION-TYPE
			OBJECTS { sleBatteryControlRequest, sleBatteryControlTimeStamp, sleBatteryControlReqResult, sleRBURechargeVoltage }
			STATUS current
			DESCRIPTION 
				"Description."
			::= { sleBatteryNotification 6 }

		
		sleBatteryPsuAcTemperThreshChanged NOTIFICATION-TYPE
			OBJECTS { sleBatteryControlRequest, sleBatteryControlTimeStamp, sleBatteryControlReqResult, slePSUTempThreshold }
			STATUS current
			DESCRIPTION 
				"Description."
			::= { sleBatteryNotification 7 }

		
		sleBatteryRBUTemperThreshChanged NOTIFICATION-TYPE
			OBJECTS { sleBatteryControlRequest, sleBatteryControlTimeStamp, sleBatteryControlReqResult, sleRBUTempLowThreshold, sleRBUTempHighThreshold
				 }
			STATUS current
			DESCRIPTION 
				"Description."
			::= { sleBatteryNotification 8 }

		
		sleBatteryBackupTable OBJECT-TYPE
			SYNTAX SEQUENCE OF SleBatteryBackupEntry
			MAX-ACCESS not-accessible
			STATUS current
			DESCRIPTION
				"Description."
			::= { sleBattery 4 }

		
		sleBatteryBackupEntry OBJECT-TYPE
			SYNTAX SleBatteryBackupEntry
			MAX-ACCESS not-accessible
			STATUS current
			DESCRIPTION
				"Description."
			INDEX { sleBatteryBackupFile }
			::= { sleBatteryBackupTable 1 }

		
		SleBatteryBackupEntry ::=
			SEQUENCE { 
				sleBatteryBackupFile
					OCTET STRING
			 }

		sleBatteryBackupFile OBJECT-TYPE
			SYNTAX OCTET STRING (SIZE (1..64))
			MAX-ACCESS read-only
			STATUS current
			DESCRIPTION
				"Description."
			::= { sleBatteryBackupEntry 1 }

		
		sleBatteryBackupControl OBJECT IDENTIFIER ::= { sleBattery 5 }

		
		sleBatteryBackupControlRequest OBJECT-TYPE
			SYNTAX INTEGER
				{
				setBatteryBackupProfile(1),
				setBatteryUpgrade(2),
				clearBatteryBackupTable(3)
				}
			MAX-ACCESS read-write
			STATUS current
			DESCRIPTION
				"Description."
			::= { sleBatteryBackupControl 1 }

		
		sleBatteryBackupControlStatus OBJECT-TYPE
			SYNTAX SleControlStatusType
			MAX-ACCESS read-only
			STATUS current
			DESCRIPTION
				"Description."
			::= { sleBatteryBackupControl 2 }

		
		sleBatteryBackupControlTimer OBJECT-TYPE
			SYNTAX Gauge32
			MAX-ACCESS read-write
			STATUS current
			DESCRIPTION
				"Description."
			::= { sleBatteryBackupControl 3 }

		
		sleBatteryBackupControlTimeStamp OBJECT-TYPE
			SYNTAX TimeTicks
			MAX-ACCESS read-only
			STATUS current
			DESCRIPTION
				"Description."
			::= { sleBatteryBackupControl 4 }

		
		sleBatteryBackupControlReqResult OBJECT-TYPE
			SYNTAX SleControlRequestResultType
			MAX-ACCESS read-only
			STATUS current
			DESCRIPTION
				"Description."
			::= { sleBatteryBackupControl 5 }

		
		sleBatteryBackupControlServerIP OBJECT-TYPE
			SYNTAX IpAddress
			MAX-ACCESS read-write
			STATUS current
			DESCRIPTION
				"Description."
			::= { sleBatteryBackupControl 6 }

		
		sleBatteryBackupControlUserID OBJECT-TYPE
			SYNTAX OCTET STRING (SIZE (1..64))
			MAX-ACCESS read-write
			STATUS current
			DESCRIPTION
				"Description."
			::= { sleBatteryBackupControl 7 }

		
		sleBatteryBackupControlPassword OBJECT-TYPE
			SYNTAX OCTET STRING (SIZE (1..64))
			MAX-ACCESS read-write
			STATUS current
			DESCRIPTION
				"Description."
			::= { sleBatteryBackupControl 8 }

		
		sleBatteryBackupControlFlag OBJECT-TYPE
			SYNTAX INTEGER
				{
				download(1),
				upload(2)
				}
			MAX-ACCESS read-write
			STATUS current
			DESCRIPTION
				"Description."
			::= { sleBatteryBackupControl 9 }

		
		sleBatteryBackupControlLocalFile OBJECT-TYPE
			SYNTAX OCTET STRING (SIZE (1..64))
			MAX-ACCESS read-write
			STATUS current
			DESCRIPTION
				"Description."
			::= { sleBatteryBackupControl 10 }

		
		sleBatteryBackupControlRemoteFile OBJECT-TYPE
			SYNTAX OCTET STRING (SIZE (1..64))
			MAX-ACCESS read-write
			STATUS current
			DESCRIPTION
				"Description."
			::= { sleBatteryBackupControl 11 }

		
		sleBatterBackupNotification OBJECT IDENTIFIER ::= { sleBattery 6 }

		
		sleBatteryBackupProfileChanged NOTIFICATION-TYPE
			OBJECTS { sleBatteryBackupControlRequest, sleBatteryBackupControlTimeStamp, sleBatteryBackupControlReqResult, sleBatteryBackupControlServerIP, sleBatteryBackupControlUserID, 
				sleBatteryBackupControlPassword, sleBatteryBackupControlFlag, sleBatteryBackupControlLocalFile, sleBatteryBackupControlRemoteFile }
			STATUS current
			DESCRIPTION 
				"Description."
			::= { sleBatterBackupNotification 1 }

		
		sleBatteryBackupUpgraded NOTIFICATION-TYPE
			OBJECTS { sleBatteryBackupControlRequest, sleBatteryBackupControlTimeStamp, sleBatteryBackupControlReqResult, sleBatteryBackupControlLocalFile }
			STATUS current
			DESCRIPTION 
				"Description."
			::= { sleBatterBackupNotification 2 }

		
		sleBatteryBackupTableCleared NOTIFICATION-TYPE
			OBJECTS { sleBatteryBackupControlRequest, sleBatteryBackupControlTimeStamp, sleBatteryBackupControlReqResult, sleBatteryBackupControlLocalFile }
			STATUS current
			DESCRIPTION 
				"Description."
			::= { sleBatterBackupNotification 3 }

		
		sleDoor OBJECT IDENTIFIER ::= { sleDevice 8 }

		
		sleDoorInfo OBJECT IDENTIFIER ::= { sleDoor 1 }

		
		sleDoorStatus OBJECT-TYPE
			SYNTAX INTEGER
				{
				close(0),
				open(1)
				}
			MAX-ACCESS read-only
			STATUS current
			DESCRIPTION
				"Description."
			::= { sleDoorInfo 1 }

		
		sleCpu OBJECT IDENTIFIER ::= { sleDevice 9 }

		
		sleCpuInfo OBJECT IDENTIFIER ::= { sleCpu 1 }

		
		sleCpuProcessor OBJECT-TYPE
			SYNTAX OCTET STRING
			MAX-ACCESS read-only
			STATUS current
			DESCRIPTION
				"Description."
			::= { sleCpuInfo 1 }

		
		sleCpuModel OBJECT-TYPE
			SYNTAX OCTET STRING
			MAX-ACCESS read-only
			STATUS current
			DESCRIPTION
				"Description."
			::= { sleCpuInfo 2 }

		
		sleCpuRevision OBJECT-TYPE
			SYNTAX OCTET STRING
			MAX-ACCESS read-only
			STATUS current
			DESCRIPTION
				"Description."
			::= { sleCpuInfo 3 }

		
		sleCpuBogomips OBJECT-TYPE
			SYNTAX OCTET STRING
			MAX-ACCESS read-only
			STATUS current
			DESCRIPTION
				"Description."
			::= { sleCpuInfo 4 }

		
		sleCpuManufacturer OBJECT-TYPE
			SYNTAX OCTET STRING
			MAX-ACCESS read-only
			STATUS current
			DESCRIPTION
				"Description."
			::= { sleCpuInfo 5 }

		
		sleCpuClock OBJECT-TYPE
			SYNTAX Integer32
			MAX-ACCESS read-only
			STATUS current
			DESCRIPTION
				"Description."
			::= { sleCpuInfo 6 }

		
		sleCpuBusClock OBJECT-TYPE
			SYNTAX Integer32
			MAX-ACCESS read-only
			STATUS current
			DESCRIPTION
				"Description."
			::= { sleCpuInfo 7 }

		
		sleClockModule OBJECT IDENTIFIER ::= { sleDevice 10 }

		
		sleClockModuleTable OBJECT-TYPE
			SYNTAX SEQUENCE OF SleClockModuleEntry
			MAX-ACCESS not-accessible
			STATUS current
			DESCRIPTION
				"Description."
			::= { sleClockModule 1 }

		
		sleClockModuleEntry OBJECT-TYPE
			SYNTAX SleClockModuleEntry
			MAX-ACCESS not-accessible
			STATUS current
			DESCRIPTION
				"Description."
			INDEX { sleClockModuleIndex }
			::= { sleClockModuleTable 1 }

		
		SleClockModuleEntry ::=
			SEQUENCE { 
				sleClockModuleIndex
					INTEGER,
				sleClockModuleBoardId
					INTEGER,
				sleClockModuleInstallStatus
					INTEGER,
				sleClockModuleInitStatus
					INTEGER,
				sleClockModuleOPMode
					INTEGER
			 }

		sleClockModuleIndex OBJECT-TYPE
			SYNTAX INTEGER (1..255)
			MAX-ACCESS read-only
			STATUS current
			DESCRIPTION
				"A unique value, greater than zero, for each module. It is recommended that values are assigned contiguously starting from 1."
			::= { sleClockModuleEntry 1 }

		
		sleClockModuleBoardId OBJECT-TYPE
			SYNTAX INTEGER
				{
				sfuA(1),
				sfuB(2)
				}
			MAX-ACCESS read-only
			STATUS current
			DESCRIPTION
				"Indication of the board identifier."
			::= { sleClockModuleEntry 2 }

		
		sleClockModuleInstallStatus OBJECT-TYPE
			SYNTAX INTEGER
				{
				removed(0),
				installed(1)
				}
			MAX-ACCESS read-only
			STATUS current
			DESCRIPTION
				"The install status of clock module."
			::= { sleClockModuleEntry 3 }

		
		sleClockModuleInitStatus OBJECT-TYPE
			SYNTAX INTEGER
				{
				failure(0),
				ok(1)
				}
			MAX-ACCESS read-only
			STATUS current
			DESCRIPTION
				"The initialization status of clock module."
			::= { sleClockModuleEntry 4 }

		
		sleClockModuleOPMode OBJECT-TYPE
			SYNTAX INTEGER
				{
				freerun(1),
				holdover(2),
				locked(3),
				prelocked2(4),
				prelocked(5),
				lostphase(6),
				unknown(255)
				}
			MAX-ACCESS read-write
			STATUS current
			DESCRIPTION
				"The CM operating mode"
			::= { sleClockModuleEntry 5 }

		
		sleClockInfo OBJECT IDENTIFIER ::= { sleClockModule 2 }

		
		sleClockInfoInSrcType OBJECT-TYPE
			SYNTAX INTEGER
				{
				ntt(1),
				ntt2(2),
				e1(3),
				t1(4),
				unknown(255)
				}
			MAX-ACCESS accessible-for-notify
			STATUS current
			DESCRIPTION
				"The clock input source type."
			::= { sleClockInfo 1 }

		
		sleClockInfoInSrcStatus OBJECT-TYPE
			SYNTAX INTEGER
				{
				true(1),
				false(2)
				}
			MAX-ACCESS accessible-for-notify
			STATUS current
			DESCRIPTION
				"The input source is Valid or Invalid."
			::= { sleClockInfo 2 }

		
		sleClockInfoInSrcAISStatus OBJECT-TYPE
			SYNTAX INTEGER
				{
				true(1),
				false(2)
				}
			MAX-ACCESS accessible-for-notify
			STATUS current
			DESCRIPTION
				"The AIS is detected or not detected."
			::= { sleClockInfo 3 }

		
		sleClockInfoInSrcLoSStatus OBJECT-TYPE
			SYNTAX INTEGER
				{
				true(1),
				false(2)
				}
			MAX-ACCESS accessible-for-notify
			STATUS current
			DESCRIPTION
				"The LoS is detected or not detected"
			::= { sleClockInfo 4 }

		
		sleClockInfoInSrcLDSCStatus OBJECT-TYPE
			SYNTAX INTEGER
				{
				true(1),
				false(2)
				}
			MAX-ACCESS accessible-for-notify
			STATUS current
			DESCRIPTION
				"The Line Driver Short Circuit is detected or not detected"
			::= { sleClockInfo 5 }

		
		sleClockInfoInSrcNtrClockType OBJECT-TYPE
			SYNTAX BITS
				{
				bit64Khz(0),
				bit8Khz(1),
				bit04Khz(2)
				}
			MAX-ACCESS accessible-for-notify
			STATUS current
			DESCRIPTION
				"The ntr clock is changed."
			::= { sleClockInfo 6 }

		
		sleSlot OBJECT IDENTIFIER ::= { sleDevice 11 }

		
		sleSlotSystemInfo OBJECT IDENTIFIER ::= { sleSlot 1 }

		
		sleSlotSystemInfoTable OBJECT-TYPE
			SYNTAX SEQUENCE OF SleSlotSystemInfoEntry
			MAX-ACCESS not-accessible
			STATUS current
			DESCRIPTION
				"Description."
			::= { sleSlotSystemInfo 1 }

		
		sleSlotSystemInfoEntry OBJECT-TYPE
			SYNTAX SleSlotSystemInfoEntry
			MAX-ACCESS not-accessible
			STATUS current
			DESCRIPTION
				"Description."
			INDEX { sleSlotSystemIndex }
			::= { sleSlotSystemInfoTable 1 }

		
		SleSlotSystemInfoEntry ::=
			SEQUENCE { 
				sleSlotSystemIndex
					Integer32,
				sleSlotSystemUptime
					TimeTicks,
				sleSlotSystemModelName
					OCTET STRING,
				sleSlotSystemSerialNumber
					OCTET STRING,
				sleSlotSystemHWVersion
					OCTET STRING,
				sleSlotSystemBLVersion
					OCTET STRING,
				sleSlotSystemSWCompatibility
					OCTET STRING,
				sleSlotSystemOSVersion
					OCTET STRING,
				sleSlotSystemMacAddress
					OCTET STRING,
				sleSlotSystemCPULoadAll
					OCTET STRING,
				sleSlotSystemCPULoadInterrupt
					OCTET STRING,
				sleSlotSystemMemoryTotal
					Gauge32,
				sleSlotSystemMemoryFree
					Gauge32,
				sleSlotSystemMemoryShared
					Gauge32,
				sleSlotSystemMemoryBuffers
					Gauge32,
				sleSlotSystemMemoryCached
					Gauge32,
				sleSlotSystemMemorySwapTotal
					Gauge32,
				sleSlotSystemMemorySwapFree
					Gauge32,
				sleSlotSystemBootReason
					INTEGER,
				sleSlotSystemBootTime
					Gauge32,
				sleSlotSystemVoltage
					Gauge32,
				sleSlotSystemPowerLevelStatus
					INTEGER,
				sleSlotSystemInfoLEDStatus
					BITS,
				sleSlotSystemInfoPackageVersion
					OCTET STRING,
				sleSlotSystemInfoManufacturer
					OCTET STRING,
				sleSlotSystemInfoManufactureDate
					OCTET STRING,
				sleSlotSystemCPULoadHighThreshold
					Integer32,
				sleSlotSystemCPULoadHighThresholdTimer
					INTEGER,
				sleSlotSystemCPULoadLowThreshold
					Integer32,
				sleSlotSystemCPULoadLowThresholdTimer
					INTEGER,
				sleSlotSystemCPULoadCurrent
					Integer32,
				sleSlotSystemCPUOverallStatus
					INTEGER,
				sleSlotSystemTemperOverallStatus
					INTEGER
			 }

		sleSlotSystemIndex OBJECT-TYPE
			SYNTAX Integer32 (1..8)
			MAX-ACCESS read-only
			STATUS current
			DESCRIPTION
				"The system slot index."
			::= { sleSlotSystemInfoEntry 1 }

		
		sleSlotSystemUptime OBJECT-TYPE
			SYNTAX TimeTicks
			MAX-ACCESS read-only
			STATUS current
			DESCRIPTION
				"The time since the network management portion of the system was last re-initialized."
			::= { sleSlotSystemInfoEntry 2 }

		
		sleSlotSystemModelName OBJECT-TYPE
			SYNTAX OCTET STRING
			MAX-ACCESS read-only
			STATUS current
			DESCRIPTION
				"The model name."
			::= { sleSlotSystemInfoEntry 3 }

		
		sleSlotSystemSerialNumber OBJECT-TYPE
			SYNTAX OCTET STRING
			MAX-ACCESS read-only
			STATUS current
			DESCRIPTION
				"The serial number "
			::= { sleSlotSystemInfoEntry 4 }

		
		sleSlotSystemHWVersion OBJECT-TYPE
			SYNTAX OCTET STRING
			MAX-ACCESS read-only
			STATUS current
			DESCRIPTION
				"The H/W version."
			::= { sleSlotSystemInfoEntry 5 }

		
		sleSlotSystemBLVersion OBJECT-TYPE
			SYNTAX OCTET STRING
			MAX-ACCESS read-only
			STATUS current
			DESCRIPTION
				"The boot loader’s S/W version."
			::= { sleSlotSystemInfoEntry 6 }

		
		sleSlotSystemSWCompatibility OBJECT-TYPE
			SYNTAX OCTET STRING
			MAX-ACCESS read-only
			STATUS current
			DESCRIPTION
				"The system compatibility."
			::= { sleSlotSystemInfoEntry 7 }

		
		sleSlotSystemOSVersion OBJECT-TYPE
			SYNTAX OCTET STRING
			MAX-ACCESS read-only
			STATUS current
			DESCRIPTION
				"The version information of current os."
			::= { sleSlotSystemInfoEntry 8 }

		
		sleSlotSystemMacAddress OBJECT-TYPE
			SYNTAX OCTET STRING
			MAX-ACCESS read-only
			STATUS current
			DESCRIPTION
				"The system’s MAC address."
			::= { sleSlotSystemInfoEntry 9 }

		
		sleSlotSystemCPULoadAll OBJECT-TYPE
			SYNTAX OCTET STRING
			MAX-ACCESS read-only
			STATUS current
			DESCRIPTION
				"The CPU all load for 5/60/600 second. (unit: 0.01%)"
			::= { sleSlotSystemInfoEntry 10 }

		
		sleSlotSystemCPULoadInterrupt OBJECT-TYPE
			SYNTAX OCTET STRING
			MAX-ACCESS read-only
			STATUS current
			DESCRIPTION
				"The CPU interrupt load for 5/60/600 second. (unit: 0.01%)"
			::= { sleSlotSystemInfoEntry 11 }

		
		sleSlotSystemMemoryTotal OBJECT-TYPE
			SYNTAX Gauge32
			MAX-ACCESS read-only
			STATUS current
			DESCRIPTION
				"The total memory size (unit: kb)"
			::= { sleSlotSystemInfoEntry 12 }

		
		sleSlotSystemMemoryFree OBJECT-TYPE
			SYNTAX Gauge32
			MAX-ACCESS read-only
			STATUS current
			DESCRIPTION
				"The freed memory size (unit: kb)"
			::= { sleSlotSystemInfoEntry 13 }

		
		sleSlotSystemMemoryShared OBJECT-TYPE
			SYNTAX Gauge32
			MAX-ACCESS read-only
			STATUS current
			DESCRIPTION
				"The shared memory size (unit: kb)"
			::= { sleSlotSystemInfoEntry 14 }

		
		sleSlotSystemMemoryBuffers OBJECT-TYPE
			SYNTAX Gauge32
			MAX-ACCESS read-only
			STATUS current
			DESCRIPTION
				"The buffer size (unit: kb)"
			::= { sleSlotSystemInfoEntry 15 }

		
		sleSlotSystemMemoryCached OBJECT-TYPE
			SYNTAX Gauge32
			MAX-ACCESS read-only
			STATUS current
			DESCRIPTION
				"The cached memory size (unit: kb)"
			::= { sleSlotSystemInfoEntry 16 }

		
		sleSlotSystemMemorySwapTotal OBJECT-TYPE
			SYNTAX Gauge32
			MAX-ACCESS read-only
			STATUS current
			DESCRIPTION
				"The total swap memory size (unit: kb)"
			::= { sleSlotSystemInfoEntry 17 }

		
		sleSlotSystemMemorySwapFree OBJECT-TYPE
			SYNTAX Gauge32
			MAX-ACCESS read-only
			STATUS current
			DESCRIPTION
				"The freed swap memory size (unit: kb)"
			::= { sleSlotSystemInfoEntry 18 }

		
		sleSlotSystemBootReason OBJECT-TYPE
			SYNTAX INTEGER
				{
				powerBoot(1),
				powerBootByLocal(2),
				hwResetBySW(3),
				hardWdogByLocal(4),
				hwRebootByMate(5),
				hwRebootBySwitchover(6),
				swReboot(10),
				swRebootByLocal(11),
				swRebootBySFU(12),
				swRebootBySwitchover(13),
				swRebootByPanic(14),
				watchdog(20),
				watchdogByLocal(21),
				swWatchdog(30),
				swWatchdogByCpuOver(31),
				swWatchdogByMemoryLow(32),
				error(255)
				}
			MAX-ACCESS read-only
			STATUS current
			DESCRIPTION
				"The system slot boot reason."
			::= { sleSlotSystemInfoEntry 19 }

		
		sleSlotSystemBootTime OBJECT-TYPE
			SYNTAX Gauge32
			UNITS "1 second"
			MAX-ACCESS read-only
			STATUS current
			DESCRIPTION
				"The system slot boot time.
				The time since the Epoch (00:00:00 UTC, January 1, 1970), measured in seconds.
				"
			::= { sleSlotSystemInfoEntry 20 }

		
		sleSlotSystemVoltage OBJECT-TYPE
			SYNTAX Gauge32
			UNITS "0.1 v"
			MAX-ACCESS read-only
			STATUS current
			DESCRIPTION
				"The system slot voltage."
			::= { sleSlotSystemInfoEntry 21 }

		
		sleSlotSystemPowerLevelStatus OBJECT-TYPE
			SYNTAX INTEGER
				{
				good(1),
				bad(2)
				}
			MAX-ACCESS read-only
			STATUS current
			DESCRIPTION
				"PCB Power level status."
			::= { sleSlotSystemInfoEntry 22 }

		
		sleSlotSystemInfoLEDStatus OBJECT-TYPE
			SYNTAX BITS
				{
				pwr(0),
				run(1),
				critical(2),
				major(3),
				minor(4),
				error(5)
				}
			MAX-ACCESS read-only
			STATUS current
			DESCRIPTION
				"The LED status of each slot."
			::= { sleSlotSystemInfoEntry 23 }

		
		sleSlotSystemInfoPackageVersion OBJECT-TYPE
			SYNTAX OCTET STRING
			MAX-ACCESS read-only
			STATUS current
			DESCRIPTION
				"The applied package revision."
			::= { sleSlotSystemInfoEntry 24 }

		
		sleSlotSystemInfoManufacturer OBJECT-TYPE
			SYNTAX OCTET STRING
			MAX-ACCESS read-only
			STATUS current
			DESCRIPTION
				"Ths manufacturer name and country."
			::= { sleSlotSystemInfoEntry 25 }

		
		sleSlotSystemInfoManufactureDate OBJECT-TYPE
			SYNTAX OCTET STRING
			MAX-ACCESS read-only
			STATUS current
			DESCRIPTION
				"Ths manufacture date."
			::= { sleSlotSystemInfoEntry 26 }

		
		sleSlotSystemCPULoadHighThreshold OBJECT-TYPE
			SYNTAX Integer32
			MAX-ACCESS read-only
			STATUS current
			DESCRIPTION
				"The high threshold of CPU load (70:default)"
			::= { sleSlotSystemInfoEntry 27 }

		
		sleSlotSystemCPULoadHighThresholdTimer OBJECT-TYPE
			SYNTAX INTEGER
				{
				timerInverval5(1),
				timerInverval60(2),
				timerInverval600(3)
				}
			MAX-ACCESS read-only
			STATUS current
			DESCRIPTION
				"The high threshold timer of CPU load (sec) (60:default)"
			::= { sleSlotSystemInfoEntry 28 }

		
		sleSlotSystemCPULoadLowThreshold OBJECT-TYPE
			SYNTAX Integer32
			MAX-ACCESS read-only
			STATUS current
			DESCRIPTION
				"The low threshold of CPU load (30:default)"
			::= { sleSlotSystemInfoEntry 29 }

		
		sleSlotSystemCPULoadLowThresholdTimer OBJECT-TYPE
			SYNTAX INTEGER
				{
				timerInverval5(1),
				timerInverval60(2),
				timerInverval600(3)
				}
			MAX-ACCESS read-only
			STATUS current
			DESCRIPTION
				"The low threshold timer of CPU load (sec) (60:default)"
			::= { sleSlotSystemInfoEntry 30 }

		
		sleSlotSystemCPULoadCurrent OBJECT-TYPE
			SYNTAX Integer32
			MAX-ACCESS read-only
			STATUS current
			DESCRIPTION
				"The CPU load currnet value (only used for trap)"
			::= { sleSlotSystemInfoEntry 31 }

		
		sleSlotSystemCPUOverallStatus OBJECT-TYPE
			SYNTAX INTEGER
				{
				good(1),
				bad(2)
				}
			MAX-ACCESS read-only
			STATUS current
			DESCRIPTION
				"The CPU Overall status for SFU & IU"
			::= { sleSlotSystemInfoEntry 32 }

		
		sleSlotSystemTemperOverallStatus OBJECT-TYPE
			SYNTAX INTEGER
				{
				good(1),
				bad(2)
				}
			MAX-ACCESS read-only
			STATUS current
			DESCRIPTION
				"The Temperature Overall status for SFU & IU"
			::= { sleSlotSystemInfoEntry 33 }

		
		sleSlotSystemControl OBJECT IDENTIFIER ::= { sleSlotSystemInfo 2 }

		
		sleSlotSystemControlRequest OBJECT-TYPE
			SYNTAX INTEGER
				{
				setSlotRestart(1),
				setSlotCpuloadThreshold(2),
				delSlotCpuloadThreshold(3)
				}
			MAX-ACCESS read-write
			STATUS current
			DESCRIPTION
				"The request of a user command"
			::= { sleSlotSystemControl 1 }

		
		sleSlotSystemControlStatus OBJECT-TYPE
			SYNTAX SleControlStatusType
			MAX-ACCESS read-only
			STATUS current
			DESCRIPTION
				"The status of user command"
			::= { sleSlotSystemControl 2 }

		
		sleSlotSystemControlTimer OBJECT-TYPE
			SYNTAX Gauge32
			MAX-ACCESS read-write
			STATUS current
			DESCRIPTION
				"The maximum time for the manager for a long running user command"
			::= { sleSlotSystemControl 3 }

		
		sleSlotSystemControlTimeStamp OBJECT-TYPE
			SYNTAX TimeTicks
			MAX-ACCESS read-only
			STATUS current
			DESCRIPTION
				"The time stamp of the last command(end of command)"
			::= { sleSlotSystemControl 4 }

		
		sleSlotSystemControlReqResult OBJECT-TYPE
			SYNTAX SleControlRequestResultType
			MAX-ACCESS read-only
			STATUS current
			DESCRIPTION
				"The result of the last user command"
			::= { sleSlotSystemControl 5 }

		
		sleSlotSystemControlSlotIndex OBJECT-TYPE
			SYNTAX Integer32
			MAX-ACCESS read-write
			STATUS current
			DESCRIPTION
				"The system slot index."
			::= { sleSlotSystemControl 6 }

		
		sleSlotSystemControlCPULoadHighThreshold OBJECT-TYPE
			SYNTAX Integer32 (21..100)
			MAX-ACCESS read-write
			STATUS current
			DESCRIPTION
				"The high threshold of CPU load (70:default)"
			::= { sleSlotSystemControl 7 }

		
		sleSlotSystemControlCPULoadHighThresholdTimer OBJECT-TYPE
			SYNTAX INTEGER
				{
				timerInverval5(1),
				timerInverval60(2),
				timerInverval600(3)
				}
			MAX-ACCESS read-write
			STATUS current
			DESCRIPTION
				"The high threshold timer of CPU load (sec) (60:default)"
			::= { sleSlotSystemControl 8 }

		
		sleSlotSystemControlCPULoadLowThreshold OBJECT-TYPE
			SYNTAX Integer32 (20..100)
			MAX-ACCESS read-write
			STATUS current
			DESCRIPTION
				"The low threshold of CPU load (30:default)"
			::= { sleSlotSystemControl 9 }

		
		sleSlotSystemControlCPULoadLowThresholdTimer OBJECT-TYPE
			SYNTAX INTEGER
				{
				timerInverval5(1),
				timerInverval60(2),
				timerInverval600(3)
				}
			MAX-ACCESS read-write
			STATUS current
			DESCRIPTION
				"The low threshold timer of CPU load (sec) (60:default)"
			::= { sleSlotSystemControl 10 }

		
		sleSlotSystemNotification OBJECT IDENTIFIER ::= { sleSlotSystemInfo 3 }

		
		sleSlotSystemRestart NOTIFICATION-TYPE
			OBJECTS { sleSlotSystemControlRequest, sleSlotSystemControlTimeStamp, sleSlotSystemControlReqResult, sleSlotSystemControlSlotIndex }
			STATUS current
			DESCRIPTION 
				"Description."
			::= { sleSlotSystemNotification 1 }

		
		sleSlotSystemCPULoadChagned NOTIFICATION-TYPE
			OBJECTS { sleSlotSystemControlRequest, sleSlotSystemControlTimeStamp, sleSlotSystemControlReqResult, sleSlotSystemControlSlotIndex, sleSlotSystemControlCPULoadHighThreshold, 
				sleSlotSystemControlCPULoadHighThresholdTimer, sleSlotSystemControlCPULoadLowThreshold, sleSlotSystemControlCPULoadLowThresholdTimer }
			STATUS current
			DESCRIPTION 
				"setSlotCpuloadThreshold"
			::= { sleSlotSystemNotification 2 }

		
		sleSlotSystemCPULoadDeleted NOTIFICATION-TYPE
			OBJECTS { sleSlotSystemControlRequest, sleSlotSystemControlTimeStamp, sleSlotSystemControlReqResult, sleSlotSystemControlSlotIndex }
			STATUS current
			DESCRIPTION 
				"delSlotCpuloadThreshold"
			::= { sleSlotSystemNotification 3 }

		
		sleSlotStatusInfo OBJECT IDENTIFIER ::= { sleSlot 2 }

		
		sleSlotStatusInfoTable OBJECT-TYPE
			SYNTAX SEQUENCE OF SleSlotStatusInfoEntry
			MAX-ACCESS not-accessible
			STATUS current
			DESCRIPTION
				"Description."
			::= { sleSlotStatusInfo 1 }

		
		sleSlotStatusInfoEntry OBJECT-TYPE
			SYNTAX SleSlotStatusInfoEntry
			MAX-ACCESS not-accessible
			STATUS current
			DESCRIPTION
				"Description."
			INDEX { sleSlotSystemIndex }
			::= { sleSlotStatusInfoTable 1 }

		
		SleSlotStatusInfoEntry ::=
			SEQUENCE { 
				sleSlotStatusPlan
					INTEGER,
				sleSlotStatusPlanCardType
					INTEGER,
				sleSlotStatusCurrentInstall
					INTEGER,
				sleSlotStatusCurrentInstallCardType
					INTEGER,
				sleSlotStatusCardOperation
					INTEGER,
				sleSlotStatusLock
					INTEGER,
				sleSlotStatusUpgradeMode
					INTEGER,
				sleSlotStatusActionEvent
					INTEGER,
				sleSlotStatusState
					INTEGER,
				sleSlotStatusPower
					INTEGER,
				sleSlotStatusSerialNumber
					OCTET STRING,
				sleSlotStatusHealthState
					INTEGER,
				sleslotStatusOverallState
					INTEGER,
				sleslotStatusSyncState
					INTEGER
			 }

		sleSlotStatusPlan OBJECT-TYPE
			SYNTAX INTEGER
				{
				notPlanned(1),
				planned(2)
				}
			MAX-ACCESS read-only
			STATUS current
			DESCRIPTION
				"Planning status of slot."
			::= { sleSlotStatusInfoEntry 1 }

		
		sleSlotStatusPlanCardType OBJECT-TYPE
			SYNTAX INTEGER
				{
				unknown(1),
				siuGE12(2),
				siuEPON12(3),
				siuGPON4(4),
				niuGE12(5),
				sfu(6),
				v5548gGE12(7),
				siuGPON4r(8),
				niuGE8(9),
				siuGE4(10),
				niu10GPlus(11),
				iu10GE(12),
				iuGE6(13),
				iuGE4(14),
				siuTDM(15),
				siuGE24(16),
				siuFE48(17),
				niu10GE2(18),
				siu10GE48(19),
				siuGE10(20),
				niu10Ge2Plus(21),
				iuGT4(22),
				iuGT6(23),
				iuTDM6(24),
				siuGE6(25),
				siuGE8(26),
				siuGT6(27),
				niuGE2(28),
				niuGE4(29),
				iuGEPON4(30),
				iu10GE8(31),
				iuGEPON8(32),
				iu10GEPON8(33),
				iuGE8(34),
				siu10GEPON8(35),
				niu10GE4(36),
				sfu10GE4(37),
				siuGPON16(38),
				iu10GE4(39),
				siuGT24(40),
				iu10GE2(41),
				cwdm(42),
				iuGT8(43)
				}
			MAX-ACCESS read-only
			STATUS current
			DESCRIPTION
				"Planning card type status of slot."
			::= { sleSlotStatusInfoEntry 2 }

		
		sleSlotStatusCurrentInstall OBJECT-TYPE
			SYNTAX INTEGER
				{
				notInstalled(1),
				installed(2),
				failed(3)
				}
			MAX-ACCESS read-only
			STATUS current
			DESCRIPTION
				"Currently installation status of slot."
			::= { sleSlotStatusInfoEntry 3 }

		
		sleSlotStatusCurrentInstallCardType OBJECT-TYPE
			SYNTAX INTEGER
				{
				unknown(1),
				siuGE12(2),
				siuEPON12(3),
				siuGPON4(4),
				niuGE12(5),
				sfu(6),
				v5548gGE12(7),
				siuGPON4r(8),
				niuGE8(9),
				siuGE4(10),
				niu10GPlus(11),
				iuGE10(12),
				iuGE6(13),
				iuGE4(14),
				siuTDM(15),
				siuGE24(16),
				siuFE48(17),
				niu10GE2(18),
				siu10GE48(19),
				siuGE10(20),
				niu10Ge2Plus(21),
				iuGT4(22),
				iuGT6(23),
				iuTDM6(24),
				siuGE6(25),
				siuGE8(26),
				siuGT6(27),
				niuGE2(28),
				niuGE4(29),
				iuGEPON4(30),
				iu10GE8(31),
				iuGEPON8(32),
				iu10GEPON8(33),
				iuGE8(34),
				siu10GEPON8(35),
				niu10GE4(36),
				sfu10GE4(37),
				siuGPON16(38),
				iu10GE4(39),
				siuGT24(40),
				iu10GE2(41),
				cwdm(42),
				iuGT8(43)
				}
			MAX-ACCESS read-only
			STATUS current
			DESCRIPTION
				"Currently installation card type status of slot."
			::= { sleSlotStatusInfoEntry 4 }

		
		sleSlotStatusCardOperation OBJECT-TYPE
			SYNTAX INTEGER
				{
				disable(1),
				init(2),
				enable(3),
				enableActive(4),
				enableStandby(5)
				}
			MAX-ACCESS read-only
			STATUS current
			DESCRIPTION
				"Currently operation status of slot."
			::= { sleSlotStatusInfoEntry 5 }

		
		sleSlotStatusLock OBJECT-TYPE
			SYNTAX INTEGER
				{
				unlocked(1),
				locked(2)
				}
			MAX-ACCESS read-only
			STATUS current
			DESCRIPTION
				"Lock status of slot."
			::= { sleSlotStatusInfoEntry 6 }

		
		sleSlotStatusUpgradeMode OBJECT-TYPE
			SYNTAX INTEGER
				{
				manual(1),
				auto(2)
				}
			MAX-ACCESS read-only
			STATUS current
			DESCRIPTION
				"Upgrade mode status of slot."
			::= { sleSlotStatusInfoEntry 7 }

		
		sleSlotStatusActionEvent OBJECT-TYPE
			SYNTAX INTEGER
				{
				uninstallAction(1),
				installAction(2),
				noPlanningAction(3),
				planningAction(4),
				lockAction(5),
				unlockAction(6),
				matchedEvent(7),
				unMatchedEvent(8),
				bootEndEvent(9),
				configEndEvent(10),
				configFailEvent(11)
				}
			MAX-ACCESS accessible-for-notify
			STATUS current
			DESCRIPTION
				"Event of slot. (accessible-for-notify)"
			::= { sleSlotStatusInfoEntry 8 }

		
		sleSlotStatusState OBJECT-TYPE
			SYNTAX INTEGER
				{
				default(1),
				planningWait(2),
				installWait(3),
				operationReady(4),
				actionBootReady(5),
				actionConfig(6),
				actionEnableReady(7),
				actionEnable(8),
				actionEnableLock(9),
				actionDisable(10)
				}
			MAX-ACCESS accessible-for-notify
			STATUS current
			DESCRIPTION
				"Status of slot. (accessible-for-notify)"
			::= { sleSlotStatusInfoEntry 9 }

		
		sleSlotStatusPower OBJECT-TYPE
			SYNTAX INTEGER
				{
				up(1),
				down(2)
				}
			MAX-ACCESS read-only
			STATUS current
			DESCRIPTION
				"Currently power status of slot."
			::= { sleSlotStatusInfoEntry 10 }

		
		sleSlotStatusSerialNumber OBJECT-TYPE
			SYNTAX OCTET STRING
			MAX-ACCESS read-only
			STATUS current
			DESCRIPTION
				"The serial number"
			::= { sleSlotStatusInfoEntry 11 }

		
		sleSlotStatusHealthState OBJECT-TYPE
			SYNTAX INTEGER
				{
				well(0),
				warning(1),
				timeout(2)
				}
			MAX-ACCESS read-only
			STATUS current
			DESCRIPTION
				"The slot health status"
			::= { sleSlotStatusInfoEntry 12 }

		
		sleslotStatusOverallState OBJECT-TYPE
			SYNTAX INTEGER
				{
				good(0),
				bad(1)
				}
			MAX-ACCESS read-only
			STATUS current
			DESCRIPTION
				"The slot overrall status"
			::= { sleSlotStatusInfoEntry 13 }

		
		sleslotStatusSyncState OBJECT-TYPE
			SYNTAX INTEGER
				{
				none(0),
				disable(1),
				process(2),
				done(3)
				}
			MAX-ACCESS read-only
			STATUS current
			DESCRIPTION
				"The slot sync status"
			::= { sleSlotStatusInfoEntry 14 }

		
		sleSlotStatusControl OBJECT IDENTIFIER ::= { sleSlotStatusInfo 2 }

		
		sleSlotStatusControlRequest OBJECT-TYPE
			SYNTAX INTEGER
				{
				setSlotLock(1),
				setSlotUnlock(2),
				setSlotPlanning(3),
				setSlotNoplanning(4),
				setSlotUpgradeMode(5),
				setSlotPowerUp(6),
				setSlotPowerDown(7),
				setSlotPowerReset(8)
				}
			MAX-ACCESS read-write
			STATUS current
			DESCRIPTION
				"The request of a user command"
			::= { sleSlotStatusControl 1 }

		
		sleSlotStatusControlStatus OBJECT-TYPE
			SYNTAX SleControlStatusType
			MAX-ACCESS read-only
			STATUS current
			DESCRIPTION
				"The status of user command"
			::= { sleSlotStatusControl 2 }

		
		sleSlotStatusControlTimer OBJECT-TYPE
			SYNTAX Gauge32
			MAX-ACCESS read-write
			STATUS current
			DESCRIPTION
				"The maximum time for the manager for a long running user command"
			::= { sleSlotStatusControl 3 }

		
		sleSlotStatusControlTimeStamp OBJECT-TYPE
			SYNTAX TimeTicks
			MAX-ACCESS read-only
			STATUS current
			DESCRIPTION
				"The time stamp of the last command(end of command)"
			::= { sleSlotStatusControl 4 }

		
		sleSlotStatusControlReqResult OBJECT-TYPE
			SYNTAX SleControlRequestResultType
			MAX-ACCESS read-only
			STATUS current
			DESCRIPTION
				"The result of the last user command"
			::= { sleSlotStatusControl 5 }

		
		sleSlotStatusControlSlotIndex OBJECT-TYPE
			SYNTAX Integer32
			MAX-ACCESS read-write
			STATUS current
			DESCRIPTION
				"The system slot index.
				255 is means all slot."
			::= { sleSlotStatusControl 6 }

		
		sleSlotStatusControlPlanCardType OBJECT-TYPE
			SYNTAX INTEGER
				{
				unknown(1),
				siuGE12(2),
				siuEPON12(3),
				siuGPON4(4),
				niuGE12(5),
				sfu(6),
				v5548gGE12(7),
				siuGPON4r(8),
				niuGE8(9),
				siuGE4(10),
				niu10GPlus(11),
				iuGE10(12),
				iuGE6(13),
				iuGE4(14),
				siuTDM(15),
				siuGE24(16),
				siuFE48(17),
				niu10GE2(18),
				siu10GE48(19),
				siuGE10(20),
				niu10Ge2Plus(21),
				iuGT4(22),
				iuGT6(23),
				iuTDM6(24),
				siuGE6(25),
				siuGE8(26),
				siuGT6(27),
				niuGE2(28),
				niuGE4(29),
				iuGEPON4(30),
				iu10GE8(31),
				iuGEPON8(32),
				iu10GEPON8(33),
				iuGE8(34),
				siu10GEPON8(35),
				niu10GE4(36),
				sfu10GE4(37),
				siuGPON16(38),
				iu10GE4(39),
				siuGT24(40),
				iu10GE2(41),
				cwdm(42),
				iuGT8(43)
				}
			MAX-ACCESS read-write
			STATUS current
			DESCRIPTION
				"Planning card type status of slot."
			::= { sleSlotStatusControl 7 }

		
		sleSlotStatusControlUpgradeMode OBJECT-TYPE
			SYNTAX INTEGER
				{
				manual(1),
				auto(2),
				autoUpgradeManualReset(3)
				}
			MAX-ACCESS read-write
			STATUS current
			DESCRIPTION
				"Upgrade mode status of slot."
			::= { sleSlotStatusControl 8 }

		
		sleSlotStatusNotification OBJECT IDENTIFIER ::= { sleSlotStatusInfo 3 }

		
		sleSlotStatusLocked NOTIFICATION-TYPE
			OBJECTS { sleSlotStatusControlRequest, sleSlotStatusControlTimeStamp, sleSlotStatusControlReqResult, sleSlotStatusControlSlotIndex }
			STATUS current
			DESCRIPTION 
				"Description."
			::= { sleSlotStatusNotification 1 }

		
		sleSlotStatusUnlocked NOTIFICATION-TYPE
			OBJECTS { sleSlotStatusControlRequest, sleSlotStatusControlTimeStamp, sleSlotStatusControlReqResult, sleSlotStatusControlSlotIndex }
			STATUS current
			DESCRIPTION 
				"Description."
			::= { sleSlotStatusNotification 2 }

		
		sleSlotStatusPlanning NOTIFICATION-TYPE
			OBJECTS { sleSlotStatusControlRequest, sleSlotStatusControlTimeStamp, sleSlotStatusControlReqResult, sleSlotStatusControlSlotIndex, sleSlotStatusControlPlanCardType
				 }
			STATUS current
			DESCRIPTION 
				"Description."
			::= { sleSlotStatusNotification 3 }

		
		sleSlotStatusNoPlanning NOTIFICATION-TYPE
			OBJECTS { sleSlotStatusControlRequest, sleSlotStatusControlTimeStamp, sleSlotStatusControlReqResult, sleSlotStatusControlSlotIndex }
			STATUS current
			DESCRIPTION 
				"Description."
			::= { sleSlotStatusNotification 4 }

		
		sleSlotStatusUpgradeModeChanged NOTIFICATION-TYPE
			OBJECTS { sleSlotStatusControlRequest, sleSlotStatusControlTimeStamp, sleSlotStatusControlReqResult, sleSlotStatusControlSlotIndex, sleSlotStatusControlUpgradeMode
				 }
			STATUS current
			DESCRIPTION 
				"Description."
			::= { sleSlotStatusNotification 5 }

		
		sleSlotStatusPowerUp NOTIFICATION-TYPE
			OBJECTS { sleSlotStatusControlRequest, sleSlotStatusControlTimeStamp, sleSlotStatusControlReqResult, sleSlotStatusControlSlotIndex }
			STATUS current
			DESCRIPTION 
				"Description."
			::= { sleSlotStatusNotification 6 }

		
		sleSlotStatusPowerDown NOTIFICATION-TYPE
			OBJECTS { sleSlotStatusControlRequest, sleSlotStatusControlTimeStamp, sleSlotStatusControlReqResult, sleSlotStatusControlSlotIndex }
			STATUS current
			DESCRIPTION 
				"Description."
			::= { sleSlotStatusNotification 7 }

		
		sleSlotStatusPowerReset NOTIFICATION-TYPE
			OBJECTS { sleSlotStatusControlRequest, sleSlotStatusControlTimeStamp, sleSlotStatusControlReqResult, sleSlotStatusControlSlotIndex }
			STATUS current
			DESCRIPTION 
				"Description."
			::= { sleSlotStatusNotification 8 }

		
		sleSlotNosInfo OBJECT IDENTIFIER ::= { sleSlot 3 }

		
		sleSlotNosInfoTable OBJECT-TYPE
			SYNTAX SEQUENCE OF SleSlotNosInfoEntry
			MAX-ACCESS not-accessible
			STATUS current
			DESCRIPTION
				"Description."
			::= { sleSlotNosInfo 1 }

		
		sleSlotNosInfoEntry OBJECT-TYPE
			SYNTAX SleSlotNosInfoEntry
			MAX-ACCESS not-accessible
			STATUS current
			DESCRIPTION
				"Description."
			INDEX { sleSlotSystemIndex }
			::= { sleSlotNosInfoTable 1 }

		
		SleSlotNosInfoEntry ::=
			SEQUENCE { 
				sleSlotNosVersion
					OCTET STRING,
				sleSlotNosRevision
					OCTET STRING,
				sleSlotNosSize
					Unsigned32,
				sleSlotNosUpgradeStatus
					INTEGER,
				sleSlotNosStbVersion
					OCTET STRING,
				sleSlotNosStbRevision
					OCTET STRING,
				sleSlotNosStbSize
					Unsigned32
			 }

		sleSlotNosVersion OBJECT-TYPE
			SYNTAX OCTET STRING
			MAX-ACCESS read-only
			STATUS current
			DESCRIPTION
				"NOS version of slot."
			::= { sleSlotNosInfoEntry 1 }

		
		sleSlotNosRevision OBJECT-TYPE
			SYNTAX OCTET STRING
			MAX-ACCESS read-only
			STATUS current
			DESCRIPTION
				"NOS revision of slot."
			::= { sleSlotNosInfoEntry 2 }

		
		sleSlotNosSize OBJECT-TYPE
			SYNTAX Unsigned32
			MAX-ACCESS read-only
			STATUS current
			DESCRIPTION
				"NOS size of slot."
			::= { sleSlotNosInfoEntry 3 }

		
		sleSlotNosUpgradeStatus OBJECT-TYPE
			SYNTAX INTEGER
				{
				upgradeIdle(1),
				upgradeStart(2),
				upgradeDone(3),
				upgradeFail(4)
				}
			MAX-ACCESS read-only
			STATUS current
			DESCRIPTION
				"NOS upgrade status of slot."
			::= { sleSlotNosInfoEntry 4 }

		
		sleSlotNosStbVersion OBJECT-TYPE
			SYNTAX OCTET STRING
			MAX-ACCESS read-only
			STATUS current
			DESCRIPTION
				"Stand by NOS version of slot"
			::= { sleSlotNosInfoEntry 5 }

		
		sleSlotNosStbRevision OBJECT-TYPE
			SYNTAX OCTET STRING
			MAX-ACCESS read-only
			STATUS current
			DESCRIPTION
				"Stand by NOS revision of slot."
			::= { sleSlotNosInfoEntry 6 }

		
		sleSlotNosStbSize OBJECT-TYPE
			SYNTAX Unsigned32
			MAX-ACCESS read-only
			STATUS current
			DESCRIPTION
				"Stand by NOS size of slot."
			::= { sleSlotNosInfoEntry 7 }

		
		sleSlotNosControl OBJECT IDENTIFIER ::= { sleSlotNosInfo 2 }

		
		sleSlotNosControlRequest OBJECT-TYPE
			SYNTAX INTEGER
				{
				setSlotUpgarde(1),
				downloadSlotNos(2),
				upgradeSlotBootloader(3)
				}
			MAX-ACCESS read-write
			STATUS current
			DESCRIPTION
				"The request of a user command"
			::= { sleSlotNosControl 1 }

		
		sleSlotNosControlStatus OBJECT-TYPE
			SYNTAX SleControlStatusType
			MAX-ACCESS read-only
			STATUS current
			DESCRIPTION
				"The status of user command"
			::= { sleSlotNosControl 2 }

		
		sleSlotNosControlTimer OBJECT-TYPE
			SYNTAX Gauge32
			MAX-ACCESS read-write
			STATUS current
			DESCRIPTION
				"The maximum time for the manager for a long running user command"
			::= { sleSlotNosControl 3 }

		
		sleSlotNosControlTimeStamp OBJECT-TYPE
			SYNTAX TimeTicks
			MAX-ACCESS read-only
			STATUS current
			DESCRIPTION
				"The time stamp of the last command(end of command)"
			::= { sleSlotNosControl 4 }

		
		sleSlotNosControlReqResult OBJECT-TYPE
			SYNTAX SleControlRequestResultType
			MAX-ACCESS read-only
			STATUS current
			DESCRIPTION
				"The result of the last user command"
			::= { sleSlotNosControl 5 }

		
		sleSlotNosControlSlotIndex OBJECT-TYPE
			SYNTAX Integer32
			MAX-ACCESS read-write
			STATUS current
			DESCRIPTION
				"The system slot index."
			::= { sleSlotNosControl 6 }

		
		sleSlotNosControlUpDownMethod OBJECT-TYPE
			SYNTAX INTEGER
				{
				ftp(1),
				tftp(2)
				}
			MAX-ACCESS read-write
			STATUS current
			DESCRIPTION
				"1: using FTP
				2: using TFTP
				"
			::= { sleSlotNosControl 7 }

		
		sleSlotNosControlUpDownFlag OBJECT-TYPE
			SYNTAX INTEGER
				{
				upload(1),
				download(2)
				}
			MAX-ACCESS read-write
			STATUS current
			DESCRIPTION
				"1. Uploading slot nos to the remote-host.
				2. Downloading slot nos from the remote-host."
			::= { sleSlotNosControl 8 }

		
		sleSlotNosControlServerAddress OBJECT-TYPE
			SYNTAX IpAddress
			MAX-ACCESS read-write
			STATUS current
			DESCRIPTION
				"The remote-host's IP address."
			::= { sleSlotNosControl 9 }

		
		sleSlotNosControlUserID OBJECT-TYPE
			SYNTAX OCTET STRING
			MAX-ACCESS read-write
			STATUS current
			DESCRIPTION
				"Account-name."
			::= { sleSlotNosControl 10 }

		
		sleSlotNosControlPassword OBJECT-TYPE
			SYNTAX OCTET STRING
			MAX-ACCESS read-write
			STATUS current
			DESCRIPTION
				"Account-password."
			::= { sleSlotNosControl 11 }

		
		sleSlotNosControlFileName OBJECT-TYPE
			SYNTAX OCTET STRING
			MAX-ACCESS read-write
			STATUS current
			DESCRIPTION
				"Slot nos file name."
			::= { sleSlotNosControl 12 }

		
		sleSlotNosNotification OBJECT IDENTIFIER ::= { sleSlotNosInfo 3 }

		
		sleSlotNosUpgrade NOTIFICATION-TYPE
			OBJECTS { sleSlotNosControlRequest, sleSlotNosControlTimeStamp, sleSlotNosControlReqResult, sleSlotNosControlSlotIndex }
			STATUS current
			DESCRIPTION 
				"Description."
			::= { sleSlotNosNotification 1 }

		
		sleSlotNosDownload NOTIFICATION-TYPE
			OBJECTS { sleSlotNosControlRequest, sleSlotNosControlTimeStamp, sleSlotNosControlReqResult, sleSlotNosControlUpDownMethod, sleSlotNosControlUpDownFlag, 
				sleSlotNosControlServerAddress, sleSlotNosControlUserID, sleSlotNosControlPassword, sleSlotNosControlFileName }
			STATUS current
			DESCRIPTION 
				"Description."
			::= { sleSlotNosNotification 2 }

		
		sleSlotNosBootloaderUpgrade NOTIFICATION-TYPE
			OBJECTS { sleSlotNosControlRequest, sleSlotNosControlTimeStamp, sleSlotNosControlReqResult, sleSlotNosControlSlotIndex, sleSlotNosControlServerAddress, 
				sleSlotNosControlUserID, sleSlotNosControlPassword, sleSlotNosControlFileName }
			STATUS current
			DESCRIPTION 
				"Description."
			::= { sleSlotNosNotification 3 }

		
		sleSlotReleasedIUNosInfo OBJECT IDENTIFIER ::= { sleSlot 4 }

		
		sleSlotReleasedNIUNosVersion OBJECT-TYPE
			SYNTAX OCTET STRING
			MAX-ACCESS read-only
			STATUS current
			DESCRIPTION
				"Released NIU NOS image version on SFU."
			::= { sleSlotReleasedIUNosInfo 1 }

		
		sleSlotReleasedNIUNosRevision OBJECT-TYPE
			SYNTAX OCTET STRING
			MAX-ACCESS read-only
			STATUS current
			DESCRIPTION
				"Released NIU NOS image revision on SFU."
			::= { sleSlotReleasedIUNosInfo 2 }

		
		sleSlotReleasedNIUNosSize OBJECT-TYPE
			SYNTAX Unsigned32
			MAX-ACCESS read-only
			STATUS current
			DESCRIPTION
				"Released NIU NOS image size on SFU."
			::= { sleSlotReleasedIUNosInfo 3 }

		
		sleSlotReleasedGPIUNosVersion OBJECT-TYPE
			SYNTAX OCTET STRING
			MAX-ACCESS read-only
			STATUS current
			DESCRIPTION
				"Released GPIU NOS image version on SFU."
			::= { sleSlotReleasedIUNosInfo 4 }

		
		sleSlotReleasedGPIUNosRevision OBJECT-TYPE
			SYNTAX OCTET STRING
			MAX-ACCESS read-only
			STATUS current
			DESCRIPTION
				"Released GPIU NOS image revision on SFU."
			::= { sleSlotReleasedIUNosInfo 5 }

		
		sleSlotReleasedGPIUNosSize OBJECT-TYPE
			SYNTAX Unsigned32
			MAX-ACCESS read-only
			STATUS current
			DESCRIPTION
				"Released GPIU NOS image size on SFU."
			::= { sleSlotReleasedIUNosInfo 6 }

		
		sleSlotReleasedSIUNosVersion OBJECT-TYPE
			SYNTAX OCTET STRING
			MAX-ACCESS read-only
			STATUS current
			DESCRIPTION
				"Released SIU NOS image version on SFU."
			::= { sleSlotReleasedIUNosInfo 7 }

		
		sleSlotReleasedSIUNosRevision OBJECT-TYPE
			SYNTAX OCTET STRING
			MAX-ACCESS read-only
			STATUS current
			DESCRIPTION
				"Released SIU NOS image revision on SFU."
			::= { sleSlotReleasedIUNosInfo 8 }

		
		sleSlotReleasedSIUNosSize OBJECT-TYPE
			SYNTAX Integer32
			MAX-ACCESS read-only
			STATUS current
			DESCRIPTION
				"Released SIU NOS image size on SFU."
			::= { sleSlotReleasedIUNosInfo 9 }

		
		sleSlotReleasedIU10GE8NosVersion OBJECT-TYPE
			SYNTAX OCTET STRING
			MAX-ACCESS read-only
			STATUS current
			DESCRIPTION
				"Released IU_10GE8 NOS image version on SFU."
			::= { sleSlotReleasedIUNosInfo 10 }

		
		sleSlotReleasedIU10GE8NosRevision OBJECT-TYPE
			SYNTAX OCTET STRING
			MAX-ACCESS read-only
			STATUS current
			DESCRIPTION
				"Released IU_10GE8 NOS image revision on SFU."
			::= { sleSlotReleasedIUNosInfo 11 }

		
		sleSlotReleasedIU10GE8NosSize OBJECT-TYPE
			SYNTAX Integer32
			MAX-ACCESS read-only
			STATUS current
			DESCRIPTION
				"Released IU_10GE8 NOS image size on SFU."
			::= { sleSlotReleasedIUNosInfo 12 }

		
		sleSlotReleasedIU10GEPON8NosVersion OBJECT-TYPE
			SYNTAX OCTET STRING
			MAX-ACCESS read-only
			STATUS current
			DESCRIPTION
				"Released IU_10GEPON8 NOS image version on SFU."
			::= { sleSlotReleasedIUNosInfo 13 }

		
		sleSlotReleasedIU10GEPON8NosRevision OBJECT-TYPE
			SYNTAX OCTET STRING
			MAX-ACCESS read-only
			STATUS current
			DESCRIPTION
				"Released IU_10GEPON8 NOS image revision on SFU."
			::= { sleSlotReleasedIUNosInfo 14 }

		
		sleSlotReleasedIU10GEPON8NosSize OBJECT-TYPE
			SYNTAX Integer32
			MAX-ACCESS read-only
			STATUS current
			DESCRIPTION
				"Released IU_10GEPON8 NOS image size on SFU."
			::= { sleSlotReleasedIUNosInfo 15 }

		
		sleSlotReleasedIUGEPON8NosVersion OBJECT-TYPE
			SYNTAX OCTET STRING
			MAX-ACCESS read-only
			STATUS current
			DESCRIPTION
				"Released IU_GEPON8 NOS image version on SFU."
			::= { sleSlotReleasedIUNosInfo 16 }

		
		sleSlotReleasedIUGEPON8NosRevision OBJECT-TYPE
			SYNTAX OCTET STRING
			MAX-ACCESS read-only
			STATUS current
			DESCRIPTION
				"Released IU_GEPON8 NOS image revision on SFU"
			::= { sleSlotReleasedIUNosInfo 17 }

		
		sleSlotReleasedIUGEPON8NosSize OBJECT-TYPE
			SYNTAX Integer32
			MAX-ACCESS read-only
			STATUS current
			DESCRIPTION
				"Released IU_GEPON8 NOS image size on SFU."
			::= { sleSlotReleasedIUNosInfo 18 }

		
		sleSlotPowerMon OBJECT IDENTIFIER ::= { sleSlot 5 }

		
		sleSlotPowerMonTable OBJECT-TYPE
			SYNTAX SEQUENCE OF SleSlotPowerMonEntry
			MAX-ACCESS not-accessible
			STATUS current
			DESCRIPTION
				"The Power-Monitoring table."
			::= { sleSlotPowerMon 1 }

		
		sleSlotPowerMonEntry OBJECT-TYPE
			SYNTAX SleSlotPowerMonEntry
			MAX-ACCESS not-accessible
			STATUS current
			DESCRIPTION
				"The Power-Monitoring entry."
			INDEX { sleSlotSystemIndex, sleSlotPowerMonIndex }
			::= { sleSlotPowerMonTable 1 }

		
		SleSlotPowerMonEntry ::=
			SEQUENCE { 
				sleSlotPowerMonIndex
					INTEGER,
				sleSlotPowerMonStatus
					INTEGER,
				sleSlotPowerMonVoltage
					Gauge32
			 }

		sleSlotPowerMonIndex OBJECT-TYPE
			SYNTAX INTEGER (1..255)
			MAX-ACCESS read-only
			STATUS current
			DESCRIPTION
				"The physical index of power-monitoring object."
			::= { sleSlotPowerMonEntry 1 }

		
		sleSlotPowerMonStatus OBJECT-TYPE
			SYNTAX INTEGER
				{
				unknown(1),
				good(2),
				bad(3),
				over(4),
				under(5),
				overUnder(6)
				}
			MAX-ACCESS read-only
			STATUS current
			DESCRIPTION
				"The monitoring status of power-monitoring object."
			::= { sleSlotPowerMonEntry 2 }

		
		sleSlotPowerMonVoltage OBJECT-TYPE
			SYNTAX Gauge32
			UNITS "0.1v"
			MAX-ACCESS read-only
			STATUS current
			DESCRIPTION
				"The voltage value of power-monitoring object.
				value 10000(1000v) indicate that FUSE."
			::= { sleSlotPowerMonEntry 3 }

		
		sleSlotAiu OBJECT IDENTIFIER ::= { sleSlot 6 }

		
		sleSlotAiuRunStatus OBJECT-TYPE
			SYNTAX INTEGER
				{
				off(0),
				on(1)
				}
			MAX-ACCESS read-only
			STATUS current
			DESCRIPTION
				"The slot AIU run status."
			::= { sleSlotAiu 1 }

		
		sleSlotAiuAlarmStatus OBJECT-TYPE
			SYNTAX INTEGER
				{
				off(0),
				on(1)
				}
			MAX-ACCESS read-only
			STATUS current
			DESCRIPTION
				"The slot AIU alarm status."
			::= { sleSlotAiu 2 }

		
		sleSlotProtection OBJECT IDENTIFIER ::= { sleSlot 7 }

		
		sleSlotProtectionBase OBJECT IDENTIFIER ::= { sleSlotProtection 1 }

		
		sleSlotProtectionInfo OBJECT IDENTIFIER ::= { sleSlotProtectionBase 1 }

		
		sleSlotProtectionSystemStatus OBJECT-TYPE
			SYNTAX INTEGER
				{
				enable(1),
				disable(2)
				}
			MAX-ACCESS read-only
			STATUS current
			DESCRIPTION
				"The system admin status(enable or disable) of overtemperature shutdown function."
			::= { sleSlotProtectionInfo 1 }

		
		sleSlotProtectionSystemThreshold OBJECT-TYPE
			SYNTAX Integer32
			MAX-ACCESS read-only
			STATUS current
			DESCRIPTION
				"The system admin threshold of overtemperature shutdown function."
			::= { sleSlotProtectionInfo 2 }

		
		sleSlotProtectionIUPowerStatus OBJECT-TYPE
			SYNTAX INTEGER
				{
				enable(1),
				disable(2)
				}
			MAX-ACCESS read-write
			STATUS current
			DESCRIPTION
				"The slot power shutdown status"
			::= { sleSlotProtectionInfo 3 }

		
		sleSlotProtectionControl OBJECT IDENTIFIER ::= { sleSlotProtectionBase 2 }

		
		sleSlotProtectionControlRequest OBJECT-TYPE
			SYNTAX INTEGER
				{
				setSlotProtectionSystemStatus(1),
				setSlotProtectionSystemThresh(2),
				setslotProtectionIUPowerStatus(3)
				}
			MAX-ACCESS read-write
			STATUS current
			DESCRIPTION
				"The request of a user command"
			::= { sleSlotProtectionControl 1 }

		
		sleSlotProtectionControlStatus OBJECT-TYPE
			SYNTAX SleControlStatusType
			MAX-ACCESS read-only
			STATUS current
			DESCRIPTION
				"The status of user command"
			::= { sleSlotProtectionControl 2 }

		
		sleSlotProtectionControlTimer OBJECT-TYPE
			SYNTAX Gauge32
			MAX-ACCESS read-write
			STATUS current
			DESCRIPTION
				"The maximum time for the manager for a long running user command"
			::= { sleSlotProtectionControl 3 }

		
		sleSlotProtectionControlTimeStamp OBJECT-TYPE
			SYNTAX TimeTicks
			MAX-ACCESS read-only
			STATUS current
			DESCRIPTION
				"The time stamp of the last command(end of command)"
			::= { sleSlotProtectionControl 4 }

		
		sleSlotProtectionControlReqResult OBJECT-TYPE
			SYNTAX SleControlRequestResultType
			MAX-ACCESS read-only
			STATUS current
			DESCRIPTION
				"The result of the last user command"
			::= { sleSlotProtectionControl 5 }

		
		sleSlotProtectionControlSystemStatus OBJECT-TYPE
			SYNTAX INTEGER
				{
				enable(1),
				disable(2)
				}
			MAX-ACCESS read-write
			STATUS current
			DESCRIPTION
				"The system admin status(enable or disable) of overtemperature shutdown function."
			::= { sleSlotProtectionControl 6 }

		
		sleSlotProtectionControlSystemThreshold OBJECT-TYPE
			SYNTAX Integer32
			MAX-ACCESS read-write
			STATUS current
			DESCRIPTION
				"The system admin threshold of overtemperature shutdown function."
			::= { sleSlotProtectionControl 7 }

		
		sleSlotProtectionControlIUPowerStatus OBJECT-TYPE
			SYNTAX INTEGER
				{
				enable(1),
				disable(2)
				}
			MAX-ACCESS read-write
			STATUS current
			DESCRIPTION
				"The slot power shutdown status"
			::= { sleSlotProtectionControl 8 }

		
		sleSlotProtectionNotification OBJECT IDENTIFIER ::= { sleSlotProtectionBase 3 }

		
		sleSlotProtectionSystemStatusChanged NOTIFICATION-TYPE
			OBJECTS { sleSlotProtectionControlRequest, sleSlotProtectionControlTimeStamp, sleSlotProtectionControlReqResult, sleSlotProtectionControlSystemStatus }
			STATUS current
			DESCRIPTION 
				"Description."
			::= { sleSlotProtectionNotification 1 }

		
		sleSlotProtectionSystemThreshChanged NOTIFICATION-TYPE
			OBJECTS { sleSlotProtectionControlRequest, sleSlotProtectionControlTimeStamp, sleSlotProtectionControlReqResult, sleSlotProtectionControlSystemThreshold }
			STATUS current
			DESCRIPTION 
				"Description."
			::= { sleSlotProtectionNotification 2 }

		
		sleSlotProtectionIUPowerStatusChanged NOTIFICATION-TYPE
			OBJECTS { sleSlotProtectionControlRequest, sleSlotProtectionControlTimeStamp, sleSlotProtectionControlReqResult, sleSlotProtectionControlIUPowerStatus }
			STATUS current
			DESCRIPTION 
				"Description."
			::= { sleSlotProtectionNotification 3 }

		
		sleSlotProtectionIU OBJECT IDENTIFIER ::= { sleSlotProtection 2 }

		
		sleSlotProtectionIUTable OBJECT-TYPE
			SYNTAX SEQUENCE OF SleSlotProtectionIUEntry
			MAX-ACCESS not-accessible
			STATUS current
			DESCRIPTION
				"Description."
			::= { sleSlotProtectionIU 1 }

		
		sleSlotProtectionIUEntry OBJECT-TYPE
			SYNTAX SleSlotProtectionIUEntry
			MAX-ACCESS not-accessible
			STATUS current
			DESCRIPTION
				"Description."
			AUGMENTS { sleSlotSystemInfoEntry }
			::= { sleSlotProtectionIUTable 1 }

		
		SleSlotProtectionIUEntry ::=
			SEQUENCE { 
				sleSlotProtectionIUTemperHighThresh
					Integer32,
				sleSlotProtectionIUTemperLowThresh
					Integer32,
				sleSlotProtectionIUPowerThresh
					Integer32,
				sleSlotProtectionIUTemper
					Integer32,
				sleSlotProtectionIUTemper2
					Integer32
			 }

		sleSlotProtectionIUTemperHighThresh OBJECT-TYPE
			SYNTAX Integer32 (1..65535)
			MAX-ACCESS read-only
			STATUS current
			DESCRIPTION
				"The Slot temperature High-threshold of overtemperature alarm"
			::= { sleSlotProtectionIUEntry 1 }

		
		sleSlotProtectionIUTemperLowThresh OBJECT-TYPE
			SYNTAX Integer32 (1..65535)
			MAX-ACCESS read-only
			STATUS current
			DESCRIPTION
				"The Slot temperature Low-threshold of overtemperature alarm"
			::= { sleSlotProtectionIUEntry 2 }

		
		sleSlotProtectionIUPowerThresh OBJECT-TYPE
			SYNTAX Integer32 (1..65535)
			MAX-ACCESS read-only
			STATUS current
			DESCRIPTION
				"The Slot temperature threshold of overtemperature power shutdown."
			::= { sleSlotProtectionIUEntry 3 }

		
		sleSlotProtectionIUTemper OBJECT-TYPE
			SYNTAX Integer32 (1..65535)
			MAX-ACCESS read-only
			STATUS current
			DESCRIPTION
				"The Slot temperature."
			::= { sleSlotProtectionIUEntry 4 }

		
		sleSlotProtectionIUTemper2 OBJECT-TYPE
			SYNTAX Integer32 (1..65535)
			MAX-ACCESS read-only
			STATUS current
			DESCRIPTION
				"The Slot temperature2."
			::= { sleSlotProtectionIUEntry 5 }

		
		sleSlotProtectionIUControl OBJECT IDENTIFIER ::= { sleSlotProtectionIU 2 }

		
		sleSlotProtectionIUControlRequest OBJECT-TYPE
			SYNTAX INTEGER
				{
				setSlotTempThreshold(1),
				setSlotPowerThresh(2)
				}
			MAX-ACCESS read-write
			STATUS current
			DESCRIPTION
				"The request of a user command"
			::= { sleSlotProtectionIUControl 1 }

		
		sleSlotProtectionIUControlStatus OBJECT-TYPE
			SYNTAX SleControlStatusType
			MAX-ACCESS read-only
			STATUS current
			DESCRIPTION
				"The status of user command"
			::= { sleSlotProtectionIUControl 2 }

		
		sleSlotProtectionIUControlTimer OBJECT-TYPE
			SYNTAX Gauge32
			MAX-ACCESS read-write
			STATUS current
			DESCRIPTION
				"The maximum time for the manager for a long running user command"
			::= { sleSlotProtectionIUControl 3 }

		
		sleSlotProtectionIUControlTimeStamp OBJECT-TYPE
			SYNTAX TimeTicks
			MAX-ACCESS read-only
			STATUS current
			DESCRIPTION
				"The time stamp of the last command(end of command)"
			::= { sleSlotProtectionIUControl 4 }

		
		sleSlotProtectionIUControlReqResult OBJECT-TYPE
			SYNTAX SleControlRequestResultType
			MAX-ACCESS read-only
			STATUS current
			DESCRIPTION
				"The result of the last user command"
			::= { sleSlotProtectionIUControl 5 }

		
		sleSlotProtectionIUControlindex OBJECT-TYPE
			SYNTAX Integer32
			MAX-ACCESS read-write
			STATUS current
			DESCRIPTION
				"the slot index"
			::= { sleSlotProtectionIUControl 6 }

		
		sleSlotProtectionIUControlTemperHighThresh OBJECT-TYPE
			SYNTAX Integer32
			MAX-ACCESS read-write
			STATUS current
			DESCRIPTION
				"The Slot temperature High-threshold of overtemperature alarm"
			::= { sleSlotProtectionIUControl 7 }

		
		sleSlotProtectionIUControlTemperLowThresh OBJECT-TYPE
			SYNTAX Integer32
			MAX-ACCESS read-write
			STATUS current
			DESCRIPTION
				"The Slot temperature Low-threshold of overtemperature alarm"
			::= { sleSlotProtectionIUControl 8 }

		
		sleSlotProtectionIUControlPowerThresh OBJECT-TYPE
			SYNTAX Integer32
			MAX-ACCESS read-write
			STATUS current
			DESCRIPTION
				"The Slot temperature threshold of overtemperature power shutdown."
			::= { sleSlotProtectionIUControl 9 }

		
		sleSlotProtectionIUNotification OBJECT IDENTIFIER ::= { sleSlotProtectionIU 3 }

		
		sleSlotProtectionIUTemperThreshChanged NOTIFICATION-TYPE
			OBJECTS { sleSlotProtectionIUControlRequest, sleSlotProtectionIUControlTimeStamp, sleSlotProtectionIUControlReqResult, sleSlotProtectionIUControlTemperHighThresh, sleSlotProtectionIUControlTemperLowThresh, 
				sleSlotProtectionIUControlindex }
			STATUS current
			DESCRIPTION 
				"Description."
			::= { sleSlotProtectionIUNotification 1 }

		
		sleSlotProtectionIUPowerThreshChanged NOTIFICATION-TYPE
			OBJECTS { sleSlotProtectionIUControlRequest, sleSlotProtectionIUControlTimeStamp, sleSlotProtectionIUControlReqResult, sleSlotProtectionIUControlindex, sleSlotProtectionIUControlPowerThresh
				 }
			STATUS current
			DESCRIPTION 
				"Description."
			::= { sleSlotProtectionIUNotification 2 }

		
		sleRF OBJECT IDENTIFIER ::= { sleDevice 12 }

		
		sleRfBaseInfo OBJECT IDENTIFIER ::= { sleRF 1 }

		
		sleRfConnectStatus OBJECT-TYPE
			SYNTAX INTEGER
				{
				connect(1),
				disconnect(2)
				}
			MAX-ACCESS read-only
			STATUS current
			DESCRIPTION
				"The RF connect status."
			::= { sleRfBaseInfo 1 }

		
		sleRfPowerStatus OBJECT-TYPE
			SYNTAX INTEGER
				{
				poweroff(0),
				poweron(1)
				}
			MAX-ACCESS read-only
			STATUS current
			DESCRIPTION
				"The RF power status."
			::= { sleRfBaseInfo 2 }

		
		sleRfEthertype OBJECT-TYPE
			SYNTAX OCTET STRING
			MAX-ACCESS read-only
			STATUS current
			DESCRIPTION
				"The RF ethertype."
			::= { sleRfBaseInfo 3 }

		
		sleRfSrcAddress OBJECT-TYPE
			SYNTAX OCTET STRING
			MAX-ACCESS read-only
			STATUS current
			DESCRIPTION
				"The RF source address."
			::= { sleRfBaseInfo 4 }

		
		sleRfDesAddress OBJECT-TYPE
			SYNTAX OCTET STRING
			MAX-ACCESS read-only
			STATUS current
			DESCRIPTION
				"The RF destination address."
			::= { sleRfBaseInfo 5 }

		
		sleRfBaseControl OBJECT IDENTIFIER ::= { sleRF 2 }

		
		sleRfBaseControlRequest OBJECT-TYPE
			SYNTAX INTEGER
				{
				setRfEthertype(1),
				resetRfEthertype(2)
				}
			MAX-ACCESS read-write
			STATUS current
			DESCRIPTION
				"The request of a user command."
			::= { sleRfBaseControl 1 }

		
		sleRfBaseControlStatus OBJECT-TYPE
			SYNTAX SleControlStatusType
			MAX-ACCESS read-only
			STATUS current
			DESCRIPTION
				"The status of user command."
			::= { sleRfBaseControl 2 }

		
		sleRfBaseControlTimer OBJECT-TYPE
			SYNTAX Integer32
			MAX-ACCESS read-write
			STATUS current
			DESCRIPTION
				"The maximum time for the manager for a long running user command."
			::= { sleRfBaseControl 3 }

		
		sleRfBaseControlTimeStamp OBJECT-TYPE
			SYNTAX TimeTicks
			MAX-ACCESS read-only
			STATUS current
			DESCRIPTION
				"The time stamp of the last command(end of command)."
			::= { sleRfBaseControl 4 }

		
		sleRfBaseControlReqResult OBJECT-TYPE
			SYNTAX SleControlRequestResultType
			MAX-ACCESS read-only
			STATUS current
			DESCRIPTION
				"The result of user command."
			::= { sleRfBaseControl 5 }

		
		sleRfBaseControlRfEthertype OBJECT-TYPE
			SYNTAX OCTET STRING
			MAX-ACCESS read-write
			STATUS current
			DESCRIPTION
				"The Rf ethertype ,the format is 0xXXXX, default value is 0x8864."
			::= { sleRfBaseControl 6 }

		
		sleRfBaseNotification OBJECT IDENTIFIER ::= { sleRF 3 }

		
		sleRFBaseEthertypeChanged NOTIFICATION-TYPE
			OBJECTS { sleRfBaseControlRequest, sleRfBaseControlTimeStamp, sleRfBaseControlReqResult, sleRfBaseControlRfEthertype }
			STATUS current
			DESCRIPTION 
				"Description."
			::= { sleRfBaseNotification 1 }

		
		sleRFBaseEthertypeResetChanged NOTIFICATION-TYPE
			OBJECTS { sleRfBaseControlRequest, sleRfBaseControlTimeStamp, sleRfBaseControlReqResult, sleRfBaseControlRfEthertype }
			STATUS current
			DESCRIPTION 
				"Description."
			::= { sleRfBaseNotification 2 }

		
		sleRfPortTable OBJECT-TYPE
			SYNTAX SEQUENCE OF SleRfPortEntry
			MAX-ACCESS not-accessible
			STATUS current
			DESCRIPTION
				"Description."
			::= { sleRF 4 }

		
		sleRfPortEntry OBJECT-TYPE
			SYNTAX SleRfPortEntry
			MAX-ACCESS not-accessible
			STATUS current
			DESCRIPTION
				"Description."
			INDEX { sleRfPortIndex }
			::= { sleRfPortTable 1 }

		
		SleRfPortEntry ::=
			SEQUENCE { 
				sleRfPortIndex
					INTEGER,
				sleRfPortAdminStatus
					INTEGER,
				sleRfPortOperStatus
					INTEGER
			 }

		sleRfPortIndex OBJECT-TYPE
			SYNTAX INTEGER (1..256)
			MAX-ACCESS read-write
			STATUS current
			DESCRIPTION
				"The RF port index."
			::= { sleRfPortEntry 1 }

		
		sleRfPortAdminStatus OBJECT-TYPE
			SYNTAX INTEGER
				{
				enable(1),
				disable(2),
				na(255)
				}
			MAX-ACCESS read-write
			STATUS current
			DESCRIPTION
				"The RF port adminStatus."
			::= { sleRfPortEntry 2 }

		
		sleRfPortOperStatus OBJECT-TYPE
			SYNTAX INTEGER
				{
				enable(1),
				disable(2),
				na(255)
				}
			MAX-ACCESS read-write
			STATUS current
			DESCRIPTION
				"The RF port operStatus."
			::= { sleRfPortEntry 3 }

		
		sleRFPortControl OBJECT IDENTIFIER ::= { sleRF 5 }

		
		sleRfPortControlRequest OBJECT-TYPE
			SYNTAX INTEGER { setRfPortStatus(1) }
			MAX-ACCESS read-write
			STATUS current
			DESCRIPTION
				"The request of a user command."
			::= { sleRFPortControl 1 }

		
		sleRfPortControlStatus OBJECT-TYPE
			SYNTAX SleControlStatusType
			MAX-ACCESS read-only
			STATUS current
			DESCRIPTION
				"The status of user command."
			::= { sleRFPortControl 2 }

		
		sleRfPortControlTimer OBJECT-TYPE
			SYNTAX Integer32
			MAX-ACCESS read-write
			STATUS current
			DESCRIPTION
				"The maximum time for the manager for a long running user command."
			::= { sleRFPortControl 3 }

		
		sleRfPortControlTimeStamp OBJECT-TYPE
			SYNTAX TimeTicks
			MAX-ACCESS read-only
			STATUS current
			DESCRIPTION
				"The time stamp of the last command(end of command)."
			::= { sleRFPortControl 4 }

		
		sleRfPortControlReqResult OBJECT-TYPE
			SYNTAX SleControlRequestResultType
			MAX-ACCESS read-only
			STATUS current
			DESCRIPTION
				"The result of user command.
				"
			::= { sleRFPortControl 5 }

		
		sleRfPortControlIndex OBJECT-TYPE
			SYNTAX Integer32 (1..8)
			MAX-ACCESS read-write
			STATUS current
			DESCRIPTION
				"The RF port index <1-8>."
			::= { sleRFPortControl 6 }

		
		sleRfPortControlAdminStatus OBJECT-TYPE
			SYNTAX INTEGER
				{
				enable(1),
				disable(2)
				}
			MAX-ACCESS read-write
			STATUS current
			DESCRIPTION
				"The RF port adminStatus."
			::= { sleRFPortControl 7 }

		
		sleRFPortNotification OBJECT IDENTIFIER ::= { sleRF 6 }

		
		sleRfPortStatusChanged NOTIFICATION-TYPE
			OBJECTS { sleRfPortControlRequest, sleRfPortControlTimeStamp, sleRfPortControlReqResult, sleRfPortControlIndex, sleRfPortControlAdminStatus
				 }
			STATUS current
			DESCRIPTION 
				"Description."
			::= { sleRFPortNotification 1 }

		
		sleEnvironmentMonitor OBJECT IDENTIFIER ::= { sleDevice 13 }

		
		sleEMTable OBJECT-TYPE
			SYNTAX SEQUENCE OF SleEMEntry
			MAX-ACCESS not-accessible
			STATUS current
			DESCRIPTION
				"Description."
			::= { sleEnvironmentMonitor 1 }

		
		sleEMEntry OBJECT-TYPE
			SYNTAX SleEMEntry
			MAX-ACCESS not-accessible
			STATUS current
			DESCRIPTION
				"Description."
			INDEX { sleEMInputIndex }
			::= { sleEMTable 1 }

		
		SleEMEntry ::=
			SEQUENCE { 
				sleEMInputIndex
					Integer32,
				sleEMAlarmString
					OCTET STRING,
				sleEMAlarmSeverity
					INTEGER,
				sleEMmode
					INTEGER
			 }

		sleEMInputIndex OBJECT-TYPE
			SYNTAX Integer32 (1..4)
			MAX-ACCESS read-only
			STATUS current
			DESCRIPTION
				"The environment monitoring input index(1-4)."
			::= { sleEMEntry 1 }

		
		sleEMAlarmString OBJECT-TYPE
			SYNTAX OCTET STRING
			MAX-ACCESS read-only
			STATUS current
			DESCRIPTION
				"The alarm string"
			::= { sleEMEntry 2 }

		
		sleEMAlarmSeverity OBJECT-TYPE
			SYNTAX INTEGER
				{
				none(0),
				critical(1),
				major(2),
				minor(3),
				warning(4),
				intermediate(5)
				}
			MAX-ACCESS read-only
			STATUS current
			DESCRIPTION
				"The alarm severity."
			::= { sleEMEntry 3 }

		
		sleEMmode OBJECT-TYPE
			SYNTAX INTEGER
				{
				normalClose(0),
				normalOpen(1)
				}
			MAX-ACCESS read-only
			STATUS current
			DESCRIPTION
				"The environment monitoring mode.(default:normal-close)"
			::= { sleEMEntry 4 }

		
		sleEMControl OBJECT IDENTIFIER ::= { sleEnvironmentMonitor 2 }

		
		sleEMControlRequest OBJECT-TYPE
			SYNTAX INTEGER
				{
				setEM(1),
				delEM(2)
				}
			MAX-ACCESS read-write
			STATUS current
			DESCRIPTION
				"The request of a user command."
			::= { sleEMControl 1 }

		
		sleEMControlStatus OBJECT-TYPE
			SYNTAX SleControlStatusType
			MAX-ACCESS read-only
			STATUS current
			DESCRIPTION
				"Description."
			::= { sleEMControl 2 }

		
		sleEMControlTimer OBJECT-TYPE
			SYNTAX Gauge32
			MAX-ACCESS read-only
			STATUS current
			DESCRIPTION
				"The maximum time for the manager for a long running user command.
				Apply your setting.
				"
			::= { sleEMControl 3 }

		
		sleEMControlTimeStamp OBJECT-TYPE
			SYNTAX TimeTicks
			MAX-ACCESS read-only
			STATUS current
			DESCRIPTION
				"Description."
			::= { sleEMControl 4 }

		
		sleEMControlReqResult OBJECT-TYPE
			SYNTAX SleControlRequestResultType
			MAX-ACCESS read-only
			STATUS current
			DESCRIPTION
				"Description."
			::= { sleEMControl 5 }

		
		sleEMControlInputIndex OBJECT-TYPE
			SYNTAX Integer32 (1..4)
			MAX-ACCESS read-write
			STATUS current
			DESCRIPTION
				"The environment monitoring input index(1-4)."
			::= { sleEMControl 6 }

		
		sleEMControlAlarmString OBJECT-TYPE
			SYNTAX OCTET STRING
			MAX-ACCESS read-write
			STATUS current
			DESCRIPTION
				"The alarm string"
			::= { sleEMControl 7 }

		
		sleEMControlAlarmSeverity OBJECT-TYPE
			SYNTAX INTEGER
				{
				none(0),
				critical(1),
				major(2),
				minor(3),
				warning(4),
				intermediate(5)
				}
			MAX-ACCESS read-write
			STATUS current
			DESCRIPTION
				"The alarm severity."
			::= { sleEMControl 8 }

		
		sleEMControlmode OBJECT-TYPE
			SYNTAX INTEGER
				{
				normalClose(0),
				normalOpen(1)
				}
			MAX-ACCESS read-write
			STATUS current
			DESCRIPTION
				"The environment monitoring mode.(default:normal-close)"
			::= { sleEMControl 9 }

		
		sleEMNotification OBJECT IDENTIFIER ::= { sleEnvironmentMonitor 3 }

		
		sleEMChanged NOTIFICATION-TYPE
			OBJECTS { sleEMControlRequest, sleEMControlTimeStamp, sleEMControlReqResult, sleEMControlInputIndex, sleEMControlAlarmString, 
				sleEMControlAlarmSeverity, sleEMControlmode }
			STATUS current
			DESCRIPTION 
				"Description."
			::= { sleEMNotification 1 }

		
		sleEMDeleted NOTIFICATION-TYPE
			OBJECTS { sleEMControlRequest, sleEMControlTimeStamp, sleEMControlReqResult, sleEMControlInputIndex }
			STATUS current
			DESCRIPTION 
				"Description."
			::= { sleEMNotification 2 }

		
		sleBypass OBJECT IDENTIFIER ::= { sleDevice 14 }

		
		sleBypassBase OBJECT IDENTIFIER ::= { sleBypass 1 }

		
		sleBypassBaseInfo OBJECT IDENTIFIER ::= { sleBypassBase 1 }

		
		sleBypassMode OBJECT-TYPE
			SYNTAX INTEGER
				{
				on(1),
				off(2),
				auto(3)
				}
			MAX-ACCESS read-only
			STATUS current
			DESCRIPTION
				"optic bypass mode"
			DEFVAL { 2 }
			::= { sleBypassBaseInfo 1 }

		
		sleBypassStatus OBJECT-TYPE
			SYNTAX INTEGER
				{
				enable(1),
				disable(2)
				}
			MAX-ACCESS read-only
			STATUS current
			DESCRIPTION
				"optic bypass status
				"
			::= { sleBypassBaseInfo 2 }

		
		sleBypassBaseControl OBJECT IDENTIFIER ::= { sleBypassBase 2 }

		
		sleBypassBaseControlRequest OBJECT-TYPE
			SYNTAX INTEGER { setBypassMode(1) }
			MAX-ACCESS read-write
			STATUS current
			DESCRIPTION
				"Description."
			::= { sleBypassBaseControl 1 }

		
		sleBypassBaseControlStatus OBJECT-TYPE
			SYNTAX SleControlStatusType
			MAX-ACCESS read-only
			STATUS current
			DESCRIPTION
				"The status of user command."
			::= { sleBypassBaseControl 2 }

		
		sleBypassBaseControlTimer OBJECT-TYPE
			SYNTAX Integer32
			MAX-ACCESS read-write
			STATUS current
			DESCRIPTION
				"The maximum time for the manager for a long running user command."
			::= { sleBypassBaseControl 3 }

		
		sleBypassBaseControlTimeStamp OBJECT-TYPE
			SYNTAX TimeTicks
			MAX-ACCESS read-only
			STATUS current
			DESCRIPTION
				"The time stamp of the last command(end of command)."
			::= { sleBypassBaseControl 4 }

		
		sleBypassBaseControlReqResult OBJECT-TYPE
			SYNTAX SleControlRequestResultType
			MAX-ACCESS read-only
			STATUS current
			DESCRIPTION
				"The result of user command."
			::= { sleBypassBaseControl 5 }

		
		sleBypassBaseControlMode OBJECT-TYPE
			SYNTAX INTEGER
				{
				on(1),
				off(2),
				auto(3)
				}
			MAX-ACCESS read-write
			STATUS current
			DESCRIPTION
				"optic bypass mode"
			::= { sleBypassBaseControl 6 }

		
		sleBypassBaseNotification OBJECT IDENTIFIER ::= { sleBypassBase 3 }

		
		sleBypassModeChanged NOTIFICATION-TYPE
			OBJECTS { sleBypassBaseControlRequest, sleBypassBaseControlTimeStamp, sleBypassBaseControlReqResult, sleBypassBaseControlMode }
			STATUS current
			DESCRIPTION 
				"setBypassMode(1)"
			::= { sleBypassBaseNotification 1 }

		
		sleBypassOption OBJECT IDENTIFIER ::= { sleBypass 2 }

		
		sleBypassOptionConnectivityTable OBJECT-TYPE
			SYNTAX SEQUENCE OF SleBypassOptionConnectivityEntry
			MAX-ACCESS not-accessible
			STATUS current
			DESCRIPTION
				"The connectivity option of bypass"
			::= { sleBypassOption 1 }

		
		sleBypassOptionConnectivityEntry OBJECT-TYPE
			SYNTAX SleBypassOptionConnectivityEntry
			MAX-ACCESS not-accessible
			STATUS current
			DESCRIPTION
				"Description."
			INDEX { sleBypassOptionConnectivityAddress, sleBypassOptionConnectivityPort }
			::= { sleBypassOptionConnectivityTable 1 }

		
		SleBypassOptionConnectivityEntry ::=
			SEQUENCE { 
				sleBypassOptionConnectivityAddress
					IpAddress,
				sleBypassOptionConnectivityPort
					Integer32
			 }

		sleBypassOptionConnectivityAddress OBJECT-TYPE
			SYNTAX IpAddress
			MAX-ACCESS read-only
			STATUS current
			DESCRIPTION
				"The target IP address of bypass health-checking"
			::= { sleBypassOptionConnectivityEntry 1 }

		
		sleBypassOptionConnectivityPort OBJECT-TYPE
			SYNTAX Integer32 (1..65535)
			MAX-ACCESS read-only
			STATUS current
			DESCRIPTION
				"The target port of bypass health-checking."
			::= { sleBypassOptionConnectivityEntry 2 }

		
		sleBypassOptionConnectivityControl OBJECT IDENTIFIER ::= { sleBypassOption 2 }

		
		sleBypassOptionConnectivityControlRequest OBJECT-TYPE
			SYNTAX INTEGER
				{
				setBypassConnectivity(1),
				unsetBypassConnectivity(2)
				}
			MAX-ACCESS read-write
			STATUS current
			DESCRIPTION
				"setBypassConnectivity(1)   : bypass-check-option connectivity (A.B.C.D) PORT
				unsetBypassConnectivity(2) : no bypass-check option connectivity"
			::= { sleBypassOptionConnectivityControl 1 }

		
		sleBypassOptionConnectivityControlStatus OBJECT-TYPE
			SYNTAX SleControlStatusType
			MAX-ACCESS read-only
			STATUS current
			DESCRIPTION
				"The status of user command."
			::= { sleBypassOptionConnectivityControl 2 }

		
		sleBypassOptionConnectivityControlTimer OBJECT-TYPE
			SYNTAX Integer32
			MAX-ACCESS read-write
			STATUS current
			DESCRIPTION
				"The maximum time for the manager for a long running user command."
			::= { sleBypassOptionConnectivityControl 3 }

		
		sleBypassOptionConnectivityControlTimeStamp OBJECT-TYPE
			SYNTAX TimeTicks
			MAX-ACCESS read-only
			STATUS current
			DESCRIPTION
				"The time stamp of the last command(end of command)."
			::= { sleBypassOptionConnectivityControl 4 }

		
		sleBypassOptionConnectivityControlReqResult OBJECT-TYPE
			SYNTAX SleControlRequestResultType
			MAX-ACCESS read-only
			STATUS current
			DESCRIPTION
				"The result of user command."
			::= { sleBypassOptionConnectivityControl 5 }

		
		sleBypassOptionConnectivityControlAddress OBJECT-TYPE
			SYNTAX IpAddress
			MAX-ACCESS read-write
			STATUS current
			DESCRIPTION
				"The target IP address of bypass health-checking"
			::= { sleBypassOptionConnectivityControl 6 }

		
		sleBypassOptionConnectivityControlPort OBJECT-TYPE
			SYNTAX Integer32
			MAX-ACCESS read-write
			STATUS current
			DESCRIPTION
				"he target port of bypass health-checking"
			::= { sleBypassOptionConnectivityControl 7 }

		
		sleBypassOptionConnectivityNotification OBJECT IDENTIFIER ::= { sleBypassOption 3 }

		
		sleBypassOptionConnectivitySet NOTIFICATION-TYPE
			OBJECTS { sleBypassOptionConnectivityControlRequest, sleBypassOptionConnectivityControlTimeStamp, sleBypassOptionConnectivityControlReqResult, sleBypassOptionConnectivityControlAddress, sleBypassOptionConnectivityControlPort
				 }
			STATUS current
			DESCRIPTION 
				"Description."
			::= { sleBypassOptionConnectivityNotification 1 }

		
		sleBypassOptionConnectivityUnset NOTIFICATION-TYPE
			OBJECTS { sleBypassOptionConnectivityControlRequest, sleBypassOptionConnectivityControlTimeStamp, sleBypassOptionConnectivityControlReqResult, sleBypassOptionConnectivityControlAddress, sleBypassOptionConnectivityControlPort
				 }
			STATUS current
			DESCRIPTION 
				"Description."
			::= { sleBypassOptionConnectivityNotification 2 }

		
		sleBypassOptionPingTable OBJECT-TYPE
			SYNTAX SEQUENCE OF SleBypassOptionPingEntry
			MAX-ACCESS not-accessible
			STATUS current
			DESCRIPTION
				"Description."
			::= { sleBypassOption 4 }

		
		sleBypassOptionPingEntry OBJECT-TYPE
			SYNTAX SleBypassOptionPingEntry
			MAX-ACCESS not-accessible
			STATUS current
			DESCRIPTION
				"Description."
			INDEX { sleBypassOptionPingAddress }
			::= { sleBypassOptionPingTable 1 }

		
		SleBypassOptionPingEntry ::=
			SEQUENCE { 
				sleBypassOptionPingAddress
					IpAddress,
				sleBypassOptionPingTransInterval
					Integer32,
				sleBypassOptionPingTranNumber
					Integer32,
				sleBypassOptionPingReqInterval
					Integer32,
				sleBypassOptionPingReqTimeout
					Integer32,
				sleBypassOptionPingLossThresh
					Integer32
			 }

		sleBypassOptionPingAddress OBJECT-TYPE
			SYNTAX IpAddress
			MAX-ACCESS read-only
			STATUS current
			DESCRIPTION
				"The target IP address of bypass ping health checking"
			::= { sleBypassOptionPingEntry 1 }

		
		sleBypassOptionPingTransInterval OBJECT-TYPE
			SYNTAX Integer32
			MAX-ACCESS read-only
			STATUS current
			DESCRIPTION
				"The ping transaction interval"
			::= { sleBypassOptionPingEntry 2 }

		
		sleBypassOptionPingTranNumber OBJECT-TYPE
			SYNTAX Integer32
			MAX-ACCESS read-only
			STATUS current
			DESCRIPTION
				"The ping transaction request number"
			::= { sleBypassOptionPingEntry 3 }

		
		sleBypassOptionPingReqInterval OBJECT-TYPE
			SYNTAX Integer32
			MAX-ACCESS read-only
			STATUS current
			DESCRIPTION
				"The ping request interval"
			::= { sleBypassOptionPingEntry 4 }

		
		sleBypassOptionPingReqTimeout OBJECT-TYPE
			SYNTAX Integer32
			MAX-ACCESS read-only
			STATUS current
			DESCRIPTION
				"The ping request timeout"
			::= { sleBypassOptionPingEntry 5 }

		
		sleBypassOptionPingLossThresh OBJECT-TYPE
			SYNTAX Integer32
			MAX-ACCESS read-only
			STATUS current
			DESCRIPTION
				"The ping loss threshold"
			::= { sleBypassOptionPingEntry 6 }

		
		sleBypassOptionPingControl OBJECT IDENTIFIER ::= { sleBypassOption 5 }

		
		sleBypassOptionPingControlRequest OBJECT-TYPE
			SYNTAX INTEGER
				{
				setBypassPing(1),
				unsetBypassPing(2)
				}
			MAX-ACCESS read-write
			STATUS current
			DESCRIPTION
				"The request of a user command."
			::= { sleBypassOptionPingControl 1 }

		
		sleBypassOptionPingControlStatus OBJECT-TYPE
			SYNTAX SleControlStatusType
			MAX-ACCESS read-only
			STATUS current
			DESCRIPTION
				"The status of user command."
			::= { sleBypassOptionPingControl 2 }

		
		sleBypassOptionPingControlTimer OBJECT-TYPE
			SYNTAX Integer32
			MAX-ACCESS read-write
			STATUS current
			DESCRIPTION
				"The maximum time for the manager for a long running user command."
			::= { sleBypassOptionPingControl 3 }

		
		sleBypassOptionPingControlTimeStamp OBJECT-TYPE
			SYNTAX TimeTicks
			MAX-ACCESS read-only
			STATUS current
			DESCRIPTION
				"The time stamp of the last command(end of command)."
			::= { sleBypassOptionPingControl 4 }

		
		sleBypassOptionPingControlReqResult OBJECT-TYPE
			SYNTAX SleControlRequestResultType
			MAX-ACCESS read-only
			STATUS current
			DESCRIPTION
				"The result of user command."
			::= { sleBypassOptionPingControl 5 }

		
		sleBypassOptionPingControlAddress OBJECT-TYPE
			SYNTAX IpAddress
			MAX-ACCESS read-write
			STATUS current
			DESCRIPTION
				"The target IP address of bypass ping health-checking"
			::= { sleBypassOptionPingControl 6 }

		
		sleBypassOptionPingControlTransInterval OBJECT-TYPE
			SYNTAX Integer32
			MAX-ACCESS read-write
			STATUS current
			DESCRIPTION
				"The ping transaction interval"
			::= { sleBypassOptionPingControl 7 }

		
		sleBypassOptionPingControlTranNumber OBJECT-TYPE
			SYNTAX Integer32
			MAX-ACCESS read-write
			STATUS current
			DESCRIPTION
				"The ping transaction request number"
			::= { sleBypassOptionPingControl 8 }

		
		sleBypassOptionPingControlReqInterval OBJECT-TYPE
			SYNTAX Integer32
			MAX-ACCESS read-write
			STATUS current
			DESCRIPTION
				"The ping request interval"
			::= { sleBypassOptionPingControl 9 }

		
		sleBypassOptionPingControlReqTimeout OBJECT-TYPE
			SYNTAX Integer32
			MAX-ACCESS read-write
			STATUS current
			DESCRIPTION
				"The ping request timeout"
			::= { sleBypassOptionPingControl 10 }

		
		sleBypassOptionPingControlLossThresh OBJECT-TYPE
			SYNTAX Integer32
			MAX-ACCESS read-write
			STATUS current
			DESCRIPTION
				"The ping loss threshold"
			::= { sleBypassOptionPingControl 11 }

		
		sleBypassOptionPingNotification OBJECT IDENTIFIER ::= { sleBypassOption 6 }

		
		sleBypassOptionPingSet NOTIFICATION-TYPE
			OBJECTS { sleBypassOptionPingControlRequest, sleBypassOptionPingControlTimeStamp, sleBypassOptionPingControlReqResult, sleBypassOptionPingControlTranNumber, sleBypassOptionPingControlReqInterval, 
				sleBypassOptionPingControlReqTimeout, sleBypassOptionPingControlLossThresh, sleBypassOptionPingControlAddress, sleBypassOptionPingControlTransInterval }
			STATUS current
			DESCRIPTION 
				"Description."
			::= { sleBypassOptionPingNotification 1 }

		
		sleBypassOptionPingUnset NOTIFICATION-TYPE
			OBJECTS { sleBypassOptionPingControlRequest, sleBypassOptionPingControlTimeStamp, sleBypassOptionPingControlReqResult, sleBypassOptionPingControlAddress }
			STATUS current
			DESCRIPTION 
				"Description."
			::= { sleBypassOptionPingNotification 2 }

		
		sleBypassOptionLinkMonitorTable OBJECT-TYPE
			SYNTAX SEQUENCE OF SleBypassOptionLinkMonitorEntry
			MAX-ACCESS not-accessible
			STATUS current
			DESCRIPTION
				"Description."
			::= { sleBypassOption 7 }

		
		sleBypassOptionLinkMonitorEntry OBJECT-TYPE
			SYNTAX SleBypassOptionLinkMonitorEntry
			MAX-ACCESS not-accessible
			STATUS current
			DESCRIPTION
				"Description."
			INDEX { sleBypassOptionLinkMonitorPort }
			::= { sleBypassOptionLinkMonitorTable 1 }

		
		SleBypassOptionLinkMonitorEntry ::=
			SEQUENCE { 
				sleBypassOptionLinkMonitorPort
					Integer32,
				sleBypassOptionLinkMonitorPortStatus
					INTEGER
			 }

		sleBypassOptionLinkMonitorPort OBJECT-TYPE
			SYNTAX Integer32 (1..65535)
			MAX-ACCESS read-only
			STATUS current
			DESCRIPTION
				"The port of bypass link health-checking"
			::= { sleBypassOptionLinkMonitorEntry 1 }

		
		sleBypassOptionLinkMonitorPortStatus OBJECT-TYPE
			SYNTAX INTEGER { enable(1) }
			MAX-ACCESS read-only
			STATUS current
			DESCRIPTION
				"The port status of bypass link health-checking"
			::= { sleBypassOptionLinkMonitorEntry 2 }

		
		sleBypassOptionLinkMonitorControl OBJECT IDENTIFIER ::= { sleBypassOption 8 }

		
		sleBypassOptionLinkMonitorControlRequest OBJECT-TYPE
			SYNTAX INTEGER { setBypassLinkMonitor(1) }
			MAX-ACCESS read-write
			STATUS current
			DESCRIPTION
				"The request of a user command."
			::= { sleBypassOptionLinkMonitorControl 1 }

		
		sleBypassOptionLinkMonitorControlStatus OBJECT-TYPE
			SYNTAX SleControlStatusType
			MAX-ACCESS read-only
			STATUS current
			DESCRIPTION
				"The status of user command."
			::= { sleBypassOptionLinkMonitorControl 2 }

		
		sleBypassOptionLinkMonitorControlTimer OBJECT-TYPE
			SYNTAX Integer32
			MAX-ACCESS read-write
			STATUS current
			DESCRIPTION
				"The maximum time for the manager for a long running user command."
			::= { sleBypassOptionLinkMonitorControl 3 }

		
		sleBypassOptionLinkMonitorControlTimeStamp OBJECT-TYPE
			SYNTAX TimeTicks
			MAX-ACCESS read-only
			STATUS current
			DESCRIPTION
				"The time stamp of the last command(end of command)."
			::= { sleBypassOptionLinkMonitorControl 4 }

		
		sleBypassOptionLinkMonitorControlReqResult OBJECT-TYPE
			SYNTAX SleControlRequestResultType
			MAX-ACCESS read-only
			STATUS current
			DESCRIPTION
				"The result of user command."
			::= { sleBypassOptionLinkMonitorControl 5 }

		
		sleBypassOptionLinkMonitorControlPort OBJECT-TYPE
			SYNTAX Integer32
			MAX-ACCESS read-write
			STATUS current
			DESCRIPTION
				"The port of bypass link health-checking"
			::= { sleBypassOptionLinkMonitorControl 6 }

		
		sleBypassOptionLinkMonitorControlPortStatus OBJECT-TYPE
			SYNTAX INTEGER
				{
				enable(1),
				disable(2)
				}
			MAX-ACCESS read-write
			STATUS current
			DESCRIPTION
				"The port status of bypass link health-checking"
			::= { sleBypassOptionLinkMonitorControl 7 }

		
		sleBypassOptioLinkMonitorNotification OBJECT IDENTIFIER ::= { sleBypassOption 9 }

		
		sleBypassOptionLinkMonitorChanged NOTIFICATION-TYPE
			OBJECTS { sleBypassOptionLinkMonitorControlRequest, sleBypassOptionLinkMonitorControlStatus, sleBypassOptionLinkMonitorControlTimeStamp, sleBypassOptionLinkMonitorControlReqResult, sleBypassOptionLinkMonitorControlPort, 
				sleBypassOptionLinkMonitorControlPortStatus }
			STATUS current
			DESCRIPTION 
				"Description."
			::= { sleBypassOptioLinkMonitorNotification 1 }

		
		sleHFC OBJECT IDENTIFIER ::= { sleDevice 15 }

		
		sleHFCTable OBJECT-TYPE
			SYNTAX SEQUENCE OF SleHFCEntry
			MAX-ACCESS not-accessible
			STATUS current
			DESCRIPTION
				"Description."
			::= { sleHFC 1 }

		
		sleHFCEntry OBJECT-TYPE
			SYNTAX SleHFCEntry
			MAX-ACCESS not-accessible
			STATUS current
			DESCRIPTION
				"Description."
			INDEX { sleHFCOptic1550OTX }
			::= { sleHFCTable 1 }

		
		SleHFCEntry ::=
			SEQUENCE { 
				sleHFCOptic1550OTX
					OCTET STRING,
				sleHFCOptic1550OTXAlarm
					INTEGER,
				sleHFCOpticUpstreamOTX
					OCTET STRING,
				sleHFCOpticUpstreamOTXAlarm
					INTEGER,
				sleHFCOpticDownstreamORX
					OCTET STRING,
				sleHFCOpticDownstreamORXAlarm
					INTEGER,
				sleHFCEDFA1OTX
					OCTET STRING,
				sleHFCEDFA1OTXAlarm
					INTEGER,
				sleHFCEDFA1ORX
					OCTET STRING,
				sleHFCEDFA1ORXAlarm
					INTEGER,
				sleHFCEDFA1LD1Current
					OCTET STRING,
				sleHFCEDFA1LD1CurrentAlarm
					INTEGER,
				sleHFCEDFA1LD2Current
					OCTET STRING,
				sleHFCEDFA1LD2CurrentAlarm
					INTEGER,
				sleHFCEDFA1LD1Temp
					OCTET STRING,
				sleHFCEDFA1LD1TempAlarm
					INTEGER,
				sleHFCEDFA1LD2Temp
					OCTET STRING,
				sleHFCEDFA1LD2TempAlarm
					INTEGER,
				sleHFCEDFA1CaseTemp
					OCTET STRING,
				sleHFCEDFA1CaseTempAlarm
					INTEGER,
				sleHFCEDFA2OTX
					OCTET STRING,
				sleHFCEDFA2OTXAarm
					INTEGER,
				sleHFCEDFA2ORX
					OCTET STRING,
				sleHFCEDFA2ORXAlarm
					INTEGER,
				sleHFCEDFA2LD1Current
					OCTET STRING,
				sleHFCEDFA2LD1CurrentAlarm
					INTEGER,
				sleHFCEDFA2LD2Current
					OCTET STRING,
				sleHFCEDFA2LD2CurrentAlarm
					INTEGER,
				sleHFCEDFA2LD1Temp
					OCTET STRING,
				sleHFCEDFA2LD1TempAlarm
					INTEGER,
				sleHFCEDFA2LD2Temp
					OCTET STRING,
				sleHFCEDFA2LD2TempAlarm
					INTEGER,
				sleHFCEDFA2CaseTemp
					OCTET STRING,
				sleHFCEDFA2CaseTempAlarm
					INTEGER
			 }

		sleHFCOptic1550OTX OBJECT-TYPE
			SYNTAX OCTET STRING
			MAX-ACCESS read-only
			STATUS current
			DESCRIPTION
				"HFC Optic 1550 OTX value."
			::= { sleHFCEntry 1 }

		
		sleHFCOptic1550OTXAlarm OBJECT-TYPE
			SYNTAX INTEGER
				{
				off(0),
				on(1)
				}
			MAX-ACCESS read-only
			STATUS current
			DESCRIPTION
				"HFC Optic 1550 OTX alarm status."
			::= { sleHFCEntry 2 }

		
		sleHFCOpticUpstreamOTX OBJECT-TYPE
			SYNTAX OCTET STRING
			MAX-ACCESS read-only
			STATUS current
			DESCRIPTION
				"HFC Optic Upstream OTX value."
			::= { sleHFCEntry 3 }

		
		sleHFCOpticUpstreamOTXAlarm OBJECT-TYPE
			SYNTAX INTEGER
				{
				off(0),
				on(1)
				}
			MAX-ACCESS read-only
			STATUS current
			DESCRIPTION
				"HFC Optic Upstream OTX alarm status."
			::= { sleHFCEntry 4 }

		
		sleHFCOpticDownstreamORX OBJECT-TYPE
			SYNTAX OCTET STRING
			MAX-ACCESS read-only
			STATUS current
			DESCRIPTION
				"HFC Optic Downstream ORX value."
			::= { sleHFCEntry 5 }

		
		sleHFCOpticDownstreamORXAlarm OBJECT-TYPE
			SYNTAX INTEGER
				{
				off(0),
				on(1)
				}
			MAX-ACCESS read-only
			STATUS current
			DESCRIPTION
				"HFC Optic Downstream ORX alarm status."
			::= { sleHFCEntry 6 }

		
		sleHFCEDFA1OTX OBJECT-TYPE
			SYNTAX OCTET STRING
			MAX-ACCESS read-only
			STATUS current
			DESCRIPTION
				"HFC EDFA1 OTX value."
			::= { sleHFCEntry 7 }

		
		sleHFCEDFA1OTXAlarm OBJECT-TYPE
			SYNTAX INTEGER
				{
				off(0),
				on(1)
				}
			MAX-ACCESS read-only
			STATUS current
			DESCRIPTION
				"HFC EDFA1 OTX alarm status."
			::= { sleHFCEntry 8 }

		
		sleHFCEDFA1ORX OBJECT-TYPE
			SYNTAX OCTET STRING
			MAX-ACCESS read-only
			STATUS current
			DESCRIPTION
				"HFC EDFA1 ORX value."
			::= { sleHFCEntry 9 }

		
		sleHFCEDFA1ORXAlarm OBJECT-TYPE
			SYNTAX INTEGER
				{
				off(0),
				on(1)
				}
			MAX-ACCESS read-only
			STATUS current
			DESCRIPTION
				"HFC EDFA1 ORX alarm status."
			::= { sleHFCEntry 10 }

		
		sleHFCEDFA1LD1Current OBJECT-TYPE
			SYNTAX OCTET STRING
			MAX-ACCESS read-only
			STATUS current
			DESCRIPTION
				"HFC EDFA1 LD1 Current value."
			::= { sleHFCEntry 11 }

		
		sleHFCEDFA1LD1CurrentAlarm OBJECT-TYPE
			SYNTAX INTEGER
				{
				off(0),
				on(1)
				}
			MAX-ACCESS read-only
			STATUS current
			DESCRIPTION
				"HFC EDFA1 LD1 Current alarm status."
			::= { sleHFCEntry 12 }

		
		sleHFCEDFA1LD2Current OBJECT-TYPE
			SYNTAX OCTET STRING
			MAX-ACCESS read-only
			STATUS current
			DESCRIPTION
				"HFC EDFA1 LD2 Current value."
			::= { sleHFCEntry 13 }

		
		sleHFCEDFA1LD2CurrentAlarm OBJECT-TYPE
			SYNTAX INTEGER
				{
				off(0),
				on(1)
				}
			MAX-ACCESS read-only
			STATUS current
			DESCRIPTION
				"HFC EDFA1 LD2 Current alarm status."
			::= { sleHFCEntry 14 }

		
		sleHFCEDFA1LD1Temp OBJECT-TYPE
			SYNTAX OCTET STRING
			MAX-ACCESS read-only
			STATUS current
			DESCRIPTION
				"HFC EDFA1 LD1 Temp value."
			::= { sleHFCEntry 15 }

		
		sleHFCEDFA1LD1TempAlarm OBJECT-TYPE
			SYNTAX INTEGER
				{
				off(0),
				on(1)
				}
			MAX-ACCESS read-only
			STATUS current
			DESCRIPTION
				"HFC EDFA1 LD1 Temp alarm status."
			::= { sleHFCEntry 16 }

		
		sleHFCEDFA1LD2Temp OBJECT-TYPE
			SYNTAX OCTET STRING
			MAX-ACCESS read-only
			STATUS current
			DESCRIPTION
				"HFC EDFA1 LD2 Temp value."
			::= { sleHFCEntry 17 }

		
		sleHFCEDFA1LD2TempAlarm OBJECT-TYPE
			SYNTAX INTEGER
				{
				off(0),
				on(1)
				}
			MAX-ACCESS read-only
			STATUS current
			DESCRIPTION
				"HFC EDFA1 LD2 Temp alarm status."
			::= { sleHFCEntry 18 }

		
		sleHFCEDFA1CaseTemp OBJECT-TYPE
			SYNTAX OCTET STRING
			MAX-ACCESS read-only
			STATUS current
			DESCRIPTION
				"HFC EDFA1 Case Temp value."
			::= { sleHFCEntry 19 }

		
		sleHFCEDFA1CaseTempAlarm OBJECT-TYPE
			SYNTAX INTEGER
				{
				off(0),
				on(1)
				}
			MAX-ACCESS read-only
			STATUS current
			DESCRIPTION
				"HFC EDFA1 Case Temp alarm status."
			::= { sleHFCEntry 20 }

		
		sleHFCEDFA2OTX OBJECT-TYPE
			SYNTAX OCTET STRING
			MAX-ACCESS read-only
			STATUS current
			DESCRIPTION
				"HFC EDFA2 OTX value."
			::= { sleHFCEntry 21 }

		
		sleHFCEDFA2OTXAarm OBJECT-TYPE
			SYNTAX INTEGER
				{
				off(0),
				on(1)
				}
			MAX-ACCESS read-only
			STATUS current
			DESCRIPTION
				"HFC EDFA2 OTX alarm status."
			::= { sleHFCEntry 22 }

		
		sleHFCEDFA2ORX OBJECT-TYPE
			SYNTAX OCTET STRING
			MAX-ACCESS read-only
			STATUS current
			DESCRIPTION
				"HFC EDFA2 ORX value."
			::= { sleHFCEntry 23 }

		
		sleHFCEDFA2ORXAlarm OBJECT-TYPE
			SYNTAX INTEGER
				{
				off(0),
				on(1)
				}
			MAX-ACCESS read-only
			STATUS current
			DESCRIPTION
				"HFC EDFA2 ORX alarm status."
			::= { sleHFCEntry 24 }

		
		sleHFCEDFA2LD1Current OBJECT-TYPE
			SYNTAX OCTET STRING
			MAX-ACCESS read-only
			STATUS current
			DESCRIPTION
				"HFC EDFA2 LD1 Current value."
			::= { sleHFCEntry 25 }

		
		sleHFCEDFA2LD1CurrentAlarm OBJECT-TYPE
			SYNTAX INTEGER
				{
				off(0),
				on(1)
				}
			MAX-ACCESS read-only
			STATUS current
			DESCRIPTION
				"HFC EDFA2 LD1 Current alarm status."
			::= { sleHFCEntry 26 }

		
		sleHFCEDFA2LD2Current OBJECT-TYPE
			SYNTAX OCTET STRING
			MAX-ACCESS read-only
			STATUS current
			DESCRIPTION
				"HFC EDFA2 LD2 Current value."
			::= { sleHFCEntry 27 }

		
		sleHFCEDFA2LD2CurrentAlarm OBJECT-TYPE
			SYNTAX INTEGER
				{
				off(0),
				on(1)
				}
			MAX-ACCESS read-only
			STATUS current
			DESCRIPTION
				"HFC EDFA2 LD2 Current alarm status."
			::= { sleHFCEntry 28 }

		
		sleHFCEDFA2LD1Temp OBJECT-TYPE
			SYNTAX OCTET STRING
			MAX-ACCESS read-only
			STATUS current
			DESCRIPTION
				"HFC EDFA2 LD1 Temp value."
			::= { sleHFCEntry 29 }

		
		sleHFCEDFA2LD1TempAlarm OBJECT-TYPE
			SYNTAX INTEGER
				{
				off(0),
				on(1)
				}
			MAX-ACCESS read-only
			STATUS current
			DESCRIPTION
				"HFC EDFA2 LD1 Temp alarm status."
			::= { sleHFCEntry 30 }

		
		sleHFCEDFA2LD2Temp OBJECT-TYPE
			SYNTAX OCTET STRING
			MAX-ACCESS read-only
			STATUS current
			DESCRIPTION
				"HFC EDFA2 LD2 Temp value."
			::= { sleHFCEntry 31 }

		
		sleHFCEDFA2LD2TempAlarm OBJECT-TYPE
			SYNTAX INTEGER
				{
				off(0),
				on(1)
				}
			MAX-ACCESS read-only
			STATUS current
			DESCRIPTION
				"HFC EDFA2 LD2 Temp alarm status."
			::= { sleHFCEntry 32 }

		
		sleHFCEDFA2CaseTemp OBJECT-TYPE
			SYNTAX OCTET STRING
			MAX-ACCESS read-only
			STATUS current
			DESCRIPTION
				"HFC EDFA2 Case Temp value."
			::= { sleHFCEntry 33 }

		
		sleHFCEDFA2CaseTempAlarm OBJECT-TYPE
			SYNTAX INTEGER
				{
				off(0),
				on(1)
				}
			MAX-ACCESS read-only
			STATUS current
			DESCRIPTION
				"HFC EDFA2 Case Temp alarm status."
			::= { sleHFCEntry 34 }

		
		sleHFCControl OBJECT IDENTIFIER ::= { sleHFC 2 }

		
		sleHFCControlRequest OBJECT-TYPE
			SYNTAX INTEGER { setHFCAlarmStatus(1) }
			MAX-ACCESS read-write
			STATUS current
			DESCRIPTION
				"The request of a user command"
			::= { sleHFCControl 1 }

		
		sleHFCControlStatus OBJECT-TYPE
			SYNTAX SleControlStatusType
			MAX-ACCESS read-only
			STATUS current
			DESCRIPTION
				"The status of user command"
			::= { sleHFCControl 2 }

		
		sleHFCControlTimer OBJECT-TYPE
			SYNTAX Gauge32
			MAX-ACCESS read-write
			STATUS current
			DESCRIPTION
				"The maximum time for the manager for a long running user command."
			::= { sleHFCControl 3 }

		
		sleHFCControlTimeStamp OBJECT-TYPE
			SYNTAX TimeTicks
			MAX-ACCESS read-only
			STATUS current
			DESCRIPTION
				"The time stamp of the last command(end of command)"
			::= { sleHFCControl 4 }

		
		sleHFCControlReqResult OBJECT-TYPE
			SYNTAX SleControlRequestResultType
			MAX-ACCESS read-only
			STATUS current
			DESCRIPTION
				"The result of the last user command"
			::= { sleHFCControl 5 }

		
		sleHFCControlAlarmIndex OBJECT-TYPE
			SYNTAX INTEGER
				{
				hfcefda1(0),
				hfcefda2(1),
				hfcoptic(2)
				}
			MAX-ACCESS read-write
			STATUS current
			DESCRIPTION
				"The HFC alarm index , edfa1 /edfa2 /optic ."
			::= { sleHFCControl 6 }

		
		sleHFCControlAlarmStatus OBJECT-TYPE
			SYNTAX INTEGER
				{
				disable(0),
				enable(1)
				}
			MAX-ACCESS read-write
			STATUS current
			DESCRIPTION
				"The HFC alrm status."
			::= { sleHFCControl 7 }

		
		sleHFCNotification OBJECT IDENTIFIER ::= { sleHFC 3 }

		
		sleHFCOpticAlarmStatusChanged NOTIFICATION-TYPE
			OBJECTS { sleHFCControlRequest, sleHFCControlTimeStamp, sleHFCControlReqResult, sleHFCControlAlarmIndex, sleHFCControlAlarmStatus
				 }
			STATUS current
			DESCRIPTION 
				"HFC Alarm Status Changed."
			::= { sleHFCNotification 1 }

		
		sleDeviceGroup OBJECT-GROUP
			OBJECTS { sleRfConnectStatus, sleRfPortIndex, sleRfPortAdminStatus, sleRfPortOperStatus, sleDeviceEthernetPortNum, 
				sleDevicePowerNum, sleDeviceFanModuleNum, sleDeviceTemperatureNum, sleDeviceFanStartTemperature, sleDeviceFanStopTemperature, 
				sleDeviceControlRequest, sleDeviceControlStatus, sleDeviceControlTimer, sleDeviceControlTimeStamp, sleDeviceControlReqResult, 
				sleDeviceControlFanStartTemperature, sleDeviceControlFanStopTemperature, sleEthernetPortIndex, sleEthernetPortPhyIndex, sleEthernetPortType, 
				sleEthernetPortAdminStatus, sleEthernetPortOperStatus, sleEthernetPortTransmissionRate, sleEthernetPortDuplexMode, sleEthernetPortFlowControl, 
				sleEthernetPortNegotiationMode, sleEthernetPortJumboFrameSize, sleEthernetPortSfpTransceiver, sleEthernetPortSfpVendorName, sleEthernetPortSfpVendorPartNumber, 
				sleEthernetPortSfpVendorRevision, sleEthernetPortSfpVendorSerialNumber, sleEthernetPortSfpDateCode, sleEthernetPortPhysicalRemoteChassis, sleEthernetPortPhysicalRemoteSlot, 
				sleEthernetPortPhysicalRemotePort, sleEthernetPortPhysicalLinkDiscoveryMode, sleEthernetPortControlRequest, sleEthernetPortControlStatus, sleEthernetPortControlTimer, 
				sleEthernetPortControlTimeStamp, sleEthernetPortControlReqResult, sleEthernetPortControlIndex, sleEthernetPortControlType, sleEthernetPortControlAdminStatus, 
				sleEthernetPortControlTransmissionRate, sleEthernetPortControlDuplexMode, sleEthernetPortControlFlowControl, sleEthernetPortControlJumboFrameSize, sleEthernetPortControlPhysicalRemoteChassis, 
				sleEthernetPortControlPhysicalRemoteSlot, sleEthernetPortControlPhysicalRemotePort, sleEthernetPortControlPhysicalLinkDiscoveryMode, slePowerIndex, slePowerPhyIndex, 
				slePowerState, sleFanModuleIndex, sleFanModulePhyIndex, sleFanModuleUnitNum, sleFanModuleAdminState, 
				sleFanModuleControlRequest, sleFanModuleControlStatus, sleFanModuleControlTimer, sleFanModuleControlTimeStamp, sleFanModuleControlReqResult, 
				sleFanModuleControlIndex, sleFanModuleControlAdminState, sleFanUnitIndex, sleFanUnitOperState, sleTemperatureIndex, 
				sleTemperatureState, sleTemperatureValue, sleBatteryIndex, sleDoorStatus, sleOperationPowerType, 
				sleOperationPowerInfo, slePSUACPowerState, slePSUTemperture, slePSUOutVoltage, slePSUOverTemp, 
				slePSUFirmwareVer, sleRBUEquipState, sleRBUModeStaus, sleBatteryBackupFile, sleBatteryBackupControlRequest, 
				sleBatteryBackupControlStatus, sleBatteryBackupControlTimer, sleBatteryBackupControlTimeStamp, sleBatteryBackupControlReqResult, sleBatteryBackupControlServerIP, 
				sleBatteryBackupControlUserID, sleBatteryBackupControlPassword, sleBatteryBackupControlFlag, sleBatteryBackupControlLocalFile, sleBatteryBackupControlRemoteFile, 
				sleCpuProcessor, sleCpuModel, sleCpuRevision, sleCpuBogomips, sleCpuManufacturer, 
				sleCpuClock, sleCpuBusClock, sleRBUTemperature1, slePSUTempThreshold, sleRBUTemperature2, 
				sleRBUOutVoltage, sleRBUChargeCurrent, sleRBURemainCapacity, sleRBUOverTemp, sleBatteryLow, 
				sleRBUBTStatus, sleRBUBTThreshold, sleRBURechargeVoltage, sleBatteryCellStatus, sleBPSUACHardwareVer, 
				sleBatteryControlRequest, sleBatteryControlStatus, sleBatteryControlTimer, sleBatteryControlTimeStamp, sleBatteryControlReqResult, 
				sleBatteryControlRBUBTStatus, sleBatteryControlRBUBTThreshold, sleBatteryControlRBURechargeVoltage, sleBatteryControlTemperThresh1, sleBatteryControlTemperThresh2, 
				sleRBUTempHighThreshold, slePowerType, sleClockModuleIndex, sleClockModuleBoardId, sleClockModuleInstallStatus, 
				sleClockModuleInitStatus, sleSlotSystemIndex, sleSlotSystemUptime, sleSlotSystemModelName, sleSlotSystemSerialNumber, 
				sleSlotSystemHWVersion, sleSlotSystemBLVersion, sleSlotSystemSWCompatibility, sleSlotSystemOSVersion, sleSlotSystemMacAddress, 
				sleSlotSystemCPULoadAll, sleSlotSystemCPULoadInterrupt, sleSlotSystemMemoryTotal, sleSlotSystemMemoryFree, sleSlotSystemMemoryShared, 
				sleSlotSystemMemoryBuffers, sleSlotSystemMemoryCached, sleSlotSystemMemorySwapTotal, sleSlotSystemMemorySwapFree, sleSlotSystemBootReason, 
				sleSlotSystemBootTime, sleSlotSystemVoltage, sleSlotSystemControlRequest, sleSlotSystemControlStatus, sleSlotSystemControlTimer, 
				sleSlotSystemControlTimeStamp, sleSlotSystemControlReqResult, sleSlotSystemControlSlotIndex, sleSlotStatusPlan, sleSlotStatusPlanCardType, 
				sleSlotStatusCurrentInstall, sleSlotStatusCurrentInstallCardType, sleSlotStatusCardOperation, sleSlotStatusLock, sleSlotStatusUpgradeMode, 
				sleSlotStatusActionEvent, sleSlotStatusState, sleSlotStatusControlRequest, sleSlotStatusControlStatus, sleSlotStatusControlTimer, 
				sleSlotStatusControlTimeStamp, sleSlotStatusControlReqResult, sleSlotStatusControlSlotIndex, sleSlotStatusControlPlanCardType, sleSlotStatusControlUpgradeMode, 
				sleSlotNosVersion, sleSlotNosRevision, sleSlotNosSize, sleSlotNosUpgradeStatus, sleSlotNosControlRequest, 
				sleSlotNosControlStatus, sleSlotNosControlTimer, sleSlotNosControlTimeStamp, sleSlotNosControlReqResult, sleSlotNosControlSlotIndex, 
				sleSlotReleasedNIUNosVersion, sleSlotReleasedNIUNosRevision, sleSlotReleasedNIUNosSize, sleSlotReleasedGPIUNosVersion, sleSlotReleasedGPIUNosRevision, 
				sleSlotReleasedGPIUNosSize, sleSlotSystemPowerLevelStatus, sleSlotPowerMonStatus, sleSlotPowerMonVoltage, sleEthernetPortDMIIndex, 
				sleEthernetPortDMITemper, sleEthernetPortDMIVoltage, sleEthernetPortDMITxBias, sleEthernetPortDMITxPower, sleEthernetPortDMIRxPower, 
				sleEthernetPortSfpTransceiverType, sleSlotNosControlUpDownMethod, sleSlotNosControlUpDownFlag, sleSlotNosControlServerAddress, sleSlotNosControlUserID, 
				sleSlotNosControlPassword, sleSlotNosControlFileName, sleFanUnitSpeed, sleSlotSystemInfoLEDStatus, sleFanModuleSpeedThreshold, 
				sleFanModuleControlSpeedThreshold, sleEthernetPortSfpTransceiverDetailType, sleClockModuleOPMode, sleClockInfoInSrcType, sleClockInfoInSrcAISStatus, 
				sleClockInfoInSrcLoSStatus, sleClockInfoInSrcLDSCStatus, sleClockInfoInSrcNtrClockType, sleDeviceJumboFrameStatus, sleDeviceControlJumboFrameStatus, 
				slePowerPSUType, sleSlotSystemInfoPackageVersion, sleEthernetSfpIndex, sleEthernetSfpTransceiver, sleEthernetSfpVendorName, 
				sleEthernetSfpVendorPartNumber, sleEthernetSfpDateCode, sleEthernetSfpTransceiverType, sleEthernetSfpTransceiverDetailType, sleTemperatureHighThreshold, 
				sleTemperatureLowThreshold, sleTemperatureControlRequest, sleTemperatureControlStatus, sleTemperatureControlTimer, sleTemperatureControlTimeStamp, 
				sleTemperatureControlReqResult, sleTemperatureControlIndex, sleTemperatureControlHighThreshold, sleTemperatureControlLowThreshold, sleEthernetSFPControlRequest, 
				sleEthernetSFPControlStatus, sleEthernetSFPControlTimer, sleEthernetSFPControlTimeStamp, sleEthernetSFPControlReqResult, sleEthernetSFPControlIndex, 
				sleTemperatureWarnHighThreshold, sleTemperatureWarnLowThreshold, sleTemperatureWarnDuration, sleTemperatureAlarmHighThreshold, sleTemperatureAlarmLowThreshold, 
				sleTemperatureAlarmDuration, sleTemperatureControlDuration, sleSlotPowerMonIndex, sleEthernetPortSlotIndex, sleEthernetPortSlotPortIndex, 
				sleEthernetSfpVendorRevision, sleEthernetSfpVendorSerialNumber, sleEthernetSfpTransceiverCodes, sleSlotNosStbVersion, sleSlotNosStbRevision, 
				sleSlotNosStbSize, sleDeviceEnvironmentMonitoringStatus, sleDeviceControlEnvironmentMonitoringStatus, sleRfPowerStatus, sleSlotAiuRunStatus, 
				sleSlotAiuAlarmStatus, sleEthernetPortAdminTransmissionRate, sleEthernetPortAdminDuplexMode, sleEthernetPortAdminFlowControl, sleEthernetPortAdminNegotiationMode, 
				sleSlotReleasedSIUNosVersion, sleSlotReleasedSIUNosRevision, sleSlotReleasedSIUNosSize, sleEMInputIndex, sleEMAlarmString, 
				sleEMAlarmSeverity, sleEMmode, sleEMControlRequest, sleEMControlStatus, sleEMControlInputIndex, 
				sleEMControlAlarmString, sleEMControlAlarmSeverity, sleEMControlmode, sleEthernetSfpSpeed, sleEthernetSfpLength, 
				sleEthernetSfpWaveLength, sleRfEthertype, sleRfSrcAddress, sleRfDesAddress, sleRBUTempLowThreshold, 
				sleEthernetPortControlNegotiationMode, sleSlotStatusPower, sleSlotStatusSerialNumber, sleEMControlTimer, sleEMControlTimeStamp, 
				sleEthernetPortAdminReason, sleEMControlReqResult, sleRfBaseControlRequest, sleRfBaseControlStatus, sleRfBaseControlTimer, 
				sleRfBaseControlTimeStamp, sleRfBaseControlReqResult, sleRfBaseControlRfEthertype, sleRfPortControlRequest, sleRfPortControlStatus, 
				sleRfPortControlTimer, sleRfPortControlTimeStamp, sleRfPortControlReqResult, sleRfPortControlIndex, sleBypassMode, 
				sleBypassStatus, sleBypassBaseControlRequest, sleBypassBaseControlStatus, sleBypassBaseControlTimer, sleBypassBaseControlTimeStamp, 
				sleBypassBaseControlReqResult, sleBypassBaseControlMode, sleBypassOptionConnectivityAddress, sleBypassOptionConnectivityPort, sleBypassOptionConnectivityControlRequest, 
				sleBypassOptionConnectivityControlStatus, sleBypassOptionConnectivityControlTimer, sleBypassOptionConnectivityControlTimeStamp, sleBypassOptionConnectivityControlReqResult, sleBypassOptionConnectivityControlAddress, 
				sleBypassOptionConnectivityControlPort, sleBypassOptionPingAddress, sleBypassOptionPingTransInterval, sleBypassOptionPingTranNumber, sleBypassOptionPingReqInterval, 
				sleBypassOptionPingReqTimeout, sleBypassOptionPingLossThresh, sleBypassOptionPingControlRequest, sleBypassOptionPingControlStatus, sleBypassOptionPingControlTimer, 
				sleBypassOptionPingControlTimeStamp, sleBypassOptionPingControlReqResult, sleBypassOptionPingControlAddress, sleBypassOptionPingControlTransInterval, sleBypassOptionPingControlTranNumber, 
				sleBypassOptionPingControlReqInterval, sleBypassOptionPingControlReqTimeout, sleBypassOptionPingControlLossThresh, sleBypassOptionLinkMonitorPort, sleBypassOptionLinkMonitorPortStatus, 
				sleBypassOptionLinkMonitorControlRequest, sleBypassOptionLinkMonitorControlStatus, sleBypassOptionLinkMonitorControlTimer, sleBypassOptionLinkMonitorControlTimeStamp, sleBypassOptionLinkMonitorControlReqResult, 
				sleBypassOptionLinkMonitorControlPort, sleBypassOptionLinkMonitorControlPortStatus, sleSlotSystemInfoManufacturer, sleSlotSystemInfoManufactureDate, sleSlotStatusHealthState, 
				sleRfPortControlAdminStatus, sleClockInfoInSrcStatus, sleEthernetSfpMultimodeLengthOm1, sleEthernetSfpMultimodeLengthOm2, sleEthernetSfpTransceiverDetailTypeStr, 
				sleEthernetSfpTransceiverLengthStr, sleEthernetSfpWaveLengthStr, sleEthernetSfpConnectorType, sleSlotReleasedIU10GE8NosVersion, sleSlotReleasedIU10GE8NosRevision, 
				sleSlotReleasedIU10GE8NosSize, sleSlotReleasedIU10GEPON8NosVersion, sleSlotReleasedIU10GEPON8NosRevision, sleSlotReleasedIU10GEPON8NosSize, sleSlotReleasedIUGEPON8NosVersion, 
				sleSlotReleasedIUGEPON8NosRevision, sleSlotReleasedIUGEPON8NosSize, sleEthernetSfpMultimodeLengthOm3, sleSlotProtectionSystemStatus, sleSlotProtectionSystemThreshold, 
				sleSlotProtectionControlRequest, sleSlotProtectionControlStatus, sleSlotProtectionControlTimer, sleSlotProtectionControlTimeStamp, sleSlotProtectionControlReqResult, 
				sleSlotProtectionControlSystemStatus, sleSlotProtectionControlSystemThreshold, sleSlotProtectionIUControlRequest, sleSlotProtectionIUControlStatus, sleSlotProtectionIUControlTimer, 
				sleSlotProtectionIUControlTimeStamp, sleSlotProtectionIUControlReqResult, sleSlotProtectionIUControlTemperHighThresh, sleSlotProtectionIUControlTemperLowThresh, sleSlotProtectionIUControlPowerThresh, 
				sleSlotProtectionIUTemperHighThresh, sleSlotProtectionIUTemperLowThresh, sleSlotProtectionIUPowerStatus, sleSlotProtectionIUPowerThresh, sleSlotProtectionIUTemper, 
				sleHFCOptic1550OTX, sleHFCOptic1550OTXAlarm, sleHFCOpticUpstreamOTX, sleHFCOpticUpstreamOTXAlarm, sleHFCOpticDownstreamORX, 
				sleHFCOpticDownstreamORXAlarm, sleHFCEDFA1OTX, sleHFCEDFA1OTXAlarm, sleHFCEDFA1ORX, sleHFCEDFA1ORXAlarm, 
				sleHFCEDFA1LD1Current, sleHFCEDFA1LD1CurrentAlarm, sleHFCEDFA1LD2Current, sleHFCEDFA1LD2CurrentAlarm, sleHFCEDFA1LD1Temp, 
				sleHFCEDFA1LD1TempAlarm, sleHFCEDFA1LD2Temp, sleHFCEDFA1LD2TempAlarm, sleHFCEDFA1CaseTemp, sleHFCEDFA1CaseTempAlarm, 
				sleHFCEDFA2OTX, sleHFCEDFA2OTXAarm, sleHFCEDFA2ORX, sleHFCEDFA2ORXAlarm, sleHFCEDFA2LD1Current, 
				sleHFCEDFA2LD1CurrentAlarm, sleHFCEDFA2LD2Current, sleHFCEDFA2LD2CurrentAlarm, sleHFCEDFA2LD1Temp, sleHFCEDFA2LD1TempAlarm, 
				sleHFCEDFA2LD2Temp, sleHFCEDFA2LD2TempAlarm, sleHFCEDFA2CaseTemp, sleHFCEDFA2CaseTempAlarm, sleHFCControlRequest, 
				sleHFCControlStatus, sleHFCControlTimer, sleHFCControlTimeStamp, sleHFCControlReqResult, sleHFCControlAlarmIndex, 
				sleHFCControlAlarmStatus, sleSlotSystemCPULoadHighThreshold, sleSlotSystemCPULoadHighThresholdTimer, sleSlotSystemCPULoadLowThreshold, sleSlotSystemCPULoadLowThresholdTimer, 
				sleSlotProtectionIUControlindex, sleSlotSystemCPULoadCurrent, sleEthernetPortLinkCheckTimer, sleEthernetPortLinkDebounceTime, sleEthernetPortCpuStatisticsLimitUnicast, 
				sleEthernetPortCpuStatisticsLimitMulticast, sleEthernetPortCpuStatisticsLimitBroadcast, sleEthernetPortFloodBlockBroadcastState, sleEthernetPortFloodBlockDlfState, sleEthernetPortControlLinkCheckTimer, 
				sleEthernetPortControlLinkDebounceTime, sleEthernetPortControlCpuStatisticsLimitUnicast, sleEthernetPortControlCpuStatisticsLimitMulticast, sleEthernetPortControlCpuStatisticsLimitBroadcast, sleEthernetPortControlFloodBlockBroadcastState, 
				sleEthernetPortControlFloodBlockDlfState, sleEthernetSfpDdmState, sleEthernetSfpNegoState, sleEthernetSfpControlDdmState, sleEthernetSFPThresholdIfIndex, 
				sleEthernetSFPThresholdType, sleEthernetSFPThresholdSfpLow, sleEthernetSFPThresholdSfpHigh, sleEthernetSFPThresholdSystemLow, sleEthernetSFPThresholdSystemHigh, 
				sleEthernetSFPThresholdControlRequest, sleEthernetSFPThresholdControlStatus, sleEthernetSFPThresholdControlTimer, sleEthernetSFPThresholdControlTimeStamp, sleEthernetSFPThresholdControlReqResult, 
				sleEthernetSFPThresholdControlIfIndex, sleEthernetSFPThresholdControlType, sleEthernetSFPThresholdControlSfpLow, sleEthernetSFPThresholdControlSfpHigh, sleEthernetSFPThresholdControlSystemLow, 
				sleEthernetSFPThresholdControlSystemHigh, sleSlotSystemCPUOverallStatus, sleSlotSystemTemperOverallStatus, sleslotStatusOverallState, sleslotStatusSyncState, 
				sleSlotProtectionIUTemper2, sleSlotProtectionControlIUPowerStatus, sleSlotSystemControlCPULoadHighThreshold, sleSlotSystemControlCPULoadHighThresholdTimer, sleSlotSystemControlCPULoadLowThreshold, 
				sleSlotSystemControlCPULoadLowThresholdTimer }
			STATUS current
			DESCRIPTION 
				"Description."
			::= { sleDevice 16 }

		
		sleDeviceNotificationGroup NOTIFICATION-GROUP
			NOTIFICATIONS { sleDeviceTemperatureThresholdChanged, sleEthernetPortChanged, sleFanAdminStateChanged, sleBatteryBackupProfileChanged, sleBatteryBackupUpgraded, 
				sleSlotSystemRestart, sleSlotStatusLocked, sleSlotStatusUnlocked, sleSlotStatusPlanning, sleSlotStatusNoPlanning, 
				sleSlotStatusUpgradeModeChanged, sleSlotNosUpgrade, sleSlotStatusPowerUp, sleSlotStatusPowerDown, sleSlotStatusPowerReset, 
				sleSlotNosDownload, sleSlotNosBootloaderUpgrade, sleFanSpeedThresholdChanged, sleDeviceJumboFrameChanged, sleTemperatureThresholdChanged, 
				sleDeviceLEDTestChanged, sleEthernetSFPRemoteReset, sleRfPortStatusChanged, sleDeviceEnvironmentMonitoringStatusChanged, sleEMChanged, 
				sleEMDeleted, sleRFBaseEthertypeChanged, sleRFBaseEthertypeResetChanged, sleBypassModeChanged, sleBypassOptionConnectivitySet, 
				sleBypassOptionConnectivityUnset, sleBypassOptionPingSet, sleBypassOptionPingUnset, sleBypassOptionLinkMonitorChanged, sleSlotProtectionSystemStatusChanged, 
				sleSlotProtectionSystemThreshChanged, sleSlotProtectionIUTemperThreshChanged, sleSlotProtectionIUPowerThreshChanged, sleSlotProtectionIUPowerStatusChanged, sleHFCOpticAlarmStatusChanged, 
				sleSlotSystemCPULoadChagned, sleSlotSystemCPULoadDeleted, sleEthernetPortLinkChanged, sleEthernetPortCpuStatisticsLimitChanged, sleEthernetPortFloodBlockStateChanged, 
				sleEthernetSFPDdmState, sleEthernetSFPThresholdSfpChanged, sleEthernetSFPThresholdSystemChanged, sleEthernetSFPThresholdDestroyed, sleBatteryBackupTableCleared, 
				sleBatteryForceChargeChanged, sleBatteryChargingStartChanged, sleBatteryForceChargeNonStopChanged, sleBatteryRBUBTStatusChanged, sleBatteryRBUBTThresholdChanged, 
				sleBatteryRBURechargeVoltageChanged, sleBatteryPsuAcTemperThreshChanged, sleBatteryRBUTemperThreshChanged }
			STATUS current
			DESCRIPTION 
				"Description."
			::= { sleDevice 17 }

		
	
	END

--
-- SLE-DEVICE-MIB.my
--
