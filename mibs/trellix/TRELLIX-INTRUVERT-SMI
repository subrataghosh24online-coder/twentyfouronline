-- *****************************************************************
-- TRELLIX CONFIDENTIAL
-- TRELLIX-SMI:  
-- Trellix Enterprise Structure of Management Information
--
-- Copyright (c) 2022  MUSARUBRA US, LLC
-- All rights reserved.
-- 
-- *****************************************************************

TRELLIX-INTRUVERT-SMI DEFINITIONS ::= BEGIN

IMPORTS
	OBJECT-IDENTITY, MODULE-IDENTITY, enterprises
		FROM SNMPv2-SMI;

trellix-intruvert MODULE-IDENTITY
LAST-UPDATED "200707090000Z"
ORGANIZATION 
"MUSARUBRA US LLC"
CONTACT-INFO 
"Trellix Customer Service Department

Postal: 6220 American Center Drive
        San Jose CA 95002-2563
        

Tel: +1 800 338 8754

E-mail: support@mcafee.com"
DESCRIPTION 
"The Structure of Management Information for the Trellix-Intruvert enterprise.
Initial version of this MIB module."
::= { enterprises 8962 }


ivConventions  OBJECT-IDENTITY
	STATUS	current
	DESCRIPTION 
		""
	::= { trellix-intruvert 1 }

-- assigned by IANA

ivProducts  OBJECT-IDENTITY
	STATUS	current
	DESCRIPTION 
		" "
	::= { trellix-intruvert 2 }

ivInventory  OBJECT-IDENTITY
	STATUS	current
	DESCRIPTION 
		""
	::= { trellix-intruvert 3 }

matdProducts OBJECT-IDENTITY
        STATUS  current
        DESCRIPTION
                ""
        ::= { trellix-intruvert 4 }

END
