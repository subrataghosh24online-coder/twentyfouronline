-- *------------------------------------------------
-- * Firebrick 2900 BGP MIB
-- *
-- * April 2020, C Malton
-- *
-- * Copyright (c) 2020 by Andrews & Arnold
-- * 
-- * See the Firebrick Manuals for more information
-- *------------------------------------------------

FIREBRICK-MIB DEFINITIONS ::= BEGIN

IMPORTS
    MODULE-IDENTITY,
    OBJECT-TYPE,
    enterprises
        FROM SNMPv2-SMI
        ;

firebrick MODULE-IDENTITY
    LAST-UPDATED "202004060000Z"
    ORGANIZATION "Andrews & Arnold Limited"
    CONTACT-INFO
        "Andrews & Arnold
        Unit 1&2, Enterprise Court
        Bracknell, Berkshire, RG12 1QS
        United Kingdom

        Tel: +44 3333 400 999
        Email: support@aa.net.uk"
    DESCRIPTION
        "This is a MIB Module for monitoring the Firebrick-specific structures
        for general system features."
    REVISION "202004060000Z"
    DESCRIPTION "Initial version of this MIB module"
    ::= { enterprises 24693 }

firebrickNewStyle  OBJECT IDENTIFIER ::= { firebrick 100 }

END
