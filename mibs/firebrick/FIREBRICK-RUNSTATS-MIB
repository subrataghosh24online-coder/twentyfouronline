-- *------------------------------------------------
-- * Firebrick Running Statistics MIB
-- *
-- * June 2020, Cliff Hones
-- *
-- * Copyright (c) 2020 by Andrews & Arnold
-- * 
-- * See the Firebrick Manuals for more information
-- *------------------------------------------------

FIREBRICK-RUNSTATS-MIB DEFINITIONS ::= BEGIN

IMPORTS
    MODULE-IDENTITY,
    OBJECT-TYPE,
    Integer32,
    enterprises
        FROM SNMPv2-SMI
    DisplayString
        FROM SNMPv2-TC
    InetAddressType,
    InetAddress
        FROM INET-ADDRESS-MIB
    OBJECT-GROUP
        FROM SNMPv2-CONF
    firebrickNewStyle
	FROM FIREBRICK-MIB
        ;

fbRunMib MODULE-IDENTITY
    LAST-UPDATED "202006170000Z"
    ORGANIZATION "Andrews & Arnold Limited"
    CONTACT-INFO
        "Andrews & Arnold
        Unit 1&2, Enterprise Court
        Bracknell, Berkshire, RG12 1QS
        United Kingdom

        Tel: +44 3333 400 999
        Email: support@aa.net.uk"
    DESCRIPTION
        "This is a MIB Module for monitoring Firebrick CPU usage."
    REVISION "202006170000Z"
    DESCRIPTION "Initial version of this MIB module"
    ::= { firebrickNewStyle 3 }

fbRunStatsTable OBJECT-TYPE
    SYNTAX SEQUENCE OF FbRunStatsEntry
    MAX-ACCESS not-accessible
    STATUS current
    DESCRIPTION
        "The table of runtime stats for this Firebrick"
    ::= { fbRunMib 1 }

fbRunStatsEntry OBJECT-TYPE
    SYNTAX FbRunStatsEntry
    MAX-ACCESS not-accessible
    STATUS current
    DESCRIPTION
        "An entry in the CPU usage table"
    INDEX { fbRunCore }
    ::= { fbRunStatsTable 1 }

FbRunStatsEntry ::= SEQUENCE {
    fbRunBuffers  Gauge32,
    fbRunCore     Integer32
}

fbRunCore OBJECT-TYPE
    SYNTAX Integer32
    MAX-ACCESS not-accessible
    STATUS current
    DESCRIPTION
        "The CPU core number covered by this table entry.
	 The numbering starts at 1, so CPU0 (CORE) is 1 and CPU1 (NET) is 2."
    ::= { fbRunStatsEntry 2 }

fbRunBuffers OBJECT-TYPE
    SYNTAX Gauge32
    MAX-ACCESS read-only
    STATUS current
    DESCRIPTION
        "The count of buffers which are currently free on this CPU core."
    ::= { fbRunStatsEntry 1 }

END
