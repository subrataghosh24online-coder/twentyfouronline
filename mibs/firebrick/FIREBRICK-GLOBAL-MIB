-- *------------------------------------------------
-- * Firebrick System Global Info MIB
-- *
-- * Feb 2023, David Honour
-- *
-- * Copyright (c) 2023 by Andrews & Arnold
-- *------------------------------------------------

FIREBRICK-GLOBAL DEFINITIONS ::= BEGIN

IMPORTS
    MODULE-IDENTITY,
    OBJECT-TYPE,
    NOTIFICATION-TYPE,
    Gauge32,
    MODULE-COMPLIANCE,
    OBJECT-GROUP,
    NOTIFICATION-GROUP
        FROM SNMPv2-CONF
    TEXTUAL-CONVENTION,
    enterprises
        FROM RFC1155-SMI
    DisplayString
        FROM SNMPv2-TC
    firebrickNewStyle
        FROM FIREBRICK-MIB
        ;

fbGlobalMib MODULE-IDENTITY
    LAST-UPDATED "202302170000Z"
    ORGANIZATION "Andrews & Arnold Limited"
    CONTACT-INFO
        "Andrews & Arnold
        Unit 1&2, Enterprise Court
        Bracknell, Berkshire, RG12 1QS
        United Kingdom

        Tel: +44 3333 400 999
        Email: support@aa.net.uk"
    DESCRIPTION "System wide status"
    REVISION "202302170000Z"
    DESCRIPTION "Add memory usage"
    ::= { firebrickNewStyle 4 }

fbGlobalMemory OBJECT IDENTIFIER ::= { fbGlobalMib 1 }

fbTotalMem OBJECT-TYPE
    SYNTAX Gauge32
    MAX-ACCESS read-only
    STATUS current
    DESCRIPTION "Total RAM (KiB)"
    ::= { fbGlobalMemory 1 }

fbFreeMem OBJECT-TYPE
    SYNTAX Gauge32
    MAX-ACCESS read-only
    STATUS current
    DESCRIPTION "Free RAM (KiB)"
    ::= { fbGlobalMemory 2 }

END
