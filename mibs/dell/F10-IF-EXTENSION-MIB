F10-IF-EXTENSION-MIB DEFINITIONS ::= BEGIN
    --  Force10 Networks, Inc.
    --  390 Holger Way
    --  San Jose, CA 95134

    --  This module provides authoritative definitions for 
    --  Force10 extenstion to the IF MIB.
    --
    --  This module will be extended, as needed.
    --  

    IMPORTS
        MODULE-IDENTITY, OBJECT-TYPE, 
        Counter64, Unsigned32 
            FROM SNMPv2-SMI
        TimeStamp, DisplayString, TruthValue
            FROM SNMPv2-TC
        MODULE-COMPLIANCE, OBJECT-GROUP
            FROM SNMPv2-CONF
        ifIndex
            FROM IF-MIB
        f10Mgmt
            FROM FORCE10-SMI;     
        
    f10IfExtensionMib MODULE-IDENTITY
    LAST-UPDATED "200804071200Z"  -- Apr 7, 2008 12:00:00 GMT
    ORGANIZATION
      "Force10 Networks, Inc."
    CONTACT-INFO
       "Force10 Networks, Inc.
        350 Holger Way
        San Jose, CA 95134 USA
        Phone: +1 (408) 571 3500
        Fax:   +1 (408) 571 3550
        Email: support@force10networks.com"

    DESCRIPTION
       "Force10 Enterprise IF Extenstion MIB. "
    
    REVISION     "200804071200Z"
    DESCRIPTION
        "Add f10IfOutThrottles."
        
    REVISION     "200710031200Z"
    DESCRIPTION
          "Initial version of this mib module."
           ::= { f10Mgmt 11 }   


    -- ### Groups ###

    f10IfExtensionMibObject OBJECT IDENTIFIER ::={ f10IfExtensionMib 1 }
    f10IfExtensionParams    OBJECT IDENTIFIER ::={ f10IfExtensionMibObject 1 }
    f10IfExtensionStats     OBJECT IDENTIFIER ::={ f10IfExtensionMibObject 2 }
        
    -- ### Force10 IF Extenstion Tables
    
    --
    -- Interface Table
    --

      f10IfTable     OBJECT-TYPE
        SYNTAX        SEQUENCE OF F10IfEntry
        MAX-ACCESS    not-accessible
        STATUS        current
        DESCRIPTION
            "Force10 Extension ifTable contains
            generic interface parameters."
        ::= { f10IfExtensionParams 1 }

      f10IfEntry  OBJECT-TYPE 
        SYNTAX        F10IfEntry
        MAX-ACCESS    not-accessible
        STATUS        current
        DESCRIPTION
            " A row defintion of Force10 Interface
            Extension parameters." 
        INDEX    { ifIndex }
        ::= { f10IfTable 1 }

      F10IfEntry    ::=
        SEQUENCE {
           f10IfIpMtu                 Unsigned32,
           f10IfDuplexMode            INTEGER,
           f10IfQueueingStrategy      DisplayString,
           f10IfRxFlowCtrl            TruthValue,
           f10IfTxFlowCtrl            TruthValue
        }
        
       f10IfIpMtu     OBJECT-TYPE
        SYNTAX        Unsigned32
        MAX-ACCESS    read-only
        STATUS        current
        DESCRIPTION
            "The IP (Internet Protocol), Maximum 
            Transmission Unit value."
        ::= { f10IfEntry 1 }

       f10IfDuplexMode  OBJECT-TYPE
        SYNTAX        INTEGER {
                      half(1),
                      full(2),
                      auto(3)
                      }
        MAX-ACCESS    read-only
        STATUS        current
        DESCRIPTION
            "Duplex mode of the interface."
        ::= { f10IfEntry 2 }

       f10IfQueueingStrategy OBJECT-TYPE
        SYNTAX        DisplayString (SIZE (0..32))
        MAX-ACCESS    read-only
        STATUS        current
        DESCRIPTION
            "Queueing strategy used for packets."
        ::= { f10IfEntry 3 }

       f10IfRxFlowCtrl OBJECT-TYPE
        SYNTAX        TruthValue
        MAX-ACCESS    read-only
        STATUS        current
        DESCRIPTION
            "Flow control receive."
        ::= { f10IfEntry 4 }

       f10IfTxFlowCtrl OBJECT-TYPE
        SYNTAX        TruthValue
        MAX-ACCESS    read-only
        STATUS        current
        DESCRIPTION
            "Flow Control transmit."
        ::= { f10IfEntry 5 }
                
    --
    -- Interface Statistics Table
    --
    
      f10IfStaticsTable     OBJECT-TYPE
        SYNTAX        SEQUENCE OF F10IfStaticsEntry
        MAX-ACCESS    not-accessible
        STATUS        current
        DESCRIPTION
            "The statistcs information of the
             interfaces for performance monitoring." 
        ::= { f10IfExtensionStats 1 }

      f10IfStaticsEntry  OBJECT-TYPE 
        SYNTAX        F10IfStaticsEntry
        MAX-ACCESS    not-accessible
        STATUS        current
        DESCRIPTION
            "A row defintion of Force10 Extension 
             interface statistics."
        INDEX    { ifIndex }
        ::= { f10IfStaticsTable 1 }

      F10IfStaticsEntry    ::=
        SEQUENCE {
           f10IfInVlanPkts                Counter64,
           f10IfIn64BytePkts              Counter64,
           f10ifIn65To127BytePkts         Counter64,
           f10IfIn128To255BytePkts        Counter64,
           f10IfIn256To511BytePkts        Counter64, 
           f10IfIn512To1023BytePkts       Counter64,
           f10IfInOver1023BytePkts        Counter64,
           f10IfInThrottles               Counter64,
           f10IfInRunts                   Counter64,
           f10IfInGiants                  Counter64,
           f10IfInCRC                     Counter64,
           f10IfInOverruns                Counter64, 
           f10IfOutVlanPkts               Counter64,
           f10IfOutUnderruns              Counter64,
           f10IfOutUnicasts               Counter64,
           f10IfOutCollisions             Counter64,
           f10IfOutWredDrops              Counter64,
           f10IfOut64BytePkts             Counter64,
           f10IfOut65To127BytePkts        Counter64,
           f10IfOut128To255BytePkts       Counter64,
           f10IfOut256To511BytePkts       Counter64,
           f10IfOut512To1023BytePkts      Counter64,
           f10IfOutOver1023BytePkts       Counter64,
           f10IfOutThrottles              Counter64,
           f10IfLastDiscontinuityTime     TimeStamp
        }
       
       f10IfInVlanPkts OBJECT-TYPE
        SYNTAX        Counter64
        MAX-ACCESS    read-only
        STATUS        current
        DESCRIPTION
             "The total number of valid VLAN Tagged 
             frames received." 
        ::= { f10IfStaticsEntry 1 }
        
       f10IfIn64BytePkts OBJECT-TYPE
        SYNTAX        Counter64
        MAX-ACCESS    read-only
        STATUS        current
        DESCRIPTION
             "The total number of frames (including bad
             frames) received that were 64 octets in length 
             (excluding framing bits but in-cluding FCS octets)." 
        ::= { f10IfStaticsEntry 2 }

       f10ifIn65To127BytePkts OBJECT-TYPE
        SYNTAX        Counter64
        MAX-ACCESS    read-only
        STATUS        current
        DESCRIPTION
             "The total number of frames (including bad 
             frames) received that were between 65 and 127
             octets in length inclusive (ex-cluding framing
             bits but including FCS octets)." 
        ::= { f10IfStaticsEntry 3 }
                
       f10IfIn128To255BytePkts OBJECT-TYPE
        SYNTAX        Counter64
        MAX-ACCESS    read-only
        STATUS        current
        DESCRIPTION
             "The total number of frames (including bad
             frames) received that were between 128 and 255 
             octets in length inclusive (excluding framing
             bits but including FCS octets)." 
        ::= { f10IfStaticsEntry 4 }
        
       f10IfIn256To511BytePkts OBJECT-TYPE
        SYNTAX        Counter64
        MAX-ACCESS    read-only
        STATUS        current
        DESCRIPTION
             "The total number of frames (including bad 
             frames) received that were between 256 and 511 
             octets in length inclusive (excluding framing 
             bits but including FCS octets)." 
        ::= { f10IfStaticsEntry 5 }        
        
       f10IfIn512To1023BytePkts OBJECT-TYPE
        SYNTAX        Counter64
        MAX-ACCESS    read-only
        STATUS        current
        DESCRIPTION
             "The total number of frames (including bad 
             frames) received that were between 512 and 1023
             octets in length inclusive (excluding framing 
             bits but including FCS octets)." 
        ::= { f10IfStaticsEntry 6 }
                
       f10IfInOver1023BytePkts OBJECT-TYPE
        SYNTAX        Counter64
        MAX-ACCESS    read-only
        STATUS        current
        DESCRIPTION
             "The total number of frames received that
              were longer than 1023 (1025 Bytes in case of
              VLAN Tag) octets (excluding framing bits, but
              including FCS octets) and were otherwise
              well formed. This counter is not incremented 
              for too long frames."  
        ::= { f10IfStaticsEntry 7 }
                
       f10IfInThrottles OBJECT-TYPE
        SYNTAX        Counter64
        MAX-ACCESS    read-only
        STATUS        current
        DESCRIPTION
             "This counter is incremented when a valid 
             frame with a length or type field value equal
             to 0x8808 (Control Frame) is re-ceived." 
        ::= { f10IfStaticsEntry 8 }
                
       f10IfInRunts OBJECT-TYPE
        SYNTAX        Counter64
        MAX-ACCESS    read-only
        STATUS        current
        DESCRIPTION
             "The total number of frames received that were
             less than 64 octets long (excluding framing bits, 
             but including FCS octets) and were otherwise 
             well formed."  
        ::= { f10IfStaticsEntry 9 }
                
       f10IfInGiants OBJECT-TYPE
        SYNTAX        Counter64
        MAX-ACCESS    read-only
        STATUS        current
        DESCRIPTION
             "The total number of frames received that were 
             longer than 1518 (1522 Bytes in case of VLAN Tag) 
             octets (excluding framing bits, but including FCS
             octets) and were otherwise well formed. This counter
             is not incremented for too long frames."  
        ::= { f10IfStaticsEntry 10 }
                
       f10IfInCRC OBJECT-TYPE
        SYNTAX        Counter64
        MAX-ACCESS    read-only
        STATUS        current
        DESCRIPTION
             "The total number of frames received that had
             a length (ex-cluding framing bits, but including
             FCS octets) of between 64 and 1518 octets, 
             inclusive, but had a bad CRC."  
        ::= { f10IfStaticsEntry 11 }
                
       f10IfInOverruns OBJECT-TYPE
        SYNTAX        Counter64
        MAX-ACCESS    read-only
        STATUS        current
        DESCRIPTION
             "The total number of frames dropped because 
             of buffer issue." 
        ::= { f10IfStaticsEntry 12 }
                
       f10IfOutVlanPkts OBJECT-TYPE
        SYNTAX        Counter64
        MAX-ACCESS    read-only
        STATUS        current
        DESCRIPTION
             "The Number of Good VLAN Tagged Frames sent 
             successfully." 
        ::= { f10IfStaticsEntry 13 }
                
       f10IfOutUnderruns OBJECT-TYPE
        SYNTAX        Counter64
        MAX-ACCESS    read-only
        STATUS        current
        DESCRIPTION
             "The total number of frames dropped because 
             of buffer underrun." 
        ::= { f10IfStaticsEntry 14 }
                
       f10IfOutUnicasts OBJECT-TYPE
        SYNTAX        Counter64
        MAX-ACCESS    read-only
        STATUS        current
        DESCRIPTION
             "The Number of Good Unicast Frames sent successfully." 
        ::= { f10IfStaticsEntry 15 }
                
       f10IfOutCollisions OBJECT-TYPE
        SYNTAX        Counter64
        MAX-ACCESS    read-only
        STATUS        current
        DESCRIPTION
             "A count of the frames that due to excessive 
             or late collisions are not transmitted successfully."  
        ::= { f10IfStaticsEntry 16 }
                
       f10IfOutWredDrops OBJECT-TYPE
        SYNTAX        Counter64
        MAX-ACCESS    read-only
        STATUS        current
        DESCRIPTION
             "A count of the frames that are dropped using 
             WRED policy because of to excessive traffic." 
        ::= { f10IfStaticsEntry 17 }
                
       f10IfOut64BytePkts OBJECT-TYPE
        SYNTAX        Counter64
        MAX-ACCESS    read-only
        STATUS        current
        DESCRIPTION
             "The Number of Good Frames sent successfully 
             whose size was 64 Bytes." 
        ::= { f10IfStaticsEntry 18 }
                
       f10IfOut65To127BytePkts OBJECT-TYPE
        SYNTAX        Counter64
        MAX-ACCESS    read-only
        STATUS        current
        DESCRIPTION
             "The Number of Good Frames sent successfully 
             whose size was in the range of 65 to 127 Bytes." 
        ::= { f10IfStaticsEntry 19 } 
               
       f10IfOut128To255BytePkts OBJECT-TYPE
        SYNTAX        Counter64
        MAX-ACCESS    read-only
        STATUS        current
        DESCRIPTION
             "The Number of Good Frames sent successfully 
             whose size was in the range of 128 to 255 Bytes." 
        ::= { f10IfStaticsEntry 20 }
               
       f10IfOut256To511BytePkts OBJECT-TYPE
        SYNTAX        Counter64
        MAX-ACCESS    read-only
        STATUS        current
        DESCRIPTION
             "The Number of Good Frames sent successfully 
             whose size was in the range of 256 to 511 Bytes." 
        ::= { f10IfStaticsEntry 21 }
                       
       f10IfOut512To1023BytePkts OBJECT-TYPE
        SYNTAX        Counter64
        MAX-ACCESS    read-only
        STATUS        current
        DESCRIPTION
             "The Number of Good Frames sent successfully 
             whose size was in the range of 512 to 1023 Bytes." 
        ::= { f10IfStaticsEntry 22 }             
          
       f10IfOutOver1023BytePkts OBJECT-TYPE
        SYNTAX        Counter64
        MAX-ACCESS    read-only
        STATUS        current
        DESCRIPTION
             "The Number of Good Frames sent successfully 
             whose size was greater than 1023 Bytes." 
        ::= { f10IfStaticsEntry 23 }               
                
       f10IfOutThrottles OBJECT-TYPE
        SYNTAX        Counter64
        MAX-ACCESS    read-only
        STATUS        current
        DESCRIPTION
             "This counter is incremented when a valid 
             frame with a length or type field value equal
             to 0x8808 (Control Frame) is sent." 
        ::= { f10IfStaticsEntry 24 }
               
       f10IfLastDiscontinuityTime OBJECT-TYPE
        SYNTAX        TimeStamp
        MAX-ACCESS    read-only
        STATUS        current
        DESCRIPTION
            "The value of sysUpTime on the most recent occasion
            at which this interface's counters suffered a 
            discontinuity via a reset. If no such discontinuities 
            have occurred since the last reinitialization of 
            the local management subsystem, then this object
            contains a zero value."
        ::= { f10IfStaticsEntry 25 }


    -- ### conformance information ###
    f10IfExtensionMibConformance OBJECT IDENTIFIER ::= { f10IfExtensionMib 2 }
    f10IfExtensionMibCompliances OBJECT IDENTIFIER ::= { f10IfExtensionMibConformance 1 }
    f10IfExtensionMibGroups      OBJECT IDENTIFIER ::= { f10IfExtensionMibConformance 2 }

    -- ## compliance statements
    f10IfExtensionMibCompliance    MODULE-COMPLIANCE
        STATUS                  current
        DESCRIPTION
            "The compliance statement for Force10
            IF Extension MIB."
        MODULE    -- this module
        MANDATORY-GROUPS {
            f10IfParamsGroup,
            f10IfStatsGroup
        }
        ::= { f10IfExtensionMibCompliances 1 }

    -- ## units of conformance

    f10IfParamsGroup OBJECT-GROUP
        OBJECTS {
           f10IfIpMtu,
           f10IfDuplexMode,
           f10IfQueueingStrategy,
           f10IfRxFlowCtrl,
           f10IfTxFlowCtrl
        }
        STATUS    current
        DESCRIPTION
            "A collection of objects providing the
            Force10 IF Extenstion parameters."
        ::= { f10IfExtensionMibGroups 1 }

    f10IfStatsGroup    OBJECT-GROUP
        OBJECTS {
           f10IfInVlanPkts,
           f10IfIn64BytePkts,
           f10ifIn65To127BytePkts,
           f10IfIn128To255BytePkts,
           f10IfIn256To511BytePkts, 
           f10IfIn512To1023BytePkts,
           f10IfInOver1023BytePkts,
           f10IfInThrottles,
           f10IfInRunts,
           f10IfInGiants,
           f10IfInCRC,
           f10IfInOverruns, 
           f10IfOutVlanPkts,
           f10IfOutUnderruns,
           f10IfOutUnicasts,
           f10IfOutCollisions,
           f10IfOutWredDrops,
           f10IfOut64BytePkts,
           f10IfOut65To127BytePkts,
           f10IfOut128To255BytePkts,
           f10IfOut256To511BytePkts,
           f10IfOut512To1023BytePkts,
           f10IfOutOver1023BytePkts,
           f10IfOutThrottles,
           f10IfLastDiscontinuityTime                                   
        }
        STATUS    current
        DESCRIPTION
            "A collection of objects providing the
            interface statistics."
        ::= { f10IfExtensionMibGroups 2 }

    END
