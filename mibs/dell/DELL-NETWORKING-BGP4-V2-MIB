-- *****************************************************************************
-- draft-ietf-idr-bgp4-mibv2-05.txt
--
-- Copyright (c) 2005 The Internet Society.
-- Copyright (c) 2007 - 2014 by Dell Inc. All Rights Reserved.
--
-- All rights reserved.
-- *****************************************************************************

DELL-NETWORKING-BGP4-V2-MIB DEFINITIONS ::= BEGIN


    IMPORTS
	MODULE-IDENTITY, OBJECT-TYPE, NOTIFICATION-TYPE,
	Counter32, Gauge32, mib-2, Unsigned32, Integer32,
     TimeTicks
	    FROM SNMPv2-SMI
	InetAddressType, InetAddress, InetPortNumber,
	InetAutonomousSystemNumber, InetAddressPrefixLength
	    FROM INET-ADDRESS-MIB
	TEXTUAL-CONVENTION, TruthValue, RowPointer, StorageType,
	RowStatus
	    FROM SNMPv2-TC
	MODULE-COMPLIANCE, OBJECT-GROUP, NOTIFICATION-GROUP
	    FROM SNMPv2-CONF
	SnmpAdminString
	    FROM SNMP-FRAMEWORK-MIB
	dellNetExperiment
	    FROM DELL-NETWORKING-SMI;


    dellNetBgpM2 MODULE-IDENTITY
	LAST-UPDATED "200704271200Z"  -- April 27, 2007 12:00:00 EDT
	ORGANIZATION "IETF IDR Working Group"
	CONTACT-INFO "E-mail:  idr@merit.net

		      Jeffrey Haas  (Editor)
		      825 Victors Way, Suite 100
		      Ann Arbor, MI  48108
		      Tel: +1 734 222-1600
		      Fax: +1 734 222-1602
		      E-mail: jhaas@nexthop.com"
	DESCRIPTION
	    "This MIB module defines management objects for
	     the Border Gateway Protocol, Version 4."
	REVISION    "200704271200Z"  -- April 27, 2007 12:00:00 EDT
	DESCRIPTION
	    "This is a Dell Networking OS proprietary version of the
	     draft-ietf-idr-bgp4-mibv2-05.txt MIB as proposed by
	     the IETF Inter-Domain Routing Working Group.
	     This mib will be obsolete when IANA-number is assigned.
	     
	     The following objects are added by Dell.	    	
	     - Added to BgpM2PeerCounterstable
	    	dellNetBgpM2PeerInKeepalives,
	    	dellNetBgpM2PeerOutKeepalives, 
	    	dellNetBgpM2PeerInOpen, 
	    	dellNetBgpM2PeerOutOpen,
	    	dellNetBgpM2PeerInRteRefresh, 
	    	dellNetBgpM2PeerOutRteRefresh	     
	     - Added to BgpM2PrefixCountersTable
	    	dellNetBgpM2PrefixWdrawnByPeer, 
	    	dellNetBgpM2PrefixWdrawnFromPeer"

--        ::= { mib-2 XXX }
        ::= { dellNetExperiment 1 }


    DellNetBgpM2Identifier ::= TEXTUAL-CONVENTION
	DISPLAY-HINT "1d."
	STATUS	     current
	DESCRIPTION
	    "The representation of a BGP Identifier.  The BGP
	     Identifier should be represented in the OCTET STRING
	     as with the first OCTET of the string containing
	     the first OCTET of the BGP Identifier received or sent
	     in the OPEN packet and so on.
	     Even though the BGP Identifier is trending away from
	     an IP address it is still displayed as if it was one,
	     even when it would be an illegal IP address."
	SYNTAX OCTET STRING(SIZE (4))


    DellNetBgpM2Afi ::= TEXTUAL-CONVENTION
	DISPLAY-HINT "d"
	STATUS	     current
	DESCRIPTION
	    "The representation of a BGP AFI"
	SYNTAX Unsigned32(0..65535)


    DellNetBgpM2Safi ::= TEXTUAL-CONVENTION
	DISPLAY-HINT "d"
	STATUS	     current
	DESCRIPTION
	    "The representation of a BGP SAFI"
	SYNTAX Unsigned32(0..255)


    DellNetBgpM2Community ::= TEXTUAL-CONVENTION
	DISPLAY-HINT "2d:"
	STATUS	     current
	DESCRIPTION
	    "The representation of a BGP Community."
	SYNTAX OCTET STRING(SIZE(4))


    DellNetBgpM2ExtendedCommunity ::= TEXTUAL-CONVENTION
	DISPLAY-HINT "1x:"
	STATUS	     current
	DESCRIPTION
	    "The representation of a BGP Extended Community."
	SYNTAX OCTET STRING(SIZE(8))


    dellNetBgpM2BaseScalars
	OBJECT IDENTIFIER ::= { dellNetBgpM2 1 }


    --
    -- Notifications
    --

    dellNetBgpM2BaseNotifications
	OBJECT IDENTIFIER ::= { dellNetBgpM2BaseScalars 0 }


    dellNetBgpM2Established NOTIFICATION-TYPE
	OBJECTS {
	    dellNetBgpM2PeerLocalAddrType,
	    dellNetBgpM2PeerLocalAddr,
	    dellNetBgpM2PeerRemoteAddrType,
	    dellNetBgpM2PeerRemoteAddr,
	    dellNetBgpM2PeerLastErrorReceived,
	    dellNetBgpM2PeerState
	}
	STATUS	current
	DESCRIPTION
	    "The BGP Established event is generated when
	     the BGP FSM enters the ESTABLISHED state."
	::= { dellNetBgpM2BaseNotifications 1 }


    dellNetBgpM2BackwardTransition NOTIFICATION-TYPE
	OBJECTS {
	    dellNetBgpM2PeerLocalAddrType,
	    dellNetBgpM2PeerLocalAddr,
	    dellNetBgpM2PeerRemoteAddrType,
	    dellNetBgpM2PeerRemoteAddr,
	    dellNetBgpM2PeerLastErrorReceived,
	    dellNetBgpM2PeerLastErrorReceivedText,
	    dellNetBgpM2PeerState
	}
	STATUS	current
	DESCRIPTION
	    "The BGPBackwardTransition Event is generated
	     when the BGP FSM moves from a higher numbered
	     state to a lower numbered state."
	::= { dellNetBgpM2BaseNotifications 2 }


    --
    -- BGP Supported Version Table
    --

    dellNetBgpM2Version
	OBJECT IDENTIFIER ::= { dellNetBgpM2BaseScalars 1 }


    dellNetBgpM2VersionTable OBJECT-TYPE
	SYNTAX	   SEQUENCE OF DellNetBgpM2VersionEntry
	MAX-ACCESS not-accessible
	STATUS	   current
	DESCRIPTION
	    "Table of supported BGP versions."
	::= { dellNetBgpM2Version 1 }


    dellNetBgpM2VersionEntry OBJECT-TYPE
	SYNTAX	   DellNetBgpM2VersionEntry
	MAX-ACCESS not-accessible
	STATUS	   current
	DESCRIPTION
	    "Entry containing data on a given supported version
	     of the Border Gateway Protocol and the level of
	     support provided.	It is expected that any agent
	     implementation supporting this MIB module will
	     report support for Version 4 of the Border Gateway
	     Protocol at the very minimum."
	INDEX {
	    dellNetBgpM2VersionIndex
	}
	::= { dellNetBgpM2VersionTable 1 }


    DellNetBgpM2VersionEntry ::= SEQUENCE {
	    dellNetBgpM2VersionIndex
		Unsigned32,
	    dellNetBgpM2VersionSupported
		TruthValue
    }


    dellNetBgpM2VersionIndex OBJECT-TYPE
	SYNTAX	   Unsigned32(0..255)
	MAX-ACCESS read-only
	STATUS	   current
	DESCRIPTION
	    "The version number of the BGP Protocol."
	::= { dellNetBgpM2VersionEntry 1 }


    dellNetBgpM2VersionSupported OBJECT-TYPE
	SYNTAX	   TruthValue
	MAX-ACCESS read-only
	STATUS	   current
	DESCRIPTION
	    "This value is TRUE if this version of the BGP protocol
	     identified in 'dellNetBgpM2VersionIndex' is supported.  The absence
	     of a row for a particular dellNetBgpM2VersionIndex indicates that
	     that dellNetBgpM2VersionIndex protocol version number is not
	     supported."
	::= { dellNetBgpM2VersionEntry 2 }

    --
    -- Supported BGP Capabilities
    --

    dellNetBgpM2SupportedCapabilities
	OBJECT IDENTIFIER ::= { dellNetBgpM2BaseScalars 2 }


    dellNetBgpM2CapabilitySupportAvailable OBJECT-TYPE
	SYNTAX	   TruthValue
	MAX-ACCESS read-only
	STATUS	   current
	DESCRIPTION
	    "This value is TRUE if capability support is
	     available and is enabled."
	::= { dellNetBgpM2SupportedCapabilities 1 }


    dellNetBgpM2SupportedCapabilitiesTable OBJECT-TYPE
	SYNTAX	   SEQUENCE OF DellNetBgpM2SupportedCapabilityEntry
	MAX-ACCESS not-accessible
	STATUS	   current
	DESCRIPTION
	    "Table of supported BGP-4 capabilities."
	::= { dellNetBgpM2SupportedCapabilities 2 }


    dellNetBgpM2SupportedCapabilitiesEntry OBJECT-TYPE
	SYNTAX	   DellNetBgpM2SupportedCapabilityEntry
	MAX-ACCESS not-accessible
	STATUS	   current
	DESCRIPTION
	    "Information about supported capabilities indexed
	     by capability number."
	INDEX {
	    dellNetBgpM2SupportedCapabilityCode
	}
	::= { dellNetBgpM2SupportedCapabilitiesTable 1 }


    DellNetBgpM2SupportedCapabilityEntry ::= SEQUENCE {
	dellNetBgpM2SupportedCapabilityCode
	    Unsigned32,
	dellNetBgpM2SupportedCapability
	    TruthValue
    }


    dellNetBgpM2SupportedCapabilityCode OBJECT-TYPE
	SYNTAX	   Unsigned32 (0..255)
	MAX-ACCESS read-only
	STATUS	   current
	DESCRIPTION
	    "Index of supported capability.  The index directly
	     corresponds with the BGP-4 Capability Advertisement
	     Capability Code."
	::= { dellNetBgpM2SupportedCapabilitiesEntry 1 }


    dellNetBgpM2SupportedCapability OBJECT-TYPE
	SYNTAX	   TruthValue
	MAX-ACCESS read-only
	STATUS	   current
	DESCRIPTION
	    "This value is True if this capability is supported,
	     False otherwise."
	::= { dellNetBgpM2SupportedCapabilitiesEntry 2 }


    --
    -- Base Scalars
    --

    dellNetBgpM2AsSize OBJECT-TYPE
	SYNTAX	   INTEGER {
	    twoOctet(1),
	    fourOctet(2)
	}
	MAX-ACCESS read-only
	STATUS	   current
	DESCRIPTION
	    "The size of the AS value in this implementation.
	     The semantics of this are determined as per the
	     as-4bytes draft."
	REFERENCE
	    "draft-ietf-idr-as4bytes-04"
	::= { dellNetBgpM2BaseScalars 4 }


    dellNetBgpM2LocalAs OBJECT-TYPE
	SYNTAX	   InetAutonomousSystemNumber
	MAX-ACCESS read-only
	STATUS	   current
	DESCRIPTION
	    "The local autonomous system number.
	     If the dellNetBgpM2AsSize is twoOctet, then the range is
	     constrained to be 0-65535."
	::= { dellNetBgpM2BaseScalars 5 }


    dellNetBgpM2LocalIdentifier OBJECT-TYPE
	SYNTAX	   DellNetBgpM2Identifier
	MAX-ACCESS read-only
	STATUS	   current
	DESCRIPTION
	    "The BGP Identifier of local system.
	     Current practice is trending away from this value being
	     treated as an IP address and more as a generic
	     identifier."
	::= { dellNetBgpM2BaseScalars 6 }


    --
    -- Base Scalar Extensions
    --

    dellNetBgpM2BaseScalarExtensions
	OBJECT IDENTIFIER ::= { dellNetBgpM2BaseScalars 7 }


    dellNetBgpM2BaseScalarNonCapExts
	OBJECT IDENTIFIER ::= { dellNetBgpM2BaseScalarExtensions 1 }


    dellNetBgpM2BaseScalarCapExts
	OBJECT IDENTIFIER ::= { dellNetBgpM2BaseScalarExtensions 2 }


    --
    -- Base Scalar Route Reflection Extensions
    --

    dellNetBgpM2BaseScalarRouteReflectExts OBJECT IDENTIFIER ::=
	{ dellNetBgpM2BaseScalarNonCapExts 2796 }


    dellNetBgpM2RouteReflector OBJECT-TYPE
	SYNTAX	    TruthValue
	MAX-ACCESS  read-only
	STATUS	    current
	DESCRIPTION
	    "This value is TRUE if this implementation supports the
	     BGP Route Reflection Extension and is enabled as a
	     route reflector.  If the BGP Route Reflection extension
	     is not supported this value must be FALSE."
	REFERENCE
	    "RFC 2796 - BGP Route Reflection"
	::= { dellNetBgpM2BaseScalarRouteReflectExts 1 }


    dellNetBgpM2ClusterId OBJECT-TYPE
	SYNTAX	    DellNetBgpM2Identifier
	MAX-ACCESS  read-only
	STATUS	    current
	DESCRIPTION
	    "The configured Cluster-ID of the BGP Speaker.  This will
	     default to the BGP Speaker's DellNetBgpM2Identifier if this
	     speaker is functioning as a route reflector and an
	     explicit Cluster-ID has not been configured.

	     A value of 0.0.0.0 will be present if Route Reflection is
	     not enabled."
	REFERENCE
	    "RFC 2796 - BGP Route Reflection"
	::= { dellNetBgpM2BaseScalarRouteReflectExts 2 }


    --
    -- Base Scalar AS Confederation Extensions
    --

    dellNetBgpM2BaseScalarASConfedExts OBJECT IDENTIFIER ::=
	 { dellNetBgpM2BaseScalarNonCapExts 3065 }


    dellNetBgpM2ConfederationRouter OBJECT-TYPE
	SYNTAX	   TruthValue
	MAX-ACCESS read-only
	STATUS	   current
	DESCRIPTION
	    "This value is TRUE if this implementation supports the
	     BGP AS Confederations Extension and this router is
	     configured to be in a confederation."
	REFERENCE
	    "RFC 3065 - Autonomous System Confederations for BGP"
	::= { dellNetBgpM2BaseScalarASConfedExts 1 }

    dellNetBgpM2ConfederationId OBJECT-TYPE
	SYNTAX	   InetAutonomousSystemNumber
	MAX-ACCESS read-only
	STATUS	   current
	DESCRIPTION
	    "The local Confederation Identification Number.

	     This value will be zero (0) if this BGP Speaker is not
	     a confederation router."
	REFERENCE
	    "RFC 3065 - Autonomous System Confederations for BGP"
	::= { dellNetBgpM2BaseScalarASConfedExts 2 }


    --
    -- Base Configuration Objects
    --

    dellNetBgpM2BaseScalarConfiguration
	OBJECT IDENTIFIER ::= { dellNetBgpM2BaseScalars 8 }


    dellNetBgpM2CfgBaseScalarStorageType OBJECT-TYPE
	SYNTAX	   StorageType
	MAX-ACCESS read-write
	STATUS	   current
	DESCRIPTION
	    "This object specifies the intended storage type for
	     all configurable base scalars."
	::= { dellNetBgpM2BaseScalarConfiguration 1 }


    dellNetBgpM2CfgLocalAs OBJECT-TYPE
	SYNTAX	   InetAutonomousSystemNumber
	MAX-ACCESS read-write
	STATUS	   current
	DESCRIPTION
	    "The local autonomous system number.

	     If the dellNetBgpM2AsSize is twoOctet, then the range is
	     constrained to be 0-65535."
	::= { dellNetBgpM2BaseScalarConfiguration 2 }


    dellNetBgpM2CfgLocalIdentifier OBJECT-TYPE
	SYNTAX	   DellNetBgpM2Identifier
	MAX-ACCESS read-write
	STATUS	   current
	DESCRIPTION
	    "The BGP Identifier of local system.

	     Current practice is trending away from this value being
	     treated as an IP address and more as a generic
	     identifier."
	::= { dellNetBgpM2BaseScalarConfiguration 3 }


    --
    -- Base Scalar Extensions
    --

    dellNetBgpM2CfgBaseScalarExtensions
	OBJECT IDENTIFIER ::= { dellNetBgpM2BaseScalarConfiguration 4 }


    dellNetBgpM2CfgBaseScalarNonCapExts
	OBJECT IDENTIFIER ::= { dellNetBgpM2CfgBaseScalarExtensions 1 }


    dellNetBgpM2CfgBaseScalarCapExts
	OBJECT IDENTIFIER ::= { dellNetBgpM2CfgBaseScalarExtensions 2 }


    --
    -- Base Scalar Route Reflection Extensions
    --

    dellNetBgpM2CfgBaseScalarReflectorExts
	OBJECT IDENTIFIER ::= { dellNetBgpM2CfgBaseScalarNonCapExts 2796 }


    dellNetBgpM2CfgRouteReflector OBJECT-TYPE
	SYNTAX	    TruthValue
	MAX-ACCESS  read-write
	STATUS	    current
	DESCRIPTION
	    "This value is set to true if this implementation will
	     be supporting route reflection."
	REFERENCE
	    "RFC 2796 - BGP Route Reflection"
	::= { dellNetBgpM2CfgBaseScalarReflectorExts 1 }


    dellNetBgpM2CfgClusterId OBJECT-TYPE
	SYNTAX	    DellNetBgpM2Identifier
	MAX-ACCESS  read-write


	STATUS	    current
	DESCRIPTION
	    "The configured Cluster-ID of the BGP Speaker.  This will
	     default to the BGP Speaker's DellNetBgpM2Identifier if this
	     speaker is functioning as a route reflector and an
	     explicit Cluster-ID has not been configured.

	     A value of 0.0.0.0 will be present if Route Reflection is
	     not enabled."
	REFERENCE
	    "RFC 2796 - BGP Route Reflection"
	::= { dellNetBgpM2CfgBaseScalarReflectorExts 2 }


    --
    -- Base Scalar AS Confederation Extensions
    --

    dellNetBgpM2CfgBaseScalarASConfedExts
	OBJECT IDENTIFIER ::= { dellNetBgpM2CfgBaseScalarNonCapExts 3065 }


    dellNetBgpM2CfgConfederationRouter OBJECT-TYPE
	SYNTAX	   TruthValue
	MAX-ACCESS read-write
	STATUS	   current
	DESCRIPTION
	    "This value is set to true if this implementation will be
	     supporting BGP AS Confederations."
	REFERENCE
	    "RFC 3065 - Autonomous System Confederations for BGP"
	::= { dellNetBgpM2CfgBaseScalarASConfedExts 1 }


    dellNetBgpM2CfgConfederationId OBJECT-TYPE
	SYNTAX	   InetAutonomousSystemNumber
	MAX-ACCESS read-write
	STATUS	   current
	DESCRIPTION
	    "The local Confederation Identification Number.

	     This value will be zero (0) if this BGP Speaker is not
	     a confederation router."
	REFERENCE
	    "RFC 3065 - Autonomous System Confederations for BGP"
	::= { dellNetBgpM2CfgBaseScalarASConfedExts 2 }

    --
    -- BGP Peer Data
    --

    dellNetBgpM2Peer
	OBJECT IDENTIFIER ::= { dellNetBgpM2 2 }


    dellNetBgpM2PeerData
	OBJECT IDENTIFIER ::= { dellNetBgpM2Peer 1 }


    dellNetBgpM2PeerTable OBJECT-TYPE
	SYNTAX	   SEQUENCE OF DellNetBgpM2PeerEntry
	MAX-ACCESS not-accessible
	STATUS	   current
	DESCRIPTION
	    "BGP peer table.

	     This table contains, one entry per remote BGP peer,
	     any information about the connections with the remote
	     BGP peers."
	::= { dellNetBgpM2PeerData 1 }


    dellNetBgpM2PeerEntry OBJECT-TYPE
	SYNTAX	   DellNetBgpM2PeerEntry
	MAX-ACCESS not-accessible
	STATUS	   current
	DESCRIPTION
	    "Entry containing information about the connection with
	     a remote BGP peer."
	INDEX {
	 dellNetBgpM2PeerInstance,
	    dellNetBgpM2PeerLocalAddrType,
	    dellNetBgpM2PeerLocalAddr,
	    dellNetBgpM2PeerRemoteAddrType,
	    dellNetBgpM2PeerRemoteAddr
	}
	::= { dellNetBgpM2PeerTable 1 }


    DellNetBgpM2PeerEntry ::= SEQUENCE {
     dellNetBgpM2PeerInstance
	 Unsigned32,
	dellNetBgpM2PeerIdentifier
	    DellNetBgpM2Identifier,
	dellNetBgpM2PeerState
	    INTEGER,
	dellNetBgpM2PeerStatus
	    INTEGER,
	dellNetBgpM2PeerConfiguredVersion
	    Unsigned32,
	dellNetBgpM2PeerNegotiatedVersion
	    Unsigned32,
	dellNetBgpM2PeerLocalAddrType
	    InetAddressType,
	dellNetBgpM2PeerLocalAddr
	    InetAddress,
	dellNetBgpM2PeerLocalPort
	    InetPortNumber,
	dellNetBgpM2PeerLocalAs
	    InetAutonomousSystemNumber,
	dellNetBgpM2PeerRemoteAddrType
	    InetAddressType,
	dellNetBgpM2PeerRemoteAddr
	    InetAddress,
	dellNetBgpM2PeerRemotePort
	    InetPortNumber,
	dellNetBgpM2PeerRemoteAs
	    InetAutonomousSystemNumber,
	dellNetBgpM2PeerIndex
	    Unsigned32
    }


    dellNetBgpM2PeerInstance OBJECT-TYPE
     SYNTAX	Unsigned32
     MAX-ACCESS read-only
     STATUS	current
     DESCRIPTION
	 "The routing instance index.

	  Some BGP implementations permit the creation of
	  multiple instances of a BGP routing process.	An
	  example includes RFC 2547 PE-CE routers.

	  Implementations that do not support multiple
	  routing instances should return 1 for this object.

	  XXX TODO - We need to provide a way to configure these
	  in the peer configuration table."
	::= { dellNetBgpM2PeerEntry 1 }


    dellNetBgpM2PeerIdentifier OBJECT-TYPE
	SYNTAX	   DellNetBgpM2Identifier
	MAX-ACCESS read-only
	STATUS	   current
	DESCRIPTION
	    "The BGP Identifier of this entry's remote BGP peer.

	     This entry should be 0.0.0.0 unless the dellNetBgpM2PeerState is
	     in the OpenConfirm or the Established state."
	REFERENCE
	    "draft-ietf-idr-bgp4-17.txt, Sec. 4.2"
	::= { dellNetBgpM2PeerEntry 2 }


    dellNetBgpM2PeerState OBJECT-TYPE
	SYNTAX	   INTEGER {
	    idle(1),
	    connect(2),
	    active(3),
	    opensent(4),
	    openconfirm(5),
	    established(6)
	}
	MAX-ACCESS read-only
	STATUS	   current
	DESCRIPTION
	    "The remote BGP peer's FSM state."
	REFERENCE
	    "draft-ietf-idr-bgp4-17.txt, Sec. 8"
	::= { dellNetBgpM2PeerEntry 3 }


    dellNetBgpM2PeerStatus OBJECT-TYPE
	SYNTAX	   INTEGER {
	    halted(1),
	    running(2)
	}
	MAX-ACCESS read-only
	STATUS	   current
	DESCRIPTION
	    "Whether or not the BGP FSM for this remote peer is halted
	     or running.  The BGP FSM for a remote peer is halted after
	     processing a Stop event.  Likewise, it is in the running
	     state after a Start event.

	     The dellNetBgpM2PeerState will generally be in the idle state when
	     the FSM is halted, although some extensions such as
	     Graceful Restart will leave the peer in the Idle state
	     but with the FSM running."
	::= { dellNetBgpM2PeerEntry 4 }


    dellNetBgpM2PeerConfiguredVersion OBJECT-TYPE
	SYNTAX	   Unsigned32 (1..255)
	MAX-ACCESS read-only
	STATUS	   current
	DESCRIPTION
	    "The configured version to originally start with this
	     remote peer.  The BGP speaker may permit negotiation to a
	     lower version number of the protocol."
	::= { dellNetBgpM2PeerEntry 5 }


    dellNetBgpM2PeerNegotiatedVersion OBJECT-TYPE
	SYNTAX	   Unsigned32 (1..255)
	MAX-ACCESS read-only
	STATUS	   current
	DESCRIPTION
	    "The negotiated version of BGP running between the two
	     peers."
	::= { dellNetBgpM2PeerEntry 6 }


    dellNetBgpM2PeerLocalAddrType OBJECT-TYPE
	SYNTAX	   InetAddressType
	MAX-ACCESS read-only
	STATUS	   current
	DESCRIPTION
	    "The address family of the local end of the peering
	     session."
	::= { dellNetBgpM2PeerEntry 7 }


    dellNetBgpM2PeerLocalAddr OBJECT-TYPE
	SYNTAX	   InetAddress (SIZE(4..20))
	MAX-ACCESS read-only
	STATUS	   current
	DESCRIPTION
	    "The address of the local end of the peering session."
	::= { dellNetBgpM2PeerEntry 8 }


    dellNetBgpM2PeerLocalPort OBJECT-TYPE
	SYNTAX	   InetPortNumber
	MAX-ACCESS read-only
	STATUS	   current
	DESCRIPTION

	    "The local port for the TCP connection between the BGP
	     peers."
	::= { dellNetBgpM2PeerEntry 9 }


    dellNetBgpM2PeerLocalAs OBJECT-TYPE
	SYNTAX	   InetAutonomousSystemNumber
	MAX-ACCESS read-only
	STATUS	   current
	DESCRIPTION
	    "Some implementations of BGP can represent themselves
	     as multiple ASs.  This is the AS that this peering
	     session is representing itself as to the remote peer."
	::= { dellNetBgpM2PeerEntry 10 }


    dellNetBgpM2PeerRemoteAddrType OBJECT-TYPE
	SYNTAX	   InetAddressType
	MAX-ACCESS read-only
	STATUS	   current
	DESCRIPTION
	    "The address family of the remote end of the peering
	     session."
	::= { dellNetBgpM2PeerEntry 11 }


    dellNetBgpM2PeerRemoteAddr OBJECT-TYPE
	SYNTAX	   InetAddress (SIZE(4..20))
	MAX-ACCESS read-only
	STATUS	   current
	DESCRIPTION
	    "The address of the remote end of the peering session."
	::= { dellNetBgpM2PeerEntry 12 }


    dellNetBgpM2PeerRemotePort OBJECT-TYPE
	SYNTAX	   InetPortNumber
	MAX-ACCESS read-only
	STATUS	   current
	DESCRIPTION
	    "The remote port for the TCP connection between the BGP
	     peers.  In the case of a transport for which the notion
	     of 'port' is irrelevant, an instance value of -1
	     should be returned by the agent for this object.

	     Note that the objects dellNetBgpM2PeerLocalAddr,
	     dellNetBgpM2PeerLocalPort, dellNetBgpM2PeerRemoteAddr and
	     dellNetBgpM2PeerRemotePort provide the appropriate reference to

	     the standard MIB TCP connection table. or even the ipv6
	     TCP MIB as in rfc2452."
	REFERENCE
	    "RFC 2012 - SNMPv2 Management Information Base for the
	     Transmission Control Protocol using SMIv2.
	     RFC 2542 - IP Version 6 Management Information Base
	     for the Transmission Control Protocol."
	::= { dellNetBgpM2PeerEntry 13 }


    dellNetBgpM2PeerRemoteAs OBJECT-TYPE
	SYNTAX	   InetAutonomousSystemNumber
	MAX-ACCESS read-only
	STATUS	   current
	DESCRIPTION
	    "The remote autonomous system number."
	::= { dellNetBgpM2PeerEntry 14 }


    dellNetBgpM2PeerIndex OBJECT-TYPE
	SYNTAX	    Unsigned32
	MAX-ACCESS  read-only
	STATUS	    current
	DESCRIPTION
	    "This value is a unique index for the remote peer entry
	     in the dellNetBgpM2PeerTable.  It is assigned by the agent
	     at the point of creation of the dellNetBgpM2PeerTable row
	     entry.  While its value is guaranteed to be unique at
	     any time, it is otherwise opaque to the management
	     application with respect to its value or the contiguity
	     of dellNetBgpM2PeerIndex row instance values across rows of
	     the dellNetBgpM2PeerTable.  It is used to provide an index
	     structure for other tables whose data is logically
	     per-peer.

	     For explicitly configured peers, this value will remain
	     consistent until this row is deleted by deleting the
	     configured peers.	Unconfigured peers will generate
	     a monotonically increasing number when a BGP FSM is
	     built to process the peering session.  Values in the
	     dellNetBgpM2PeerTable and other tables utilizing dellNetBgpM2PeerIndex
	     are expected to remain in existence for an arbitrary
	     time after the unconfigured peer has been deleted
	     in order to allow management applications to extract
	     useful management information for those peers.  Thus,
	     an unconfigured peer using the same indices as the
	     dellNetBgpM2PeerTable that comes up while this row still
	     exists will re-utilize the same row."

	 ::= { dellNetBgpM2PeerEntry 15 }


    --
    -- Errors
    --

    dellNetBgpM2PeerErrors
	OBJECT IDENTIFIER ::= { dellNetBgpM2Peer 2 }

    dellNetBgpM2PeerErrorsTable OBJECT-TYPE
	SYNTAX	   SEQUENCE OF DellNetBgpM2PeerErrorsEntry
	MAX-ACCESS not-accessible
	STATUS	   current
	DESCRIPTION
	    "On a per peer basis, this table reflects the last
	     protocol-defined error encountered and reported on
	     the peer session.	If no entry for a given peer,
	     by its dellNetBgpM2PeerIndex, exists in this table, then no
	     such errors have been observed, reported, and
	     recorded on the  session."
	::= { dellNetBgpM2PeerErrors 1 }


    dellNetBgpM2PeerErrorsEntry OBJECT-TYPE
	SYNTAX	   DellNetBgpM2PeerErrorsEntry
	MAX-ACCESS not-accessible
	STATUS	   current
	DESCRIPTION
	    "Each entry contains information about errors sent
	     and received for a particular BGP peer."
	AUGMENTS {
	    dellNetBgpM2PeerEntry
	}
	::= { dellNetBgpM2PeerErrorsTable 1 }


    DellNetBgpM2PeerErrorsEntry ::= SEQUENCE {
	dellNetBgpM2PeerLastErrorReceived
	    OCTET STRING,
	dellNetBgpM2PeerLastErrorSent
	    OCTET STRING,
	dellNetBgpM2PeerLastErrorReceivedTime
	    TimeTicks,
	dellNetBgpM2PeerLastErrorSentTime
	    TimeTicks,
	dellNetBgpM2PeerLastErrorReceivedText
	    SnmpAdminString,
	dellNetBgpM2PeerLastErrorSentText
	    SnmpAdminString,
	dellNetBgpM2PeerLastErrorReceivedData
	    OCTET STRING,
	dellNetBgpM2PeerLastErrorSentData
	    OCTET STRING
    }


    dellNetBgpM2PeerLastErrorReceived OBJECT-TYPE
	SYNTAX	   OCTET STRING (SIZE (2))
	MAX-ACCESS read-only
	STATUS	   current
	DESCRIPTION
	    "The last error code and subcode received by this BGP
	     Speaker via a NOTIFICATION message for this peer.
	     If no error has occurred, this field is zero.
	     Otherwise, the first byte of this two byte
	     OCTET STRING contains the error code, and the second
	     byte contains the subcode."
	REFERENCE
	    "draft-ietf-idr-bgp4-15.txt, Sec. 4.5"
	::= { dellNetBgpM2PeerErrorsEntry 1 }


    dellNetBgpM2PeerLastErrorSent OBJECT-TYPE
	SYNTAX	   OCTET STRING (SIZE (2))
	MAX-ACCESS read-only
	STATUS	   current
	DESCRIPTION
	    "The last error code and subcode sent by this BGP
	     Speaker via a NOTIFICATION message to this peer.
	     If no error has occurred, this field is zero.
	     Otherwise, the first byte of this two byte
	     OCTET STRING contains the error code, and the second
	     byte contains the subcode."
	REFERENCE
	    "draft-ietf-idr-bgp4-15.txt, Sec. 4.5"
	::= { dellNetBgpM2PeerErrorsEntry 2 }


    dellNetBgpM2PeerLastErrorReceivedTime OBJECT-TYPE
	SYNTAX	   TimeTicks
	MAX-ACCESS read-only
	STATUS	   current
	DESCRIPTION
	    "The timestamp that the last NOTIFICATION was received from
	     this peer."


	REFERENCE
	    "draft-ietf-idr-bgp4-15.txt, Sec. 4.5"
	::= { dellNetBgpM2PeerErrorsEntry 3 }


    dellNetBgpM2PeerLastErrorSentTime OBJECT-TYPE
	SYNTAX	   TimeTicks
	MAX-ACCESS read-only
	STATUS	   current
	DESCRIPTION
	    "The timestamp that the last NOTIFICATION was sent to
	     this peer."
	REFERENCE
	    "draft-ietf-idr-bgp4-15.txt, Sec. 4.5"
	::= { dellNetBgpM2PeerErrorsEntry 4 }


    dellNetBgpM2PeerLastErrorReceivedText OBJECT-TYPE
	SYNTAX	   SnmpAdminString
	MAX-ACCESS read-only
	STATUS	   current
	DESCRIPTION
	    "This object contains an implementation specific
	     explanation of the error that was reported."
	::= { dellNetBgpM2PeerErrorsEntry 5 }


    dellNetBgpM2PeerLastErrorSentText OBJECT-TYPE
	SYNTAX	   SnmpAdminString
	MAX-ACCESS read-only
	STATUS	   current
	DESCRIPTION
	    "This object contains an implementation specific
	     explanation of the error that is being reported."
	::= { dellNetBgpM2PeerErrorsEntry 6 }


    dellNetBgpM2PeerLastErrorReceivedData OBJECT-TYPE
	SYNTAX	   OCTET STRING (SIZE(0..4075))
	MAX-ACCESS read-only
	STATUS	   current
	DESCRIPTION
	    "The last error code's data seen by this peer."
	REFERENCE
	    "draft-ietf-idr-bgp4-15.txt, Sec. 4.5"
	::= { dellNetBgpM2PeerErrorsEntry 7 }


    dellNetBgpM2PeerLastErrorSentData OBJECT-TYPE
	SYNTAX	   OCTET STRING (SIZE(0..4075))
	MAX-ACCESS read-only
	STATUS	   current
	DESCRIPTION
	    "The last error code's data sent to this peer."
	REFERENCE
	    "draft-ietf-idr-bgp4-15.txt, Sec. 4.5"
	::= { dellNetBgpM2PeerErrorsEntry 8 }


    --
    -- Peer Event Times
    --

    dellNetBgpM2PeerTimers
	OBJECT IDENTIFIER ::= { dellNetBgpM2Peer 3 }


    dellNetBgpM2PeerEventTimesTable OBJECT-TYPE
	SYNTAX	   SEQUENCE OF DellNetBgpM2PeerEventTimesEntry
	MAX-ACCESS not-accessible
	STATUS	   current
	DESCRIPTION
	    "A table reporting the per-peering session amount
	     of time elapsed and update events since the peering
	     session advanced into the Established state."
	::= { dellNetBgpM2PeerTimers 1 }


    dellNetBgpM2PeerEventTimesEntry OBJECT-TYPE
	SYNTAX	   DellNetBgpM2PeerEventTimesEntry
	MAX-ACCESS not-accessible
	STATUS	   current
	DESCRIPTION
	    "Each row contains a set of statistics about time
	     spent and events encountered in the peer session
	     Established state."
	AUGMENTS {
	    dellNetBgpM2PeerEntry
	}
	::= { dellNetBgpM2PeerEventTimesTable 1 }


    DellNetBgpM2PeerEventTimesEntry ::= SEQUENCE {
	dellNetBgpM2PeerFsmEstablishedTime
	    Gauge32,
	dellNetBgpM2PeerInUpdatesElapsedTime
	    Gauge32
    }


    dellNetBgpM2PeerFsmEstablishedTime OBJECT-TYPE
	SYNTAX	   Gauge32
	MAX-ACCESS read-only
	STATUS	   current
	DESCRIPTION
	    "This timer indicates how long (in seconds) this
	     peer has been in the Established state or how long
	     since this peer was last in the Established state.
	     It is set to zero when a new peer is configured or
	     the router is booted."
	::= { dellNetBgpM2PeerEventTimesEntry 1 }


    dellNetBgpM2PeerInUpdatesElapsedTime OBJECT-TYPE
	SYNTAX	   Gauge32
	MAX-ACCESS read-only
	STATUS	   current
	DESCRIPTION
	    "Elapsed time in seconds since the last BGP UPDATE
	     message was received from the peer.  Each time
	     dellNetBgpM2PeerInUpdates is incremented, the value of this
	     object is set to zero (0).	 This value shall also be
	     zero (0) when the peer is not in the Established state"
	::= { dellNetBgpM2PeerEventTimesEntry 2 }


    --
    -- Peer Configured Timers
    --

    dellNetBgpM2PeerConfiguredTimersTable OBJECT-TYPE
	SYNTAX	   SEQUENCE OF DellNetBgpM2PeerConfiguredTimersEntry
	MAX-ACCESS not-accessible
	STATUS	   current
	DESCRIPTION
	    "Per peer management data on BGP session timers."
	::= { dellNetBgpM2PeerTimers 2 }

    dellNetBgpM2PeerConfiguredTimersEntry OBJECT-TYPE
	SYNTAX	   DellNetBgpM2PeerConfiguredTimersEntry
	MAX-ACCESS not-accessible
	STATUS	   current
	DESCRIPTION
	    "Each entry corresponds to the current state of

	     BGP timers on a given peering session."
	AUGMENTS {
	    dellNetBgpM2PeerEntry
	}
	::= { dellNetBgpM2PeerConfiguredTimersTable 1 }


    DellNetBgpM2PeerConfiguredTimersEntry ::= SEQUENCE {
	dellNetBgpM2PeerConnectRetryInterval
	    Unsigned32,
	dellNetBgpM2PeerHoldTimeConfigured
	    Unsigned32,
	dellNetBgpM2PeerKeepAliveConfigured
	    Unsigned32,
	dellNetBgpM2PeerMinASOrigInterval
	    Unsigned32,
	dellNetBgpM2PeerMinRouteAdverInterval
	    Unsigned32
    }


    dellNetBgpM2PeerConnectRetryInterval OBJECT-TYPE
	SYNTAX	   Unsigned32 (1..65535)
	MAX-ACCESS read-only
	STATUS	   current
	DESCRIPTION
	    "Time interval in seconds for the ConnectRetry
	     timer.  The suggested value for this timer is 120
	     seconds."
	::= { dellNetBgpM2PeerConfiguredTimersEntry 1 }


    dellNetBgpM2PeerHoldTimeConfigured OBJECT-TYPE
	SYNTAX	   Unsigned32 ( 0 | 3..65535 )
	MAX-ACCESS read-only
	STATUS	   current
	DESCRIPTION
	    "Time interval in seconds for the Hold Time configured
	     for this BGP speaker with this peer.  This value
	     is placed in an OPEN message sent to this peer by
	     this BGP speaker, and is compared with the Hold
	     Time field in an OPEN message received from the
	     peer when determining the Hold Time (dellNetBgpM2PeerHoldTime)
	     with the peer.  This value must not be less than
	     three seconds if it is not zero (0) in which case
	     the Hold Time is NOT to be established with the
	     peer.  The suggested value for this timer is 90
	     seconds."
	REFERENCE
	    "draft-ietf-idr-bgp4-17.txt, Appendix 6.4"
	::= { dellNetBgpM2PeerConfiguredTimersEntry 2 }


    dellNetBgpM2PeerKeepAliveConfigured OBJECT-TYPE
	SYNTAX	   Unsigned32 ( 0 | 1..21845 )
	MAX-ACCESS read-only
	STATUS	   current
	DESCRIPTION
	    "Time interval in seconds for the KeepAlive timer
	     configured for this BGP speaker with this peer.
	     The value of this object will only determine the
	     KEEPALIVE messages frequency relative to the value
	     specified in dellNetBgpM2PeerHoldTimeConfigured; the actual
	     time interval for the KEEPALIVE messages is indicated
	     by dellNetBgpM2PeerKeepAlive.  A reasonable maximum value
	     for this timer would be configured to be one third
	     of that of dellNetBgpM2PeerHoldTimeConfigured.

	     If the value of this object is zero (0), no
	     periodical KEEPALIVE messages are sent to the peer
	     after the BGP connection has been established.
	     The suggested value for this timer is 30 seconds."
	REFERENCE
	    "draft-ietf-idr-bgp4-17.txt, Appendix 6.4"
	::= { dellNetBgpM2PeerConfiguredTimersEntry 3 }


    dellNetBgpM2PeerMinASOrigInterval OBJECT-TYPE
	SYNTAX	   Unsigned32 (0..65535)
	MAX-ACCESS read-only
	STATUS	   current
	DESCRIPTION
	    "Time interval in seconds for the MinASOriginationInterval
	     timer.  The suggested value for this timer is 15
	     seconds."
	::= { dellNetBgpM2PeerConfiguredTimersEntry 4 }


    dellNetBgpM2PeerMinRouteAdverInterval OBJECT-TYPE
	SYNTAX	   Unsigned32 (0..65535)
	MAX-ACCESS read-only
	STATUS	   current
	DESCRIPTION
	    "Time interval in seconds for the
	     MinRouteAdvertisementInterval timer.  The suggested
	     value for this timer is 30 seconds."
	::= { dellNetBgpM2PeerConfiguredTimersEntry 5 }


    --
    -- Peer Negotiated Timers
    --

    dellNetBgpM2PeerNegotiatedTimersTable OBJECT-TYPE
	SYNTAX	   SEQUENCE OF DellNetBgpM2PeerNegotiatedTimersEntry
	MAX-ACCESS not-accessible
	STATUS	   current
	DESCRIPTION
	    "Current values of per-peer timers which can be
	     dynamically set in the dellNetBgpM2PeerConfiguredTimersTable.
	     Values reflected in this table are the current
	     operational values, after negotiation from values
	     derived from initial configuration or last set from
	     dellNetBgpM2PeerConfiguredTimersTable row instances."
	::= { dellNetBgpM2PeerTimers 3 }


    dellNetBgpM2PeerNegotiatedTimersEntry OBJECT-TYPE
	SYNTAX	   DellNetBgpM2PeerNegotiatedTimersEntry
	MAX-ACCESS not-accessible
	STATUS	   current
	DESCRIPTION
	    "Each entry reflects a value of the currently
	     operational, negotiated timers as reflected in the
	     DellNetBgpM2PeerNegotiatedTimersEntry."
	AUGMENTS {
	    dellNetBgpM2PeerEntry
	}
	::= { dellNetBgpM2PeerNegotiatedTimersTable 1 }


    DellNetBgpM2PeerNegotiatedTimersEntry ::= SEQUENCE {
	dellNetBgpM2PeerHoldTime
	    Unsigned32,
	dellNetBgpM2PeerKeepAlive
	    Unsigned32
    }


    dellNetBgpM2PeerHoldTime OBJECT-TYPE
	SYNTAX	   Unsigned32  ( 0 | 3..65535 )
	MAX-ACCESS read-only
	STATUS	   current
	DESCRIPTION
	    "The value of this object is calculated by this BGP
	     Speaker as being;

	     zero (0) - if this was the value sent by the peer and
	     this value is permitted by this BGP Speaker.  In this
	     case, no keepalive messages are sent and the Hold Timer
	     is not set.

	     At least three (3).  This value is the smaller of
	     the value sent by this peer in the OPEN message and
	     dellNetBgpM2PeerHoldTimeConfigured for this peer.

	     This value is only defined when the peering session is
	     in the Established state."
	REFERENCE
	    "draft-ietf-idr-bgp4-17.txt, Sec. 4.2"
	::= { dellNetBgpM2PeerNegotiatedTimersEntry 1 }


    dellNetBgpM2PeerKeepAlive OBJECT-TYPE
	SYNTAX	   Unsigned32 ( 0 | 1..21845 )
	MAX-ACCESS read-only
	STATUS	   current
	DESCRIPTION
	    "Time interval in seconds for the KeepAlive timer
	     established with the peer.	 The value of this object
	     is calculated by this BGP speaker such that, when
	     compared with dellNetBgpM2PeerHoldTime, it has the same
	     proportion as what dellNetBgpM2PeerKeepAliveConfigured has
	     when compared with dellNetBgpM2PeerHoldTimeConfigured.  If
	     the value of this object is zero (0), it indicates
	     that the KeepAlive timer has not been established
	     with the peer, or, the value of
	     dellNetBgpM2PeerKeepAliveConfigured is zero (0).

	     This value is only defined when the peering session is
	     in the Established state."
	REFERENCE
	    "draft-ietf-idr-bgp4-17, Sec. 4.4"
	::= { dellNetBgpM2PeerNegotiatedTimersEntry 2 }


    --
    -- Peer Capabilities
    --

    dellNetBgpM2PeerCapabilities
	OBJECT IDENTIFIER ::= { dellNetBgpM2Peer 4 }


    --
    -- Announced Capabilities
    --

    dellNetBgpM2PeerCapsAnnouncedTable OBJECT-TYPE
	SYNTAX	   SEQUENCE OF DellNetBgpM2PeerCapsAnnouncedEntry
	MAX-ACCESS not-accessible
	STATUS	   current
	DESCRIPTION
	    "This table contains the capabilities
	     that are supported for a given peer."
	::= { dellNetBgpM2PeerCapabilities 1 }


    dellNetBgpM2PeerCapsAnnouncedEntry OBJECT-TYPE
	SYNTAX	   DellNetBgpM2PeerCapsAnnouncedEntry
	MAX-ACCESS not-accessible
	STATUS	   current
	DESCRIPTION
	    "These entries are keyed by a BGP-4 peer remote
	     address and the BGP Capability Code"
	INDEX {
	    dellNetBgpM2PeerIndex,
	    dellNetBgpM2PeerCapAnnouncedCode,
	    dellNetBgpM2PeerCapAnnouncedIndex
	}
	::= { dellNetBgpM2PeerCapsAnnouncedTable 1 }


    DellNetBgpM2PeerCapsAnnouncedEntry ::= SEQUENCE {
	dellNetBgpM2PeerCapAnnouncedCode
	    Unsigned32,
	dellNetBgpM2PeerCapAnnouncedIndex
	    Unsigned32,
	dellNetBgpM2PeerCapAnnouncedValue
	    OCTET STRING
    }


    dellNetBgpM2PeerCapAnnouncedCode OBJECT-TYPE
	SYNTAX	   Unsigned32 (0..255)
	MAX-ACCESS read-only
	STATUS	   current
	DESCRIPTION
	    "The BGP Capability Advertisement Capability Code."
	::= { dellNetBgpM2PeerCapsAnnouncedEntry 1 }


    dellNetBgpM2PeerCapAnnouncedIndex OBJECT-TYPE
	SYNTAX	   Unsigned32 (1..128)
	MAX-ACCESS read-only
	STATUS	   current
	DESCRIPTION
	    "Multiple instances of a given capability may be sent
	     bgp a BGP speaker.	 This variable is used to index them."
	::= { dellNetBgpM2PeerCapsAnnouncedEntry 2 }


    dellNetBgpM2PeerCapAnnouncedValue OBJECT-TYPE
	SYNTAX	   OCTET STRING (SIZE(0..255))
	MAX-ACCESS read-only
	STATUS	   current
	DESCRIPTION
	    "The value of the announced capability."
	::= { dellNetBgpM2PeerCapsAnnouncedEntry 3 }


    --
    -- Received Capabilities
    --

    dellNetBgpM2PeerCapsReceivedTable OBJECT-TYPE
	SYNTAX	   SEQUENCE OF DellNetBgpM24PeerCapsReceivedEntry
	MAX-ACCESS not-accessible
	STATUS	   current
	DESCRIPTION
	    "This table contains the capabilities
	    that are supported for a given peer."
	::= { dellNetBgpM2PeerCapabilities 2 }


    dellNetBgpM2PeerCapsReceivedEntry OBJECT-TYPE
	SYNTAX	   DellNetBgpM24PeerCapsReceivedEntry
	MAX-ACCESS not-accessible
	STATUS	   current
	DESCRIPTION
	    "These entries are keyed by a BGP-4 peer remote
	    address and the BGP Capability Code"
	INDEX {
	    dellNetBgpM2PeerIndex,
	    dellNetBgpM2PeerCapReceivedCode,
	    dellNetBgpM2PeerCapReceivedIndex
	}
	::= { dellNetBgpM2PeerCapsReceivedTable 1 }


    DellNetBgpM24PeerCapsReceivedEntry ::= SEQUENCE {
	dellNetBgpM2PeerCapReceivedCode
	    Unsigned32,
	dellNetBgpM2PeerCapReceivedIndex
	    Unsigned32,
	dellNetBgpM2PeerCapReceivedValue
	    OCTET STRING
    }


    dellNetBgpM2PeerCapReceivedCode OBJECT-TYPE
	SYNTAX	   Unsigned32 (0..255)
	MAX-ACCESS read-only
	STATUS	   current
	DESCRIPTION
	    "The BGP Capability Advertisement Capability Code."
	::= { dellNetBgpM2PeerCapsReceivedEntry 1 }


    dellNetBgpM2PeerCapReceivedIndex OBJECT-TYPE
	SYNTAX	   Unsigned32 (1..128)
	MAX-ACCESS read-only
	STATUS	   current
	DESCRIPTION
	    "Multiple instances of a given capability may be sent
	     bgp a BGP speaker.	 This variable is used to index them."
	::= { dellNetBgpM2PeerCapsReceivedEntry 2 }


    dellNetBgpM2PeerCapReceivedValue OBJECT-TYPE
	SYNTAX	   OCTET STRING (SIZE(0..255))
	MAX-ACCESS read-only
	STATUS	   current
	DESCRIPTION
	    "The value of the announced capability."
	::= { dellNetBgpM2PeerCapsReceivedEntry 3 }


    --
    -- Per-peer counters
    --

    dellNetBgpM2PeerCounters
	OBJECT IDENTIFIER ::= { dellNetBgpM2Peer 6 }


    dellNetBgpM2PeerCountersTable OBJECT-TYPE
	SYNTAX	   SEQUENCE OF DellNetBgpM2PeerCountersEntry
	MAX-ACCESS not-accessible
	STATUS	   current
	DESCRIPTION
	    "The counters associated with a BGP Peer."
	::= { dellNetBgpM2PeerCounters 1 }


    dellNetBgpM2PeerCountersEntry OBJECT-TYPE
	SYNTAX	   DellNetBgpM2PeerCountersEntry
	MAX-ACCESS not-accessible
	STATUS	   current
	DESCRIPTION
	    "Each entry contains counters of message transmissions
	     and FSM transitions for a given BGP Peering session."
	AUGMENTS {
	    dellNetBgpM2PeerEntry
	}
	::= { dellNetBgpM2PeerCountersTable 1 }


    DellNetBgpM2PeerCountersEntry ::= SEQUENCE {
	dellNetBgpM2PeerInUpdates
	    Counter32,
	dellNetBgpM2PeerOutUpdates
	    Counter32,
	dellNetBgpM2PeerInTotalMessages
	    Counter32,
	dellNetBgpM2PeerOutTotalMessages
	    Counter32,
	dellNetBgpM2PeerFsmEstablishedTrans
	    Counter32,
	dellNetBgpM2PeerInKeepalives
	    Counter32,
	dellNetBgpM2PeerOutKeepalives 
	    Counter32,
	dellNetBgpM2PeerInOpen 
	    Counter32,
	dellNetBgpM2PeerOutOpen
	    Counter32,
	dellNetBgpM2PeerInRteRefresh 
	    Counter32,
	dellNetBgpM2PeerOutRteRefresh 
	    Counter32	
    }


-- +++wayne need to describe what happens if connection is broken
-- and then reestablished. Does the prior counter value accumulate?
    dellNetBgpM2PeerInUpdates OBJECT-TYPE
	SYNTAX	   Counter32
	MAX-ACCESS read-only
	STATUS	   current
	DESCRIPTION
	    "The number of BGP UPDATE messages received on this
	     connection.  This object should be initialized to zero
	     (0) when the connection is established."
	::= { dellNetBgpM2PeerCountersEntry 1 }


    dellNetBgpM2PeerOutUpdates OBJECT-TYPE
	SYNTAX	   Counter32
	MAX-ACCESS read-only
	STATUS	   current
	DESCRIPTION
	    "The number of BGP UPDATE messages transmitted on this
	     connection.  This object should be initialized to zero
	     (0) when the connection is established."
	::= { dellNetBgpM2PeerCountersEntry 2 }


    dellNetBgpM2PeerInTotalMessages OBJECT-TYPE
	SYNTAX	   Counter32
	MAX-ACCESS read-only
	STATUS	   current
	DESCRIPTION
	    "The total number of messages received from the remote
	     peer on this connection.  This object should be
	     initialized to zero when the connection is established."
	::= { dellNetBgpM2PeerCountersEntry 3 }


    dellNetBgpM2PeerOutTotalMessages OBJECT-TYPE
	SYNTAX	   Counter32
	MAX-ACCESS read-only
	STATUS	   current
	DESCRIPTION
	"The total number of messages transmitted to the remote
	peer on this connection.  This object should be
	initialized to zero when the connection is established."
	::= { dellNetBgpM2PeerCountersEntry 4 }


    dellNetBgpM2PeerFsmEstablishedTrans OBJECT-TYPE
	SYNTAX	   Counter32
	MAX-ACCESS read-only
	STATUS	   current
	DESCRIPTION
	"The total number of times the BGP FSM
	transitioned into the established state
	for this peer."
	::= { dellNetBgpM2PeerCountersEntry 5 }

    dellNetBgpM2PeerInKeepalives OBJECT-TYPE
	SYNTAX	   Counter32
	MAX-ACCESS read-only
	STATUS	   current
	DESCRIPTION
	"The number of Keepalive messages 
	received from a peer.Implemented by Dell."
	::= { dellNetBgpM2PeerCountersEntry 6 }

    dellNetBgpM2PeerOutKeepalives OBJECT-TYPE
	SYNTAX	   Counter32
	MAX-ACCESS read-only
	STATUS	   current
	DESCRIPTION
	"The number of Keepalive messages sent 
	to a peer. Implemented by Dell."
	::= { dellNetBgpM2PeerCountersEntry 7 }

    dellNetBgpM2PeerInOpen OBJECT-TYPE
	SYNTAX	   Counter32
	MAX-ACCESS read-only
	STATUS	   current
	DESCRIPTION
	"The number of Open messages received 
	from a peer. Implemented by Dell."
	::= { dellNetBgpM2PeerCountersEntry 8 }

    dellNetBgpM2PeerOutOpen OBJECT-TYPE
	SYNTAX	   Counter32
	MAX-ACCESS read-only
	STATUS	   current
	DESCRIPTION
	"The number of Open messages sent to a peer.
	Implemented by Dell."
	::= { dellNetBgpM2PeerCountersEntry 9 }

    dellNetBgpM2PeerInRteRefresh OBJECT-TYPE
	SYNTAX	   Counter32
	MAX-ACCESS read-only
	STATUS	   current
	DESCRIPTION
	"The number of Route Refresh messages 
	received from a peer. Implemented by Dell."
	::= { dellNetBgpM2PeerCountersEntry 10 }

    dellNetBgpM2PeerOutRteRefresh OBJECT-TYPE
	SYNTAX	   Counter32
	MAX-ACCESS read-only
	STATUS	   current
	DESCRIPTION
	"The number of Route Refresh messages sent 
	to a peer. Implemented by Dell."
	::= { dellNetBgpM2PeerCountersEntry 11 }


    --
    -- Per-Peer Prefix Counters
    --

    dellNetBgpM2PrefixCountersTable OBJECT-TYPE



	SYNTAX	   SEQUENCE OF DellNetBgpM2PrefixCountersEntry
	MAX-ACCESS not-accessible
	STATUS	   current
	DESCRIPTION
	    "Additional per-peer, per AFI SAFI counters for prefixes"
	::= { dellNetBgpM2PeerCounters 2 }


    dellNetBgpM2PrefixCountersEntry OBJECT-TYPE
	SYNTAX	   DellNetBgpM2PrefixCountersEntry
	MAX-ACCESS not-accessible
	STATUS	   current
	DESCRIPTION
	    "Entry containing information about a bgp-peers prefix
	     counters."
	INDEX {
	    dellNetBgpM2PeerIndex,
	    dellNetBgpM2PrefixCountersAfi,
	    dellNetBgpM2PrefixCountersSafi
	}
	::= { dellNetBgpM2PrefixCountersTable 1 }


    DellNetBgpM2PrefixCountersEntry ::= SEQUENCE {
	dellNetBgpM2PrefixCountersAfi
	    DellNetBgpM2Afi,
	dellNetBgpM2PrefixCountersSafi
	    DellNetBgpM2Safi,
	dellNetBgpM2PrefixInPrefixes
	    Gauge32,
	dellNetBgpM2PrefixInPrefixesAccepted
	    Gauge32,
	dellNetBgpM2PrefixInPrefixesRejected
	    Gauge32,
	dellNetBgpM2PrefixOutPrefixes
	    Gauge32,
	dellNetBgpM2PrefixWdrawnByPeer 
	    Gauge32,
	dellNetBgpM2PrefixWdrawnFromPeer 
	    Gauge32
    }


    dellNetBgpM2PrefixCountersAfi OBJECT-TYPE
	SYNTAX	   DellNetBgpM2Afi
	MAX-ACCESS read-only
	STATUS	   current
	DESCRIPTION
	    "The AFI index of the per-peer, per prefix counters"
	::= { dellNetBgpM2PrefixCountersEntry 1 }


    dellNetBgpM2PrefixCountersSafi OBJECT-TYPE
	SYNTAX	   DellNetBgpM2Safi
	MAX-ACCESS read-only
	STATUS	   current
	DESCRIPTION
	    "The SAFI index of the per-peer, per prefix counters"
	::= { dellNetBgpM2PrefixCountersEntry 2 }


    dellNetBgpM2PrefixInPrefixes OBJECT-TYPE
	SYNTAX	   Gauge32
	MAX-ACCESS read-only
	STATUS	   current
	DESCRIPTION
	    "The number of prefixes received from a peer and are
	     stored in the Adj-Ribs-In for that peer."
	     -- jmh - note that we are allowing stuff to be discarded
	::= { dellNetBgpM2PrefixCountersEntry 7 }


    dellNetBgpM2PrefixInPrefixesAccepted OBJECT-TYPE
	SYNTAX	   Gauge32
	MAX-ACCESS read-only
	STATUS	   current
	DESCRIPTION
	    "The number of prefixes for a peer that are installed
	     in the Adj-Ribs-In and are eligible to become active
	     in the Loc-Rib."
	::= { dellNetBgpM2PrefixCountersEntry 8 }


    dellNetBgpM2PrefixInPrefixesRejected OBJECT-TYPE
	SYNTAX	   Gauge32
	MAX-ACCESS read-only
	STATUS	   current
	DESCRIPTION
	    "The number of prefixes for a peer that are installed
	     in the Adj-Ribs-In and are NOT eligible to become active
	     in the Loc-Rib."
	::= { dellNetBgpM2PrefixCountersEntry 9 }


    dellNetBgpM2PrefixOutPrefixes OBJECT-TYPE
	SYNTAX	   Gauge32
	MAX-ACCESS read-only
	STATUS	   current
	DESCRIPTION
	    "The number of prefixes for a peer that are installed
	     in that peers Adj-Ribs-Out."
	::= { dellNetBgpM2PrefixCountersEntry 10 }

    dellNetBgpM2PrefixWdrawnByPeer OBJECT-TYPE
	SYNTAX	   Gauge32
	MAX-ACCESS read-only
	STATUS	   current
	DESCRIPTION
	    "The number of prefixes withdrawn by a peer.
	    Implemened by Dell."
	::= { dellNetBgpM2PrefixCountersEntry 11 }

    dellNetBgpM2PrefixWdrawnFromPeer OBJECT-TYPE
	SYNTAX	   Gauge32
	MAX-ACCESS read-only
	STATUS	   current
	DESCRIPTION
	    "The number of prefixes withdrawn from a peer.
	    Implemened by Dell."
	::= { dellNetBgpM2PrefixCountersEntry 12 }



    dellNetBgpM2PeerExtensions
	OBJECT IDENTIFIER ::= { dellNetBgpM2Peer 7 }


    dellNetBgpM2PeerNonCapExts
	OBJECT IDENTIFIER ::= { dellNetBgpM2PeerExtensions 1 }


    dellNetBgpM2PeerCapExts
	OBJECT IDENTIFIER ::= { dellNetBgpM2PeerExtensions 2 }


    --
    -- Peer Route Reflection Extensions
    --

    dellNetBgpM2PeerRouteReflectionExts
	OBJECT IDENTIFIER ::= { dellNetBgpM2PeerNonCapExts 2796 }


    dellNetBgpM2PeerReflectorClientTable OBJECT-TYPE
	SYNTAX	   SEQUENCE OF DellNetBgpM2PeerReflectorClientEntry
	MAX-ACCESS not-accessible
	STATUS	   current
	DESCRIPTION
	    "Table of route reflection client settings on a per-peer
	     basis."
	REFERENCE
	    "RFC 2796 - BGP Route Reflection"
	::= { dellNetBgpM2PeerRouteReflectionExts 1 }


    dellNetBgpM2PeerReflectorClientEntry OBJECT-TYPE
	SYNTAX	   DellNetBgpM2PeerReflectorClientEntry
	MAX-ACCESS not-accessible
	STATUS	   current
	DESCRIPTION
	    "Entry containing data on a per-peer basis on whether
	     the peer is configured as a route reflector client."
	REFERENCE
	    "RFC 2796 - BGP Route Reflection"
	AUGMENTS {
	    dellNetBgpM2PeerEntry

	}
	::= { dellNetBgpM2PeerReflectorClientTable 1 }


    DellNetBgpM2PeerReflectorClientEntry ::= SEQUENCE {
	dellNetBgpM2PeerReflectorClient
	    INTEGER
    }

    dellNetBgpM2PeerReflectorClient OBJECT-TYPE
	SYNTAX	  INTEGER {
	    nonClient(0),
	    client(1),
	    meshedClient(2)
	}
	MAX-ACCESS  read-only
	STATUS	    current
	DESCRIPTION
	    "This value indicates whether the given peer is a
	     reflector client of this router, or not.  A value of
	     nonClient indicates that this peer is not a reflector
	     client.  A value of client indicates that this peer is a
	     reflector client that is not fully meshed with other
	     reflector clients.	 A value of meshedClient indicates
	     that the peer is a reflector client and is fully meshed
	     with all other reflector clients.

	     This value must be nonClient (0) for BGP external peers."
	REFERENCE
	    "RFC 2796 - BGP Route Reflection"
	::= { dellNetBgpM2PeerReflectorClientEntry 1 }


    --
    -- Peer AS Confederations Extensions
    --

    dellNetBgpM2PeerASConfederationExts
	OBJECT IDENTIFIER ::= { dellNetBgpM2PeerNonCapExts 3065 }


    dellNetBgpM2PeerConfedMemberTable OBJECT-TYPE
	SYNTAX	   SEQUENCE OF DellNetBgpM2PeerConfedMemberEntry
	MAX-ACCESS not-accessible
	STATUS	   current
	DESCRIPTION
	    "Table of confederation member settings on a per-peer
	     basis."


	REFERENCE
	    "RFC 3065 - BGP Confederations"
	::= { dellNetBgpM2PeerASConfederationExts 1 }


    dellNetBgpM2PeerConfedMemberEntry OBJECT-TYPE
	SYNTAX	   DellNetBgpM2PeerConfedMemberEntry
	MAX-ACCESS not-accessible
	STATUS	   current
	DESCRIPTION
	    "Entry containing data on a per-peer basis on whether
	     the peer is configured as a BGP confederation member."
	REFERENCE
	    "RFC 3065 - BGP Confederations"
	AUGMENTS {
	    dellNetBgpM2PeerEntry
	}
	::= { dellNetBgpM2PeerConfedMemberTable 1 }


    DellNetBgpM2PeerConfedMemberEntry ::= SEQUENCE {
	dellNetBgpM2PeerConfedMember
	    TruthValue
    }


    dellNetBgpM2PeerConfedMember OBJECT-TYPE
	SYNTAX	    TruthValue
	MAX-ACCESS  read-only
	STATUS	    current
	DESCRIPTION
	    "This value indicates whether the given peer is in our
	     confederation or not."
	REFERENCE
	    "RFC 3065 - BGP Confederations"
	::= { dellNetBgpM2PeerConfedMemberEntry 1 }


    --
    -- Peer configuration objects
    --

    dellNetBgpM2PeerConfiguration
	OBJECT IDENTIFIER ::= { dellNetBgpM2Peer 8 }


    --
    -- Administering activated peering sessions
    --

    dellNetBgpM2CfgPeerAdminStatusTable OBJECT-TYPE
	SYNTAX	   SEQUENCE OF DellNetBgpM2CfgPeerAdminStatusEntry
	MAX-ACCESS not-accessible
	STATUS	   current
	DESCRIPTION
	    "Table containing rows for administratively starting and
	     stopping peering sessions."
	::= { dellNetBgpM2PeerConfiguration 1 }


    dellNetBgpM2CfgPeerAdminStatusEntry OBJECT-TYPE
	SYNTAX	   DellNetBgpM2CfgPeerAdminStatusEntry
	MAX-ACCESS not-accessible
	STATUS	   current
	DESCRIPTION
	    "Entry containing row for administratively starting and
	     stopping peers."
	INDEX {
	    dellNetBgpM2PeerIndex
	}
	::= { dellNetBgpM2CfgPeerAdminStatusTable 1 }


    DellNetBgpM2CfgPeerAdminStatusEntry ::= SEQUENCE {
	dellNetBgpM2CfgPeerAdminStatus
	    INTEGER
    }


    dellNetBgpM2CfgPeerAdminStatus OBJECT-TYPE
	SYNTAX	    INTEGER {
	    stop(1),
	    start(2)
	}
	MAX-ACCESS read-write
	STATUS	current
	DESCRIPTION
	    "This object allows the Manual Stop and Manual Start
	     events to be sent to an activated peering session."
	::= { dellNetBgpM2CfgPeerAdminStatusEntry 1 }


    --
    -- Peer Configuration
    --


    dellNetBgpM2CfgPeerNextIndex OBJECT-TYPE
	SYNTAX	   Integer32 (0..65535)
	MAX-ACCESS read-only
	STATUS	   current
	DESCRIPTION
	    "This object contains the next appropriate value to
	     use as an index for creation of a row instance in
	     in the dellNetBgpM2CfgPeerTable.	If the number of available
	     entries in the dellNetBgpM2CfgPeerTable is exhausted, a
	     retrieval value of this object instance will return
	     0.	 A value of 0 may also be returned if the agent
	     is otherwise incapable of dellNetBgpM2CfgPeerTable row creation
	     at the time of dellNetBgpM2CfgPeerNextIndex retrieval."
	::= { dellNetBgpM2PeerConfiguration 2 }


    dellNetBgpM2CfgPeerTable OBJECT-TYPE
	SYNTAX	   SEQUENCE OF DellNetBgpM2CfgPeerEntry
	MAX-ACCESS not-accessible
	STATUS	   current
	DESCRIPTION
	    "BGP configuration peer table.

	     This table allows the configuration of the parameters
	     for a session with a BGP peer.

	     +++wayne provide description of how config should be done
	     for a peer per table."
	::= { dellNetBgpM2PeerConfiguration 3 }


    dellNetBgpM2CfgPeerEntry OBJECT-TYPE
	SYNTAX	   DellNetBgpM2CfgPeerEntry
	MAX-ACCESS not-accessible
	STATUS	   current
	DESCRIPTION
	    "Entry containing information set up by a management
	     entity to configure a connection with a BGP peer."
	INDEX { dellNetBgpM2CfgPeerIndex }
	::= { dellNetBgpM2CfgPeerTable 1 }


    DellNetBgpM2CfgPeerEntry ::= SEQUENCE {
	dellNetBgpM2CfgPeerConfiguredVersion
	    Unsigned32,
	dellNetBgpM2CfgAllowVersionNegotiation
	    TruthValue,
	dellNetBgpM2CfgPeerLocalAddrType
	    InetAddressType,
	dellNetBgpM2CfgPeerLocalAddr
	    InetAddress,
	dellNetBgpM2CfgPeerLocalAs
	    InetAutonomousSystemNumber,
	dellNetBgpM2CfgPeerRemoteAddrType
	    InetAddressType,
	dellNetBgpM2CfgPeerRemoteAddr
	    InetAddress,
	dellNetBgpM2CfgPeerRemoteAs
	    InetAutonomousSystemNumber,
	dellNetBgpM2CfgPeerEntryStorageType
	    StorageType,
	dellNetBgpM2CfgPeerError
	    INTEGER,
	dellNetBgpM2CfgPeerBgpPeerEntry
	    RowPointer,
	dellNetBgpM2CfgPeerRowEntryStatus
	    RowStatus,
	dellNetBgpM2CfgPeerIndex
	    Integer32,
	dellNetBgpM2CfgPeerStatus
	    INTEGER
	}


    dellNetBgpM2CfgPeerConfiguredVersion OBJECT-TYPE
	SYNTAX	   Unsigned32 (1..255)
	MAX-ACCESS read-create
	STATUS	   current
	DESCRIPTION
	    "The configured version to originally start with
	     this peer.	 The BGP speaker may permit negotiation
	     to a lower version number of the protocol depending on the
	     set value of dellNetBgpM2CfgAllowVersionNegotiation."
	DEFVAL	   { 4 }
	::= { dellNetBgpM2CfgPeerEntry 1 }


    dellNetBgpM2CfgAllowVersionNegotiation OBJECT-TYPE
	SYNTAX	   TruthValue
	MAX-ACCESS read-create
	STATUS	   current
	DESCRIPTION
	    "If set to true, during session establishment with this
	     peer, negotiation to a version lower than that specified
	     in dellNetBgpM2CfgPeerConfiguredVersion will be allowed."
	DEFVAL { false }


	::= { dellNetBgpM2CfgPeerEntry 2 }


    dellNetBgpM2CfgPeerLocalAddrType OBJECT-TYPE
	SYNTAX	   InetAddressType
	MAX-ACCESS read-create
	STATUS	   current
	DESCRIPTION
	    "The address family of the speakers of this BGP
	     session."
	::= { dellNetBgpM2CfgPeerEntry 3 }


    dellNetBgpM2CfgPeerLocalAddr OBJECT-TYPE
	SYNTAX	   InetAddress (SIZE (4..20))
	MAX-ACCESS read-create
	STATUS	   current
	DESCRIPTION
	    "The address of the local end of the peering session."
	::= { dellNetBgpM2CfgPeerEntry 4 }


    dellNetBgpM2CfgPeerLocalAs OBJECT-TYPE
	SYNTAX	   InetAutonomousSystemNumber
	MAX-ACCESS read-create
	STATUS	   current
	DESCRIPTION
	    "Autonomous system represented to peer on peering
	     session initialization.  Some implementations of
	     BGP can represent themselves as multiple ASes.
	     These implementations can set this to an alternate
	     autonomous system.	 If this object is set to zero
	     (0) at the point this row instance is set to active,
	     then the implementation will initialize this session
	     representing itself as the value of dellNetBgpM2CfgLocalAs."
	DEFVAL { 0 }
	::= { dellNetBgpM2CfgPeerEntry 5 }


    dellNetBgpM2CfgPeerRemoteAddrType OBJECT-TYPE
	SYNTAX	   InetAddressType
	MAX-ACCESS read-create
	STATUS	   current
	DESCRIPTION
	    "The address family of the speakers of the remote BGP
	     session."
	::= { dellNetBgpM2CfgPeerEntry 6 }

    dellNetBgpM2CfgPeerRemoteAddr OBJECT-TYPE
	SYNTAX	    InetAddress (SIZE(4..20))
	MAX-ACCESS  read-create
	STATUS	    current
	DESCRIPTION
	    "The address of the remote end (destination address
	     of peer) for peering session."
	::= { dellNetBgpM2CfgPeerEntry 7 }


    dellNetBgpM2CfgPeerRemoteAs OBJECT-TYPE
	SYNTAX	   InetAutonomousSystemNumber
	MAX-ACCESS read-create
	STATUS	   current
	DESCRIPTION
	    "Autonomous system number of the remote peer."
	::= { dellNetBgpM2CfgPeerEntry 8 }


    dellNetBgpM2CfgPeerEntryStorageType OBJECT-TYPE
	SYNTAX	   StorageType
	MAX-ACCESS read-create
	STATUS	   current
	DESCRIPTION
	    "This object type specifies the intended storage
	     type for the dellNetBgpM2CfgPeerEntry row instance."
	::= { dellNetBgpM2CfgPeerEntry 9 }


    dellNetBgpM2CfgPeerError  OBJECT-TYPE
	SYNTAX	    INTEGER {
	    unknown(0),
	    notActivated (1),
	    errDuplicatePeeringSession (2),
	    activated (3)
	    -- +++wayne more to follow
	}
	MAX-ACCESS  read-only
	STATUS	    current
	DESCRIPTION
	    "This value indicates the current error status of
	     the row denoting the configured error status.

	     If this row is still under creation (has not been activated
	     dellNetBgpM2CfgPeerRowEntryStatus), then this instance will be set to
	     not-activated (1).

	     At the point that the row is activated, dellNetBgpM2CfgPeerError
	     will reflect the error status of the row data itself.  If
	     there is another session already activated with the same
	     local and remote addresses as denoted by
	     {dellNetBgpM2CfgPeerLocalAddrType, dellNetBgpM2CfgPeerLocalAddr,
	     dellNetBgpM2CfgPeerRemoteAddr}, then
	     the value of this will be set to
	     err-duplicate-peering-session (2).

	     If this row is associated with a peer session whose
	     initialization has been attempted, the value will be
	     set to activated (3) (and, dellNetBgpM2PeerCfgPeerEntry will
	     be set to the row instance of the entry in the
	     dellNetBgpM2PeerTable which reflects the state of the peering
	     session).

	     Note that this object only reflects the error as a
	     function of the attempted activation of this row as
	     containing data for a bgp peering session.	 The actual
	     state of the session at the point of any protocol exchange
	     or session state machine initiation is reflected in the
	     dellNetBgpM2PeerTable row instance (as reflected through
	     dellNetBgpM2CfgPeerPeerEntry) associated with this row instance."
	::= { dellNetBgpM2CfgPeerEntry 10 }


    dellNetBgpM2CfgPeerBgpPeerEntry OBJECT-TYPE
	SYNTAX	    RowPointer
	MAX-ACCESS  read-only
	STATUS	    current
	DESCRIPTION
	    "Upon activation of the session data contained in this
	     row instance, this object points to an instance of a row
	     within the dellNetBgpM2PeerTable reflecting the session in its
	     initializing or operational state.	 Retrieval of this
	     column instance will always yield a value of {0.0} unless
	     the session has successfully been activated (via
	     dellNetBgpM2CfgPeerRowEntryStatus).  Such row instances will always
	     have a value of dellNetBgpM2CfgPeerError which is activated (3)."
	::= { dellNetBgpM2CfgPeerEntry 11 }


    dellNetBgpM2CfgPeerRowEntryStatus	OBJECT-TYPE
	SYNTAX	   RowStatus
	MAX-ACCESS read-create
	STATUS	   current
	DESCRIPTION
	    "This object type is used to control creation,
	     activation, and deletion of this row instance."

	    -- +++wayne need better directions for agent auto-removal
	    -- of row instances which have moved to active or error
	    -- state
	::= { dellNetBgpM2CfgPeerEntry 12 }


    dellNetBgpM2CfgPeerIndex OBJECT-TYPE
	SYNTAX	   Integer32 (1..65535)
	MAX-ACCESS accessible-for-notify
	STATUS	   current
	DESCRIPTION
	    "Uniquely identifies an instance of a peer row, as
	     an element of configuration."
	::= { dellNetBgpM2CfgPeerEntry 13 }


    dellNetBgpM2CfgPeerStatus OBJECT-TYPE
	SYNTAX	    INTEGER {
	    halted(1),
	    running(2)
	}
	MAX-ACCESS read-create
	STATUS	current
	DESCRIPTION
	     "This specifies the state of the peering session upon
	      activation.  If disabled, the FSM is in the halted
	      state and no Automatic Start events are generated.
	      If enabled, the FSM is in the running state and
	      Automatic Start events may be generated."
	::= { dellNetBgpM2CfgPeerEntry 14 }


    --
    -- Per-peer timers table
    --

    dellNetBgpM2CfgPeerTimersTable OBJECT-TYPE
	SYNTAX	   SEQUENCE OF DellNetBgpM2CfgPeerTimersEntry
	MAX-ACCESS not-accessible
	STATUS	   current
	DESCRIPTION
	    "Table for configuration of per-peer timers."
	::= {  dellNetBgpM2PeerConfiguration 4 }


    dellNetBgpM2CfgPeerTimersEntry OBJECT-TYPE
	SYNTAX	    DellNetBgpM2CfgPeerTimersEntry
	MAX-ACCESS not-accessible


	STATUS	   current
	DESCRIPTION
	    "Entry containing per-peer timer configuration."
	AUGMENTS {
	    dellNetBgpM2CfgPeerEntry
	}
	::= { dellNetBgpM2CfgPeerTimersTable 1 }


    DellNetBgpM2CfgPeerTimersEntry ::= SEQUENCE {
	dellNetBgpM2CfgPeerConnectRetryInterval
	    Unsigned32,
	dellNetBgpM2CfgPeerHoldTimeConfigured
	    Unsigned32,
	dellNetBgpM2CfgPeerKeepAliveConfigured
	    Unsigned32,
	dellNetBgpM2CfgPeerMinASOrigInterval
	    Unsigned32,
	dellNetBgpM2CfgPeerMinRouteAdverInter
	    Unsigned32
    }


    dellNetBgpM2CfgPeerConnectRetryInterval OBJECT-TYPE
	SYNTAX	   Unsigned32 (1..65535)
	MAX-ACCESS read-create
	STATUS	   current
	DESCRIPTION
	    "Time interval in seconds for the ConnectRetry
	     timer.  The suggested value for this timer is 120
	     seconds."
	DEFVAL {
	    120
	}
	::= { dellNetBgpM2CfgPeerTimersEntry 1 }


    dellNetBgpM2CfgPeerHoldTimeConfigured OBJECT-TYPE
	SYNTAX	   Unsigned32 ( 0 | 3..65535 )
	MAX-ACCESS read-create
	STATUS	   current
	DESCRIPTION
	    "Time interval in seconds for the Hold Time configured
	     for this BGP speaker with this peer.  This value
	     is placed in an OPEN message sent to this peer by
	     this BGP speaker, and is compared with the Hold
	     Time field in an OPEN message received from the
	     peer when determining the Hold Time (dellNetBgpM2PeerHoldTime)
	     with the peer.  This value must not be less than
	     three seconds if it is not zero (0) in which case
	     the Hold Time is NOT to be established with the
	     peer.  The suggested value for this timer is 90
	     seconds."
	REFERENCE
	    "draft-ietf-idr-bgp4-17.txt, Appendix 6.4"
	DEFVAL {
	    90
	}
	::= { dellNetBgpM2CfgPeerTimersEntry 2 }


    dellNetBgpM2CfgPeerKeepAliveConfigured OBJECT-TYPE
	SYNTAX	   Unsigned32 ( 0 | 1..21845 )
	MAX-ACCESS read-create
	STATUS	   current
	DESCRIPTION
	    "Time interval in seconds for the KeepAlive timer
	     configured for this BGP speaker with this peer.
	     The value of this object will only determine the
	     KEEPALIVE messages frequency relative to the value
	     specified in dellNetBgpM2PeerHoldTimeConfigured; the actual
	     time interval for the KEEPALIVE messages is indicated
	     by dellNetBgpM2PeerKeepAlive.  A reasonable maximum value
	     for this timer would be configured to be one third
	     of that of dellNetBgpM2PeerHoldTimeConfigured.

	     If the value of this object is zero (0), no
	     periodical KEEPALIVE messages are sent to the peer
	     after the BGP connection has been established.
	     The suggested value for this timer is 30 seconds."
	REFERENCE
	    "draft-ietf-idr-bgp4-17.txt, Appendix 6.4"
	DEFVAL {
	    30
	}
	::= { dellNetBgpM2CfgPeerTimersEntry 3 }


    dellNetBgpM2CfgPeerMinASOrigInterval OBJECT-TYPE
	SYNTAX	   Unsigned32 (0..65535)
	MAX-ACCESS read-create
	STATUS	   current
	DESCRIPTION
	    "Time interval in seconds for the MinASOriginationInterval
	     timer.  The suggested value for this timer is 15
	     seconds."

	DEFVAL {
	    15
	}
	::= { dellNetBgpM2CfgPeerTimersEntry 4 }


    dellNetBgpM2CfgPeerMinRouteAdverInter OBJECT-TYPE
	SYNTAX	   Unsigned32 (0..65535)
	MAX-ACCESS read-create
	STATUS	   current
	DESCRIPTION
	    "Time interval in seconds for the
	     MinRouteAdvertisementInterval timer.  The suggested
	     value for this timer is 30 seconds."
	DEFVAL {
	    30
	}
	::= { dellNetBgpM2CfgPeerTimersEntry 5 }


    --
    -- Per-peer configuration extensions
    --

    dellNetBgpM2CfgPeerExtensions
	OBJECT IDENTIFIER ::= { dellNetBgpM2PeerConfiguration 5 }


    dellNetBgpM2CfgPeerNonCapExts
	OBJECT IDENTIFIER ::= { dellNetBgpM2CfgPeerExtensions 1 }


    dellNetBgpM2CfgPeerCapExts
	OBJECT IDENTIFIER ::= { dellNetBgpM2CfgPeerExtensions 2 }


    --
    -- Peer route reflection configuration
    --

    dellNetBgpM2CfgPeerRouteReflectionExts
	OBJECT IDENTIFIER ::= { dellNetBgpM2CfgPeerNonCapExts 2796 }


    dellNetBgpM2CfgPeerReflectorClientTable OBJECT-TYPE
	SYNTAX	   SEQUENCE OF DellNetBgpM2CfgPeerReflectorClientEntry
	MAX-ACCESS not-accessible
	STATUS	   current


	DESCRIPTION
	    "Table of route reflection client settings on a per-peer
	     basis."
	REFERENCE
	    "RFC 2796 - BGP Route Reflection"
	::= { dellNetBgpM2CfgPeerRouteReflectionExts 1 }


    dellNetBgpM2CfgPeerReflectorClientEntry OBJECT-TYPE
	SYNTAX	   DellNetBgpM2CfgPeerReflectorClientEntry
	MAX-ACCESS not-accessible
	STATUS	   current
	DESCRIPTION
	    "Entry containing data on a per-peer basis on whether
	     the peer is configured as a route reflector client."
	REFERENCE
	    "RFC 2796 - BGP Route Reflection"
	AUGMENTS {
	    dellNetBgpM2CfgPeerEntry
	}
	::= { dellNetBgpM2CfgPeerReflectorClientTable 1 }


    DellNetBgpM2CfgPeerReflectorClientEntry ::= SEQUENCE {
	dellNetBgpM2CfgPeerReflectorClient
	    INTEGER
    }

    dellNetBgpM2CfgPeerReflectorClient OBJECT-TYPE
	SYNTAX	  INTEGER {
	    nonClient(0),
	    client(1),
	    meshedClient(2)
	}
	MAX-ACCESS  read-create
	STATUS	    current
	DESCRIPTION
	    "This value indicates whether the given peer is a
	     reflector client of this router, or not.  A value of
	     nonClient indicates that this peer is not a reflector
	     client.  A value of client indicates that this peer is a
	     reflector client that is not fully meshed with other
	     reflector clients.	 A value of meshedClient indicates
	     that the peer is a reflector client and is fully meshed
	     with all other reflector clients.

	     This value must be nonClient (0) for BGP external peers."
	REFERENCE

	    "RFC 2796 - BGP Route Reflection"
	::= { dellNetBgpM2CfgPeerReflectorClientEntry 1 }


    --
    -- Peer AS Confederations Extensions
    --

    dellNetBgpM2CfgPeerASConfederationExts
	OBJECT IDENTIFIER ::= { dellNetBgpM2CfgPeerNonCapExts 3065 }


    dellNetBgpM2CfgPeerConfedMemberTable OBJECT-TYPE
	SYNTAX	   SEQUENCE OF DellNetBgpM2CfgPeerConfedMemberEntry
	MAX-ACCESS not-accessible
	STATUS	   current
	DESCRIPTION
	    "Table of confederation member settings on a per-peer
	     basis."
	REFERENCE
	    "RFC 3065 - BGP Confederations"
	::= { dellNetBgpM2CfgPeerASConfederationExts 1 }


    dellNetBgpM2CfgPeerConfedMemberEntry OBJECT-TYPE
	SYNTAX	   DellNetBgpM2CfgPeerConfedMemberEntry
	MAX-ACCESS not-accessible
	STATUS	   current
	DESCRIPTION
	    "Entry containing data on a per-peer basis on whether
	     the peer is configured as a BGP confederation member."
	REFERENCE
	    "RFC 3065 - BGP Confederations"
	AUGMENTS {
	    dellNetBgpM2PeerEntry
	}
	::= { dellNetBgpM2CfgPeerConfedMemberTable 1 }


    DellNetBgpM2CfgPeerConfedMemberEntry ::= SEQUENCE {
	dellNetBgpM2CfgPeerConfedMember
	    TruthValue
    }


    dellNetBgpM2CfgPeerConfedMember OBJECT-TYPE
	SYNTAX	    TruthValue
	MAX-ACCESS  read-create
	STATUS	    current
	DESCRIPTION
	    "This value indicates whether the given peer is in our
	     confederation or not."
	REFERENCE
	    "RFC 3065 - BGP Confederations"
	::= { dellNetBgpM2CfgPeerConfedMemberEntry 1 }


    --
    -- BGP NLRI Data
    --

    dellNetBgpM2Rib
	OBJECT IDENTIFIER ::= { dellNetBgpM2 3 }


    --
    -- NLRI Table
    --

    dellNetBgpM2NlriTable OBJECT-TYPE
	SYNTAX	   SEQUENCE OF DellNetBgpM2NlriEntry
	MAX-ACCESS not-accessible
	STATUS	   current
	DESCRIPTION
	    "The BGP-4 Received Path Attribute Table contains
	     information about paths to destination networks
	     received from all BGP4 peers.  Collectively, this
	     represents the Adj-Ribs-In.  The route where
	     dellNetBgpM2NlriBest is TRUE represents, for this NLRI,
	     the route that is installed in the LocRib from the
	     Adj-Ribs-In."
	::= { dellNetBgpM2Rib 1 }


    dellNetBgpM2NlriEntry OBJECT-TYPE
	SYNTAX	   DellNetBgpM2NlriEntry
	MAX-ACCESS not-accessible
	STATUS	   current
	DESCRIPTION
	    "Information about a path to a network."
	INDEX {
	    dellNetBgpM2PeerIndex,
	    dellNetBgpM2NlriAfi,
	    dellNetBgpM2NlriSafi,
	    dellNetBgpM2NlriPrefix,
	    dellNetBgpM2NlriPrefixLen,

	    dellNetBgpM2NlriIndex
	}
	::= { dellNetBgpM2NlriTable 1 }


    DellNetBgpM2NlriEntry ::= SEQUENCE {
	dellNetBgpM2NlriIndex
	    Unsigned32,
	dellNetBgpM2NlriAfi
	    DellNetBgpM2Afi,
	dellNetBgpM2NlriSafi
	    DellNetBgpM2Safi,
	dellNetBgpM2NlriPrefixType
	    InetAddressType,
	dellNetBgpM2NlriPrefix
	    InetAddress,
	dellNetBgpM2NlriPrefixLen
	    InetAddressPrefixLength,
	dellNetBgpM2NlriBest
	    TruthValue,
	dellNetBgpM2NlriCalcLocalPref
	    Unsigned32,
	dellNetBgpM2PathAttrIndex
	    Unsigned32,
	dellNetBgpM2NlriOpaqueType
	    INTEGER,
	dellNetBgpM2NlriOpaquePointer
	    RowPointer
    }


    dellNetBgpM2NlriIndex OBJECT-TYPE
	SYNTAX	   Unsigned32
	MAX-ACCESS read-only
	STATUS	   current
	DESCRIPTION
	    "This index allows for multiple instances of a base
	     prefix for a certain AFI SAFI from a given peer.
	     This is currently useful for two things:
	     1. Allowing for a peer in future implementations to
		send more than a single route instance.
	     2. Allow for extensions which extend the NLRI field
		to send the same prefix while utilizing other
		extension specific information.	 An example of
		this is RFC 3107 - Carrying MPLS labels in BGP."
	REFERENCE
	    "RFC 3107 - Carrying Label Information in BGP-4"
	::= { dellNetBgpM2NlriEntry 1 }


    dellNetBgpM2NlriAfi OBJECT-TYPE
	SYNTAX	   DellNetBgpM2Afi
	MAX-ACCESS read-only
	STATUS	   current
	DESCRIPTION
	    "The address family of the prefix for this NLRI."
	::= { dellNetBgpM2NlriEntry 2 }


    dellNetBgpM2NlriSafi OBJECT-TYPE
	SYNTAX	   DellNetBgpM2Safi
	MAX-ACCESS read-only
	STATUS	   current
	DESCRIPTION
	    "The subsequent address family of the prefix for
	     this NLRI"
	REFERENCE
	    "RFC 2858 - Multiprotocol Extensions for BGP-4"
	::= { dellNetBgpM2NlriEntry 3 }


    dellNetBgpM2NlriPrefixType OBJECT-TYPE
	SYNTAX	   InetAddressType
	MAX-ACCESS read-only
	STATUS	   current
	DESCRIPTION
	    "The type of the IP address prefix in the
	  Network Layer Reachability Information field.
	  The value of this object is derived from the
	  appropriate value from the dellNetBgpM2NlriAfi field.
	  Where an appropriate InetAddressType is not
	  available, the value of the object must be
	  unknown(0).

	  XXX TODO - This seems like a hack."
	::= { dellNetBgpM2NlriEntry 4 }


    dellNetBgpM2NlriPrefix OBJECT-TYPE
	SYNTAX	   InetAddress	(SIZE (4..20))
	MAX-ACCESS read-only
	STATUS	   current
	DESCRIPTION
	    "An IP address prefix in the Network Layer
	     Reachability Information field.  This object
	     is an IP address containing the prefix with
	     length specified by
	     dellNetBgpM2PathAttrAddrPrefixLen.

	     Any bits beyond the length specified by
	     dellNetBgpM2PathAttrAddrPrefixLen are zeroed."
	::= { dellNetBgpM2NlriEntry 5 }


    dellNetBgpM2NlriPrefixLen OBJECT-TYPE
	SYNTAX	   InetAddressPrefixLength
	MAX-ACCESS read-only
	STATUS	   current
	DESCRIPTION
	    "Length in bits of the address prefix in
	     the Network Layer Reachability Information field."
	::= { dellNetBgpM2NlriEntry 6 }


    dellNetBgpM2NlriBest OBJECT-TYPE
	SYNTAX	   TruthValue
	MAX-ACCESS read-only
	STATUS	   current
	DESCRIPTION
	    "An indication of whether or not this route
	     was chosen as the best BGP4 route."
	::= { dellNetBgpM2NlriEntry 7 }


    dellNetBgpM2NlriCalcLocalPref OBJECT-TYPE
	SYNTAX	   Unsigned32
	MAX-ACCESS read-only
	STATUS	   current
	DESCRIPTION
	    "The degree of preference calculated by the
	     receiving BGP4 speaker for an advertised
	     route."
	::= { dellNetBgpM2NlriEntry 8 }


    dellNetBgpM2PathAttrIndex OBJECT-TYPE
	SYNTAX	   Unsigned32
	MAX-ACCESS read-only
	STATUS	   current
	DESCRIPTION
	    "This value is a unique index for the per-NLRI entry
	     in the dellNetBgpM2PathAttrTable.	 It is assigned by the
	     agent at the point of creation of the dellNetBgpM2PathAttrTable
	     row entry.	 While its value is guaranteed to be unique
	     at any time, it is otherwise opaque to the management
	     application with respect to its value or the contiguity
	     of dellNetBgpM2PathAttrIndex row instance values across rows
	     of the dellNetBgpM2PeerAttrTable.	 It is used to provide an
	     index structure for other tables whose data is logically
	     per-peer, per-NLRI."
	::= { dellNetBgpM2NlriEntry 9 }


    dellNetBgpM2NlriOpaqueType OBJECT-TYPE
	SYNTAX	   INTEGER {
	    none(0),
	    bgpMplsLabelStack(1)
	}
	MAX-ACCESS read-only
	STATUS	   current
	DESCRIPTION
	    "This object enumerates the type of the row that is
	     pointed to in the table row dellNetBgpM2NlriOpaquePointer
	     instance, if dellNetBgpM2NlriOpaquePointer is in fact not
	     a zero length.  dellNetBgpM2NlriOpaqueType is necessary since
	     the data referenced by dellNetBgpM2NlriOpaquePointer is
	     opaque to BGP.  For example, in the case of RFC 3107,
	     the label stack that is pointed to may occur in the
	     mplsLabelStackTable from the MPLS-LSR-MIB, and the
	     instance value of dellNetBgpM2NlriOpaqueType would be
	     bgpMplsLabelStack(1)."
	REFERENCE
	    "RFC 3107 - Carrying Label Information in BGP-4
	     draft-ietf-mpls-lsr-mib-08.txt"
	::= { dellNetBgpM2NlriEntry 10 }


    dellNetBgpM2NlriOpaquePointer OBJECT-TYPE
	SYNTAX	   RowPointer
	MAX-ACCESS read-only
	STATUS	   current
	DESCRIPTION
	    "Pointer to a row that decomposes the data that is
	     opaque to the BGP MIB but is sent in the NLRI.
	     This RowPointer has zero (0) length data instance
	     if dellNetBgpM2NlriOpaqueType is none."
	::= { dellNetBgpM2NlriEntry 11 }


    --
    -- Adj-Ribs-Out Table
    --

    dellNetBgpM2AdjRibsOutTable OBJECT-TYPE
	SYNTAX	   SEQUENCE OF DellNetBgpM2AdjRibsOutEntry
	MAX-ACCESS not-accessible
	STATUS	   current
	DESCRIPTION
	    "This table contains on a per-peer basis one or more
	     routes from the dellNetBgpM2NlriTable that have been
	     placed in this peer's Adj-Ribs-Out."
	REFERENCE
	    "draft-ietf-idr-bgp4-17.txt, Sec. 3.2"
	::= { dellNetBgpM2Rib 2 }


    dellNetBgpM2AdjRibsOutEntry OBJECT-TYPE
	SYNTAX	   DellNetBgpM2AdjRibsOutEntry
	MAX-ACCESS not-accessible
	STATUS	   current
	DESCRIPTION
	    "List of BGP routes that have been placed into a
	     peer's Adj-Ribs-Out."
	INDEX {
	    dellNetBgpM2PeerIndex,
	    dellNetBgpM2NlriAfi,
	    dellNetBgpM2NlriSafi,
	    dellNetBgpM2NlriPrefix,
	    dellNetBgpM2NlriPrefixLen,
	    dellNetBgpM2AdjRibsOutIndex
	}
	::= { dellNetBgpM2AdjRibsOutTable 1 }


    DellNetBgpM2AdjRibsOutEntry ::= SEQUENCE {
	dellNetBgpM2AdjRibsOutIndex
	    Unsigned32,
	dellNetBgpM2AdjRibsOutRoute
	    RowPointer
    }


    dellNetBgpM2AdjRibsOutIndex OBJECT-TYPE
	SYNTAX	   Unsigned32
	MAX-ACCESS read-only
	STATUS	   current
	DESCRIPTION
	    "Certain extensions to BGP permit multiple instance of
	     a per afi, per safi prefix to be advertised to a peer.
	     This object allows the enumeration of them."
	::= { dellNetBgpM2AdjRibsOutEntry 1 }


    dellNetBgpM2AdjRibsOutRoute OBJECT-TYPE
	SYNTAX	   RowPointer
	MAX-ACCESS read-only
	STATUS	   current
	DESCRIPTION
	    "This object points to the route in the dellNetBgpM2NlriTable
	     that corresponds to the entry in the peer's
	     Adj-Rib-Out.  Outgoing route maps are not
	     reflected at this point as those are part of the
	     Update-Send process."
	REFERENCE
	    "draft-ietf-idr-bgp4-17.txt, Sec. 9.2"
	::= { dellNetBgpM2AdjRibsOutEntry 2 }


    --
    -- BGP Rib Path Attributes Table
    --

    --
    -- Path Attribute Counter
    --

    dellNetBgpM2PathAttrCount OBJECT-TYPE
	SYNTAX	   Counter32
	MAX-ACCESS read-only
	STATUS	   current
	DESCRIPTION
	    "The number of entries in the dellNetBgpM2PathAttrTable."
	::= { dellNetBgpM2Rib 3 }


    --
    -- Path Attributes Table
    --

    dellNetBgpM2PathAttrTable OBJECT-TYPE
	SYNTAX	   SEQUENCE OF DellNetBgpM2PathAttrEntry
	MAX-ACCESS not-accessible
	STATUS	   current
	DESCRIPTION
	    "Provides per advertised network-prefix attribute data,
	     as advertised over a peering session."
	::= { dellNetBgpM2Rib 4 }


    dellNetBgpM2PathAttrEntry OBJECT-TYPE
	SYNTAX	   DellNetBgpM2PathAttrEntry
	MAX-ACCESS not-accessible
	STATUS	   current
	DESCRIPTION
	    "Each entry contains data about a given network
	     prefix, per-prefix and per-advertising peer."
	INDEX {
	    dellNetBgpM2PathAttrIndex
	}
	::= { dellNetBgpM2PathAttrTable 1 }


    DellNetBgpM2PathAttrEntry ::= SEQUENCE {
	dellNetBgpM2PathAttrOrigin
	    INTEGER,
	dellNetBgpM2PathAttrNextHopAddrType
	    InetAddressType,
	dellNetBgpM2PathAttrNextHop
	    InetAddress,
	dellNetBgpM2PathAttrMedPresent
	    TruthValue,
	dellNetBgpM2PathAttrMed
	    Unsigned32,
	dellNetBgpM2PathAttrLocalPrefPresent
	    TruthValue,
	dellNetBgpM2PathAttrLocalPref
	    Unsigned32,
	dellNetBgpM2PathAttrAtomicAggregate
	    INTEGER,
	dellNetBgpM2PathAttrAggregatorAS
	    InetAutonomousSystemNumber,
	dellNetBgpM2PathAttrAggregatorAddr
	    DellNetBgpM2Identifier,
	dellNetBgpM2AsPathCalcLength
	    Unsigned32,
	dellNetBgpM2AsPathString
	    SnmpAdminString,
	dellNetBgpM2AsPathIndex
	    Unsigned32
    }


    dellNetBgpM2PathAttrOrigin OBJECT-TYPE
	SYNTAX	   INTEGER {
	    igp(1),-- networks are interior
	    egp(2),-- networks learned via the EGP protocol
	    incomplete(3) -- undetermined
	    }
	MAX-ACCESS read-only
	STATUS	   current
	DESCRIPTION
	    "The ultimate origin of the path information."
	::= { dellNetBgpM2PathAttrEntry 1 }


    dellNetBgpM2PathAttrNextHopAddrType OBJECT-TYPE
	SYNTAX	    InetAddressType
	MAX-ACCESS  read-only
	STATUS	    current
	DESCRIPTION
	    "The address family of the address for
	     the border router that should be used
	     to access the destination network."
	::= { dellNetBgpM2PathAttrEntry 2 }


    dellNetBgpM2PathAttrNextHop OBJECT-TYPE
	SYNTAX	   InetAddress (SIZE(4..20))
	MAX-ACCESS read-only
	STATUS	   current
	DESCRIPTION
	    "The address of the border router that
	     should be used to access the destination
	     network.  This address is the nexthop
	     address received in the UPDATE packet.
	     The address family of this object will be the
	     same as that of the prefix in this row.

	     Note that for RFC2545 style double nexthops,
	     this object will always contain the global scope
	     nexthop.  dellNetBgpM2LinkLocalNextHopTable will contain
	     the linklocal scope nexthop.

	     In the case that the mechanism documented in
	     draft-kato-bgp-ipv6-link-local-00.txt is used and
	     only a link local nexthop has been sent, ,
	     dellNetBgpM2LinkLocalNextHopPresent will be false
	     and dellNetBgpM2PathAttrNextHop will contain the link local
	     nexthop."
	::= { dellNetBgpM2PathAttrEntry 3 }


    dellNetBgpM2PathAttrMedPresent OBJECT-TYPE
	SYNTAX	   TruthValue
	MAX-ACCESS read-only
	STATUS	   current
	DESCRIPTION
	    "Whether or not the MED value is present.
	     If it is not present, the dellNetBgpM2PathAttrMed
	     object has no useful value and should be set to 0."
	::= { dellNetBgpM2PathAttrEntry 4 }


    dellNetBgpM2PathAttrMed OBJECT-TYPE
	SYNTAX	   Unsigned32
	MAX-ACCESS read-only
	STATUS	   current
	DESCRIPTION
	    "This metric is used to discriminate
	     between multiple exit points to an
	     adjacent autonomous system."
	::= { dellNetBgpM2PathAttrEntry 5 }


    dellNetBgpM2PathAttrLocalPrefPresent OBJECT-TYPE
	SYNTAX	   TruthValue
	MAX-ACCESS read-only
	STATUS	   current
	DESCRIPTION
	    "Whether or not the LocalPref value is present.
	     If it is not present, the dellNetBgpM2PathAttrLocalPref
	     object has no useful value and should be set to 0."
	::= { dellNetBgpM2PathAttrEntry 6 }


    dellNetBgpM2PathAttrLocalPref OBJECT-TYPE
	SYNTAX	   Unsigned32
	MAX-ACCESS read-only
	STATUS	   current
	DESCRIPTION
	    "The originating BGP4 speakers degree of
	     preference for an advertised route."
	::= { dellNetBgpM2PathAttrEntry 7 }


    dellNetBgpM2PathAttrAtomicAggregate OBJECT-TYPE
	SYNTAX	   INTEGER {
	    atomicAggregatePresent(1),
	    atomicAggregateMissing(2)
	    }
	MAX-ACCESS read-only
	STATUS	   current
	DESCRIPTION
	    "When this object is set to atomicAggregatePresent,
	  the ATOMIC_AGGREGATE Path Attribute is present


	  and indicates that the NLRI MUST NOT be made
	  more specific."
	::= { dellNetBgpM2PathAttrEntry 8 }


    dellNetBgpM2PathAttrAggregatorAS OBJECT-TYPE
	SYNTAX	   InetAutonomousSystemNumber
	MAX-ACCESS read-only
	STATUS	   current
	DESCRIPTION
	    "The AS number of the last BGP4 speaker that
	     performed route aggregation.  A value of
	     zero (0) indicates the absence of this
	     attribute.

	     Note propagation of AS of zero is illegal in
	     the Internet."
	::= { dellNetBgpM2PathAttrEntry 9 }


    dellNetBgpM2PathAttrAggregatorAddr OBJECT-TYPE
	SYNTAX	   DellNetBgpM2Identifier
	MAX-ACCESS read-only
	STATUS	   current
	DESCRIPTION
	    "The IP address of the last BGP4 speaker
	     that performed route aggregation.	A
	     value of 0.0.0.0 indicates the absence
	     of this attribute."
	::= { dellNetBgpM2PathAttrEntry 10 }


    dellNetBgpM2AsPathCalcLength OBJECT-TYPE
	SYNTAX	   Unsigned32
	MAX-ACCESS read-only
	STATUS	   current
	DESCRIPTION
	    "This value represents the calculated length of the
	     AS Path according to the rules of the BGP specification.
	     This value is used in route selection."
	REFERENCE
	    "draft-ietf-idr-bgp4-17.txt, Sec. 9.1.2.2.a"
	::= { dellNetBgpM2PathAttrEntry 11 }


    dellNetBgpM2AsPathString OBJECT-TYPE
	SYNTAX	   SnmpAdminString
	MAX-ACCESS read-only


	STATUS	   current
	DESCRIPTION
	    "This is a string depicting the autonomous system
	     path to this network which was received from the
	     peer which advertised it.	The format of the string
	     is implementation-dependent, and should be designed
	     for operator readability."
	::= { dellNetBgpM2PathAttrEntry 12 }


    dellNetBgpM2AsPathIndex OBJECT-TYPE
	SYNTAX	   Unsigned32
	MAX-ACCESS read-only
	STATUS	   current
	DESCRIPTION
	    "This value is a unique index for the decomposed AS Path
	     in the dellNetBgpM2AsPathTable.  It is assigned by the
	     agent at the point of creation of the dellNetBgpM2AsPathTable
	     row entry.	 While its value is guaranteed to be unique
	     at any time, it is otherwise opaque to the management
	     application with respect to its value or the contiguity
	     of dellNetBgpM2AsPathIndex row instance values across rows
	     of the dellNetBgpM2AsPathTable."
	::= { dellNetBgpM2PathAttrEntry 13 }


    --
    -- As-4 byte AS_PATH
    --

    dellNetBgpM2AsPath4byteTable OBJECT-TYPE
	SYNTAX	   SEQUENCE OF DellNetBgpM2AsPath4byteEntry
	MAX-ACCESS not-accessible
	STATUS	   current
	DESCRIPTION
	    "This table is present for BGP speakers that support
	     the AS 4byte specification and are functioning as
	     a router between 2-byte and 4-byte AS space."
	REFERENCE
	    "draft-ietf-idr-as4bytes-04.txt - BGP support for
	     four-octet AS number space"
	::= { dellNetBgpM2Rib 5 }


    dellNetBgpM2AsPath4byteEntry OBJECT-TYPE
	SYNTAX	   DellNetBgpM2AsPath4byteEntry
	MAX-ACCESS not-accessible
	STATUS	   current
	DESCRIPTION
	    "Each row contains the information for the AS 4-byte
	     extension's NEW_AS_PATH and NEW_AGGREGATOR attributes."
	AUGMENTS {
	    dellNetBgpM2PathAttrEntry
	}
	::= { dellNetBgpM2AsPath4byteTable 1 }


    DellNetBgpM2AsPath4byteEntry ::= SEQUENCE {
	dellNetBgpM2AsPath4bytePathPresent
	    TruthValue,
	dellNetBgpM2AsPath4byteAggregatorAS
	    InetAutonomousSystemNumber,
	dellNetBgpM2AsPath4byteCalcLength
	    Unsigned32,
	dellNetBgpM2AsPath4byteString
	    SnmpAdminString,
	dellNetBgpM2AsPath4byteIndex
	    Unsigned32
    }


    dellNetBgpM2AsPath4bytePathPresent OBJECT-TYPE
	SYNTAX	   TruthValue
	MAX-ACCESS read-only
	STATUS	   current
	DESCRIPTION
	    "This value may only be true if this BGP Speaker
	     is functioning as a router between ASs that
	     are in 2-byte and 4-byte AS space.	 If this
	     value is true, then the NEW_AS_PATH attributes
	     are present and the 4-byte versions of the
	     appropriate path attributes are in this row.

	     If this value is false, then the following values
	     will be present in the row:

	     dellNetBgpM2PathAttrAggregatorAS - zero (0).
	     dellNetBgpM2AsPathCalcLength - zero (0).
	     dellNetBgpM2AsPathString - zero (0) length string.
	     dellNetBgpM2AsPathIndex - zero (0)."
	::= { dellNetBgpM2AsPath4byteEntry 1 }


    dellNetBgpM2AsPath4byteAggregatorAS OBJECT-TYPE
	SYNTAX	   InetAutonomousSystemNumber
	MAX-ACCESS read-only

	STATUS	   current
	DESCRIPTION
	    "The NEW_AGGREGATOR AS number of the last BGP4 speaker
	     that performed route aggregation.	A value of
	     zero (0) indicates the absence of this
	     attribute.

	     Note propagation of AS of zero is illegal in
	     the Internet."
	::= { dellNetBgpM2AsPath4byteEntry 2 }


    dellNetBgpM2AsPath4byteCalcLength OBJECT-TYPE
	SYNTAX	   Unsigned32
	MAX-ACCESS read-only
	STATUS	   current
	DESCRIPTION
	    "This value represents the calculated length of the
	     NEW_AS_PATH according to the rules of the BGP specification.
	     This value is used in route selection."
	REFERENCE
	    "draft-ietf-idr-bgp4-17.txt, Sec. 9.1.2.2.a"
	::= { dellNetBgpM2AsPath4byteEntry 3 }


    dellNetBgpM2AsPath4byteString OBJECT-TYPE
	SYNTAX	   SnmpAdminString
	MAX-ACCESS read-only
	STATUS	   current
	DESCRIPTION
	    "This is a string depicting the autonomous system
	     path to this network which was received from the
	     peer which advertised it.	The format of the string
	     is implementation-dependent, and should be designed
	     for operator readability."
	::= { dellNetBgpM2AsPath4byteEntry 4 }


    dellNetBgpM2AsPath4byteIndex OBJECT-TYPE
	SYNTAX	   Unsigned32
	MAX-ACCESS read-only
	STATUS	   current
	DESCRIPTION
	    "This value is a unique index for the decomposed AS Path
	     in the dellNetBgpM2AsPathTable.  It is assigned by the
	     agent at the point of creation of the dellNetBgpM2AsPathTable
	     row entry.	 While its value is guaranteed to be unique
	     at any time, it is otherwise opaque to the management

	     application with respect to its value or the contiguity
	     of dellNetBgpM2AsPathIndex row instance values across rows
	     of the dellNetBgpM2AsPathTable. "
	::= { dellNetBgpM2AsPath4byteEntry 5 }


    --	  BGP 4 Path attribute AS Path Table.  There is one row in
    --	  this table for each AS which is advertised for a given
    --	  route as provided from a peer.

-- JMH
-- We need one of these for the NewAsPath for the 4byte draft

    dellNetBgpM2AsPathTable OBJECT-TYPE
	SYNTAX	   SEQUENCE OF DellNetBgpM2AsPathEntry
	MAX-ACCESS not-accessible
	STATUS	   current
	DESCRIPTION
	    "The BGP-4 Path Attribute AS Path Table
	     contains the per network path (NLRI)
	     AS PATH data received from the
	     advertising BGP peer."
	::= { dellNetBgpM2Rib 6 }


    dellNetBgpM2AsPathTableEntry OBJECT-TYPE
	SYNTAX	   DellNetBgpM2AsPathEntry
	MAX-ACCESS not-accessible
	STATUS	   current
	DESCRIPTION
	    "Information about an AS path provided with a path to
	     a network."
	INDEX {
	    dellNetBgpM2PathAttrIndex,
	    dellNetBgpM2AsPathSegmentIndex,
	    dellNetBgpM2AsPathElementIndex
	}
	::= { dellNetBgpM2AsPathTable 1 }


    DellNetBgpM2AsPathEntry ::= SEQUENCE {
	dellNetBgpM2AsPathSegmentIndex
	    Unsigned32,
	dellNetBgpM2AsPathElementIndex
	    Unsigned32,
	dellNetBgpM2AsPathType
	    INTEGER,
	dellNetBgpM2AsPathElementValue
	    InetAutonomousSystemNumber
    }


    dellNetBgpM2AsPathSegmentIndex OBJECT-TYPE
	SYNTAX	   Unsigned32
	MAX-ACCESS read-only
	STATUS	   current
	DESCRIPTION
	    "A per-AS path segment index.  This will index a set of
	     autonomous systems in an AS path which are part
	     of the same sequence or set (as determined by
	     the row value of dellNetBgpM2AsPathType, which
	     should be the same value for each dellNetBgpM2AsPathTable
	     entry indexed by the same (dellNetBgpM2PathAttrIndex,
	     dellNetBgpM2AsPathIndex) pair)."
	::= { dellNetBgpM2AsPathTableEntry 1 }


    dellNetBgpM2AsPathElementIndex OBJECT-TYPE
	SYNTAX	   Unsigned32
	MAX-ACCESS read-only
	STATUS	   current
	DESCRIPTION
	    "A per-AS element index.  This will index a particular
	     AS within a sequence or set of autonomous systems in
	     an AS path."
	::= { dellNetBgpM2AsPathTableEntry 2 }


    dellNetBgpM2AsPathType OBJECT-TYPE
	SYNTAX	INTEGER {
	    asSet(1),
	    asSequence(2),
	    confedSequence(3),
	    confedSet(4)
	 }
	 MAX-ACCESS  read-only
	 STATUS	     current
	 DESCRIPTION
	     "The type of sequence in which this asPath
	      was advertised as an attribute.  Note that
	      all asPath row instances for a given (dellNetBgpM2PathAttrIndex,
	      dellNetBgpM2AsPathIndex) index pair will have their
	      dellNetBgpM2AsPathType set to the same value.
	      The values for dellNetBgpM2AsPathType are
	      interpreted as defined in the base BGP document
	      and the BGP AS Confederations document."
	REFERENCE
	    "draft-ietf-idr-bgp4-16
	     RFC 3065 - BGP AS Confederations"
	::= { dellNetBgpM2AsPathTableEntry 3 }


    dellNetBgpM2AsPathElementValue OBJECT-TYPE
	SYNTAX	   InetAutonomousSystemNumber
	MAX-ACCESS read-only
	STATUS	   current
	DESCRIPTION
	    "An AS value for an AS the related NLRI traversed
	     in the propagation of its advertisement.  This
	     value is to be interpreted in the context of the
	     sequence implied by dellNetBgpM2AsPathIndex and
	     dellNetBgpM2AsPathType (and, in sequence of the
	     other table rows with the same value of
	     dellNetBgpM2PathAttrIndex and dellNetBgpM2AsPathIndex)."
	::= { dellNetBgpM2AsPathTableEntry 4 }


    --	  BGP 4 Path unknown attribute.	 There is one row in
    --	  this table for each attribute not known by this BGP
    --	  implementation (or agent instrumentation), but provided
    --	  from a peer.

    dellNetBgpM2PathAttrUnknownTable OBJECT-TYPE
	SYNTAX	   SEQUENCE OF DellNetBgpM2PathAttrUnknownEntry
	MAX-ACCESS not-accessible
	STATUS	   current
	DESCRIPTION
	    "The BGP-4 Path Attribute Unknown Table
	     contains the per network path (NLRI)
	     data on the path attributes advertised
	     with a route but not known to the local BGP implementation
	     or not otherwise capable of being returned from this agent.

	     The absence of row data for a given index value for
	     dellNetBgpM2PathAttrIndex indicates a lack of such unknown
	     attribute information for the indicated network path
	     (as indexed by that dellNetBgpM2PathAttrIndex value in the
	     dellNetBgpM2PathAttrTable)."
	::= { dellNetBgpM2Rib 7 }


    dellNetBgpM2PathAttrUnknownEntry OBJECT-TYPE
	SYNTAX	   DellNetBgpM2PathAttrUnknownEntry
	MAX-ACCESS not-accessible
	STATUS	   current
	DESCRIPTION
	    "Information about an unknown attribute
	     provided with a path to a network."
	INDEX {
	    dellNetBgpM2PathAttrIndex,
	    dellNetBgpM2PathAttrUnknownIndex
	}
	::= { dellNetBgpM2PathAttrUnknownTable 1 }


    DellNetBgpM2PathAttrUnknownEntry ::= SEQUENCE {
	dellNetBgpM2PathAttrUnknownIndex
	    Unsigned32,
	dellNetBgpM2PathAttrUnknownType
	    Unsigned32,
	dellNetBgpM2PathAttrUnknownValue
	    OCTET STRING
    }


    dellNetBgpM2PathAttrUnknownIndex OBJECT-TYPE
	SYNTAX Unsigned32
	MAX-ACCESS read-only
	STATUS	   current
	DESCRIPTION
	    "An integer index for a row in this table."
	::= { dellNetBgpM2PathAttrUnknownEntry 1 }


    dellNetBgpM2PathAttrUnknownType OBJECT-TYPE
	SYNTAX Unsigned32
	MAX-ACCESS read-only
	STATUS	   current
	DESCRIPTION
	    "The attribute type advertised with this unknown
	     attribute by the peer."
	::= { dellNetBgpM2PathAttrUnknownEntry 2 }


    -- Maximum size of the following is derived as
    --	   4096	  max message size
    --	 -  16	  BGP message marker bytes
    --	 -   2	  BGP message size
    --	 -   1	  BGP message type (UPDATE with unknown attr)
    --	 -   2	  UPDATE routes length (even assuming no routes)
    --	 -   2	  UPDATE path attributes length
    --	 -   1	  path attribute flag octet
    --	 -   2	  unknown path attr type (in dellNetBgpM2PathAttrUnknownType)
    --	---------
    --	  4070 bytes maximum per-message attribute value data


    dellNetBgpM2PathAttrUnknownValue OBJECT-TYPE
	SYNTAX	   OCTET STRING (SIZE(0..4070))
	MAX-ACCESS read-only
	STATUS	   current
	DESCRIPTION
	    "Value of path attribute not understood
	     by the base BGP-4 document.

	     Octets beyond the maximum size, if any,
	     are not recorded by this row object. "
	::= { dellNetBgpM2PathAttrUnknownEntry 3 }


    --
    -- Path Attribute Extensions
    --

    dellNetBgpM2PathAttrExtensions
	OBJECT IDENTIFIER ::= { dellNetBgpM2Rib 8 }


    dellNetBgpM2PathAttrNonCapExts
	OBJECT IDENTIFIER ::= { dellNetBgpM2PathAttrExtensions 1 }


    dellNetBgpM2PathAttrCapExts
	OBJECT IDENTIFIER ::= { dellNetBgpM2PathAttrExtensions 2 }


    --
    -- Path Attribute Route Reflection Extensions
    --

    --
    -- Originator ID Table
    --

    dellNetBgpM2PathAttrRouteReflectionExts
	OBJECT IDENTIFIER ::= { dellNetBgpM2PathAttrNonCapExts 2796 }


    dellNetBgpM2PathAttrOriginatorIdTable OBJECT-TYPE
	SYNTAX	    SEQUENCE OF DellNetBgpM2PathAttrOriginatorIdEntry
	MAX-ACCESS  not-accessible
	STATUS	    current
	DESCRIPTION
	    "Per prefix data pertinent to advertisement of a
	     network prefix through an originator."
	REFERENCE
	    "RFC 2796 - BGP Route Reflection"
	::= { dellNetBgpM2PathAttrRouteReflectionExts 1 }


    dellNetBgpM2PathAttrOriginatorIdEntry OBJECT-TYPE
	SYNTAX	    DellNetBgpM2PathAttrOriginatorIdEntry
	MAX-ACCESS  not-accessible
	STATUS	    current
	DESCRIPTION
	    "Each entry contains data pertinent to a network
	     prefix as received through its originating BGP
	     route reflector."
	REFERENCE
	    "RFC 2796 - BGP Route Reflection"
	INDEX {
	    dellNetBgpM2PathAttrIndex
	}
	::= { dellNetBgpM2PathAttrOriginatorIdTable 1 }


    DellNetBgpM2PathAttrOriginatorIdEntry ::= SEQUENCE {
	dellNetBgpM2PathAttrOriginatorId
	    DellNetBgpM2Identifier
    }


    dellNetBgpM2PathAttrOriginatorId OBJECT-TYPE
	SYNTAX	    DellNetBgpM2Identifier
	MAX-ACCESS  read-only
	STATUS	    current
	DESCRIPTION
	    "The Originator-ID identifying the router that initially
	     advertised this destination to a Route Reflector.	A
	     value of 0.0.0.0 indicates the absence of this attribute."
	REFERENCE
	     "This attribute is defined in [RFC2796]."
	::= { dellNetBgpM2PathAttrOriginatorIdEntry 1 }


    --
    -- Cluster table
    --


    dellNetBgpM2PathAttrClusterTable OBJECT-TYPE
	SYNTAX	   SEQUENCE OF DellNetBgpM2PathAttrClusterEntry
	MAX-ACCESS not-accessible
	STATUS	   current
	DESCRIPTION
	    "The BGP-4 Path Attribute Cluster Table
	     contains the per network path (NLRI)
	     data on the reflection path which a
	     route has traversed.  The absence of row
	     data for a given index value for dellNetBgpM2PathAttrIndex
	     indicates a lack of this attribute information
	     for the indicated network path (as indexed by
	     that dellNetBgpM2PathAttrIndex value in the dellNetBgpM2PathAttrTable)."
	::= { dellNetBgpM2PathAttrRouteReflectionExts 2 }


    dellNetBgpM2PathAttrClusterEntry OBJECT-TYPE
	SYNTAX	   DellNetBgpM2PathAttrClusterEntry
	MAX-ACCESS not-accessible
	STATUS	   current
	DESCRIPTION
	    "Information about a cluster traversal
	     provided with a path to a network."
	INDEX {
	    dellNetBgpM2PathAttrIndex,
	    dellNetBgpM2PathAttrClusterIndex
	}
	::= { dellNetBgpM2PathAttrClusterTable 1 }


    DellNetBgpM2PathAttrClusterEntry ::= SEQUENCE {
	dellNetBgpM2PathAttrClusterIndex
	    Unsigned32,
	dellNetBgpM2PathAttrClusterValue
	    DellNetBgpM2Identifier
    }


    dellNetBgpM2PathAttrClusterIndex OBJECT-TYPE
	SYNTAX	   Unsigned32
	MAX-ACCESS read-only
	STATUS	   current
	DESCRIPTION
	    "An integral index for a row in this table."
	::= { dellNetBgpM2PathAttrClusterEntry 1 }


    dellNetBgpM2PathAttrClusterValue OBJECT-TYPE
	SYNTAX	    DellNetBgpM2Identifier
	MAX-ACCESS  read-only
	STATUS	    current
	DESCRIPTION
	    "A four octet long value representing a part of the
	    reflection path that the route has passed.	Each such four
	    octet long value represents the ID of a cluster that
	    the route has traversed.  The sequence of this path as
	    received in the route advertisement will be preserved in
	    the sequence of dellNetBgpM2PathAttrClusterTable rows (and the
	    dellNetBgpM2PathAttrClusterValues in each row) as returned for
	    a given dellNetBgpM2PathAttrIndex value, and the monotonically
	    increasing sequence of dellNetBgpM2PathAttrClusterIndex values
	    for that dellNetBgpM2PathAttrIndex."
	REFERENCE
	    "This attribute is defined in [RFC2796]."
	::= { dellNetBgpM2PathAttrClusterEntry 2 }


    --
    -- BGP Communities
    --

    dellNetBgpM2PathAttrCommunityExts
	OBJECT IDENTIFIER ::= { dellNetBgpM2PathAttrNonCapExts 1997 }


    dellNetBgpM2PathAttrCommTable OBJECT-TYPE
	SYNTAX	   SEQUENCE OF DellNetBgpM2PathAttrCommEntry
	MAX-ACCESS not-accessible
	STATUS	   current
	DESCRIPTION
	    "The BGP-4 Path Attribute Community Table
	     contains the per network path (NLRI)
	     data on the community membership advertised
	     with a route.  The absence of row
	     data for a given index value for dellNetBgpM2PathAttrIndex
	     indicates a lack of this attribute information
	     for the indicated network path (as indexed by
	     that dellNetBgpM2PathAttrIndex value in the dellNetBgpM2PathAttrTable)."
	::= { dellNetBgpM2PathAttrCommunityExts 1 }


    dellNetBgpM2PathAttrCommEntry OBJECT-TYPE
	SYNTAX	   DellNetBgpM2PathAttrCommEntry
	MAX-ACCESS not-accessible
	STATUS	   current
	DESCRIPTION

	    "Information about a community association
	     provided with a path to a network."
	INDEX {
	    dellNetBgpM2PathAttrIndex,
	    dellNetBgpM2PathAttrCommIndex
	}
	::= { dellNetBgpM2PathAttrCommTable 1 }


    DellNetBgpM2PathAttrCommEntry ::= SEQUENCE {
	dellNetBgpM2PathAttrCommIndex
	    Unsigned32,
	dellNetBgpM2PathAttrCommValue
	    DellNetBgpM2Community
    }


    dellNetBgpM2PathAttrCommIndex OBJECT-TYPE
	SYNTAX Unsigned32
	MAX-ACCESS read-only
	STATUS	   current
	DESCRIPTION
	    "An integer index for a row in this table."
	::= { dellNetBgpM2PathAttrCommEntry 1 }


    dellNetBgpM2PathAttrCommValue  OBJECT-TYPE
	SYNTAX	    DellNetBgpM2Community
	MAX-ACCESS  read-only
	STATUS	    current
	DESCRIPTION
	    "A value representing a community.	 There are certain
	     4-octet long values which could be returned in this
	     columnar row data that carry additional semantics."
	REFERENCE
	    "RFC 1997 - BGP Communities Attribute"
	::= { dellNetBgpM2PathAttrCommEntry 2 }


    --
    -- BGP Extended Communities
    --

    dellNetBgpM2PathAttrExtCommTable OBJECT-TYPE
	SYNTAX	   SEQUENCE OF DellNetBgpM2PathAttrExtCommEntry
	MAX-ACCESS not-accessible
	STATUS	   current
	DESCRIPTION
	    "The BGP-4 Path Attribute Community Table
	    contains the per network path (NLRI)
	    data on the extended community membership advertised
	    with a route.  The absence of row
	    data for a given index value for dellNetBgpM2PathAttrIndex
	    indicates a lack of this attribute information
	    for the indicated network path (as indexed by
	    that dellNetBgpM2PathAttrIndex value in the dellNetBgpM2PathAttrTable).

	    XXX JMH - can not assign the OID until an RFC is published."
	::= { dellNetBgpM2PathAttrNonCapExts 3501 }		-- Dell Networking OS


    dellNetBgpM2PathAttrExtCommEntry OBJECT-TYPE
	SYNTAX	   DellNetBgpM2PathAttrExtCommEntry
	MAX-ACCESS not-accessible
	STATUS	   current
	DESCRIPTION
	    "Information about an extended community association
	     provided with a path to a network."
	INDEX {
	    dellNetBgpM2PathAttrIndex,
	    dellNetBgpM2PathAttrExtCommIndex
	}
	::= { dellNetBgpM2PathAttrExtCommTable 1 }


    DellNetBgpM2PathAttrExtCommEntry ::= SEQUENCE {
	dellNetBgpM2PathAttrExtCommIndex
	    Unsigned32,
	dellNetBgpM2PathAttrExtCommValue
	    DellNetBgpM2ExtendedCommunity
    }


    dellNetBgpM2PathAttrExtCommIndex OBJECT-TYPE
	SYNTAX Unsigned32
	MAX-ACCESS read-only
	STATUS	   current
	DESCRIPTION
	    "An integral index for a row in this table."
	::= { dellNetBgpM2PathAttrExtCommEntry 1 }


    dellNetBgpM2PathAttrExtCommValue  OBJECT-TYPE
	SYNTAX	    DellNetBgpM2ExtendedCommunity
	MAX-ACCESS  read-only
	STATUS	    current



	DESCRIPTION
	    "A value representing an extended community which was
	    received with the route implied by the dellNetBgpM2PathAttr
	    Index value of this row data.   There are certain
	    8-octet long values which could be returned in this
	    columnar row data that carry additional semantics."
	REFERENCE
	    "BGP-EXTCOMM - BGP Extended Communities Attribute"
	::= { dellNetBgpM2PathAttrExtCommEntry 2 }


    --
    -- RFC 2545 link local nexthop
    --

    dellNetBgpM2LinkLocalNextHopTable OBJECT-TYPE
	SYNTAX	   SEQUENCE OF DellNetBgpM2LinkLocalNextHopEntry
	MAX-ACCESS not-accessible
	STATUS	   current
	DESCRIPTION
	    "Table of link local nexthops as sent by RFC 2545
	     for IPv6 BGP Speakers."
	REFERENCE
	    "RFC 2545 - Use of BGP-4 Multiprotocol Extensions
	     for IPv6 Inter-Domain Routing"
	::= { dellNetBgpM2PathAttrNonCapExts 2545 }


    dellNetBgpM2LinkLocalNextHopEntry OBJECT-TYPE
	SYNTAX	   DellNetBgpM2LinkLocalNextHopEntry
	MAX-ACCESS not-accessible
	STATUS	   current
	DESCRIPTION
	    "Entry containing the link-local nexthops as sent
	     by a BGP speaker running RFC 2545 extensions for
	     double-nexthops."
	INDEX {
	    dellNetBgpM2PathAttrIndex
	}
	::= { dellNetBgpM2LinkLocalNextHopTable 1 }


    DellNetBgpM2LinkLocalNextHopEntry ::= SEQUENCE {
	dellNetBgpM2LinkLocalNextHopPresent
	    TruthValue,
	dellNetBgpM2LinkLocalNextHop
	    InetAddress
    }


    dellNetBgpM2LinkLocalNextHopPresent OBJECT-TYPE
	SYNTAX	   TruthValue
	MAX-ACCESS read-only
	STATUS	   current
	DESCRIPTION
	    "This value is TRUE if and only if the BGP
	     speaker is receiving IPv6 NLRI using the
	     RFC 2545 double nexthop convention and it
	     has received a link local scope nexthop in
	     addition to the global scope nexthop."
	::= { dellNetBgpM2LinkLocalNextHopEntry 1 }


    dellNetBgpM2LinkLocalNextHop OBJECT-TYPE
	SYNTAX	   InetAddress (SIZE(20))
	MAX-ACCESS read-only
	STATUS	   current
	DESCRIPTION
	    "This value contains an IPv6 link local address of
	    InetAddressType of type ipv6z.  This value is only
	    present if dellNetBgpM2LinkLocalNextHopPresent is true."
	::= { dellNetBgpM2LinkLocalNextHopEntry 2 }


    --
    -- Conformance Information
    --

    dellNetBgpM2Conformance
	OBJECT IDENTIFIER ::= { dellNetBgpM2 4 }


    dellNetBgpM2MIBCompliances OBJECT IDENTIFIER ::=
	{ dellNetBgpM2Conformance 1 }


    dellNetBgpM2MIBGroups	OBJECT IDENTIFIER ::=
	{ dellNetBgpM2Conformance 2 }


    dellNetBgpM2MIBCompliance MODULE-COMPLIANCE
	STATUS	current
	DESCRIPTION
	    "The compliance statement for entities which
	    implement the BGP4 mib."
	 MODULE	 -- this module
	 MANDATORY-GROUPS {
	    dellNetBgpM2TimersGroup,
	    dellNetBgpM2CountersGroup,
	    dellNetBgpM2AsPathGroup,
	    dellNetBgpM2As4byteGroup,
	    dellNetBgpM2BaseGroup,
	    dellNetBgpM2ErrorsGroup,
	    dellNetBgpM2PeerGroup,
	    dellNetBgpM2PathAttributesGroup
	    }
	GROUP dellNetBgpM2MIBNotificationsGroup
	DESCRIPTION
	    "The notifications group is completely optional,
	     but highly recommended."
	GROUP dellNetBgpM2CommunitiesGroup
	DESCRIPTION
	    "The communities group is mandatory only for those
	     which support the BGP community attribute."
	GROUP dellNetBgpM2ExtCommunitiesGroup
	DESCRIPTION
	    "The communities group is mandatory only for those
	     which support the BGP extended community attribute."
	GROUP dellNetBgpM2RouteReflectionGroup
	DESCRIPTION
	    "The communities group is mandatory only for those
	     which support the BGP route reflection relationships."
	GROUP dellNetBgpM2AsConfederationGroup
	DESCRIPTION
	    "The communities group is mandatory only for those
	     which support the BGP confederation membership."
	GROUP dellNetBgpM2TimersGroup
	DESCRIPTION
	    "This group is mandatory for all agent implementations."
	GROUP dellNetBgpM2CountersGroup
	DESCRIPTION
	    "This group is mandatory for all agent implementations."
	GROUP dellNetBgpM2CapabilitiesGroup
	DESCRIPTION
	    "This group is mandatory for all agent implementations."
	GROUP dellNetBgpM2AsPathGroup
	DESCRIPTION
	    "This group is mandatory for all agent implementations."
	GROUP dellNetBgpM2As4byteGroup
	DESCRIPTION
	    "This group is mandatory for all agent implementations."
	GROUP dellNetBgpM2BaseGroup
	DESCRIPTION
	    "This group is mandatory for all agent implementations."
	GROUP dellNetBgpM2ErrorsGroup
	DESCRIPTION
	    "This group is mandatory for all agent implementations."
	GROUP dellNetBgpM2PeerGroup
	DESCRIPTION
	    "This group is mandatory for all agent implementations."
	GROUP dellNetBgpM2PathAttributesGroup
	DESCRIPTION
	    "This group is mandatory for all agent implementations."
	GROUP dellNetBgpM2PeerConfigurationGroup
	DESCRIPTION
	    "This group is optional for implementations that wish to
	     support configuration via SNMP."
	GROUP dellNetBgpM2PeerRouteReflectorCfgGroup
	DESCRIPTION
	    "This group is optional for implementations that wish to
	     support configuration of route reflection via SNMP.
	     Implementation of this feature requires support of the
	     dellNetBgpM2PeerConfigurationGroup."
	GROUP dellNetBgpM2PeerAsConfederationCfgGroup
	DESCRIPTION
	    "This group is optional for implementations that wish to
	     support configuration of BGP AS Confederations via SNMP.
	     Implementation of this feature requires support of the
	     dellNetBgpM2PeerConfigurationGroup."
	GROUP dellNetBgpM2Rfc2545Group
	DESCRIPTION
	    "This group is required for peers that support exchanging
	     of IPv6 NLRI per RFC 2545."
	::= { dellNetBgpM2MIBCompliances 1 }



    dellNetBgpM2CommunitiesGroup OBJECT-GROUP
	OBJECTS {
	    dellNetBgpM2PathAttrCommIndex,
	    dellNetBgpM2PathAttrCommValue
	}
	STATUS current
	DESCRIPTION
	    "Objects associated with BGP communities."
	::= { dellNetBgpM2MIBGroups 1 }


    dellNetBgpM2ExtCommunitiesGroup OBJECT-GROUP
	OBJECTS {
	    dellNetBgpM2PathAttrExtCommIndex,
	    dellNetBgpM2PathAttrExtCommValue
	}
	STATUS current


	DESCRIPTION
	    "Objects associated with BGP extended communities."
	::= { dellNetBgpM2MIBGroups 2 }


    dellNetBgpM2RouteReflectionGroup OBJECT-GROUP
	OBJECTS {
	    dellNetBgpM2RouteReflector,
	    dellNetBgpM2ClusterId,
	    dellNetBgpM2PeerReflectorClient,
	    dellNetBgpM2PathAttrOriginatorId,
	    dellNetBgpM2PathAttrClusterIndex,
	    dellNetBgpM2PathAttrClusterValue
	}
	STATUS current
	DESCRIPTION
	    "Objects associated with BGP route reflection."
	::= { dellNetBgpM2MIBGroups 3 }


    dellNetBgpM2AsConfederationGroup OBJECT-GROUP
	OBJECTS {
	    dellNetBgpM2ConfederationRouter,
	    dellNetBgpM2ConfederationId,
	    dellNetBgpM2PeerConfedMember
	}
	STATUS current
	DESCRIPTION
	    "Objects associated with BGP confederation membership."
	::= { dellNetBgpM2MIBGroups 4 }


    dellNetBgpM2TimersGroup OBJECT-GROUP
	OBJECTS {
	    dellNetBgpM2PeerFsmEstablishedTime,
	    dellNetBgpM2PeerInUpdatesElapsedTime,
	    dellNetBgpM2PeerConnectRetryInterval,
	    dellNetBgpM2PeerHoldTimeConfigured,
	    dellNetBgpM2PeerKeepAliveConfigured,
	    dellNetBgpM2PeerMinASOrigInterval,
	    dellNetBgpM2PeerMinRouteAdverInterval,
	    dellNetBgpM2PeerHoldTime,
	    dellNetBgpM2PeerKeepAlive
	}
	STATUS current
	DESCRIPTION
	    "Objects associated with BGP peering timers."
	::= { dellNetBgpM2MIBGroups 5 }


    dellNetBgpM2CountersGroup OBJECT-GROUP
	OBJECTS {
	    dellNetBgpM2PeerInUpdates,
	    dellNetBgpM2PeerOutUpdates,
	    dellNetBgpM2PeerInTotalMessages,
	    dellNetBgpM2PeerOutTotalMessages,
	    dellNetBgpM2PeerFsmEstablishedTrans,
	    dellNetBgpM2PeerInKeepalives,
	    dellNetBgpM2PeerOutKeepalives, 
	    dellNetBgpM2PeerInOpen, 
	    dellNetBgpM2PeerOutOpen,
	    dellNetBgpM2PeerInRteRefresh, 
	    dellNetBgpM2PeerOutRteRefresh, 
	    dellNetBgpM2PrefixCountersAfi,
	    dellNetBgpM2PrefixCountersSafi,
	    dellNetBgpM2PrefixInPrefixes,
	    dellNetBgpM2PrefixInPrefixesAccepted,
	    dellNetBgpM2PrefixInPrefixesRejected,
	    dellNetBgpM2PrefixOutPrefixes,
	    dellNetBgpM2PrefixWdrawnByPeer, 
	    dellNetBgpM2PrefixWdrawnFromPeer
	}
	STATUS current
	DESCRIPTION
	    "Objects to count discrete events and exchanges on BGP
	     sessions."
	 ::= { dellNetBgpM2MIBGroups 6 }


    dellNetBgpM2CapabilitiesGroup OBJECT-GROUP
	OBJECTS {
	    dellNetBgpM2CapabilitySupportAvailable,
	    dellNetBgpM2SupportedCapabilityCode,
	    dellNetBgpM2SupportedCapability,
	    dellNetBgpM2PeerCapAnnouncedCode,
	    dellNetBgpM2PeerCapAnnouncedIndex,
	    dellNetBgpM2PeerCapAnnouncedValue,
	    dellNetBgpM2PeerCapReceivedCode,
	    dellNetBgpM2PeerCapReceivedIndex,
	    dellNetBgpM2PeerCapReceivedValue
	}
	STATUS current
	DESCRIPTION
	    "Objects to report capabilities as received on BGP
	     sessions."
	::= { dellNetBgpM2MIBGroups 7 }


    dellNetBgpM2AsPathGroup OBJECT-GROUP
	OBJECTS {
	    dellNetBgpM2AsPathSegmentIndex,
	    dellNetBgpM2AsPathElementIndex,
	    dellNetBgpM2AsPathType,
	    dellNetBgpM2AsPathElementValue
	}
	STATUS current


	DESCRIPTION
	    "Objects to report AS paths received on BGP NLRIs."
	::= { dellNetBgpM2MIBGroups 8 }


    dellNetBgpM2As4byteGroup OBJECT-GROUP
	OBJECTS {
	    dellNetBgpM2AsSize,
	    dellNetBgpM2AsPath4bytePathPresent,
	    dellNetBgpM2AsPath4byteAggregatorAS,
	    dellNetBgpM2AsPath4byteCalcLength,
	    dellNetBgpM2AsPath4byteString,
	    dellNetBgpM2AsPath4byteIndex
	}
	STATUS current
	DESCRIPTION
	    "AS Size objects."
	::= { dellNetBgpM2MIBGroups 9 }


    dellNetBgpM2BaseGroup OBJECT-GROUP
	OBJECTS {
	    dellNetBgpM2LocalAs,
	    dellNetBgpM2LocalIdentifier,
	    dellNetBgpM2VersionIndex,
	    dellNetBgpM2VersionSupported
	}
	STATUS current
	DESCRIPTION
	    "Basic objects in local BGP implementation."
	::= { dellNetBgpM2MIBGroups 10 }


    dellNetBgpM2ErrorsGroup OBJECT-GROUP
	OBJECTS {
	    dellNetBgpM2PeerLastErrorReceived,
	    dellNetBgpM2PeerLastErrorReceivedData,
	    dellNetBgpM2PeerLastErrorReceivedTime,
	    dellNetBgpM2PeerLastErrorReceivedText,
	    dellNetBgpM2PeerLastErrorSent,
	    dellNetBgpM2PeerLastErrorSentData,
	    dellNetBgpM2PeerLastErrorSentTime,
	    dellNetBgpM2PeerLastErrorSentText
	}
	STATUS current
	DESCRIPTION
	    "Errors received on BGP peering sessions."
	::= { dellNetBgpM2MIBGroups 11 }


    dellNetBgpM2PeerGroup OBJECT-GROUP
	OBJECTS {
	    dellNetBgpM2PeerInstance,
	    dellNetBgpM2PeerIdentifier,
	    dellNetBgpM2PeerState,
	    dellNetBgpM2PeerStatus,
	    dellNetBgpM2PeerConfiguredVersion,
	    dellNetBgpM2PeerNegotiatedVersion,
	    dellNetBgpM2PeerLocalAddrType,
	    dellNetBgpM2PeerLocalAddr,
	    dellNetBgpM2PeerLocalPort,
	    dellNetBgpM2PeerLocalAs,
	    dellNetBgpM2PeerRemoteAddrType,
	    dellNetBgpM2PeerRemoteAddr,
	    dellNetBgpM2PeerRemotePort,
	    dellNetBgpM2PeerRemoteAs,
	    dellNetBgpM2PeerIndex
	}
	STATUS current
	DESCRIPTION
	    "Core object types on BGP peering sessions."
	::= { dellNetBgpM2MIBGroups 12 }


    dellNetBgpM2PathAttributesGroup OBJECT-GROUP
	OBJECTS {
	    dellNetBgpM2PathAttrCount,
	    dellNetBgpM2AsPathCalcLength,
	    dellNetBgpM2AsPathElementValue,
	    dellNetBgpM2AsPathIndex,
	    dellNetBgpM2AsPathString,
	    dellNetBgpM2AsPathType,
	    dellNetBgpM2NlriAfi,
	    dellNetBgpM2NlriBest,
	    dellNetBgpM2NlriPrefixType,
	    dellNetBgpM2NlriPrefix,
	    dellNetBgpM2NlriPrefixLen,
	    dellNetBgpM2NlriSafi,
	    dellNetBgpM2NlriOpaqueType,
	    dellNetBgpM2NlriOpaquePointer,
	    dellNetBgpM2NlriIndex,
	    dellNetBgpM2NlriCalcLocalPref,
	    dellNetBgpM2AdjRibsOutIndex,
	    dellNetBgpM2AdjRibsOutRoute,
	    dellNetBgpM2PathAttrAggregatorAS,
	    dellNetBgpM2PathAttrAggregatorAddr,
	    dellNetBgpM2PathAttrAtomicAggregate,
	    dellNetBgpM2PathAttrIndex,
	    dellNetBgpM2PathAttrLocalPref,
	    dellNetBgpM2PathAttrLocalPrefPresent,
	    dellNetBgpM2PathAttrMed,
	    dellNetBgpM2PathAttrMedPresent,
	    dellNetBgpM2PathAttrNextHop,
	    dellNetBgpM2PathAttrNextHopAddrType,
	    dellNetBgpM2PathAttrOrigin,
	    dellNetBgpM2PathAttrUnknownIndex,
	    dellNetBgpM2PathAttrUnknownType,
	    dellNetBgpM2PathAttrUnknownValue
	}
	STATUS current
	DESCRIPTION
	    "Attributes received on BGP peering sessions."
	::= { dellNetBgpM2MIBGroups 13 }

    dellNetBgpM2PeerConfigurationGroup OBJECT-GROUP
	OBJECTS {
	    dellNetBgpM2CfgBaseScalarStorageType,
	    dellNetBgpM2CfgLocalAs,
	    dellNetBgpM2CfgLocalIdentifier,
	    dellNetBgpM2CfgPeerAdminStatus,
	    dellNetBgpM2CfgPeerNextIndex,
	    dellNetBgpM2CfgPeerConfiguredVersion,
	    dellNetBgpM2CfgAllowVersionNegotiation,
	    dellNetBgpM2CfgPeerLocalAddrType,
	    dellNetBgpM2CfgPeerLocalAddr,
	    dellNetBgpM2CfgPeerLocalAs,
	    dellNetBgpM2CfgPeerRemoteAddrType,
	    dellNetBgpM2CfgPeerRemoteAddr,
	    dellNetBgpM2CfgPeerRemoteAs,
	    dellNetBgpM2CfgPeerEntryStorageType,
	    dellNetBgpM2CfgPeerError,
	    dellNetBgpM2CfgPeerBgpPeerEntry,
	    dellNetBgpM2CfgPeerRowEntryStatus,
	    dellNetBgpM2CfgPeerIndex,
	    dellNetBgpM2CfgPeerStatus,
	    dellNetBgpM2CfgPeerConnectRetryInterval,
	    dellNetBgpM2CfgPeerHoldTimeConfigured,
	    dellNetBgpM2CfgPeerKeepAliveConfigured,
	    dellNetBgpM2CfgPeerMinASOrigInterval,
	    dellNetBgpM2CfgPeerMinRouteAdverInter
	}
	STATUS current
	DESCRIPTION
	    "Configuration objects for BGP peers."
	::= { dellNetBgpM2MIBGroups 14 }



    dellNetBgpM2PeerRouteReflectorCfgGroup OBJECT-GROUP
	OBJECTS {
	    dellNetBgpM2CfgRouteReflector,
	    dellNetBgpM2CfgClusterId,
	    dellNetBgpM2CfgPeerReflectorClient
	}
	STATUS current
	DESCRIPTION
	    "Configuration objects for BGP peers that support route
	     reflection."
	::= { dellNetBgpM2MIBGroups 15 }


    dellNetBgpM2PeerAsConfederationCfgGroup OBJECT-GROUP
	OBJECTS {
	    dellNetBgpM2CfgConfederationRouter,
	    dellNetBgpM2CfgConfederationId,
	    dellNetBgpM2CfgPeerConfedMember
	}
	STATUS current
	DESCRIPTION
	    "Configuration objects for BGP peers that support BGP
	     confederations."
	::= { dellNetBgpM2MIBGroups 16 }


    dellNetBgpM2MIBNotificationsGroup NOTIFICATION-GROUP
	NOTIFICATIONS {
	    dellNetBgpM2Established,
	    dellNetBgpM2BackwardTransition
	}
	STATUS	current
	DESCRIPTION
	    "This group contains objects for notifications
	     supported by this mib module."
	::= { dellNetBgpM2MIBGroups 17 }


    dellNetBgpM2Rfc2545Group OBJECT-GROUP
	OBJECTS {
	    dellNetBgpM2LinkLocalNextHopPresent,
	    dellNetBgpM2LinkLocalNextHop
	}
	STATUS current
	DESCRIPTION
	    "This group is required for peers that support exchanging
	     of IPv6 NLRI per RFC 2545."
	::= { dellNetBgpM2MIBGroups 18 }

END
