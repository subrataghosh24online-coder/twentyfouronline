--
-- MIB generated by IONODES on 2015-06-18.
--

IONODES-IONSERIES-MIB DEFINITIONS ::= BEGIN

   IMPORTS
      OBJECT-GROUP
         FROM SNMPv2-CONF
      MODULE-IDENTITY, OBJECT-TYPE, NOTIFICATION-TYPE,
      enterprises, Integer32, Unsigned32
         FROM SNMPv2-SMI;


--
-- Textual conventions (type definitions)
--

   AnalogVideoSignalLockState ::= TEXTUAL-CONVENTION
      DISPLAY-HINT "d"
      STATUS current
      DESCRIPTION
         "Possible analog signal lock states."
      SYNTAX INTEGER
      {
         locked(1),
         unlocked(2)
      }


   AnalogVideoStandard ::= TEXTUAL-CONVENTION
      DISPLAY-HINT "d"
      STATUS current
      DESCRIPTION
         "Possible analog video standards."
      SYNTAX INTEGER
      {
         ntsc(1),
         pal(2)
      }


   DigitalVideoConnState ::= TEXTUAL-CONVENTION
      DISPLAY-HINT "d"
      STATUS current
      DESCRIPTION
         "Possible digital video connection states."
      SYNTAX INTEGER
      {
         connected(1),
         notconnected(2)
      }


   DigitalVideoStandard ::= TEXTUAL-CONVENTION
      DISPLAY-HINT "d"
      STATUS current
      DESCRIPTION
         "Possible digital video standards."
      SYNTAX INTEGER
      {
         hdmi720p(1),
         hdmi720p50(2),
         hdmi1080i(3),
         hdmi1080i50(4),
         hdmi1080p(5),
         hdmi1080p50(6),
         hdmi1080p25(7),
         hdmi1080p30(8)
      }


   StreamState ::= TEXTUAL-CONVENTION
      DISPLAY-HINT "d"
      STATUS current
      DESCRIPTION
         "Possible stream states."
      SYNTAX INTEGER
      {
         connected(1),
         notconnected(2)
      }


   IoPinState ::= TEXTUAL-CONVENTION
      DISPLAY-HINT "d"
      STATUS current
      DESCRIPTION
         "Possible states of digital I/O pins."
      SYNTAX INTEGER
      {
         open(1),
         closed(2)
      }


--
-- Module definition
--

   -- 1.3.6.1.4.1.40748.1.1.1
   ionSeriesModule MODULE-IDENTITY
      LAST-UPDATED "201506180000Z"
      ORGANIZATION "IONODES Inc."
      CONTACT-INFO
         "Stephane Pare
          IONODES Inc.

          EMail:    stephane.pare@ionodes.com
          phone:    +1 450 696-1060
          postal:   1855 rue Bernard-Lefebvre, suite 201
                    Laval, Qc H7C 0A5
                    Canada
         "
      DESCRIPTION
         "The MIB module for IONODES' IONSERIES line of products.
          Copyright (C) IONODES Inc (2013-2015).
         "
      ::= { ionModules 1 }


--
-- Node definitions
--

   -- 1.3.6.1.4.1.40748
   ionodes OBJECT IDENTIFIER ::= { enterprises 40748 }


   -- 1.3.6.1.4.1.40748.1
   ionReg OBJECT IDENTIFIER ::= { ionodes 1 }


   -- 1.3.6.1.4.1.40748.1.1
   ionModules OBJECT IDENTIFIER ::= { ionReg 1 }


   -- 1.3.6.1.4.1.40748.1.2
   ionConformance OBJECT IDENTIFIER ::= { ionReg 2 }


   -- 1.3.6.1.4.1.40748.1.2.1
   ionObjectGroups OBJECT-GROUP
      OBJECTS
      {
         ionSysCpuUsage, ionSysMemUsage, ionSysTemperature, ionVInNumber, ionVInIndex,
         ionVInDescr, ionVInAnalogSignalLock, ionVInAnalogStandard
      }
      STATUS current
      DESCRIPTION
         "Description."
      ::= { ionConformance 1 }


   -- 1.3.6.1.4.1.40748.1.3
   ionProducts OBJECT IDENTIFIER ::= { ionReg 3 }


   -- 1.3.6.1.4.1.40748.1.3.1
   ionIONSeries OBJECT IDENTIFIER ::= { ionProducts 1 }


   -- 1.3.6.1.4.1.40748.1.3.1.1
   ionE100 OBJECT IDENTIFIER ::= { ionIONSeries 1 }


   -- 1.3.6.1.4.1.40748.1.3.1.2
   ionE400 OBJECT IDENTIFIER ::= { ionIONSeries 2 }


   -- 1.3.6.1.4.1.40748.1.3.1.3
   ionE100Mini OBJECT IDENTIFIER ::= { ionIONSeries 3 }


   -- 1.3.6.1.4.1.40748.1.3.1.4
   ionE100HD OBJECT IDENTIFIER ::= { ionIONSeries 4 }


   -- 1.3.6.1.4.1.40748.1.3.1.5
   ionR100 OBJECT IDENTIFIER ::= { ionIONSeries 5 }


   -- 1.3.6.1.4.1.40748.1.3.1.6
   tve110sd OBJECT IDENTIFIER ::= { ionIONSeries 6 }


   -- 1.3.6.1.4.1.40748.1.3.2
   ionCIRRUSSeries OBJECT IDENTIFIER ::= { ionProducts 2 }


   -- 1.3.6.1.4.1.40748.2
   ionSystem OBJECT IDENTIFIER ::= { ionodes 2 }


   -- 1.3.6.1.4.1.40748.2.1
   ionSysCpuUsage OBJECT-TYPE
      SYNTAX Integer32 (0..100)
      UNITS "%"
      MAX-ACCESS read-only
      STATUS current
      DESCRIPTION
         "Current core CPU usage percentage."
      ::= { ionSystem 1 }


   -- 1.3.6.1.4.1.40748.2.2
   ionSysMemUsage OBJECT-TYPE
      SYNTAX Integer32 (0..100)
      UNITS "%"
      MAX-ACCESS read-only
      STATUS current
      DESCRIPTION
         "Current system memory usage percentage."
      ::= { ionSystem 2 }


   -- 1.3.6.1.4.1.40748.2.3
   ionSysTemperature OBJECT-TYPE
      SYNTAX Integer32
      UNITS "Celcius"
      MAX-ACCESS read-only
      STATUS current
      DESCRIPTION
         "Current system temperature, in degrees celcius."
      ::= { ionSystem 3 }


   -- 1.3.6.1.4.1.40748.3
   ionVideoInputs OBJECT IDENTIFIER ::= { ionodes 3 }


   -- 1.3.6.1.4.1.40748.3.1
   ionVInNumber OBJECT-TYPE
      SYNTAX Integer32
      MAX-ACCESS read-only
      STATUS current
      DESCRIPTION
         "Number of video inputs present."
      ::= { ionVideoInputs 1 }


   -- 1.3.6.1.4.1.40748.3.2
   ionVInTable OBJECT-TYPE
      SYNTAX SEQUENCE OF IonVInEntry
      MAX-ACCESS not-accessible
      STATUS current
      DESCRIPTION
         "Table containing the description of all video inputs present."
      ::= { ionVideoInputs 2 }


   -- 1.3.6.1.4.1.40748.3.2.1
   ionVInEntry OBJECT-TYPE
      SYNTAX IonVInEntry
      MAX-ACCESS not-accessible
      STATUS current
      DESCRIPTION
         "Description of a video input."
      INDEX { ionVInIndex }
      ::= { ionVInTable 1 }


   IonVInEntry ::=
      SEQUENCE
      {
         ionVInIndex
            Integer32 (1..4),
         ionVInDescr
            OCTET STRING,
         ionVInAnalogSignalLock
            AnalogVideoSignalLockState,
         ionVInAnalogStandard
            AnalogVideoStandard,
         ionVInDigitalConnState
            DigitalVideoConnState,
         ionVInDigitalStandard
            DigitalVideoStandard
      }


   -- 1.3.6.1.4.1.40748.3.2.1.1
   ionVInIndex OBJECT-TYPE
      SYNTAX Integer32 (1..4)
      MAX-ACCESS read-only
      STATUS current
      DESCRIPTION
         "Index of the video input (1-based)."
      ::= { ionVInEntry 1 }


   -- 1.3.6.1.4.1.40748.3.2.1.2
   ionVInDescr OBJECT-TYPE
      SYNTAX OCTET STRING
      MAX-ACCESS read-only
      STATUS current
      DESCRIPTION
         "Video input user-friendly name."
      ::= { ionVInEntry 2 }


   -- 1.3.6.1.4.1.40748.3.2.1.3
   ionVInAnalogSignalLock OBJECT-TYPE
      SYNTAX AnalogVideoSignalLockState
      MAX-ACCESS read-only
      STATUS current
      DESCRIPTION
         "Analog signal lock state of the video input."
      ::= { ionVInEntry 3 }


   -- 1.3.6.1.4.1.40748.3.2.1.4
   ionVInAnalogStandard OBJECT-TYPE
      SYNTAX AnalogVideoStandard
      MAX-ACCESS read-only
      STATUS current
      DESCRIPTION
         "Analog video standard (NTSC/PAL) currently detected by the video input.  This value is irrelevant if the analog video input lock state is unlocked."
      ::= { ionVInEntry 4 }


   -- 1.3.6.1.4.1.40748.3.2.1.5
   ionVInDigitalConnState OBJECT-TYPE
      SYNTAX DigitalVideoConnState
      MAX-ACCESS read-only
      STATUS current
      DESCRIPTION
         "Digital video connection state of the video input."
      ::= { ionVInEntry 5 }


   -- 1.3.6.1.4.1.40748.3.2.1.6
   ionVInDigitalStandard OBJECT-TYPE
      SYNTAX DigitalVideoStandard
      MAX-ACCESS read-only
      STATUS current
      DESCRIPTION
         "Digital video standard (HDMI) currently detected by the video input.  This value is irrelevant if the digital video input lock state is unlocked."
      ::= { ionVInEntry 6 }


   -- 1.3.6.1.4.1.40748.4
   ionVideoOutputs OBJECT IDENTIFIER ::= { ionodes 4 }


   -- 1.3.6.1.4.1.40748.4.1
   ionVOutNumber OBJECT-TYPE
      SYNTAX Integer32
      MAX-ACCESS read-only
      STATUS current
      DESCRIPTION
         "Number of video outputs present."
      ::= { ionVideoOutputs 1 }


   -- 1.3.6.1.4.1.40748.4.2
   ionVOutTable OBJECT-TYPE
      SYNTAX SEQUENCE OF IonVOutEntry
      MAX-ACCESS not-accessible
      STATUS current
      DESCRIPTION
         "Table containing the description of all video outputs present."
      ::= { ionVideoOutputs 2 }


   -- 1.3.6.1.4.1.40748.4.2.1
   ionVOutEntry OBJECT-TYPE
      SYNTAX IonVOutEntry
      MAX-ACCESS not-accessible
      STATUS current
      DESCRIPTION
         "Description of a video output."
      INDEX { ionVOutIndex }
      ::= { ionVOutTable 1 }


   IonVOutEntry ::=
      SEQUENCE
      {
         ionVOutIndex
            Integer32 (1..4),
         ionVOutDescr
            OCTET STRING,
         ionVOutAnalogSignalLock
            AnalogVideoSignalLockState,
         ionVOutAnalogStandard
            AnalogVideoStandard,
         ionVOutDigitalConnState
            DigitalVideoConnState,
         ionVOutDigitalStandard
            DigitalVideoStandard,
         ionVOutStream1State
            StreamState,
         ionVOutStream2State
            StreamState,
         ionVOutStream3State
            StreamState,
         ionVOutStream4State
            StreamState
      }


   -- 1.3.6.1.4.1.40748.4.2.1.1
   ionVOutIndex OBJECT-TYPE
      SYNTAX Integer32 (1..4)
      MAX-ACCESS read-only
      STATUS current
      DESCRIPTION
         "Index of the video output (1-based)."
      ::= { ionVOutEntry 1 }


   -- 1.3.6.1.4.1.40748.4.2.1.2
   ionVOutDescr OBJECT-TYPE
      SYNTAX OCTET STRING
      MAX-ACCESS read-only
      STATUS current
      DESCRIPTION
         "Video output user-friendly name."
      ::= { ionVOutEntry 2 }


   -- 1.3.6.1.4.1.40748.4.2.1.3
   ionVOutAnalogSignalLock OBJECT-TYPE
      SYNTAX AnalogVideoSignalLockState
      MAX-ACCESS read-only
      STATUS current
      DESCRIPTION
         "Analog signal lock state of the video output."
      ::= { ionVOutEntry 3 }


   -- 1.3.6.1.4.1.40748.4.2.1.4
   ionVOutAnalogStandard OBJECT-TYPE
      SYNTAX AnalogVideoStandard
      MAX-ACCESS read-only
      STATUS current
      DESCRIPTION
         "Analog video standard (NTSC/PAL) currently detected by the video output.  This value is irrelevant if the analog video output lock state is unlocked."
      ::= { ionVOutEntry 4 }


   -- 1.3.6.1.4.1.40748.4.2.1.5
   ionVOutDigitalConnState OBJECT-TYPE
      SYNTAX DigitalVideoConnState
      MAX-ACCESS read-only
      STATUS current
      DESCRIPTION
         "Digital video connection state of the video output."
      ::= { ionVOutEntry 5 }


   -- 1.3.6.1.4.1.40748.4.2.1.6
   ionVOutDigitalStandard OBJECT-TYPE
      SYNTAX DigitalVideoStandard
      MAX-ACCESS read-only
      STATUS current
      DESCRIPTION
         "Digital video standard (HDMI) currently detected by the video output.  This value is irrelevant if the digital video output lock state is unlocked."
      ::= { ionVOutEntry 6 }


   -- 1.3.6.1.4.1.40748.4.2.1.7
   ionVOutStream1State OBJECT-TYPE
      SYNTAX StreamState
      MAX-ACCESS read-only
      STATUS current
      DESCRIPTION
         "State of the video stream #1 feeding the video output."
      ::= { ionVOutEntry 7 }


   -- 1.3.6.1.4.1.40748.4.2.1.8
   ionVOutStream2State OBJECT-TYPE
      SYNTAX StreamState
      MAX-ACCESS read-only
      STATUS current
      DESCRIPTION
         "State of the video stream #2 feeding the video output."
      ::= { ionVOutEntry 8 }


   -- 1.3.6.1.4.1.40748.4.2.1.9
   ionVOutStream3State OBJECT-TYPE
      SYNTAX StreamState
      MAX-ACCESS read-only
      STATUS current
      DESCRIPTION
         "State of the video stream #3 feeding the video output."
      ::= { ionVOutEntry 9 }


   -- 1.3.6.1.4.1.40748.4.2.1.10
   ionVOutStream4State OBJECT-TYPE
      SYNTAX StreamState
      MAX-ACCESS read-only
      STATUS current
      DESCRIPTION
         "State of the video stream #4 feeding the video output."
      ::= { ionVOutEntry 10 }


   -- 1.3.6.1.4.1.40748.5
   ionAudioInputs OBJECT IDENTIFIER ::= { ionodes 5 }


   -- 1.3.6.1.4.1.40748.6
   ionAudioOutputs OBJECT IDENTIFIER ::= { ionodes 6 }


   -- 1.3.6.1.4.1.40748.7
   ionIoInputs OBJECT IDENTIFIER ::= { ionodes 7 }


   -- 1.3.6.1.4.1.40748.7.1
   ionIoInNumber OBJECT-TYPE
      SYNTAX Integer32
      MAX-ACCESS read-only
      STATUS current
      DESCRIPTION
         "Number of digital I/O input pins present."
      ::= { ionIoInputs 1 }


   -- 1.3.6.1.4.1.40748.7.2
   ionIoInTable OBJECT-TYPE
      SYNTAX SEQUENCE OF IonIoInEntry
      MAX-ACCESS not-accessible
      STATUS current
      DESCRIPTION
         "Table containing the description of all digital I/O input pins present."
      ::= { ionIoInputs 2 }


   -- 1.3.6.1.4.1.40748.7.2.1
   ionIoInEntry OBJECT-TYPE
      SYNTAX IonIoInEntry
      MAX-ACCESS not-accessible
      STATUS current
      DESCRIPTION
         "Description of a digital I/O input pin."
      INDEX { ionIoInIndex }
      ::= { ionIoInTable 1 }


   IonIoInEntry ::=
      SEQUENCE
      {
         ionIoInIndex
            Integer32 (1..4),
         ionIoInDescr
            OCTET STRING,
         ionIoInPinState
            IoPinState
      }


   -- 1.3.6.1.4.1.40748.7.2.1.1
   ionIoInIndex OBJECT-TYPE
      SYNTAX Integer32 (1..4)
      MAX-ACCESS read-only
      STATUS current
      DESCRIPTION
         "Index of the digital I/O input pin (1-based)."
      ::= { ionIoInEntry 1 }


   -- 1.3.6.1.4.1.40748.7.2.1.2
   ionIoInDescr OBJECT-TYPE
      SYNTAX OCTET STRING
      MAX-ACCESS read-only
      STATUS current
      DESCRIPTION
         "Digital I/O input pin user-friendly name."
      ::= { ionIoInEntry 2 }


   -- 1.3.6.1.4.1.40748.7.2.1.3
   ionIoInPinState OBJECT-TYPE
      SYNTAX IoPinState
      MAX-ACCESS read-only
      STATUS current
      DESCRIPTION
         "State of the digital I/O input pin."
      ::= { ionIoInEntry 3 }


   -- 1.3.6.1.4.1.40748.8
   ionIoOutputs OBJECT IDENTIFIER ::= { ionodes 8 }


   -- 1.3.6.1.4.1.40748.8.1
   ionIoOutNumber OBJECT-TYPE
      SYNTAX Integer32
      MAX-ACCESS read-only
      STATUS current
      DESCRIPTION
         "Number of digital I/O output pins present."
      ::= { ionIoOutputs 1 }


   -- 1.3.6.1.4.1.40748.8.2
   ionIoOutTable OBJECT-TYPE
      SYNTAX SEQUENCE OF IonIoOutEntry
      MAX-ACCESS not-accessible
      STATUS current
      DESCRIPTION
         "Table containing the description of all digital I/O output pins present."
      ::= { ionIoOutputs 2 }


   -- 1.3.6.1.4.1.40748.8.2.1
   ionIoOutEntry OBJECT-TYPE
      SYNTAX IonIoOutEntry
      MAX-ACCESS not-accessible
      STATUS current
      DESCRIPTION
         "Description of a digital I/O output pin."
      INDEX { ionIoOutIndex }
      ::= { ionIoOutTable 1 }


   IonIoOutEntry ::=
      SEQUENCE
      {
         ionIoOutIndex
            Integer32 (1..4),
         ionIoOutDescr
            OCTET STRING,
         ionIoOutPinState
            IoPinState
      }


   -- 1.3.6.1.4.1.40748.8.2.1.1
   ionIoOutIndex OBJECT-TYPE
      SYNTAX Integer32 (1..4)
      MAX-ACCESS read-only
      STATUS current
      DESCRIPTION
         "Index of the digital I/O output pin (1-based)."
      ::= { ionIoOutEntry 1 }


   -- 1.3.6.1.4.1.40748.8.2.1.2
   ionIoOutDescr OBJECT-TYPE
      SYNTAX OCTET STRING
      MAX-ACCESS read-only
      STATUS current
      DESCRIPTION
         "Digital I/O output pin user-friendly name."
      ::= { ionIoOutEntry 2 }


   -- 1.3.6.1.4.1.40748.8.2.1.3
   ionIoOutPinState OBJECT-TYPE
      SYNTAX IoPinState
      MAX-ACCESS read-only
      STATUS current
      DESCRIPTION
         "State of the digital I/O output pin."
      ::= { ionIoOutEntry 3 }


   -- 1.3.6.1.4.1.40748.9
   ionSerialPorts OBJECT IDENTIFIER ::= { ionodes 9 }


END
