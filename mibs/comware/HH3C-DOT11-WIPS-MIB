-- =============================================================================
-- Copyright (c) 2004-2016 New H3C Tech. Co., Ltd.  All rights reserved.
--
-- Description:
--   The file defines a MIB to provide wireless intrusion prevention service
--   feature.
-- Reference:
-- Version: V1.1
-- History:
--   V1.0 created by sunanzhi
--     Initial version 2015-03-20
--        2015-12-08 updated by sunanzhi
--     Modify the node name of Hh3cDot11WIPSVsdEntry,Hh3cDot11WIPSAp2VsdEntry,
--     Hh3cDot11WIPSApRadioEntry,Hh3cDot11WIPSDctAPEntry,
--     Hh3cDot11WIPSDctStaEntry
--     Add new objects Hh3cDot11WIPSRuleEntry,Hh3cDot11WIPSAlySigRuleEntry,
--     Hh3cDot11WIPSAlyClaRuleEntry,Hh3cDot11WIPSTrustMacEntry,
--     Hh3cDot11WIPSBlockMacEntry,Hh3cDot11WIPSManulClaEntry,
--     Hh3cDot11WIPSTrustOuiEntry,Hh3cDot11WIPSTrustSSidEntry,
--     Hh3cDot11WIPSMalfDtcEntry,Hh3cDot11WIPSLgeDutEntry,
--     Hh3cDot11WIPSRtLmtEntry,Hh3cDot11WIPSDtcAckEntry,
--     Hh3cDot11WIPSDtcDevTimeEntry,Hh3cDot11WIPSApimperEntry,
--     Hh3cDot11WIPSDctSoftApEntry,Hh3cDot11WIPSPowerSaveEntry,
--     Hh3cDot11WIPSIgnListMacEntry,Hh3cDot11WIPSHoneyPotEntry,
--     Hh3cDot11WIPSAPFldEntry,Hh3cDot11WIPSCtmManualsEntry,
--     Hh3cDot11WIPSCtmSensorEntry,Hh3cDot11WIPSInvOuiStateEntry,
--     Hh3cDot11WIPSAPClaAuthEntry,Hh3cDot11WIPSAPClaCltOnlEntry,
--     Hh3cDot11WIPSAPClaDiscrEntry,Hh3cDot11WIPSAPClaRssiEntry,
--     Hh3cDot11WIPSAPClaUpdurEntry,Hh3cDot11WIPSAPClaOuiEntry,
--     Hh3cDot11WIPSAPClaSryEntry,Hh3cDot11WIPSAPClaSsidEntry,
--     Hh3cDot11WIPSDtcSigEntry,Hh3cDot11WIPSPolicyEntry,
--     Hh3cDot11WIPSSigFrameTypeEntry,Hh3cDot11WIPSCtmEntry,
--     Hh3cDot11WIPSSigPatternEntry,Hh3cDot11WIPSSigSeqNumEntry,
--     Hh3cDot11WIPSSigSsidEntry,Hh3cDot11WIPSSigSsidLengthEntry,
--     Hh3cDot11WIPSFldDetectEntry,Hh3cDot11WIPSSignatureMacEntry,
--     Hh3cDot11WIPSRadioCfgEntry,Hh3cDot11WIPSNatDetectEntry,
--     Hh3cDot11WIPSApAssoCltEntry,Hh3cDot11WIPSApRpSenEntry,
--     Hh3cDot11WIPSCtmRecEntry,Hh3cDot11WIPSDevEntry,Hh3cDot11WIPSCtmDevEntry,
--     Hh3cDot11WIPSCltProbeEntry,Hh3cDot11WIPSPbeStaEntry,
--     Hh3cDot11WIPSCltRptApEntry,Hh3cDot11WIPSNatDtcCltEntry,
--     Hh3cDot11WIPSAckStaEntry
--   V1.1 2016-02-17 updated by sunanzhi
--     Modify the objects Hh3cDot11WIPSEncryptMethod,Hh3cDot11WIPSAuthMethod
--     Hh3cDot11WIPSAPSecurityType,hh3cDot11WIPSDctAPSSID
--        2016-03-28 updated by sunanzhi
--     Delete the objects Hh3cDot11WIPSCltProbeEntry,Hh3cDot11WIPSPbeStaEntry
--     Hh3cDot11WIPSRadioCfgEntry
-- =============================================================================
HH3C-DOT11-WIPS-MIB DEFINITIONS ::= BEGIN

IMPORTS
    TimeTicks, Integer32, Unsigned32, OBJECT-TYPE, MODULE-IDENTITY
        FROM SNMPv2-SMI
    TruthValue, RowStatus, MacAddress, TEXTUAL-CONVENTION
        FROM SNMPv2-TC
    hh3cDot11
        FROM HH3C-OID-MIB;

hh3cDot11WIPS MODULE-IDENTITY
    LAST-UPDATED "201603280951Z"        -- March 28, 2016 at 09:51 GMT
    ORGANIZATION
        "New H3C Technologies Co., Ltd."
    CONTACT-INFO
        "Platform Team New H3C Technologies Co., Ltd.
        Hai-Dian District Beijing P.R. China
        http://www.h3c.com
        Zip:100085
        "
    DESCRIPTION
        "This MIB provides information about the Wireless Intrusion
        Prevention System (WIPS) feature.

        WIPS is designed to protect an area that is serviced by
        a wireless network.
        It aids in early detection of malicious outsider attacks
        and intrusions via wireless networks, and takes countermeasures
        to ensure the wireless environment security.
        "
    REVISION "201603280951Z"        -- March 28, 2016 at 09:51 GMT
    DESCRIPTION
        "Delete table for probe."
    REVISION "201602161051Z"        -- February 16, 2016 at 10:51 GMT
    DESCRIPTION
        "Modify objects."
    REVISION "201512081551Z"        -- December 08, 2015 at 15:51 GMT
    DESCRIPTION
        "Add new objects."
    REVISION "201503311351Z"        -- March 31, 2015 at 13:51 GMT
    DESCRIPTION
        "The initial revision of this MIB module."
    ::= {  hh3cDot11 15 }

--
-- Textual conventions
--
Hh3cDot11WIPSEnabledStatus ::= TEXTUAL-CONVENTION
    STATUS      current
    DESCRIPTION
        "The enable status values for objects.
        Values include enabled and disbaled."
    SYNTAX      INTEGER { enabled(1), disabled(2) }

Hh3cDot11WIPSRtLmtType ::= TEXTUAL-CONVENTION
    STATUS current
    DESCRIPTION
        "Represents the type of rate limit configuration."
    SYNTAX INTEGER
        {
        ap(1),
        client(4)
        }

Hh3cDot11WIPSDeviceType ::= TEXTUAL-CONVENTION
    STATUS current
    DESCRIPTION
        "Represents the type of device."
    SYNTAX INTEGER
        {
        ap(1),
        client(2)
        }

Hh3cDot11WIPSPolicyTypeValue ::= TEXTUAL-CONVENTION
    STATUS current
    DESCRIPTION
        "Represents the type of policy."
    SYNTAX INTEGER
        {
        classification(1),
        countermeasure(2),
        detect(3),
        signature(4)
        }

Hh3cDot11WIPSClassifyType ::= TEXTUAL-CONVENTION
   STATUS current
   DESCRIPTION
        "Represents the category of the device detected by WIPS."
   SYNTAX INTEGER
       {
       none(1),
       authorizedap(2),
       misconfiguredap(3),
       rogueap(4),
       externalap(5),
       adhoc(6),
       meshap(7),
       potentialauthorizedap(8),
       potentialrogueap(9),
       potentialexternalap(10),
       uncategorizedap(11),
       authorizedclient(12),
       unauthorizedclient(13),
       misassociaionclient(14),
       uncategorizedclient(15)
       }

Hh3cDot11WIPSRadioType ::= TEXTUAL-CONVENTION
    STATUS current
    DESCRIPTION
        "Represents AP 802.11 radio type of 802.11a/b/g/n as per
        the standard.
        The following values are supported:
        dot11a  - 802.11a
        dot11b  - 802.11b
        dot11g  - 802.11g
        dot11n  - 802.11n
        dot11gn  - 802.11gn
        dot11an  - 802.11an
        dot11ac  - 802.11ac
        dot11gac  - 802.11gac"
    SYNTAX INTEGER
        {
        dot11a(1),
        dot11b(2),
        dot11g(4),
        dot11n(8),
        dot11gn(16),
        dot11an(32),
        dot11ac(64),
        dot11gac(128)
        }

Hh3cDot11WIPSDevStatus ::= TEXTUAL-CONVENTION
    STATUS current
    DESCRIPTION
        "Represents the status of devices detected by WIPS."
    SYNTAX INTEGER
        {
        active(1),
        inactive(2)
        }

Hh3cDot11WIPSAPType ::= TEXTUAL-CONVENTION
    STATUS current
    DESCRIPTION
        "Represents the type of AP detected by WIPS."
    SYNTAX INTEGER
        {
        normal(1),
        adhoc(2),
        mesh(3)
        }


Hh3cDot11WIPSDevClassifyWay ::= TEXTUAL-CONVENTION
    STATUS current
    DESCRIPTION
        "Represents the method that the device is categorized."
    SYNTAX INTEGER
        {
        manual(1),
        invalidOUI(2),
        trustlist(3),
        blocklist(4),
        associated(5),
        userdefined(6),
        auto(7)
        }

Hh3cDot11WIPSAPClassifyType ::= TEXTUAL-CONVENTION
    STATUS current
    DESCRIPTION
        "Represents the category of the AP detected by WIPS."
    SYNTAX INTEGER
        {
        authorized(1),
        misconfigured(2),
        rogue(3),
        external(4),
        adhoc(5),
        mesh(6),
        potentialAuthorized(7),
        potentialRogue(8),
        potentialExternal(9),
        uncategorized(10)
        }

Hh3cDot11WIPSStaClassifyType ::= TEXTUAL-CONVENTION
    STATUS current
    DESCRIPTION
        "Represents the category of the client detected by WIPS."
    SYNTAX INTEGER
        {
        authorized(1),
        unauthorized(2),
        misassociated(3),
        uncategorized(4)
        }

Hh3cDot11WIPSChannel ::= TEXTUAL-CONVENTION
    DISPLAY-HINT "d"
    STATUS current
    DESCRIPTION
        "Represents the channel number."
    SYNTAX Integer32 (1..224)

Hh3cDot11WIPSEncryptMethod ::= TEXTUAL-CONVENTION
    DISPLAY-HINT "d"
    STATUS current
    DESCRIPTION
        "Represents the frame encryption cipher types(bitmap) for
        frames on IEEE 802.11 radio interfaces.
        The MIB defines TC by referring to the 802.11i protocol.
        The following bits are supported:
        first bit:    none,
        second bit:   wep,
        third bit:    wep40,
        fourth bit:   tkip
        fifth bit:    reserve
        sixth bit:    ccmp
        seventh bit:  wep104
        eighth bit:   wep128"
    SYNTAX Integer32 (1..65535)

Hh3cDot11WIPSAuthMethod ::= TEXTUAL-CONVENTION
    DISPLAY-HINT "d"
    STATUS current
    DESCRIPTION
        "Represents the key management mode(bitmap), compliant with 802.11i.
        The following bits are supported:
        first bit:   none         - No key management mode is specified,
        second bit:  dot1x        - 802.1X authentication.
        third bit:   psk          - Pre-shared key authentication,
        fourth bit:  other        - Other authentication."
    SYNTAX Integer32 (1..65535)

Hh3cDot11WIPSAPSecurityType ::= TEXTUAL-CONVENTION
    DISPLAY-HINT "d"
    STATUS current
    DESCRIPTION
        "Represents the AP security type(bitmap).
        The following bits are supported:
        first bit:   none,
        second bit:  wpa2,
        third bit:   wpa,
        fourth bit:  wlanex
        fifth bit:   wep"
    SYNTAX Integer32 (1..255)

Hh3cDot11WIPSMalformedType ::= TEXTUAL-CONVENTION
    STATUS current
    DESCRIPTION
        "Represents the category of malformed packet."
    SYNTAX INTEGER
        {
        duplicatedie(1),
        fatajack(2),
        illegalibssess(3),
        invalidaddresscombination(4),
        invalidassocreq(5),
        invalidauth(6),
        invaliddeauthcode(7),
        invaliddisassoccode(8),
        invalidhtie(9),
        invalidielength(10),
        invalidpktlength(11),
        nullproberesp(13),
        overfloweapolkey(14),
        overflowssid(15),
        redundantie(16)
        }

Hh3cDot11WIPSCtmType ::= TEXTUAL-CONVENTION
    STATUS current
    DESCRIPTION
        "Represents the category of countermeasure method."
    SYNTAX INTEGER
        {
        externalAp(1),
        misassociationClient(2),
        misconfiguredAp(3),
        potentialAuthorizedAp(4),
        potentialExternalAp(5),
        potentialRogueAp(6),
        rogueAp(7),
        unauthorizedClient(8),
        uncategorizedAp(9),
        uncategorizedClient(10),
        attack(11),
        adhoc(12)
        }

Hh3cDot11WIPSRuleTypes ::= TEXTUAL-CONVENTION
    STATUS current
    DESCRIPTION
        "Represents the type of rule"
    SYNTAX INTEGER
        {
        signature(4),
        apclassfication(5)
        }

Hh3cDot11WIPSSigFrameTypes ::= TEXTUAL-CONVENTION
    STATUS current
    DESCRIPTION
        "Represents the type of signature frame configuration."
    SYNTAX INTEGER
        {
        management(1),
        control(2),
        data(3)
        }

Hh3cDot11WIPSSigFrameSubTypes ::= TEXTUAL-CONVENTION
    STATUS current
    DESCRIPTION
        "Represents the type of signature manage frame configuration."
    SYNTAX INTEGER
        {
        assocerq(1),
        assocresp(2),
        probereq(3),
        beacon(4),
        disasso(5),
        auth(6),
        deauth(7)
        }

Hh3cDot11WIPSSigSsidMatchTypes ::= TEXTUAL-CONVENTION
    STATUS current
    DESCRIPTION
        "Represents the match type of signature ssid configuration."
    SYNTAX INTEGER
        {
        equal(1),
        notequal(2),
        include(3),
        notinclude(4)
        }

Hh3cDot11WIPSSigMacMacType ::= TEXTUAL-CONVENTION
    STATUS current
    DESCRIPTION
        "Represents the mac type of signature ssid configuration."
    SYNTAX INTEGER
        {
        source(1),
        destination(2),
        bssid(3)
        }

Hh3cDot11WIPSManualAPType ::= TEXTUAL-CONVENTION
    STATUS current
    DESCRIPTION
        "Represents the type of AP manual classification."
    SYNTAX INTEGER
        {
       authap(1),
       misconfiguredap(2),
        rogueap(3),
        externalap(4)
        }

Hh3cDot11WIPSDtcAckTypes ::= TEXTUAL-CONVENTION
    STATUS current
    DESCRIPTION
        "Represents the type of attack detect."
    SYNTAX INTEGER
        {
        apspoof(1),
        clientspoof(4),
        weakiv(6),
        windowsbridge(7),
        fortymhz(8),
        omerta(11),
        disassoc(12),
        deauth(13),
        prohibitedchannel(14),
        authunencryptedap(16),
        authunencryptedclient(17),
        hotspot(18),
        greenmode(19),
        tableoverflow(20),
        mitm(22),
        wirelessbridge(23),
        apchannelchange(25)
        }

Hh3cDot11WIPSDtcDevTimeTypes ::= TEXTUAL-CONVENTION
    STATUS current
    DESCRIPTION
        "Represents the type of device time."
    SYNTAX INTEGER
        {
        deviceap(1),
        deviceclient(2)
        }

Hh3cDot11WIPSFldDctType ::= TEXTUAL-CONVENTION
    STATUS current
    DESCRIPTION
        "Represents the type of flood detect."
    SYNTAX INTEGER
        {
        associationrequest(1),
        authentication(2),
        beacon(3),
        blockack(4),
        cts(5),
        deauthentication(6),
        disassociation(7),
        eapolstart(8),
        nulldata(9),
        proberequest(10),
        reassociationrequest(11),
        rts(12),
        eapollogoff(13),
        eapfailure(14),
        eapsuccess(15)
        }

Hh3cDot11WIPSAPClaAuthMethods ::= TEXTUAL-CONVENTION
    STATUS current
    DESCRIPTION
        "Represents the type of AP classification method."
    SYNTAX INTEGER
        {
        none(1),
        dot1x(2),
        psk(3),
        other(5)
        }


Hh3cDot11WIPSAPClassifyCmpType ::= TEXTUAL-CONVENTION
    STATUS current
    DESCRIPTION
        "Represents the compare type of AP classification method.
        The following values are supported:
        equal         - equal.
        include       - include."
    SYNTAX INTEGER
        {
        equal(1),
        include(3)
        }

Hh3cDot11WIPSAPClasSsidCmpType ::= TEXTUAL-CONVENTION
    STATUS current
    DESCRIPTION
        "Represents the compare type of AP classification ssid.
        The following values are supported:
        equal         - equal.
        not equal     - not equal.
        include       - include.
        not include   - not include."
    SYNTAX INTEGER
        {
        equal(1),
        notequal(2),
        include(3),
        notinclude(4)
        }


Hh3cDot11WIPSAPClaSecurityType ::= TEXTUAL-CONVENTION
    STATUS current
    DESCRIPTION
        "Represents the type of AP classification security.
        clear   1
        wpa2   2
        wpa    3
        wep    9"
    SYNTAX INTEGER
        {
        clear(1),
        wpa2(2),
        wpa(3),
        wep(9)
        }

Hh3cDot11WIPSAlyAPClaRuleType ::= TEXTUAL-CONVENTION
    STATUS current
    DESCRIPTION
        "Represents the category of apply AP classification rule."
    SYNTAX INTEGER
        {
        rogue(1),
        external(2),
        misconfigured(3),
        authorized(4)
        }

Hh3cDot11WIPSOuiAddress ::= TEXTUAL-CONVENTION
    DISPLAY-HINT "1x:"
    STATUS       current
    DESCRIPTION
        "Represents an 802 OUI address represented in the
        `canonical' order defined by IEEE 802.1a, i.e., as if it
        were transmitted least significant bit first, even though
        802.5 (in contrast to other 802.x protocols) requires MAC
        addresses to be transmitted most significant bit first."
    SYNTAX       OCTET STRING (SIZE (3))

--
-- Node definitions
--
hh3cDot11WIPSConfigGroup OBJECT IDENTIFIER ::= { hh3cDot11WIPS 1 }
hh3cDot11WIPSDataGroup OBJECT IDENTIFIER ::= { hh3cDot11WIPS 2 }

hh3cDot11WIPSVsdTable OBJECT-TYPE
    SYNTAX SEQUENCE OF Hh3cDot11WIPSVsdEntry
    MAX-ACCESS not-accessible
    STATUS current
    DESCRIPTION
        "The table provides information about virtual security domains (VSDs)."
    ::= { hh3cDot11WIPSConfigGroup 1 }

hh3cDot11WIPSVsdEntry OBJECT-TYPE
    SYNTAX Hh3cDot11WIPSVsdEntry
    MAX-ACCESS not-accessible
    STATUS current
    DESCRIPTION
        "Each entry contains information about one VSD."
    INDEX { hh3cDot11WIPSVsdName }
    ::= { hh3cDot11WIPSVsdTable 1 }

Hh3cDot11WIPSVsdEntry ::= SEQUENCE {
        hh3cDot11WIPSVsdName                      OCTET STRING,
        hh3cDot11WIPSVsdRowStatus                 RowStatus,
        hh3cDot11WIPSVsdDetectPolicy              OCTET STRING,
        hh3cDot11WIPSVsdCtmPolicy                 OCTET STRING,
        hh3cDot11WIPSVsdSignaturePolicy           OCTET STRING,
        hh3cDot11WIPSVsdClasPolicy                OCTET STRING
     }

hh3cDot11WIPSVsdName OBJECT-TYPE
    SYNTAX OCTET STRING (SIZE (1..63))
    MAX-ACCESS not-accessible
    STATUS current
    DESCRIPTION
        "Represents the name of the virtual security domain."
    ::= { hh3cDot11WIPSVsdEntry 1 }

hh3cDot11WIPSVsdRowStatus OBJECT-TYPE
    SYNTAX RowStatus
    MAX-ACCESS read-create
    STATUS current
    DESCRIPTION
        "The status of this table entry."
    ::= { hh3cDot11WIPSVsdEntry 2 }

hh3cDot11WIPSVsdDetectPolicy OBJECT-TYPE
    SYNTAX OCTET STRING (SIZE (0..63))
    MAX-ACCESS read-create
    STATUS current
    DESCRIPTION
        "Represents the name of the attack detect policy attached to the VSD,
        zero-length for not config."
    ::= { hh3cDot11WIPSVsdEntry 3 }

hh3cDot11WIPSVsdCtmPolicy OBJECT-TYPE
    SYNTAX OCTET STRING (SIZE (0..63))
    MAX-ACCESS read-create
    STATUS current
    DESCRIPTION
        "Represents the name of the countermeasure policy attached to the VSD,
        zero-length for not config."
    ::= { hh3cDot11WIPSVsdEntry 4 }

hh3cDot11WIPSVsdSignaturePolicy OBJECT-TYPE
    SYNTAX OCTET STRING (SIZE (0..63))
    MAX-ACCESS read-create
    STATUS current
    DESCRIPTION
        "Represents the name of the signature policy attached to the VSD,
        zero-length for not config."
    ::= { hh3cDot11WIPSVsdEntry 5 }

hh3cDot11WIPSVsdClasPolicy OBJECT-TYPE
    SYNTAX OCTET STRING (SIZE (0..63))
    MAX-ACCESS read-create
    STATUS current
    DESCRIPTION
        "Represents the name of the malformed packet detect policy attached
        to the VSD,zero-length for not config."
    ::= { hh3cDot11WIPSVsdEntry 6 }

hh3cDot11WIPSAp2VsdTable OBJECT-TYPE
    SYNTAX SEQUENCE OF Hh3cDot11WIPSAp2VsdEntry
    MAX-ACCESS not-accessible
    STATUS current
    DESCRIPTION
        "The table defines sensors attached to VSDs."
    ::= { hh3cDot11WIPSConfigGroup 2 }

hh3cDot11WIPSAp2VsdEntry OBJECT-TYPE
    SYNTAX Hh3cDot11WIPSAp2VsdEntry
    MAX-ACCESS not-accessible
    STATUS current
    DESCRIPTION
        "Each entry contains information about a sensor in a VSD."
    INDEX { hh3cDot11WIPSAp2VsdApName }
    ::= { hh3cDot11WIPSAp2VsdTable 1 }

Hh3cDot11WIPSAp2VsdEntry ::= SEQUENCE {
        hh3cDot11WIPSAp2VsdApName        OCTET STRING,
        hh3cDot11WIPSAp2VsdRowStatus     RowStatus,
        hh3cDot11WIPSAp2VsdVsdName       OCTET STRING
     }

hh3cDot11WIPSAp2VsdApName OBJECT-TYPE
    SYNTAX OCTET STRING (SIZE (1..64))
    MAX-ACCESS not-accessible
    STATUS current
    DESCRIPTION
        "Represents the sensor name."
    ::= { hh3cDot11WIPSAp2VsdEntry 1 }

hh3cDot11WIPSAp2VsdRowStatus OBJECT-TYPE
    SYNTAX RowStatus
    MAX-ACCESS read-create
    STATUS current
    DESCRIPTION
        "The status of this table entry."
    ::= { hh3cDot11WIPSAp2VsdEntry 2 }

hh3cDot11WIPSAp2VsdVsdName OBJECT-TYPE
    SYNTAX OCTET STRING (SIZE (1..63))
    MAX-ACCESS read-create
    STATUS current
    DESCRIPTION
        "Represents the name of a virtual security domain."
    ::= { hh3cDot11WIPSAp2VsdEntry 3 }


hh3cDot11WIPSApRadioTable OBJECT-TYPE
    SYNTAX SEQUENCE OF Hh3cDot11WIPSApRadioEntry
    MAX-ACCESS not-accessible
    STATUS current
    DESCRIPTION
        "The table contains the enable status of WIPS on radios of sensors."
    ::= { hh3cDot11WIPSConfigGroup 3 }

hh3cDot11WIPSApRadioEntry OBJECT-TYPE
    SYNTAX Hh3cDot11WIPSApRadioEntry
    MAX-ACCESS not-accessible
    STATUS current
    DESCRIPTION
        "Each entry contains the enable status
         of WIPS on one radio of a sensor."
    INDEX { hh3cDot11WIPSApRadioApName, hh3cDot11WIPSApRadioRadioID }
    ::= { hh3cDot11WIPSApRadioTable 1 }

Hh3cDot11WIPSApRadioEntry ::= SEQUENCE {
        hh3cDot11WIPSApRadioApName       OCTET STRING,
        hh3cDot11WIPSApRadioRadioID      Integer32,
        hh3cDot11WIPSApRadioStatus       Hh3cDot11WIPSEnabledStatus
     }

hh3cDot11WIPSApRadioApName OBJECT-TYPE
    SYNTAX OCTET STRING (SIZE (1..64))
    MAX-ACCESS not-accessible
    STATUS current
    DESCRIPTION
        "Represents the sensor name."
    ::= { hh3cDot11WIPSApRadioEntry 1 }

hh3cDot11WIPSApRadioRadioID OBJECT-TYPE
    SYNTAX Integer32 (1..4)
    MAX-ACCESS not-accessible
    STATUS current
    DESCRIPTION
        "Represents a radio identifier."
    ::= { hh3cDot11WIPSApRadioEntry 2 }

hh3cDot11WIPSApRadioStatus OBJECT-TYPE
    SYNTAX  Hh3cDot11WIPSEnabledStatus
    MAX-ACCESS read-write
    STATUS current
    DESCRIPTION
        "The enable status of WIPS on the radio."
    ::= { hh3cDot11WIPSApRadioEntry 3 }

hh3cDot11WIPSRuleTable OBJECT-TYPE
    SYNTAX SEQUENCE OF Hh3cDot11WIPSRuleEntry
    MAX-ACCESS not-accessible
    STATUS current
    DESCRIPTION
        "The table defines signature rule or ap-class rule."
    ::= { hh3cDot11WIPSConfigGroup 4 }

hh3cDot11WIPSRuleEntry OBJECT-TYPE
    SYNTAX Hh3cDot11WIPSRuleEntry
    MAX-ACCESS not-accessible
    STATUS current
    DESCRIPTION
        "Each entry contains information about
         signature rule or ap-class rule."
    INDEX { hh3cDot11WIPSRuleType, hh3cDot11WIPSRuleId }
    ::= { hh3cDot11WIPSRuleTable 1 }

Hh3cDot11WIPSRuleEntry ::= SEQUENCE {
        hh3cDot11WIPSRuleType                Hh3cDot11WIPSRuleTypes,
        hh3cDot11WIPSRuleId                  Integer32,
        hh3cDot11WIPSRuleRowStatus           RowStatus
     }

hh3cDot11WIPSRuleType OBJECT-TYPE
    SYNTAX Hh3cDot11WIPSRuleTypes
    MAX-ACCESS not-accessible
    STATUS current
    DESCRIPTION
        "Represents the rule type."
    ::= { hh3cDot11WIPSRuleEntry 1 }

hh3cDot11WIPSRuleId OBJECT-TYPE
    SYNTAX Integer32 (1..65535)
    MAX-ACCESS not-accessible
    STATUS current
    DESCRIPTION
        "Represents the rule id."
    ::= { hh3cDot11WIPSRuleEntry 2 }

hh3cDot11WIPSRuleRowStatus OBJECT-TYPE
    SYNTAX RowStatus
    MAX-ACCESS read-create
    STATUS current
    DESCRIPTION
        "The status of this table entry."
    ::= { hh3cDot11WIPSRuleEntry 3 }

hh3cDot11WIPSAlySigRuleTable OBJECT-TYPE
    SYNTAX SEQUENCE OF Hh3cDot11WIPSAlySigRuleEntry
    MAX-ACCESS not-accessible
    STATUS current
    DESCRIPTION
        "The table provides information about applying signature rule."
    ::= { hh3cDot11WIPSConfigGroup 5 }

hh3cDot11WIPSAlySigRuleEntry OBJECT-TYPE
    SYNTAX Hh3cDot11WIPSAlySigRuleEntry
    MAX-ACCESS not-accessible
    STATUS current
    DESCRIPTION
        "Each entry contains information about applying signature rule."
    INDEX { hh3cDot11WIPSAlySigPolicyName, hh3cDot11WIPSAlySigRuleID }
    ::= { hh3cDot11WIPSAlySigRuleTable 1 }

Hh3cDot11WIPSAlySigRuleEntry ::= SEQUENCE {
        hh3cDot11WIPSAlySigPolicyName                OCTET STRING,
        hh3cDot11WIPSAlySigRuleID                    Integer32,
        hh3cDot11WIPSAlySigRowStatus                 RowStatus
     }

hh3cDot11WIPSAlySigPolicyName OBJECT-TYPE
    SYNTAX OCTET STRING (SIZE (1..63))
    MAX-ACCESS not-accessible
    STATUS current
    DESCRIPTION
        "Represents the name of signature policy name."
    ::= { hh3cDot11WIPSAlySigRuleEntry 1 }

hh3cDot11WIPSAlySigRuleID OBJECT-TYPE
    SYNTAX Integer32 (1..65535)
    MAX-ACCESS not-accessible
    STATUS current
    DESCRIPTION
        "Represents the rule id of signature."
    ::= { hh3cDot11WIPSAlySigRuleEntry 2 }

hh3cDot11WIPSAlySigRowStatus OBJECT-TYPE
    SYNTAX RowStatus
    MAX-ACCESS read-create
    STATUS current
    DESCRIPTION
        "The status of this table entry."
    ::= { hh3cDot11WIPSAlySigRuleEntry 3 }

hh3cDot11WIPSAlyClaRuleTable OBJECT-TYPE
    SYNTAX SEQUENCE OF Hh3cDot11WIPSAlyClaRuleEntry
    MAX-ACCESS not-accessible
    STATUS current
    DESCRIPTION
        "The table provides information about applying classification rule."
    ::= { hh3cDot11WIPSConfigGroup 6 }

hh3cDot11WIPSAlyClaRuleEntry OBJECT-TYPE
    SYNTAX Hh3cDot11WIPSAlyClaRuleEntry
    MAX-ACCESS not-accessible
    STATUS current
    DESCRIPTION
        "Each entry contains information about applying classification rule."
    INDEX { hh3cDot11WIPSAlyClaPolicyName, hh3cDot11WIPSAlyClasRuleID }
    ::= { hh3cDot11WIPSAlyClaRuleTable 1 }

Hh3cDot11WIPSAlyClaRuleEntry ::= SEQUENCE {
        hh3cDot11WIPSAlyClaPolicyName           OCTET STRING,
        hh3cDot11WIPSAlyClasRuleID              Integer32,
        hh3cDot11WIPSAlyClaRuleType             Hh3cDot11WIPSAlyAPClaRuleType,
        hh3cDot11WIPSAlyClaRuleLevel            Integer32,
        hh3cDot11WIPSAlyClaRowStatus            RowStatus
     }

hh3cDot11WIPSAlyClaPolicyName OBJECT-TYPE
    SYNTAX OCTET STRING (SIZE (1..63))
    MAX-ACCESS not-accessible
    STATUS current
    DESCRIPTION
        "Represents the name of classification policy name."
    ::= { hh3cDot11WIPSAlyClaRuleEntry 1 }

hh3cDot11WIPSAlyClasRuleID OBJECT-TYPE
    SYNTAX Integer32 (1..65535)
    MAX-ACCESS not-accessible
    STATUS current
    DESCRIPTION
        "Represents the rule id of classification."
    ::= { hh3cDot11WIPSAlyClaRuleEntry 2 }

hh3cDot11WIPSAlyClaRuleType OBJECT-TYPE
    SYNTAX Hh3cDot11WIPSAlyAPClaRuleType
    MAX-ACCESS read-create
    STATUS current
    DESCRIPTION
        "The type of applying classfication rule."
    ::= { hh3cDot11WIPSAlyClaRuleEntry 3 }

hh3cDot11WIPSAlyClaRuleLevel OBJECT-TYPE
    SYNTAX Integer32 (1..100)
    MAX-ACCESS read-create
    STATUS current
    DESCRIPTION
        "The level of applying classfication rule."
    ::= { hh3cDot11WIPSAlyClaRuleEntry 4 }

hh3cDot11WIPSAlyClaRowStatus OBJECT-TYPE
    SYNTAX RowStatus
    MAX-ACCESS read-create
    STATUS current
    DESCRIPTION
        "The status of this table entry."
    ::= { hh3cDot11WIPSAlyClaRuleEntry 5 }

hh3cDot11WIPSTrustMacTable OBJECT-TYPE
    SYNTAX SEQUENCE OF Hh3cDot11WIPSTrustMacEntry
    MAX-ACCESS not-accessible
    STATUS current
    DESCRIPTION
        "The table defines adding a MacAdress to the trust-device-list(TDL)"
    ::= { hh3cDot11WIPSConfigGroup 7 }

hh3cDot11WIPSTrustMacEntry OBJECT-TYPE
    SYNTAX Hh3cDot11WIPSTrustMacEntry
    MAX-ACCESS not-accessible
    STATUS current
    DESCRIPTION
        "Each entry contains information about a Mac in a TDL."
    INDEX { hh3cDot11WIPSTrustMacPolicyName, hh3cDot11WIPSTrustMacAddress }
    ::= { hh3cDot11WIPSTrustMacTable 1 }

Hh3cDot11WIPSTrustMacEntry ::= SEQUENCE {
        hh3cDot11WIPSTrustMacPolicyName     OCTET STRING,
        hh3cDot11WIPSTrustMacAddress        MacAddress,
        hh3cDot11WIPSTrustMacRowStatus      RowStatus
     }

hh3cDot11WIPSTrustMacPolicyName OBJECT-TYPE
    SYNTAX OCTET STRING (SIZE (1..63))
    MAX-ACCESS not-accessible
    STATUS current
    DESCRIPTION
        "Represents the classification policy name."
    ::= { hh3cDot11WIPSTrustMacEntry 1 }

hh3cDot11WIPSTrustMacAddress OBJECT-TYPE
    SYNTAX MacAddress
    MAX-ACCESS not-accessible
    STATUS current
    DESCRIPTION
        "Represents the MAC address."
    ::= { hh3cDot11WIPSTrustMacEntry 2 }

hh3cDot11WIPSTrustMacRowStatus OBJECT-TYPE
    SYNTAX RowStatus
    MAX-ACCESS read-create
    STATUS current
    DESCRIPTION
        "The status of this table entry."
    ::= { hh3cDot11WIPSTrustMacEntry 3 }

hh3cDot11WIPSBlockMacTable OBJECT-TYPE
    SYNTAX SEQUENCE OF Hh3cDot11WIPSBlockMacEntry
    MAX-ACCESS not-accessible
    STATUS current
    DESCRIPTION
        "The table defines add MacAdress to the static-forbidden-list(SFL)"
    ::= { hh3cDot11WIPSConfigGroup 8 }

hh3cDot11WIPSBlockMacEntry OBJECT-TYPE
    SYNTAX Hh3cDot11WIPSBlockMacEntry
    MAX-ACCESS not-accessible
    STATUS current
    DESCRIPTION
        "Each entry contains information about a Mac in a SFL."
    INDEX { hh3cDot11WIPSBlockMacPolicyName, hh3cDot11WIPSBlockMacAddress }
    ::= { hh3cDot11WIPSBlockMacTable 1 }

Hh3cDot11WIPSBlockMacEntry ::= SEQUENCE {
        hh3cDot11WIPSBlockMacPolicyName       OCTET STRING,
        hh3cDot11WIPSBlockMacAddress          MacAddress,
        hh3cDot11WIPSBlockMacRowStatus        RowStatus
     }

hh3cDot11WIPSBlockMacPolicyName OBJECT-TYPE
    SYNTAX OCTET STRING (SIZE (1..63))
    MAX-ACCESS not-accessible
    STATUS current
    DESCRIPTION
        "Represents the classification policy name."
    ::= { hh3cDot11WIPSBlockMacEntry 1 }

hh3cDot11WIPSBlockMacAddress OBJECT-TYPE
    SYNTAX MacAddress
    MAX-ACCESS not-accessible
    STATUS current
    DESCRIPTION
        "Represents the MAC address."
    ::= { hh3cDot11WIPSBlockMacEntry 2 }

hh3cDot11WIPSBlockMacRowStatus OBJECT-TYPE
    SYNTAX RowStatus
    MAX-ACCESS read-create
    STATUS current
    DESCRIPTION
        "The status of this table entry."
    ::= { hh3cDot11WIPSBlockMacEntry 3 }

hh3cDot11WIPSManulClaTable OBJECT-TYPE
    SYNTAX SEQUENCE OF Hh3cDot11WIPSManulClaEntry
    MAX-ACCESS not-accessible
    STATUS current
    DESCRIPTION
        "The table contains the manual classify information."
    ::= { hh3cDot11WIPSConfigGroup 9 }

hh3cDot11WIPSManulClaEntry OBJECT-TYPE
    SYNTAX Hh3cDot11WIPSManulClaEntry
    MAX-ACCESS not-accessible
    STATUS current
    DESCRIPTION
        "Each entry contains the address specified manually in a policy."
    INDEX { hh3cDot11WIPSManulClaPlyName, hh3cDot11WIPSManulClaMac }
    ::= { hh3cDot11WIPSManulClaTable 1 }

Hh3cDot11WIPSManulClaEntry ::= SEQUENCE {
        hh3cDot11WIPSManulClaPlyName        OCTET STRING,
        hh3cDot11WIPSManulClaMac            MacAddress,
        hh3cDot11WIPSManulClassifyType      Hh3cDot11WIPSManualAPType,
        hh3cDot11WIPSManuClaRowStatus       RowStatus
     }

hh3cDot11WIPSManulClaPlyName OBJECT-TYPE
    SYNTAX OCTET STRING (SIZE (1..63))
    MAX-ACCESS not-accessible
    STATUS current
    DESCRIPTION
        "Represents the policy name."
    ::= { hh3cDot11WIPSManulClaEntry 1 }

hh3cDot11WIPSManulClaMac OBJECT-TYPE
    SYNTAX MacAddress
    MAX-ACCESS not-accessible
    STATUS current
    DESCRIPTION
        "Represents the MAC address of AP."
    ::= { hh3cDot11WIPSManulClaEntry 2 }

hh3cDot11WIPSManulClassifyType OBJECT-TYPE
    SYNTAX  Hh3cDot11WIPSManualAPType
    MAX-ACCESS read-create
    STATUS current
    DESCRIPTION
        "The classification type of AP."
    ::= { hh3cDot11WIPSManulClaEntry 3 }

hh3cDot11WIPSManuClaRowStatus OBJECT-TYPE
    SYNTAX RowStatus
    MAX-ACCESS read-create
    STATUS current
    DESCRIPTION
        "The status of this table entry."
    ::= { hh3cDot11WIPSManulClaEntry 4 }

hh3cDot11WIPSTrustOuiTable OBJECT-TYPE
    SYNTAX SEQUENCE OF Hh3cDot11WIPSTrustOuiEntry
    MAX-ACCESS not-accessible
    STATUS current
    DESCRIPTION
        "The table provides information about trust oui."
    ::= { hh3cDot11WIPSConfigGroup 10 }

hh3cDot11WIPSTrustOuiEntry OBJECT-TYPE
    SYNTAX Hh3cDot11WIPSTrustOuiEntry
    MAX-ACCESS not-accessible
    STATUS current
    DESCRIPTION
        "Each entry contains information about trust oui."
    INDEX { hh3cDot11WIPSTrustOuiPolicyName, hh3cDot11WIPSTrustOuiMac }
    ::= { hh3cDot11WIPSTrustOuiTable 1 }

Hh3cDot11WIPSTrustOuiEntry ::= SEQUENCE {
        hh3cDot11WIPSTrustOuiPolicyName                OCTET STRING,
        hh3cDot11WIPSTrustOuiMac                       Hh3cDot11WIPSOuiAddress,
        hh3cDot11WIPSTrustOuiRowStatus                 RowStatus
     }

hh3cDot11WIPSTrustOuiPolicyName OBJECT-TYPE
    SYNTAX OCTET STRING (SIZE (1..63))
    MAX-ACCESS not-accessible
    STATUS current
    DESCRIPTION
        "Represents the name of classification policy name."
    ::= { hh3cDot11WIPSTrustOuiEntry 1 }

hh3cDot11WIPSTrustOuiMac OBJECT-TYPE
    SYNTAX Hh3cDot11WIPSOuiAddress
    MAX-ACCESS not-accessible
    STATUS current
    DESCRIPTION
        "Represents the address of trust oui."
    ::= { hh3cDot11WIPSTrustOuiEntry 2 }

hh3cDot11WIPSTrustOuiRowStatus OBJECT-TYPE
    SYNTAX RowStatus
    MAX-ACCESS read-create
    STATUS current
    DESCRIPTION
        "The status of this table entry."
    ::= { hh3cDot11WIPSTrustOuiEntry 3 }

hh3cDot11WIPSTrustSSidTable OBJECT-TYPE
    SYNTAX SEQUENCE OF Hh3cDot11WIPSTrustSSidEntry
    MAX-ACCESS not-accessible
    STATUS current
    DESCRIPTION
        "The table defines add one SSID to the trust-device-list(TDL)"
    ::= { hh3cDot11WIPSConfigGroup 11 }

hh3cDot11WIPSTrustSSidEntry OBJECT-TYPE
    SYNTAX Hh3cDot11WIPSTrustSSidEntry
    MAX-ACCESS not-accessible
    STATUS current
    DESCRIPTION
        "Each entry contains information about a SSID in a TDL."
    INDEX { hh3cDot11WIPSTrustSSidPlyName, hh3cDot11WIPSTrustSSidName }
    ::= { hh3cDot11WIPSTrustSSidTable 1 }

Hh3cDot11WIPSTrustSSidEntry ::= SEQUENCE {
        hh3cDot11WIPSTrustSSidPlyName          OCTET STRING,
        hh3cDot11WIPSTrustSSidName             OCTET STRING,
        hh3cDot11WIPSTrustSSidRowStatus        RowStatus
     }

hh3cDot11WIPSTrustSSidPlyName OBJECT-TYPE
    SYNTAX OCTET STRING (SIZE (1..63))
    MAX-ACCESS not-accessible
    STATUS current
    DESCRIPTION
        "Represents the classification policy name."
    ::= { hh3cDot11WIPSTrustSSidEntry 1 }

hh3cDot11WIPSTrustSSidName OBJECT-TYPE
    SYNTAX OCTET STRING (SIZE (1..32))
    MAX-ACCESS not-accessible
    STATUS current
    DESCRIPTION
        "Represents the SSID name."
    ::= { hh3cDot11WIPSTrustSSidEntry 2 }

hh3cDot11WIPSTrustSSidRowStatus OBJECT-TYPE
    SYNTAX RowStatus
    MAX-ACCESS read-create
    STATUS current
    DESCRIPTION
        "The status of this table entry."
    ::= { hh3cDot11WIPSTrustSSidEntry 3 }

hh3cDot11WIPSMalfDtcTable OBJECT-TYPE
    SYNTAX SEQUENCE OF Hh3cDot11WIPSMalfDtcEntry
    MAX-ACCESS not-accessible
    STATUS current
    DESCRIPTION
        "The table contains the malformed packet detect information."
    ::= { hh3cDot11WIPSConfigGroup 12 }

hh3cDot11WIPSMalfDtcEntry OBJECT-TYPE
    SYNTAX Hh3cDot11WIPSMalfDtcEntry
    MAX-ACCESS not-accessible
    STATUS current
    DESCRIPTION
        "Each entry contains the malformed type in a detect policy."
    INDEX { hh3cDot11WIPSMalfDtcPolicyName, hh3cDot11WIPSMalfDtcType }
    ::= { hh3cDot11WIPSMalfDtcTable 1 }

Hh3cDot11WIPSMalfDtcEntry ::= SEQUENCE {
        hh3cDot11WIPSMalfDtcPolicyName       OCTET STRING,
        hh3cDot11WIPSMalfDtcType             Hh3cDot11WIPSMalformedType,
        hh3cDot11WIPSMalfDtcQuietTime        Integer32,
        hh3cDot11WIPSMalfDtciStatus          Hh3cDot11WIPSEnabledStatus
     }

hh3cDot11WIPSMalfDtcPolicyName OBJECT-TYPE
    SYNTAX OCTET STRING (SIZE (1..63))
    MAX-ACCESS not-accessible
    STATUS current
    DESCRIPTION
        "Represents the policy name."
    ::= { hh3cDot11WIPSMalfDtcEntry 1 }

hh3cDot11WIPSMalfDtcType OBJECT-TYPE
    SYNTAX  Hh3cDot11WIPSMalformedType
    MAX-ACCESS not-accessible
    STATUS current
    DESCRIPTION
        "The malformed type of detect."
    ::= { hh3cDot11WIPSMalfDtcEntry 2 }

hh3cDot11WIPSMalfDtcQuietTime OBJECT-TYPE
    SYNTAX Integer32 (5..604800)
    MAX-ACCESS read-write
    STATUS current
    DESCRIPTION
        "Represents the quiet time."
    ::= { hh3cDot11WIPSMalfDtcEntry 3 }

hh3cDot11WIPSMalfDtciStatus OBJECT-TYPE
    SYNTAX  Hh3cDot11WIPSEnabledStatus
    MAX-ACCESS read-write
    STATUS current
    DESCRIPTION
        "The enable status of malformed detect."
    ::= { hh3cDot11WIPSMalfDtcEntry 4 }

hh3cDot11WIPSLgeDutTable OBJECT-TYPE
    SYNTAX SEQUENCE OF Hh3cDot11WIPSLgeDutEntry
    MAX-ACCESS not-accessible
    STATUS current
    DESCRIPTION
        "The table contains the infomation about
         large duration malformed detect."
    ::= { hh3cDot11WIPSConfigGroup 13 }

hh3cDot11WIPSLgeDutEntry OBJECT-TYPE
    SYNTAX Hh3cDot11WIPSLgeDutEntry
    MAX-ACCESS not-accessible
    STATUS current
    DESCRIPTION
        "Each entry contains the infomation about
         large duration malformed detect."
    INDEX { hh3cDot11WIPSLgeDutPolicyName }
    ::= { hh3cDot11WIPSLgeDutTable 1 }

Hh3cDot11WIPSLgeDutEntry ::= SEQUENCE {
        hh3cDot11WIPSLgeDutPolicyName           OCTET STRING,
        hh3cDot11WIPSLgeDutThreshold            Integer32,
        hh3cDot11WIPSLgeDutQuietTime            Integer32,
        hh3cDot11WIPSLgeDutStatus               Hh3cDot11WIPSEnabledStatus
     }

hh3cDot11WIPSLgeDutPolicyName OBJECT-TYPE
    SYNTAX OCTET STRING (SIZE (1..63))
    MAX-ACCESS not-accessible
    STATUS current
    DESCRIPTION
        "Represents the detect policy name."
    ::= { hh3cDot11WIPSLgeDutEntry 1 }

hh3cDot11WIPSLgeDutThreshold OBJECT-TYPE
    SYNTAX Integer32 (1..32767)
    MAX-ACCESS read-write
    STATUS current
    DESCRIPTION
        "Represents large duration malformed detect threshold."
    ::= { hh3cDot11WIPSLgeDutEntry 2 }

hh3cDot11WIPSLgeDutQuietTime OBJECT-TYPE
    SYNTAX Integer32 (5..604800)
    MAX-ACCESS read-write
    STATUS current
    DESCRIPTION
        "Represents large duration malformed detect quiet time ."
    ::= { hh3cDot11WIPSLgeDutEntry 3 }

hh3cDot11WIPSLgeDutStatus OBJECT-TYPE
    SYNTAX  Hh3cDot11WIPSEnabledStatus
    MAX-ACCESS read-write
    STATUS current
    DESCRIPTION
        "The enable status of large duration malformed detect."
    ::= { hh3cDot11WIPSLgeDutEntry 4 }

hh3cDot11WIPSRtLmtTable OBJECT-TYPE
    SYNTAX SEQUENCE OF Hh3cDot11WIPSRtLmtEntry
    MAX-ACCESS not-accessible
    STATUS current
    DESCRIPTION
        "The table defines the control of AP learned the devices rate."
    ::= { hh3cDot11WIPSConfigGroup 14 }

hh3cDot11WIPSRtLmtEntry OBJECT-TYPE
    SYNTAX Hh3cDot11WIPSRtLmtEntry
    MAX-ACCESS not-accessible
    STATUS current
    DESCRIPTION
        "Each entry contains information about a control of AP learned rate ."
    INDEX { hh3cDot11WIPSRtLmtPolicyName, hh3cDot11WIPSRtLmtRtLmtType }
    ::= { hh3cDot11WIPSRtLmtTable 1 }

Hh3cDot11WIPSRtLmtEntry ::= SEQUENCE {
        hh3cDot11WIPSRtLmtPolicyName       OCTET STRING,
        hh3cDot11WIPSRtLmtRtLmtType        Hh3cDot11WIPSRtLmtType,
        hh3cDot11WIPSRtLmtInterval         Integer32,
        hh3cDot11WIPSRtLmtThreshold        Integer32,
        hh3cDot11WIPSRtLmtQuiet            Integer32,
        hh3cDot11WIPSRtLmtStatus           Hh3cDot11WIPSEnabledStatus
     }

hh3cDot11WIPSRtLmtPolicyName OBJECT-TYPE
    SYNTAX OCTET STRING (SIZE (1..63))
    MAX-ACCESS not-accessible
    STATUS current
    DESCRIPTION
        "Represents the classification policy name."
    ::= { hh3cDot11WIPSRtLmtEntry 1 }

hh3cDot11WIPSRtLmtRtLmtType OBJECT-TYPE
    SYNTAX  Hh3cDot11WIPSRtLmtType
    MAX-ACCESS not-accessible
    STATUS current
    DESCRIPTION
        "Represents the device type."
    ::= { hh3cDot11WIPSRtLmtEntry 2 }

hh3cDot11WIPSRtLmtInterval OBJECT-TYPE
    SYNTAX Integer32(1..3600)
    MAX-ACCESS read-write
    STATUS current
    DESCRIPTION
        "The statistics cycle of AP learned device."
    ::= { hh3cDot11WIPSRtLmtEntry 3 }

hh3cDot11WIPSRtLmtThreshold OBJECT-TYPE
    SYNTAX Integer32(1..4096)
    MAX-ACCESS read-write
    STATUS current
    DESCRIPTION
        "The maximum devices number of AP learned."
    ::= { hh3cDot11WIPSRtLmtEntry 4 }

hh3cDot11WIPSRtLmtQuiet OBJECT-TYPE
    SYNTAX Integer32(1200..3600)
    MAX-ACCESS read-write
    STATUS current
    DESCRIPTION
        "Represents a quiet time after the warning log had been sent."
    ::= { hh3cDot11WIPSRtLmtEntry 5 }

hh3cDot11WIPSRtLmtStatus OBJECT-TYPE
    SYNTAX Hh3cDot11WIPSEnabledStatus
    MAX-ACCESS read-write
    STATUS current
    DESCRIPTION
        "The enable status of the control of AP learned the devices rate."
    ::= { hh3cDot11WIPSRtLmtEntry 6 }

hh3cDot11WIPSDtcAckTable OBJECT-TYPE
    SYNTAX SEQUENCE OF Hh3cDot11WIPSDtcAckEntry
    MAX-ACCESS not-accessible
    STATUS current
    DESCRIPTION
        "The table contains the infomation about detect attack."
    ::= { hh3cDot11WIPSConfigGroup 15 }

hh3cDot11WIPSDtcAckEntry OBJECT-TYPE
    SYNTAX Hh3cDot11WIPSDtcAckEntry
    MAX-ACCESS not-accessible
    STATUS current
    DESCRIPTION
        "Each entry contains the infomation about detect attack."
    INDEX { hh3cDot11WIPSDtcAckPolicyName, hh3cDot11WIPSDtcAckType }
    ::= { hh3cDot11WIPSDtcAckTable 1 }

Hh3cDot11WIPSDtcAckEntry ::= SEQUENCE {
        hh3cDot11WIPSDtcAckPolicyName            OCTET STRING,
        hh3cDot11WIPSDtcAckType                  Hh3cDot11WIPSDtcAckTypes,
        hh3cDot11WIPSDtcAckQuietTime             Integer32,
        hh3cDot11WIPSDtcAckInterval              Integer32,
        hh3cDot11WIPSDtcAckThreshold             Integer32,
        hh3cDot11WIPSDtcAckStatus                Hh3cDot11WIPSEnabledStatus
     }

hh3cDot11WIPSDtcAckPolicyName OBJECT-TYPE
    SYNTAX OCTET STRING (SIZE (1..63))
    MAX-ACCESS not-accessible
    STATUS current
    DESCRIPTION
        "Represents the detect policy name."
    ::= { hh3cDot11WIPSDtcAckEntry 1 }

hh3cDot11WIPSDtcAckType OBJECT-TYPE
    SYNTAX Hh3cDot11WIPSDtcAckTypes
    MAX-ACCESS not-accessible
    STATUS current
    DESCRIPTION
        "Represents the detect attack type."
    ::= { hh3cDot11WIPSDtcAckEntry 2 }


hh3cDot11WIPSDtcAckQuietTime OBJECT-TYPE
    SYNTAX Integer32 (5..604800)
    MAX-ACCESS read-write
    STATUS current
    DESCRIPTION
        "Represents detect attack quiet time ."
    ::= { hh3cDot11WIPSDtcAckEntry 3 }

hh3cDot11WIPSDtcAckInterval OBJECT-TYPE
    SYNTAX Integer32 (1..3600)
    MAX-ACCESS read-write
    STATUS current
    DESCRIPTION
        "Represents detect attack  interval."
    ::= { hh3cDot11WIPSDtcAckEntry 4 }

hh3cDot11WIPSDtcAckThreshold OBJECT-TYPE
    SYNTAX Integer32 (1..100000)
    MAX-ACCESS read-write
    STATUS current
    DESCRIPTION
        "Represents detect attack threshold."
    ::= { hh3cDot11WIPSDtcAckEntry 5 }

hh3cDot11WIPSDtcAckStatus OBJECT-TYPE
    SYNTAX  Hh3cDot11WIPSEnabledStatus
    MAX-ACCESS read-write
    STATUS current
    DESCRIPTION
        "The enable status of detect attack."
    ::= { hh3cDot11WIPSDtcAckEntry 6 }

hh3cDot11WIPSDtcDevTimeTable OBJECT-TYPE
    SYNTAX SEQUENCE OF Hh3cDot11WIPSDtcDevTimeEntry
    MAX-ACCESS not-accessible
    STATUS current
    DESCRIPTION
        "The table contains the infomation about detect device time."
    ::= { hh3cDot11WIPSConfigGroup 16 }

hh3cDot11WIPSDtcDevTimeEntry OBJECT-TYPE
    SYNTAX Hh3cDot11WIPSDtcDevTimeEntry
    MAX-ACCESS not-accessible
    STATUS current
    DESCRIPTION
        "Each entry contains the infomation about detect device time."
    INDEX { hh3cDot11WIPSDtcDevTimePlyName, hh3cDot11WIPSDtcDevTimeType }
    ::= { hh3cDot11WIPSDtcDevTimeTable 1 }

Hh3cDot11WIPSDtcDevTimeEntry ::= SEQUENCE {
        hh3cDot11WIPSDtcDevTimePlyName         OCTET STRING,
        hh3cDot11WIPSDtcDevTimeType            Hh3cDot11WIPSDtcDevTimeTypes,
        hh3cDot11WIPSDtcDevTimeInactive        Integer32,
        hh3cDot11WIPSDtcDevTimeAging           Integer32,
        hh3cDot11WIPSDtcDevTimeStatus          Hh3cDot11WIPSEnabledStatus
     }

hh3cDot11WIPSDtcDevTimePlyName OBJECT-TYPE
    SYNTAX OCTET STRING (SIZE (1..63))
    MAX-ACCESS not-accessible
    STATUS current
    DESCRIPTION
        "Represents the detect policy name."
    ::= { hh3cDot11WIPSDtcDevTimeEntry 1 }

hh3cDot11WIPSDtcDevTimeType OBJECT-TYPE
    SYNTAX Hh3cDot11WIPSDtcDevTimeTypes
    MAX-ACCESS not-accessible
    STATUS current
    DESCRIPTION
        "Represents the detect device time type."
    ::= { hh3cDot11WIPSDtcDevTimeEntry 2 }

hh3cDot11WIPSDtcDevTimeInactive OBJECT-TYPE
    SYNTAX Integer32 (60..1200)
    MAX-ACCESS read-write
    STATUS current
    DESCRIPTION
        "Represents detect device time inactive time."
    ::= { hh3cDot11WIPSDtcDevTimeEntry 3 }

hh3cDot11WIPSDtcDevTimeAging OBJECT-TYPE
    SYNTAX Integer32 (120..86400)
    MAX-ACCESS read-write
    STATUS current
    DESCRIPTION
        "Represents detect device time aging time."
    ::= { hh3cDot11WIPSDtcDevTimeEntry 4 }

hh3cDot11WIPSDtcDevTimeStatus OBJECT-TYPE
    SYNTAX  Hh3cDot11WIPSEnabledStatus
    MAX-ACCESS read-write
    STATUS current
    DESCRIPTION
        "The enable status of detect device time."
    ::= { hh3cDot11WIPSDtcDevTimeEntry 5 }

hh3cDot11WIPSApimperTable OBJECT-TYPE
    SYNTAX SEQUENCE OF Hh3cDot11WIPSApimperEntry
    MAX-ACCESS not-accessible
    STATUS current
    DESCRIPTION
        "The table provides information about AP impersonation."
    ::= { hh3cDot11WIPSConfigGroup 17 }

hh3cDot11WIPSApimperEntry OBJECT-TYPE
    SYNTAX Hh3cDot11WIPSApimperEntry
    MAX-ACCESS not-accessible
    STATUS current
    DESCRIPTION
        "Each entry contains information about one AP impersonation."
    INDEX { hh3cDot11WIPSApimperPolicyName }
    ::= { hh3cDot11WIPSApimperTable 1 }

Hh3cDot11WIPSApimperEntry ::= SEQUENCE {
        hh3cDot11WIPSApimperPolicyName      OCTET STRING,
        hh3cDot11WIPSApimperQuiet           Integer32,
        hh3cDot11WIPSApimperStatus          Hh3cDot11WIPSEnabledStatus
      }

hh3cDot11WIPSApimperPolicyName OBJECT-TYPE
    SYNTAX OCTET STRING (SIZE (1..63))
    MAX-ACCESS not-accessible
    STATUS current
    DESCRIPTION
        "Represents the name of policy."
    ::= { hh3cDot11WIPSApimperEntry 1 }

hh3cDot11WIPSApimperQuiet OBJECT-TYPE
    SYNTAX Integer32 (5..604800)
    MAX-ACCESS read-write
    STATUS current
    DESCRIPTION
        "The quiet of this table entry."
    ::= { hh3cDot11WIPSApimperEntry 2 }

hh3cDot11WIPSApimperStatus OBJECT-TYPE
    SYNTAX Hh3cDot11WIPSEnabledStatus
    MAX-ACCESS read-write
    STATUS current
    DESCRIPTION
        "The status of this table entry."
    ::= { hh3cDot11WIPSApimperEntry 3 }

hh3cDot11WIPSDctSoftApTable OBJECT-TYPE
    SYNTAX SEQUENCE OF Hh3cDot11WIPSDctSoftApEntry
    MAX-ACCESS not-accessible
    STATUS current
    DESCRIPTION
        "The table contains the enable status of detect of soft AP."
    ::= { hh3cDot11WIPSConfigGroup 18 }

hh3cDot11WIPSDctSoftApEntry OBJECT-TYPE
    SYNTAX Hh3cDot11WIPSDctSoftApEntry
    MAX-ACCESS not-accessible
    STATUS current
    DESCRIPTION
        "Each entry contains the enable status of detect a soft AP."
    INDEX { hh3cDot11WIPSDctSoftApPlyName }
    ::= { hh3cDot11WIPSDctSoftApTable 1 }

Hh3cDot11WIPSDctSoftApEntry ::= SEQUENCE {
        hh3cDot11WIPSDctSoftApPlyName      OCTET STRING,
        hh3cDot11WIPSDctSoftApThold        Integer32,
        hh3cDot11WIPSDctSoftApStatus       Hh3cDot11WIPSEnabledStatus
     }

hh3cDot11WIPSDctSoftApPlyName OBJECT-TYPE
    SYNTAX OCTET STRING (SIZE (1..63))
    MAX-ACCESS not-accessible
    STATUS current
    DESCRIPTION
        "Represents the detect policy name."
    ::= { hh3cDot11WIPSDctSoftApEntry 1 }

hh3cDot11WIPSDctSoftApThold OBJECT-TYPE
    SYNTAX Integer32 (5..600)
    MAX-ACCESS read-write
    STATUS current
    DESCRIPTION
        "Represents a convert time."
    ::= { hh3cDot11WIPSDctSoftApEntry 2 }

hh3cDot11WIPSDctSoftApStatus OBJECT-TYPE
    SYNTAX  Hh3cDot11WIPSEnabledStatus
    MAX-ACCESS read-write
    STATUS current
    DESCRIPTION
        "The enable status of detect a soft AP."
    ::= { hh3cDot11WIPSDctSoftApEntry 3 }

hh3cDot11WIPSPowerSaveTable OBJECT-TYPE
    SYNTAX SEQUENCE OF Hh3cDot11WIPSPowerSaveEntry
    MAX-ACCESS not-accessible
    STATUS current
    DESCRIPTION
        "This table contains the power-save detect information."
    ::= { hh3cDot11WIPSConfigGroup 19 }

hh3cDot11WIPSPowerSaveEntry OBJECT-TYPE
    SYNTAX Hh3cDot11WIPSPowerSaveEntry
    MAX-ACCESS not-accessible
    STATUS current
    DESCRIPTION
        "Each entry contains information about power-save detect."
    INDEX { hh3cDot11WIPSPowerSavePlyName }
    ::= { hh3cDot11WIPSPowerSaveTable 1 }

Hh3cDot11WIPSPowerSaveEntry ::= SEQUENCE {
        hh3cDot11WIPSPowerSavePlyName       OCTET STRING,
        hh3cDot11WIPSPowerSaveInterval      Integer32,
        hh3cDot11WIPSPowerSaveMinOffPkt     Integer32,
        hh3cDot11WIPSPowerSaveOnOffPct      Integer32,
        hh3cDot11WIPSPowerSaveQuiet         Integer32,
        hh3cDot11WIPSPowerSaveStatus        Hh3cDot11WIPSEnabledStatus
     }

hh3cDot11WIPSPowerSavePlyName OBJECT-TYPE
    SYNTAX OCTET STRING (SIZE (1..63))
    MAX-ACCESS not-accessible
    STATUS current
    DESCRIPTION
        "Represents the policy name."
    ::= { hh3cDot11WIPSPowerSaveEntry 1 }

hh3cDot11WIPSPowerSaveInterval OBJECT-TYPE
    SYNTAX Integer32 (1..3600)
    MAX-ACCESS read-write
    STATUS current
    DESCRIPTION
        "Represents the interval of power-save detect."
    ::= { hh3cDot11WIPSPowerSaveEntry 2 }

hh3cDot11WIPSPowerSaveMinOffPkt OBJECT-TYPE
    SYNTAX Integer32 (10..150)
    MAX-ACCESS read-write
    STATUS current
    DESCRIPTION
        "Represents the minoffpacket of power-save detect."
    ::= { hh3cDot11WIPSPowerSaveEntry 3 }

hh3cDot11WIPSPowerSaveOnOffPct OBJECT-TYPE
    SYNTAX Integer32 (0..100)
    MAX-ACCESS read-write
    STATUS current
    DESCRIPTION
        "Represents the onoffpercent of power-save detect."
    ::= { hh3cDot11WIPSPowerSaveEntry 4 }

hh3cDot11WIPSPowerSaveQuiet OBJECT-TYPE
    SYNTAX Integer32 (5..604800)
    MAX-ACCESS read-write
    STATUS current
    DESCRIPTION
        "Represents the quiettime of power-save detect."
    ::= { hh3cDot11WIPSPowerSaveEntry 5 }

hh3cDot11WIPSPowerSaveStatus OBJECT-TYPE
    SYNTAX Hh3cDot11WIPSEnabledStatus
    MAX-ACCESS read-write
    STATUS current
    DESCRIPTION
        "Represents the enabled status of power-save detect."
    ::= { hh3cDot11WIPSPowerSaveEntry 6 }

hh3cDot11WIPSIgnListMacTable OBJECT-TYPE
    SYNTAX SEQUENCE OF Hh3cDot11WIPSIgnListMacEntry
    MAX-ACCESS not-accessible
    STATUS current
    DESCRIPTION
        "The table defines ignore list MAC."
    ::= { hh3cDot11WIPSConfigGroup 20 }

hh3cDot11WIPSIgnListMacEntry OBJECT-TYPE
    SYNTAX Hh3cDot11WIPSIgnListMacEntry
    MAX-ACCESS not-accessible
    STATUS current
    DESCRIPTION
        "Each entry contains information about ignore list MAC."
    INDEX { hh3cDot11WIPSIgnListMacMacAddr }
    ::= { hh3cDot11WIPSIgnListMacTable 1 }

Hh3cDot11WIPSIgnListMacEntry ::= SEQUENCE {
        hh3cDot11WIPSIgnListMacMacAddr        MacAddress,
        hh3cDot11WIPSIgnListMacRowStus        RowStatus
     }

hh3cDot11WIPSIgnListMacMacAddr OBJECT-TYPE
    SYNTAX MacAddress
    MAX-ACCESS not-accessible
    STATUS current
    DESCRIPTION
        "Represents the MAC address."
    ::= { hh3cDot11WIPSIgnListMacEntry 1 }

hh3cDot11WIPSIgnListMacRowStus OBJECT-TYPE
    SYNTAX RowStatus
    MAX-ACCESS read-create
    STATUS current
    DESCRIPTION
        "The status of this table entry."
    ::= { hh3cDot11WIPSIgnListMacEntry 2 }

hh3cDot11WIPSHoneyPotTable OBJECT-TYPE
    SYNTAX SEQUENCE OF Hh3cDot11WIPSHoneyPotEntry
    MAX-ACCESS not-accessible
    STATUS current
    DESCRIPTION
        "The table defines the detect of honey-pot."
    ::= { hh3cDot11WIPSConfigGroup 21 }

hh3cDot11WIPSHoneyPotEntry OBJECT-TYPE
    SYNTAX Hh3cDot11WIPSHoneyPotEntry
    MAX-ACCESS not-accessible
    STATUS current
    DESCRIPTION
        "Each entry contains the enable status of detect honey-pot."
    INDEX { hh3cDot11WIPSHoneyPotPlyName }
    ::= { hh3cDot11WIPSHoneyPotTable 1 }

Hh3cDot11WIPSHoneyPotEntry ::= SEQUENCE {
        hh3cDot11WIPSHoneyPotPlyName        OCTET STRING,
        hh3cDot11WIPSHoneyPotSim            Integer32,
        hh3cDot11WIPSHoneyPotQuiet          Integer32,
        hh3cDot11WIPSHoneyPotStatus         Hh3cDot11WIPSEnabledStatus
     }

hh3cDot11WIPSHoneyPotPlyName OBJECT-TYPE
    SYNTAX OCTET STRING (SIZE (1..63))
    MAX-ACCESS not-accessible
    STATUS current
    DESCRIPTION
        "Represents the detect policy name."
    ::= { hh3cDot11WIPSHoneyPotEntry 1 }

hh3cDot11WIPSHoneyPotSim OBJECT-TYPE
    SYNTAX Integer32 (70..100)
    MAX-ACCESS read-write
    STATUS current
    DESCRIPTION
        "Represents the similarity-value of matching SSID."
    ::= { hh3cDot11WIPSHoneyPotEntry 2 }

hh3cDot11WIPSHoneyPotQuiet OBJECT-TYPE
     SYNTAX Integer32 (5..604800)
     MAX-ACCESS read-write
     STATUS current
     DESCRIPTION
         "Represents a quiet time after the warning log had been sent."
     ::= { hh3cDot11WIPSHoneyPotEntry 3 }

hh3cDot11WIPSHoneyPotStatus OBJECT-TYPE
    SYNTAX  Hh3cDot11WIPSEnabledStatus
    MAX-ACCESS read-write
    STATUS current
    DESCRIPTION
        "The enable status of detect honey-pot."
    ::= { hh3cDot11WIPSHoneyPotEntry 4 }

hh3cDot11WIPSAPFldTable OBJECT-TYPE
    SYNTAX SEQUENCE OF Hh3cDot11WIPSAPFldEntry
    MAX-ACCESS not-accessible
    STATUS current
    DESCRIPTION
        "The table defines the detect of AP-flood."
    ::= { hh3cDot11WIPSConfigGroup 22 }

hh3cDot11WIPSAPFldEntry OBJECT-TYPE
    SYNTAX Hh3cDot11WIPSAPFldEntry
    MAX-ACCESS not-accessible
    STATUS current
    DESCRIPTION
        "Each entry contains the enable status of detect AP-flood."
    INDEX { hh3cDot11WIPSAPFldPolicyName }
    ::= { hh3cDot11WIPSAPFldTable 1 }

Hh3cDot11WIPSAPFldEntry ::= SEQUENCE {
        hh3cDot11WIPSAPFldPolicyName        OCTET STRING,
        hh3cDot11WIPSAPFldApnum             Integer32,
        hh3cDot11WIPSAPFldExceed            Integer32,
        hh3cDot11WIPSAPFldQuiet             Integer32,
        hh3cDot11WIPSAPFldStatus            Hh3cDot11WIPSEnabledStatus
     }

hh3cDot11WIPSAPFldPolicyName OBJECT-TYPE
    SYNTAX OCTET STRING (SIZE (1..63))
    MAX-ACCESS not-accessible
    STATUS current
    DESCRIPTION
        "Represents the detect policy name."
    ::= { hh3cDot11WIPSAPFldEntry 1 }

hh3cDot11WIPSAPFldApnum OBJECT-TYPE
    SYNTAX Integer32 (10..200)
    MAX-ACCESS read-write
    STATUS current
    DESCRIPTION
        "Represents allowable AP devices number in a wireless network."
    ::= { hh3cDot11WIPSAPFldEntry 2 }

hh3cDot11WIPSAPFldExceed OBJECT-TYPE
     SYNTAX Integer32 (10..200)
     MAX-ACCESS read-write
     STATUS current
     DESCRIPTION
         "Represents the allowable maximum AP devices number had exceed."
     ::= { hh3cDot11WIPSAPFldEntry 3 }

hh3cDot11WIPSAPFldQuiet OBJECT-TYPE
     SYNTAX Integer32 (5..604800)
     MAX-ACCESS read-write
     STATUS current
     DESCRIPTION
         "Represents a quiet time after the warning log had been sent."
     ::= { hh3cDot11WIPSAPFldEntry 4 }

hh3cDot11WIPSAPFldStatus OBJECT-TYPE
    SYNTAX  Hh3cDot11WIPSEnabledStatus
    MAX-ACCESS read-write
    STATUS current
    DESCRIPTION
        "The enable status of detect AP-flood."
    ::= { hh3cDot11WIPSAPFldEntry 5 }

hh3cDot11WIPSCtmManualsTable OBJECT-TYPE
    SYNTAX SEQUENCE OF Hh3cDot11WIPSCtmManualsEntry
    MAX-ACCESS not-accessible
    STATUS current
    DESCRIPTION
        "This table contains the manual countermeasure information."
    ::= { hh3cDot11WIPSConfigGroup 23 }

hh3cDot11WIPSCtmManualsEntry OBJECT-TYPE
    SYNTAX Hh3cDot11WIPSCtmManualsEntry
    MAX-ACCESS not-accessible
    STATUS current
    DESCRIPTION
        "Each entry contains information about manual countermeasure."
    INDEX { hh3cDot11WIPSCtmManualsPlyName, hh3cDot11WIPSCtmManualsMacAddr }
    ::= { hh3cDot11WIPSCtmManualsTable 1 }

Hh3cDot11WIPSCtmManualsEntry ::= SEQUENCE {
        hh3cDot11WIPSCtmManualsPlyName    OCTET STRING,
        hh3cDot11WIPSCtmManualsMacAddr    MacAddress,
        hh3cDot11WIPSCtmManualsRowStus     RowStatus
     }

hh3cDot11WIPSCtmManualsPlyName OBJECT-TYPE
    SYNTAX OCTET STRING (SIZE (1..63))
    MAX-ACCESS not-accessible
    STATUS current
    DESCRIPTION
        "Represents the policy name."
    ::= { hh3cDot11WIPSCtmManualsEntry 1 }

hh3cDot11WIPSCtmManualsMacAddr OBJECT-TYPE
    SYNTAX MacAddress
    MAX-ACCESS not-accessible
    STATUS current
    DESCRIPTION
        "Represents the MAC address."
    ::= { hh3cDot11WIPSCtmManualsEntry 2 }

hh3cDot11WIPSCtmManualsRowStus OBJECT-TYPE
    SYNTAX RowStatus
    MAX-ACCESS read-create
    STATUS current
    DESCRIPTION
        "The status of this table entry."
    ::= { hh3cDot11WIPSCtmManualsEntry 3 }

hh3cDot11WIPSCtmSensorTable OBJECT-TYPE
    SYNTAX SEQUENCE OF Hh3cDot11WIPSCtmSensorEntry

    MAX-ACCESS not-accessible
    STATUS current
    DESCRIPTION
        "The table contains the countermeasure all sensor information."
    ::= { hh3cDot11WIPSConfigGroup 24 }

hh3cDot11WIPSCtmSensorEntry OBJECT-TYPE
    SYNTAX Hh3cDot11WIPSCtmSensorEntry
    MAX-ACCESS not-accessible
    STATUS current
    DESCRIPTION
        "Each entry contains information about countermeasure all sensor."
    INDEX { hh3cDot11WIPSCtmSensorPolicyName }
    ::= { hh3cDot11WIPSCtmSensorTable 1 }

Hh3cDot11WIPSCtmSensorEntry ::= SEQUENCE {
        hh3cDot11WIPSCtmSensorPolicyName        OCTET STRING,
        hh3cDot11WIPSCtmSensoriStatus           Hh3cDot11WIPSEnabledStatus
     }

hh3cDot11WIPSCtmSensorPolicyName OBJECT-TYPE
    SYNTAX OCTET STRING (SIZE (1..63))
    MAX-ACCESS not-accessible
    STATUS current
    DESCRIPTION
        "Represents the policy name."
    ::= { hh3cDot11WIPSCtmSensorEntry 1 }

hh3cDot11WIPSCtmSensoriStatus OBJECT-TYPE
    SYNTAX  Hh3cDot11WIPSEnabledStatus
    MAX-ACCESS read-write
    STATUS current
    DESCRIPTION
        "The status of this table entry."
    ::= { hh3cDot11WIPSCtmSensorEntry 2 }


hh3cDot11WIPSInvOuiStateTable OBJECT-TYPE
    SYNTAX SEQUENCE OF Hh3cDot11WIPSInvOuiStateEntry
    MAX-ACCESS not-accessible
    STATUS current
    DESCRIPTION
        "The table contains the invalid OUI classification information."
    ::= { hh3cDot11WIPSConfigGroup 25 }

hh3cDot11WIPSInvOuiStateEntry OBJECT-TYPE
    SYNTAX Hh3cDot11WIPSInvOuiStateEntry
    MAX-ACCESS not-accessible
    STATUS current
    DESCRIPTION
        "Each entry contains about status of invalid OUI classification."
    INDEX { hh3cDot11WIPSInvOuiStaPlyName }
    ::= { hh3cDot11WIPSInvOuiStateTable 1 }

Hh3cDot11WIPSInvOuiStateEntry ::= SEQUENCE {
        hh3cDot11WIPSInvOuiStaPlyName       OCTET STRING,
        hh3cDot11WIPSInvOuiStaiStatus       Hh3cDot11WIPSEnabledStatus
     }

hh3cDot11WIPSInvOuiStaPlyName OBJECT-TYPE
    SYNTAX OCTET STRING (SIZE (1..63))
    MAX-ACCESS not-accessible
    STATUS current
    DESCRIPTION
        "Represents the policy name."
    ::= { hh3cDot11WIPSInvOuiStateEntry 1 }

hh3cDot11WIPSInvOuiStaiStatus OBJECT-TYPE
    SYNTAX  Hh3cDot11WIPSEnabledStatus
    MAX-ACCESS read-write
    STATUS current
    DESCRIPTION
        "The enable status of invalid OUI classification."
    ::= { hh3cDot11WIPSInvOuiStateEntry 2 }

hh3cDot11WIPSAPClaAuthTable OBJECT-TYPE
    SYNTAX SEQUENCE OF Hh3cDot11WIPSAPClaAuthEntry
    MAX-ACCESS not-accessible
    STATUS current
    DESCRIPTION
        "The table contains the enable status of
         WIPS AP classification authentication."
    ::= { hh3cDot11WIPSConfigGroup 26 }

hh3cDot11WIPSAPClaAuthEntry OBJECT-TYPE
    SYNTAX Hh3cDot11WIPSAPClaAuthEntry
    MAX-ACCESS not-accessible
    STATUS current
    DESCRIPTION
        "Each entry contains the enable status of
         WIPS AP classification authentication."
    INDEX { hh3cDot11WIPSAPClaAuthRuleID }
    ::= { hh3cDot11WIPSAPClaAuthTable 1 }

Hh3cDot11WIPSAPClaAuthEntry ::= SEQUENCE {
        hh3cDot11WIPSAPClaAuthRuleID        Integer32,
        hh3cDot11WIPSAPClaAuthMethod        Hh3cDot11WIPSAPClaAuthMethods,
        hh3cDot11WIPSAPClaAuthType          Hh3cDot11WIPSAPClassifyCmpType,
        hh3cDot11WIPSAPClaAuthStatus        Hh3cDot11WIPSEnabledStatus
     }

hh3cDot11WIPSAPClaAuthRuleID OBJECT-TYPE
    SYNTAX Integer32 (1..65535)
    MAX-ACCESS not-accessible
    STATUS current
    DESCRIPTION
        "Represents the rule ID."
    ::= { hh3cDot11WIPSAPClaAuthEntry 1 }

hh3cDot11WIPSAPClaAuthMethod OBJECT-TYPE
    SYNTAX Hh3cDot11WIPSAPClaAuthMethods
    MAX-ACCESS read-write
    STATUS current
    DESCRIPTION
        "Represents the AP classification authentication method."
    ::= { hh3cDot11WIPSAPClaAuthEntry 2 }

hh3cDot11WIPSAPClaAuthType OBJECT-TYPE
    SYNTAX Hh3cDot11WIPSAPClassifyCmpType
    MAX-ACCESS read-write
    STATUS current
    DESCRIPTION
        "Represents the AP classification authentication compare type."
    ::= { hh3cDot11WIPSAPClaAuthEntry 3 }

hh3cDot11WIPSAPClaAuthStatus OBJECT-TYPE
    SYNTAX  Hh3cDot11WIPSEnabledStatus
    MAX-ACCESS read-write
    STATUS current
    DESCRIPTION
        "The enable status of AP classification authentication."
    ::= { hh3cDot11WIPSAPClaAuthEntry 4 }

hh3cDot11WIPSAPClaCltOnlTable OBJECT-TYPE
    SYNTAX SEQUENCE OF Hh3cDot11WIPSAPClaCltOnlEntry
    MAX-ACCESS not-accessible
    STATUS current
    DESCRIPTION
        "The table contains the enable status of
         AP classification clinet online."
    ::= { hh3cDot11WIPSConfigGroup 27 }

hh3cDot11WIPSAPClaCltOnlEntry OBJECT-TYPE
    SYNTAX Hh3cDot11WIPSAPClaCltOnlEntry
    MAX-ACCESS not-accessible
    STATUS current
    DESCRIPTION
        "Each entry contains the enable status of
         AP classification clinet online."
    INDEX { hh3cDot11WIPSAPClaCltOnlRuleID }
    ::= { hh3cDot11WIPSAPClaCltOnlTable 1 }

Hh3cDot11WIPSAPClaCltOnlEntry ::= SEQUENCE {
        hh3cDot11WIPSAPClaCltOnlRuleID      Integer32,
        hh3cDot11WIPSAPClaCltOnlV1          Integer32,
        hh3cDot11WIPSAPClaCltOnlV2          Integer32,
        hh3cDot11WIPSAPClaCltOnlSts         Hh3cDot11WIPSEnabledStatus
     }

hh3cDot11WIPSAPClaCltOnlRuleID OBJECT-TYPE
    SYNTAX Integer32 (1..65535)
    MAX-ACCESS not-accessible
    STATUS current
    DESCRIPTION
        "Represents the rule ID."
    ::= { hh3cDot11WIPSAPClaCltOnlEntry 1 }

hh3cDot11WIPSAPClaCltOnlV1 OBJECT-TYPE
    SYNTAX Integer32 (0..128)
    MAX-ACCESS read-write
    STATUS current
    DESCRIPTION
        "Represents the AP classification clinet online value1."
    ::= { hh3cDot11WIPSAPClaCltOnlEntry 2 }

hh3cDot11WIPSAPClaCltOnlV2 OBJECT-TYPE
    SYNTAX Integer32 (0..128)
    MAX-ACCESS read-write
    STATUS current
    DESCRIPTION
        "Represents the AP classification clinet online value2."
    ::= { hh3cDot11WIPSAPClaCltOnlEntry 3 }

hh3cDot11WIPSAPClaCltOnlSts OBJECT-TYPE
    SYNTAX  Hh3cDot11WIPSEnabledStatus
    MAX-ACCESS read-write
    STATUS current
    DESCRIPTION
        "The enable status of WIPS AP classification clinet online."
    ::= { hh3cDot11WIPSAPClaCltOnlEntry 4 }

hh3cDot11WIPSAPClaDiscrTable OBJECT-TYPE
    SYNTAX SEQUENCE OF Hh3cDot11WIPSAPClaDiscrEntry
    MAX-ACCESS not-accessible
    STATUS current
    DESCRIPTION
        "The table contains the enable status of AP classification discover."
    ::= { hh3cDot11WIPSConfigGroup 28 }

hh3cDot11WIPSAPClaDiscrEntry OBJECT-TYPE
    SYNTAX Hh3cDot11WIPSAPClaDiscrEntry
    MAX-ACCESS not-accessible
    STATUS current
    DESCRIPTION
        "Each entry contains the enable status of AP classification discover."
    INDEX { hh3cDot11WIPSAPClaDiscrRuleID }
    ::= { hh3cDot11WIPSAPClaDiscrTable 1 }

Hh3cDot11WIPSAPClaDiscrEntry ::= SEQUENCE {
        hh3cDot11WIPSAPClaDiscrRuleID       Integer32,
        hh3cDot11WIPSAPClaDiscrV1           Integer32,
        hh3cDot11WIPSAPClaDiscrV2           Integer32,
        hh3cDot11WIPSAPClaDiscrSta          Hh3cDot11WIPSEnabledStatus
     }

hh3cDot11WIPSAPClaDiscrRuleID OBJECT-TYPE
    SYNTAX Integer32 (1..65535)
    MAX-ACCESS not-accessible
    STATUS current
    DESCRIPTION
        "Represents the rule ID."
    ::= { hh3cDot11WIPSAPClaDiscrEntry 1 }

hh3cDot11WIPSAPClaDiscrV1 OBJECT-TYPE
    SYNTAX Integer32 (1..128)
    MAX-ACCESS read-write
    STATUS current
    DESCRIPTION
        "Represents the AP classification discover value1."
    ::= { hh3cDot11WIPSAPClaDiscrEntry 2 }

hh3cDot11WIPSAPClaDiscrV2 OBJECT-TYPE
    SYNTAX Integer32 (1..128)
    MAX-ACCESS read-write
    STATUS current
    DESCRIPTION
        "Represents the AP classification discover value2."
    ::= { hh3cDot11WIPSAPClaDiscrEntry 3 }

hh3cDot11WIPSAPClaDiscrSta OBJECT-TYPE
    SYNTAX  Hh3cDot11WIPSEnabledStatus
    MAX-ACCESS read-write
    STATUS current
    DESCRIPTION
        "The enable status of AP classification discover."
    ::= { hh3cDot11WIPSAPClaDiscrEntry 4 }

--
-- APClassifyRssi
--
hh3cDot11WIPSAPClaRssiTable OBJECT-TYPE
    SYNTAX SEQUENCE OF Hh3cDot11WIPSAPClaRssiEntry
    MAX-ACCESS not-accessible
    STATUS current
    DESCRIPTION
        "The table contains the enable status of AP classification rssi."
    ::= { hh3cDot11WIPSConfigGroup 29 }

hh3cDot11WIPSAPClaRssiEntry OBJECT-TYPE
    SYNTAX Hh3cDot11WIPSAPClaRssiEntry
    MAX-ACCESS not-accessible
    STATUS current
    DESCRIPTION
        "Each entry contains the enable status of AP classification rssi."
    INDEX { hh3cDot11WIPSAPClaRssiRuleID }
    ::= { hh3cDot11WIPSAPClaRssiTable 1 }

Hh3cDot11WIPSAPClaRssiEntry ::= SEQUENCE {
        hh3cDot11WIPSAPClaRssiRuleID        Integer32,
        hh3cDot11WIPSAPClaRssiV1            Integer32,
        hh3cDot11WIPSAPClaRssiV2            Integer32,
        hh3cDot11WIPSAPClaRssiSta           Hh3cDot11WIPSEnabledStatus
     }

hh3cDot11WIPSAPClaRssiRuleID OBJECT-TYPE
    SYNTAX Integer32 (1..65535)
    MAX-ACCESS not-accessible
    STATUS current
    DESCRIPTION
        "Represents the rule ID."
    ::= { hh3cDot11WIPSAPClaRssiEntry 1 }

hh3cDot11WIPSAPClaRssiV1 OBJECT-TYPE
    SYNTAX Integer32 (0..100)
    MAX-ACCESS read-write
    STATUS current
    DESCRIPTION
        "Represents the AP classification rssi value1."
    ::= { hh3cDot11WIPSAPClaRssiEntry 2 }

hh3cDot11WIPSAPClaRssiV2 OBJECT-TYPE
    SYNTAX Integer32 (0..100)
    MAX-ACCESS read-write
    STATUS current
    DESCRIPTION
        "Represents the AP classification rssi value2."
    ::= { hh3cDot11WIPSAPClaRssiEntry 3 }

hh3cDot11WIPSAPClaRssiSta OBJECT-TYPE
    SYNTAX  Hh3cDot11WIPSEnabledStatus
    MAX-ACCESS read-write
    STATUS current
    DESCRIPTION
        "The enable status of AP classification rssi."
    ::= { hh3cDot11WIPSAPClaRssiEntry 4 }

hh3cDot11WIPSAPClaUpdurTable OBJECT-TYPE
    SYNTAX SEQUENCE OF Hh3cDot11WIPSAPClaUpdurEntry
    MAX-ACCESS not-accessible
    STATUS current
    DESCRIPTION
        "The table contains the enable status of AP classification upduration."
    ::= { hh3cDot11WIPSConfigGroup 30 }

hh3cDot11WIPSAPClaUpdurEntry OBJECT-TYPE
    SYNTAX Hh3cDot11WIPSAPClaUpdurEntry
    MAX-ACCESS not-accessible
    STATUS current
    DESCRIPTION
        "Each entry contains the enable status of AP classification upduration."
    INDEX { hh3cDot11WIPSAPClaUpdurRuleID }
    ::= { hh3cDot11WIPSAPClaUpdurTable 1 }

Hh3cDot11WIPSAPClaUpdurEntry ::= SEQUENCE {
        hh3cDot11WIPSAPClaUpdurRuleID       Integer32,
        hh3cDot11WIPSAPClaUpdurV1           Integer32,
        hh3cDot11WIPSAPClaUpdurV2           Integer32,
        hh3cDot11WIPSAPClaUpdurSta          Hh3cDot11WIPSEnabledStatus
     }

hh3cDot11WIPSAPClaUpdurRuleID OBJECT-TYPE
    SYNTAX Integer32 (1..65535)
    MAX-ACCESS not-accessible
    STATUS current
    DESCRIPTION
        "Represents the rule ID."
    ::= { hh3cDot11WIPSAPClaUpdurEntry 1 }

hh3cDot11WIPSAPClaUpdurV1 OBJECT-TYPE
    SYNTAX Integer32 (0..2592000)
    MAX-ACCESS read-write
    STATUS current
    DESCRIPTION
        "Represents the AP classification upduration value1."
    ::= { hh3cDot11WIPSAPClaUpdurEntry 2 }

hh3cDot11WIPSAPClaUpdurV2 OBJECT-TYPE
    SYNTAX Integer32 (0..2592000)
    MAX-ACCESS read-write
    STATUS current
    DESCRIPTION
        "Represents the AP classification upduration value2."
    ::= { hh3cDot11WIPSAPClaUpdurEntry 3 }

hh3cDot11WIPSAPClaUpdurSta OBJECT-TYPE
    SYNTAX  Hh3cDot11WIPSEnabledStatus
    MAX-ACCESS read-write
    STATUS current
    DESCRIPTION
        "The enable status of AP classification upduration."
    ::= { hh3cDot11WIPSAPClaUpdurEntry 4 }

hh3cDot11WIPSAPClaOuiTable OBJECT-TYPE
    SYNTAX SEQUENCE OF Hh3cDot11WIPSAPClaOuiEntry
    MAX-ACCESS not-accessible
    STATUS current
    DESCRIPTION
        "The table contains the enable status of AP classification oui."
    ::= { hh3cDot11WIPSConfigGroup 31 }

hh3cDot11WIPSAPClaOuiEntry OBJECT-TYPE
    SYNTAX Hh3cDot11WIPSAPClaOuiEntry
    MAX-ACCESS not-accessible
    STATUS current
    DESCRIPTION
        "Each entry contains the enable status of AP classification oui."
    INDEX { hh3cDot11WIPSAPClaOuiRuleID }
    ::= { hh3cDot11WIPSAPClaOuiTable 1 }

Hh3cDot11WIPSAPClaOuiEntry ::= SEQUENCE {
        hh3cDot11WIPSAPClaOuiRuleID        Integer32,
        hh3cDot11WIPSAPClaOuiMac           Hh3cDot11WIPSOuiAddress,
        hh3cDot11WIPSAPClaOuiStatus        Hh3cDot11WIPSEnabledStatus
     }

hh3cDot11WIPSAPClaOuiRuleID OBJECT-TYPE
    SYNTAX Integer32 (1..65535)
    MAX-ACCESS not-accessible
    STATUS current
    DESCRIPTION
        "Represents the rule ID."
    ::= { hh3cDot11WIPSAPClaOuiEntry 1 }

hh3cDot11WIPSAPClaOuiMac OBJECT-TYPE
    SYNTAX Hh3cDot11WIPSOuiAddress
    MAX-ACCESS read-write
    STATUS current
    DESCRIPTION
        "Represents the AP classification oui."
    ::= { hh3cDot11WIPSAPClaOuiEntry 2 }

hh3cDot11WIPSAPClaOuiStatus OBJECT-TYPE
    SYNTAX  Hh3cDot11WIPSEnabledStatus
    MAX-ACCESS read-write
    STATUS current
    DESCRIPTION
        "The enable status of AP classification oui."
    ::= { hh3cDot11WIPSAPClaOuiEntry 3 }

hh3cDot11WIPSAPClaSryTable OBJECT-TYPE
    SYNTAX SEQUENCE OF Hh3cDot11WIPSAPClaSryEntry
    MAX-ACCESS not-accessible
    STATUS current
    DESCRIPTION
        "The table contains the enable status of AP classification security."
    ::= { hh3cDot11WIPSConfigGroup 32 }

hh3cDot11WIPSAPClaSryEntry OBJECT-TYPE
    SYNTAX Hh3cDot11WIPSAPClaSryEntry
    MAX-ACCESS not-accessible
    STATUS current
    DESCRIPTION
        "Each entry contains the enable status of AP classification security."
    INDEX { hh3cDot11WIPSAPClaSryRuleID }
    ::= { hh3cDot11WIPSAPClaSryTable 1 }

Hh3cDot11WIPSAPClaSryEntry ::= SEQUENCE {
        hh3cDot11WIPSAPClaSryRuleID         Integer32,
        hh3cDot11WIPSAPClaSryType           Hh3cDot11WIPSAPClaSecurityType,
        hh3cDot11WIPSAPClaSryCmpType        Hh3cDot11WIPSAPClassifyCmpType,
        hh3cDot11WIPSAPClaSrySta            Hh3cDot11WIPSEnabledStatus
     }

hh3cDot11WIPSAPClaSryRuleID OBJECT-TYPE
    SYNTAX Integer32 (1..65535)
    MAX-ACCESS not-accessible
    STATUS current
    DESCRIPTION
        "Represents the rule ID."
    ::= { hh3cDot11WIPSAPClaSryEntry 1 }

hh3cDot11WIPSAPClaSryType OBJECT-TYPE
    SYNTAX Hh3cDot11WIPSAPClaSecurityType
    MAX-ACCESS read-write
    STATUS current
    DESCRIPTION
        "Represents the AP classification security."
    ::= { hh3cDot11WIPSAPClaSryEntry 2 }

hh3cDot11WIPSAPClaSryCmpType OBJECT-TYPE
    SYNTAX Hh3cDot11WIPSAPClassifyCmpType
    MAX-ACCESS read-write
    STATUS current
    DESCRIPTION
        "Represents the AP classification security."
    ::= { hh3cDot11WIPSAPClaSryEntry 3 }

hh3cDot11WIPSAPClaSrySta OBJECT-TYPE
    SYNTAX  Hh3cDot11WIPSEnabledStatus
    MAX-ACCESS read-write
    STATUS current
    DESCRIPTION
        "The enable status of AP classification security."
    ::= { hh3cDot11WIPSAPClaSryEntry 4 }

hh3cDot11WIPSAPClaSsidTable OBJECT-TYPE
    SYNTAX SEQUENCE OF Hh3cDot11WIPSAPClaSsidEntry
    MAX-ACCESS not-accessible
    STATUS current
    DESCRIPTION
        "The table contains the enable status of AP classification ssid."
    ::= { hh3cDot11WIPSConfigGroup 33 }

hh3cDot11WIPSAPClaSsidEntry OBJECT-TYPE
    SYNTAX Hh3cDot11WIPSAPClaSsidEntry
    MAX-ACCESS not-accessible
    STATUS current
    DESCRIPTION
        "Each entry contains the enable status of AP classification ssid."
    INDEX { hh3cDot11WIPSAPClaSsidRuleID }
    ::= { hh3cDot11WIPSAPClaSsidTable 1 }

Hh3cDot11WIPSAPClaSsidEntry ::= SEQUENCE {
        hh3cDot11WIPSAPClaSsidRuleID         Integer32,
        hh3cDot11WIPSAPClaSsidName           OCTET STRING,
        hh3cDot11WIPSAPClaSsidcase           TruthValue,
        hh3cDot11WIPSAPClaSsidCmpType        Hh3cDot11WIPSAPClasSsidCmpType,
        hh3cDot11WIPSAPClaSsidStatus         Hh3cDot11WIPSEnabledStatus
     }

hh3cDot11WIPSAPClaSsidRuleID OBJECT-TYPE
    SYNTAX Integer32 (1..65535)
    MAX-ACCESS not-accessible
    STATUS current
    DESCRIPTION
        "Represents the rule ID."
    ::= { hh3cDot11WIPSAPClaSsidEntry 1 }

hh3cDot11WIPSAPClaSsidName OBJECT-TYPE
    SYNTAX OCTET STRING (SIZE (1..32))
    MAX-ACCESS read-write
    STATUS current
    DESCRIPTION
        "Represents the AP classification ssid name."
    ::= { hh3cDot11WIPSAPClaSsidEntry 2 }

hh3cDot11WIPSAPClaSsidcase OBJECT-TYPE
    SYNTAX TruthValue
    MAX-ACCESS read-write
    STATUS current
    DESCRIPTION
        "Represents the AP classification case-sensitive."
    ::= { hh3cDot11WIPSAPClaSsidEntry 3 }

hh3cDot11WIPSAPClaSsidCmpType OBJECT-TYPE
    SYNTAX Hh3cDot11WIPSAPClasSsidCmpType
    MAX-ACCESS read-write
    STATUS current
    DESCRIPTION
        "Represents the AP classification ssid compare type."
    ::= { hh3cDot11WIPSAPClaSsidEntry 4 }

hh3cDot11WIPSAPClaSsidStatus OBJECT-TYPE
    SYNTAX  Hh3cDot11WIPSEnabledStatus
    MAX-ACCESS read-write
    STATUS current
    DESCRIPTION
        "The enable status of AP classification ssid."
    ::= { hh3cDot11WIPSAPClaSsidEntry 5 }

hh3cDot11WIPSDtcSigTable OBJECT-TYPE
    SYNTAX SEQUENCE OF Hh3cDot11WIPSDtcSigEntry
    MAX-ACCESS not-accessible
    STATUS current
    DESCRIPTION
        "The table provides information about detect signature."
    ::= { hh3cDot11WIPSConfigGroup 34 }

hh3cDot11WIPSDtcSigEntry OBJECT-TYPE
    SYNTAX Hh3cDot11WIPSDtcSigEntry
    MAX-ACCESS not-accessible
    STATUS current
    DESCRIPTION
        "Each entry contains information about signature detect."
    INDEX { hh3cDot11WIPSDtcSigPolicyName }
    ::= { hh3cDot11WIPSDtcSigTable 1 }

Hh3cDot11WIPSDtcSigEntry ::= SEQUENCE {
        hh3cDot11WIPSDtcSigPolicyName               OCTET STRING,
        hh3cDot11WIPSDtcSigInterval                 Integer32,
        hh3cDot11WIPSDtcSigQuiet                    Integer32,
        hh3cDot11WIPSDtcSigThreshold                Integer32,
        hh3cDot11WIPSDtcSigStatus                   Hh3cDot11WIPSEnabledStatus
      }

hh3cDot11WIPSDtcSigPolicyName OBJECT-TYPE
    SYNTAX OCTET STRING (SIZE (1..63))
    MAX-ACCESS not-accessible
    STATUS current
    DESCRIPTION
        "Represents the name of the policy."
    ::= { hh3cDot11WIPSDtcSigEntry 1 }

hh3cDot11WIPSDtcSigInterval OBJECT-TYPE
    SYNTAX Integer32 (1..3600)
    MAX-ACCESS read-write
    STATUS current
    DESCRIPTION
        "Represents the interval of signature detect."
    ::= { hh3cDot11WIPSDtcSigEntry 2 }

hh3cDot11WIPSDtcSigQuiet OBJECT-TYPE
    SYNTAX Integer32 (5..604800)
    MAX-ACCESS read-write
    STATUS current
    DESCRIPTION
        "Represents the quiet of signature detect."
    ::= { hh3cDot11WIPSDtcSigEntry 3 }

hh3cDot11WIPSDtcSigThreshold OBJECT-TYPE
    SYNTAX Integer32 (1..100000)
    MAX-ACCESS read-write
    STATUS current
    DESCRIPTION
        "Represents the threshold of signature detect."
    ::= { hh3cDot11WIPSDtcSigEntry 4 }

hh3cDot11WIPSDtcSigStatus OBJECT-TYPE
    SYNTAX Hh3cDot11WIPSEnabledStatus
    MAX-ACCESS read-write
    STATUS current
    DESCRIPTION
        "The status of this table entry."
    ::= { hh3cDot11WIPSDtcSigEntry 5 }

hh3cDot11WIPSPolicyTable OBJECT-TYPE
    SYNTAX SEQUENCE OF Hh3cDot11WIPSPolicyEntry
    MAX-ACCESS not-accessible
    STATUS current
    DESCRIPTION
        "The table provides information about policy."
    ::= { hh3cDot11WIPSConfigGroup 35 }

hh3cDot11WIPSPolicyEntry OBJECT-TYPE
    SYNTAX Hh3cDot11WIPSPolicyEntry
    MAX-ACCESS not-accessible
    STATUS current
    DESCRIPTION
        "Each entry contains the enable status of policy configuration."
    INDEX { hh3cDot11WIPSPolicyType ,hh3cDot11WIPSPolicyName}
    ::= { hh3cDot11WIPSPolicyTable 1 }

Hh3cDot11WIPSPolicyEntry ::= SEQUENCE {
        hh3cDot11WIPSPolicyType                 Hh3cDot11WIPSPolicyTypeValue,
        hh3cDot11WIPSPolicyName                 OCTET STRING,
        hh3cDot11WIPSPolicyRowStatus            RowStatus
     }

hh3cDot11WIPSPolicyType OBJECT-TYPE
    SYNTAX Hh3cDot11WIPSPolicyTypeValue
    MAX-ACCESS not-accessible
    STATUS current
    DESCRIPTION
        "Represents the type of policy."
    ::= { hh3cDot11WIPSPolicyEntry 1 }

hh3cDot11WIPSPolicyName OBJECT-TYPE
    SYNTAX OCTET STRING (SIZE (1..63))
    MAX-ACCESS not-accessible
    STATUS current
    DESCRIPTION
        "Represents the name of the policy."
    ::= { hh3cDot11WIPSPolicyEntry 2 }

hh3cDot11WIPSPolicyRowStatus OBJECT-TYPE
    SYNTAX RowStatus
    MAX-ACCESS read-create
    STATUS current
    DESCRIPTION
        "The status of this table entry."
    ::= { hh3cDot11WIPSPolicyEntry 3 }

hh3cDot11WIPSSigFrameTypeTable OBJECT-TYPE
    SYNTAX SEQUENCE OF Hh3cDot11WIPSSigFrameTypeEntry
    MAX-ACCESS not-accessible
    STATUS current
    DESCRIPTION
        "The table contains the enable status of signature frame type."
    ::= { hh3cDot11WIPSConfigGroup 36 }

hh3cDot11WIPSSigFrameTypeEntry OBJECT-TYPE
    SYNTAX Hh3cDot11WIPSSigFrameTypeEntry
    MAX-ACCESS not-accessible
    STATUS current
    DESCRIPTION
        "Each entry contains the status of signature frame type."
    INDEX { hh3cDot11WIPSSigFrameTypeRuleId }
    ::= { hh3cDot11WIPSSigFrameTypeTable 1 }

Hh3cDot11WIPSSigFrameTypeEntry ::= SEQUENCE {
        hh3cDot11WIPSSigFrameTypeRuleId         Integer32,
        hh3cDot11WIPSSigFrameType               Hh3cDot11WIPSSigFrameTypes,
        hh3cDot11WIPSSigFrameSubType            Hh3cDot11WIPSSigFrameSubTypes,
        hh3cDot11WIPSSigFrameTypeStatus         Hh3cDot11WIPSEnabledStatus
     }

hh3cDot11WIPSSigFrameTypeRuleId OBJECT-TYPE
    SYNTAX Integer32 (1..65535)
    MAX-ACCESS not-accessible
    STATUS current
    DESCRIPTION
        "Represents the signature rule ID."
    ::= { hh3cDot11WIPSSigFrameTypeEntry 1 }

hh3cDot11WIPSSigFrameType OBJECT-TYPE
    SYNTAX Hh3cDot11WIPSSigFrameTypes
    MAX-ACCESS read-write
    STATUS current
    DESCRIPTION
        "Represents the signature frame type."
    ::= { hh3cDot11WIPSSigFrameTypeEntry 2 }

hh3cDot11WIPSSigFrameSubType OBJECT-TYPE
    SYNTAX Hh3cDot11WIPSSigFrameSubTypes
    MAX-ACCESS read-write
    STATUS current
    DESCRIPTION
        "Represents the signature frame subtype."
    ::= { hh3cDot11WIPSSigFrameTypeEntry 3 }

hh3cDot11WIPSSigFrameTypeStatus OBJECT-TYPE
    SYNTAX  Hh3cDot11WIPSEnabledStatus
    MAX-ACCESS read-write
    STATUS current
    DESCRIPTION
        "The enable status of signature frame type."
    ::= { hh3cDot11WIPSSigFrameTypeEntry 4 }

hh3cDot11WIPSCtmTable OBJECT-TYPE
    SYNTAX SEQUENCE OF Hh3cDot11WIPSCtmEntry
    MAX-ACCESS not-accessible
    STATUS current
    DESCRIPTION
        "The table contains the countermeasure commands."
    ::= { hh3cDot11WIPSConfigGroup 37 }

hh3cDot11WIPSCtmEntry OBJECT-TYPE
    SYNTAX Hh3cDot11WIPSCtmEntry
    MAX-ACCESS not-accessible
    STATUS current
    DESCRIPTION
        "Each entry contains the enable command of countermeasure."
    INDEX { hh3cDot11WIPSCtmPolicyName, hh3cDot11WIPSCtmClassifyType }
    ::= { hh3cDot11WIPSCtmTable 1 }

Hh3cDot11WIPSCtmEntry ::= SEQUENCE {
        hh3cDot11WIPSCtmPolicyName       OCTET STRING,
        hh3cDot11WIPSCtmClassifyType     Hh3cDot11WIPSCtmType,
        hh3cDot11WIPSCtmStatus           Hh3cDot11WIPSEnabledStatus
     }

hh3cDot11WIPSCtmPolicyName OBJECT-TYPE
    SYNTAX OCTET STRING (SIZE (1..63))
    MAX-ACCESS not-accessible
    STATUS current
    DESCRIPTION
        "Represents the countermeasure policy name."
    ::= { hh3cDot11WIPSCtmEntry 1 }

hh3cDot11WIPSCtmClassifyType OBJECT-TYPE
    SYNTAX Hh3cDot11WIPSCtmType
    MAX-ACCESS not-accessible
    STATUS current
    DESCRIPTION
        "Represents a countermeasure command identifier."
    ::= { hh3cDot11WIPSCtmEntry 2 }

hh3cDot11WIPSCtmStatus OBJECT-TYPE
    SYNTAX  Hh3cDot11WIPSEnabledStatus
    MAX-ACCESS read-write
    STATUS current
    DESCRIPTION
        "The enable status of one countermeasure command."
    ::= { hh3cDot11WIPSCtmEntry 3 }

hh3cDot11WIPSSigPatternTable OBJECT-TYPE
    SYNTAX SEQUENCE OF Hh3cDot11WIPSSigPatternEntry
    MAX-ACCESS not-accessible
    STATUS current
    DESCRIPTION
        "The table defines signature pattern."
    ::= { hh3cDot11WIPSConfigGroup 38 }

hh3cDot11WIPSSigPatternEntry OBJECT-TYPE
    SYNTAX Hh3cDot11WIPSSigPatternEntry
    MAX-ACCESS not-accessible
    STATUS current
    DESCRIPTION
        "Each entry contains information about signature pattern."
    INDEX { hh3cDot11WIPSSigPatternRuleId, hh3cDot11WIPSSigPatternNum }
    ::= { hh3cDot11WIPSSigPatternTable 1 }

Hh3cDot11WIPSSigPatternEntry ::= SEQUENCE {
        hh3cDot11WIPSSigPatternRuleId           Integer32,
        hh3cDot11WIPSSigPatternNum              Integer32,
        hh3cDot11WIPSSigPatternOffset           Integer32,
        hh3cDot11WIPSSigPatternMask             OCTET STRING,
        hh3cDot11WIPSSigPatternValue1           Integer32,
        hh3cDot11WIPSSigPatternValue2           Integer32,
        hh3cDot11WIPSSigPatternFromPld          TruthValue,
        hh3cDot11WIPSSigPatternRowStatus        RowStatus
     }

hh3cDot11WIPSSigPatternRuleId OBJECT-TYPE
    SYNTAX Integer32 (1..65535)
    MAX-ACCESS not-accessible
    STATUS current
    DESCRIPTION
        "Represents the signature pattern rule id."
    ::= { hh3cDot11WIPSSigPatternEntry 1 }

hh3cDot11WIPSSigPatternNum OBJECT-TYPE
    SYNTAX Integer32 (0..65535)
    MAX-ACCESS not-accessible
    STATUS current
    DESCRIPTION
        "Represents the signature pattern pattern number."
    ::= { hh3cDot11WIPSSigPatternEntry 2 }

hh3cDot11WIPSSigPatternOffset OBJECT-TYPE
    SYNTAX Integer32 (0..2346)
    MAX-ACCESS read-create
    STATUS current
    DESCRIPTION
        "Represents the signature pattern offset."
    ::= { hh3cDot11WIPSSigPatternEntry 3 }

hh3cDot11WIPSSigPatternMask OBJECT-TYPE
    SYNTAX OCTET STRING (SIZE (1..4))
    MAX-ACCESS read-create
    STATUS current
    DESCRIPTION
        "Represents the signature pattern mask."
    ::= { hh3cDot11WIPSSigPatternEntry 4 }

hh3cDot11WIPSSigPatternValue1 OBJECT-TYPE
    SYNTAX Integer32 (0..65535)
    MAX-ACCESS read-create
    STATUS current
    DESCRIPTION
        "Represents the signature pattern value1."
    ::= { hh3cDot11WIPSSigPatternEntry 5 }

hh3cDot11WIPSSigPatternValue2 OBJECT-TYPE
    SYNTAX Integer32 (0..65535)
    MAX-ACCESS read-create
    STATUS current
    DESCRIPTION
        "Represents the signature pattern value2."
    ::= { hh3cDot11WIPSSigPatternEntry 6 }

hh3cDot11WIPSSigPatternFromPld OBJECT-TYPE
    SYNTAX TruthValue
    MAX-ACCESS read-create
    STATUS current
    DESCRIPTION
        "Represents the signature pattern frome payload."
    ::= { hh3cDot11WIPSSigPatternEntry 7 }

hh3cDot11WIPSSigPatternRowStatus OBJECT-TYPE
    SYNTAX RowStatus
    MAX-ACCESS read-create
    STATUS current
    DESCRIPTION
        "The status of this table entry."
    ::= { hh3cDot11WIPSSigPatternEntry 8 }

hh3cDot11WIPSSigSeqNumTable OBJECT-TYPE
    SYNTAX SEQUENCE OF Hh3cDot11WIPSSigSeqNumEntry
    MAX-ACCESS not-accessible
    STATUS current
    DESCRIPTION
        "The table contains the infomation about signature sequence number."
    ::= { hh3cDot11WIPSConfigGroup 39 }

hh3cDot11WIPSSigSeqNumEntry OBJECT-TYPE
    SYNTAX Hh3cDot11WIPSSigSeqNumEntry
    MAX-ACCESS not-accessible
    STATUS current
    DESCRIPTION
        "Each entry contains the infomation about signature sequence number."
    INDEX { hh3cDot11WIPSSigSeqNumRuleId }
    ::= { hh3cDot11WIPSSigSeqNumTable 1 }

Hh3cDot11WIPSSigSeqNumEntry ::= SEQUENCE {
        hh3cDot11WIPSSigSeqNumRuleId          Integer32,
        hh3cDot11WIPSSigSeqNumValue1          Integer32,
        hh3cDot11WIPSSigSeqNumValue2          Integer32,
        hh3cDot11WIPSSigSeqNumStatus          Hh3cDot11WIPSEnabledStatus
     }

hh3cDot11WIPSSigSeqNumRuleId OBJECT-TYPE
    SYNTAX Integer32 (1..65535)
    MAX-ACCESS not-accessible
    STATUS current
    DESCRIPTION
        "Represents the signature rule ID."
    ::= { hh3cDot11WIPSSigSeqNumEntry 1 }

hh3cDot11WIPSSigSeqNumValue1 OBJECT-TYPE
    SYNTAX Integer32 (0..4095)
    MAX-ACCESS read-write
    STATUS current
    DESCRIPTION
        "Represents sequence number value1."
    ::= { hh3cDot11WIPSSigSeqNumEntry 2 }

hh3cDot11WIPSSigSeqNumValue2 OBJECT-TYPE
    SYNTAX Integer32 (0..4095)
    MAX-ACCESS read-write
    STATUS current
    DESCRIPTION
        "Represents sequence number value2 ."
    ::= { hh3cDot11WIPSSigSeqNumEntry 3 }

hh3cDot11WIPSSigSeqNumStatus OBJECT-TYPE
    SYNTAX  Hh3cDot11WIPSEnabledStatus
    MAX-ACCESS read-write
    STATUS current
    DESCRIPTION
        "The enable status of signature sequence number."
    ::= { hh3cDot11WIPSSigSeqNumEntry 4 }

hh3cDot11WIPSSigSsidTable OBJECT-TYPE
    SYNTAX SEQUENCE OF Hh3cDot11WIPSSigSsidEntry
    MAX-ACCESS not-accessible
    STATUS current
    DESCRIPTION
        "The table contains the infomation about signature SSID."
    ::= { hh3cDot11WIPSConfigGroup 40 }

hh3cDot11WIPSSigSsidEntry OBJECT-TYPE
    SYNTAX Hh3cDot11WIPSSigSsidEntry
    MAX-ACCESS not-accessible
    STATUS current
    DESCRIPTION
        "Each entry contains the infomation about signature SSID."
    INDEX { hh3cDot11WIPSSigSsidRuleId }
    ::= { hh3cDot11WIPSSigSsidTable 1 }

Hh3cDot11WIPSSigSsidEntry ::= SEQUENCE {
        hh3cDot11WIPSSigSsidRuleId            Integer32,
        hh3cDot11WIPSSigSsidSsid              OCTET STRING,
        hh3cDot11WIPSSigSsidCase              TruthValue,
        hh3cDot11WIPSSigSsidMatchType         Hh3cDot11WIPSSigSsidMatchTypes,
        hh3cDot11WIPSSigSsidStatus            Hh3cDot11WIPSEnabledStatus
     }

hh3cDot11WIPSSigSsidRuleId OBJECT-TYPE
    SYNTAX Integer32 (1..65535)
    MAX-ACCESS not-accessible
    STATUS current
    DESCRIPTION
        "Represents the signature rule ID."
    ::= { hh3cDot11WIPSSigSsidEntry 1 }

hh3cDot11WIPSSigSsidSsid OBJECT-TYPE
    SYNTAX OCTET STRING (SIZE (1..32))
    MAX-ACCESS read-write
    STATUS current
    DESCRIPTION
        "Represents the name of signature SSID."
    ::= { hh3cDot11WIPSSigSsidEntry 2 }

hh3cDot11WIPSSigSsidCase OBJECT-TYPE
    SYNTAX TruthValue
    MAX-ACCESS read-write
    STATUS current
    DESCRIPTION
        "Represents the case sensitive of signature SSID."
    ::= { hh3cDot11WIPSSigSsidEntry 3 }

hh3cDot11WIPSSigSsidMatchType OBJECT-TYPE
    SYNTAX Hh3cDot11WIPSSigSsidMatchTypes
    MAX-ACCESS read-write
    STATUS current
    DESCRIPTION
        "Represents the match type of signature SSID."
    ::= { hh3cDot11WIPSSigSsidEntry 4 }

hh3cDot11WIPSSigSsidStatus OBJECT-TYPE
    SYNTAX  Hh3cDot11WIPSEnabledStatus
    MAX-ACCESS read-write
    STATUS current
    DESCRIPTION
        "The enable status of signature SSID."
    ::= { hh3cDot11WIPSSigSsidEntry 5 }

hh3cDot11WIPSSigSsidLengthTable OBJECT-TYPE
    SYNTAX SEQUENCE OF Hh3cDot11WIPSSigSsidLengthEntry
    MAX-ACCESS not-accessible
    STATUS current
    DESCRIPTION
        "The table contains the infomation about signature SSID length."
    ::= { hh3cDot11WIPSConfigGroup 41 }

hh3cDot11WIPSSigSsidLengthEntry OBJECT-TYPE
    SYNTAX Hh3cDot11WIPSSigSsidLengthEntry
    MAX-ACCESS not-accessible
    STATUS current
    DESCRIPTION
        "Each entry contains the infomation about signature SSID length."
    INDEX { hh3cDot11WIPSSigSsidLengthRuleId }
    ::= { hh3cDot11WIPSSigSsidLengthTable 1 }

Hh3cDot11WIPSSigSsidLengthEntry ::= SEQUENCE {
        hh3cDot11WIPSSigSsidLengthRuleId          Integer32,
        hh3cDot11WIPSSigSsidLengthValue1          Integer32,
        hh3cDot11WIPSSigSsidLengthValue2          Integer32,
        hh3cDot11WIPSSigSsidLengthStatus          Hh3cDot11WIPSEnabledStatus
     }

hh3cDot11WIPSSigSsidLengthRuleId OBJECT-TYPE
    SYNTAX Integer32 (1..65535)
    MAX-ACCESS not-accessible
    STATUS current
    DESCRIPTION
        "Represents the signature rule ID."
    ::= { hh3cDot11WIPSSigSsidLengthEntry 1 }

hh3cDot11WIPSSigSsidLengthValue1 OBJECT-TYPE
    SYNTAX Integer32 (1..32)
    MAX-ACCESS read-write
    STATUS current
    DESCRIPTION
        "Represents signature SSID length value1."
    ::= { hh3cDot11WIPSSigSsidLengthEntry 2 }

hh3cDot11WIPSSigSsidLengthValue2 OBJECT-TYPE
    SYNTAX Integer32 (1..32)
    MAX-ACCESS read-write
    STATUS current
    DESCRIPTION
        "Represents signature SSID length value2 ."
    ::= { hh3cDot11WIPSSigSsidLengthEntry 3 }

hh3cDot11WIPSSigSsidLengthStatus OBJECT-TYPE
    SYNTAX  Hh3cDot11WIPSEnabledStatus
    MAX-ACCESS read-write
    STATUS current
    DESCRIPTION
        "The enable status of signature SSID length."
    ::= { hh3cDot11WIPSSigSsidLengthEntry 4 }

hh3cDot11WIPSFldDetectTable OBJECT-TYPE
    SYNTAX SEQUENCE OF Hh3cDot11WIPSFldDetectEntry
    MAX-ACCESS not-accessible
    STATUS current
    DESCRIPTION
        "This table contains the flood detect information."
    ::= { hh3cDot11WIPSConfigGroup 42 }

hh3cDot11WIPSFldDetectEntry OBJECT-TYPE
    SYNTAX Hh3cDot11WIPSFldDetectEntry
    MAX-ACCESS not-accessible
    STATUS current
    DESCRIPTION
        "Each entry contains information about one type of flood detect."
    INDEX { hh3cDot11WIPSFldDetectPlyName, hh3cDot11WIPSFldDetectType }
    ::= { hh3cDot11WIPSFldDetectTable 1 }

Hh3cDot11WIPSFldDetectEntry ::= SEQUENCE {
        hh3cDot11WIPSFldDetectPlyName       OCTET STRING,
        hh3cDot11WIPSFldDetectType          Hh3cDot11WIPSFldDctType,
        hh3cDot11WIPSFldDetectInter         Integer32,
        hh3cDot11WIPSFldDetectThresh        Integer32,
        hh3cDot11WIPSFldDetectQuiet         Integer32,
        hh3cDot11WIPSFldDetectStatus        Hh3cDot11WIPSEnabledStatus
     }

hh3cDot11WIPSFldDetectPlyName OBJECT-TYPE
    SYNTAX OCTET STRING (SIZE (1..63))
    MAX-ACCESS not-accessible
    STATUS current
    DESCRIPTION
        "Represents the policy name of detect."
    ::= { hh3cDot11WIPSFldDetectEntry 1 }

hh3cDot11WIPSFldDetectType OBJECT-TYPE
    SYNTAX Hh3cDot11WIPSFldDctType
    MAX-ACCESS not-accessible
    STATUS current
    DESCRIPTION
        "Represents the type of flood detect."
    ::= { hh3cDot11WIPSFldDetectEntry 2 }

hh3cDot11WIPSFldDetectInter OBJECT-TYPE
    SYNTAX Integer32 (1..3600)
    MAX-ACCESS read-write
    STATUS current
    DESCRIPTION
        "Represents the interval of flood detect."
    ::= { hh3cDot11WIPSFldDetectEntry 3 }

hh3cDot11WIPSFldDetectThresh OBJECT-TYPE
    SYNTAX Integer32 (1..100000)
    MAX-ACCESS read-write
    STATUS current
    DESCRIPTION
        "Represents the threshold of flood detect."
    ::= { hh3cDot11WIPSFldDetectEntry 4 }

hh3cDot11WIPSFldDetectQuiet OBJECT-TYPE
    SYNTAX Integer32 (5..604800)
    MAX-ACCESS read-write
    STATUS current
    DESCRIPTION
        "Represents the quiet time of flood detect."
    ::= { hh3cDot11WIPSFldDetectEntry 5 }

hh3cDot11WIPSFldDetectStatus OBJECT-TYPE
    SYNTAX Hh3cDot11WIPSEnabledStatus
    MAX-ACCESS read-write
    STATUS current
    DESCRIPTION
         "The enable status of flood detect."
    ::= { hh3cDot11WIPSFldDetectEntry 6 }

hh3cDot11WIPSSignatureMacTable OBJECT-TYPE
    SYNTAX SEQUENCE OF Hh3cDot11WIPSSignatureMacEntry
    MAX-ACCESS not-accessible
    STATUS current
    DESCRIPTION
        "The table contains the infomation about signature MAC address."
    ::= { hh3cDot11WIPSConfigGroup 43 }

hh3cDot11WIPSSignatureMacEntry OBJECT-TYPE
    SYNTAX Hh3cDot11WIPSSignatureMacEntry
    MAX-ACCESS not-accessible
    STATUS current
    DESCRIPTION
        "Each entry contains the infomation about signature MAC address."
    INDEX { hh3cDot11WIPSSignatureMacRuleId }
    ::= { hh3cDot11WIPSSignatureMacTable 1 }

Hh3cDot11WIPSSignatureMacEntry ::= SEQUENCE {
        hh3cDot11WIPSSignatureMacRuleId           Integer32,
        hh3cDot11WIPSSignatureMacMacTyp           Hh3cDot11WIPSSigMacMacType,
        hh3cDot11WIPSSignatureMacMacAdd           MacAddress,
        hh3cDot11WIPSSignatureMacStatus           Hh3cDot11WIPSEnabledStatus
     }

hh3cDot11WIPSSignatureMacRuleId OBJECT-TYPE
    SYNTAX Integer32 (1..65535)
    MAX-ACCESS not-accessible
    STATUS current
    DESCRIPTION
        "Represents the signature rule ID."
    ::= { hh3cDot11WIPSSignatureMacEntry 1 }

hh3cDot11WIPSSignatureMacMacTyp OBJECT-TYPE
    SYNTAX Hh3cDot11WIPSSigMacMacType
    MAX-ACCESS read-write
    STATUS current
    DESCRIPTION
        "Represents the type of signature MAC address."
    ::= { hh3cDot11WIPSSignatureMacEntry 2 }

hh3cDot11WIPSSignatureMacMacAdd OBJECT-TYPE
    SYNTAX MacAddress
    MAX-ACCESS read-write
    STATUS current
    DESCRIPTION
        "Represents the MAC address of signature MAC address."
    ::= { hh3cDot11WIPSSignatureMacEntry 3 }

hh3cDot11WIPSSignatureMacStatus OBJECT-TYPE
    SYNTAX  Hh3cDot11WIPSEnabledStatus
    MAX-ACCESS read-write
    STATUS current
    DESCRIPTION
        "The enable status of signature MAC address."
    ::= { hh3cDot11WIPSSignatureMacEntry 4 }

hh3cDot11WIPSNatDetectTable OBJECT-TYPE
    SYNTAX SEQUENCE OF Hh3cDot11WIPSNatDetectEntry
    MAX-ACCESS not-accessible
    STATUS current
    DESCRIPTION
        "The table contains the enable status of WIPS NAT detect."
    ::= { hh3cDot11WIPSConfigGroup 45 }

hh3cDot11WIPSNatDetectEntry OBJECT-TYPE
    SYNTAX Hh3cDot11WIPSNatDetectEntry
    MAX-ACCESS not-accessible
    STATUS current
    DESCRIPTION
        "Each entry contains the enable status of NAT detect."
    INDEX { hh3cDot11WIPSNatDetectApName }
    ::= { hh3cDot11WIPSNatDetectTable 1 }

Hh3cDot11WIPSNatDetectEntry ::= SEQUENCE {
        hh3cDot11WIPSNatDetectApName       OCTET STRING,
        hh3cDot11WIPSNatDetectStatus       Hh3cDot11WIPSEnabledStatus
     }

hh3cDot11WIPSNatDetectApName OBJECT-TYPE
    SYNTAX OCTET STRING (SIZE (1..64))
    MAX-ACCESS not-accessible
    STATUS current
    DESCRIPTION
        "Represents the name of AP."
    ::= { hh3cDot11WIPSNatDetectEntry 1 }

hh3cDot11WIPSNatDetectStatus OBJECT-TYPE
    SYNTAX  Hh3cDot11WIPSEnabledStatus
    MAX-ACCESS read-write
    STATUS current
    DESCRIPTION
        "The enable status of NAT detect on AP."
    ::= { hh3cDot11WIPSNatDetectEntry 2 }

hh3cDot11WIPSDctAPTable OBJECT-TYPE
    SYNTAX SEQUENCE OF Hh3cDot11WIPSDctAPEntry
    MAX-ACCESS not-accessible
    STATUS current
    DESCRIPTION
        "The table contains BSS information for APs
         detected by WIPS."
    ::= { hh3cDot11WIPSDataGroup 1 }

hh3cDot11WIPSDctAPEntry OBJECT-TYPE
    SYNTAX Hh3cDot11WIPSDctAPEntry
    MAX-ACCESS not-accessible
    STATUS current
    DESCRIPTION
        "Each entry contains BSS information for one AP."
    INDEX { hh3cDot11WIPSDctAPVSD, hh3cDot11WIPSDctAPMac }
    ::= { hh3cDot11WIPSDctAPTable 1 }

Hh3cDot11WIPSDctAPEntry ::= SEQUENCE {
        hh3cDot11WIPSDctAPVSD               OCTET STRING,
        hh3cDot11WIPSDctAPMac               MacAddress,
        hh3cDot11WIPSDctAPClassifyWay       Hh3cDot11WIPSDevClassifyWay,
        hh3cDot11WIPSDctAPClassifyType      Hh3cDot11WIPSAPClassifyType,
        hh3cDot11WIPSDctAPSeverityLevel     Unsigned32,
        hh3cDot11WIPSDctAPStatus            Hh3cDot11WIPSDevStatus,
        hh3cDot11WIPSDctAPStatusDut         TimeTicks,
        hh3cDot11WIPSDctAPVendor            OCTET STRING,
        hh3cDot11WIPSDctAPSSID              OCTET STRING,
        hh3cDot11WIPSDctAPSecurity          Hh3cDot11WIPSAPSecurityType,
        hh3cDot11WIPSDctAPEncryptMethod     Hh3cDot11WIPSEncryptMethod,
        hh3cDot11WIPSDctAPAuthMethod        Hh3cDot11WIPSAuthMethod,
        hh3cDot11WIPSDctAPRadioType         Hh3cDot11WIPSRadioType,
        hh3cDot11WIPSDctAPWorkChannel       Hh3cDot11WIPSChannel,
        hh3cDot11WIPSDctAPIsCountered       TruthValue,
        hh3cDot11WIPSDctAPAttachStaNum      Integer32,
        hh3cDot11WIPSDctAPRptSensorNum      Integer32,
        hh3cDot11WIPSDctAPIsBdcastSSID      TruthValue,
        hh3cDot11WIPSDctAPType              Hh3cDot11WIPSAPType,
        hh3cDot11WIPSDctAPIsQosSported      TruthValue,
        hh3cDot11WIPSDctAPBeaconItv         Integer32,
        hh3cDot11WIPSDctAPUpDuration        TimeTicks
     }

hh3cDot11WIPSDctAPVSD OBJECT-TYPE
    SYNTAX OCTET STRING (SIZE (1..63))
    MAX-ACCESS not-accessible
    STATUS current
    DESCRIPTION
        "Represents the virtual security domain in which the BSS was detected."
    ::= { hh3cDot11WIPSDctAPEntry 1 }

hh3cDot11WIPSDctAPMac OBJECT-TYPE
    SYNTAX MacAddress
    MAX-ACCESS not-accessible
    STATUS current
    DESCRIPTION
        "Represents the Basic Service Set."
    ::= { hh3cDot11WIPSDctAPEntry 2 }

hh3cDot11WIPSDctAPClassifyWay OBJECT-TYPE
    SYNTAX Hh3cDot11WIPSDevClassifyWay
    MAX-ACCESS read-only
    STATUS current
    DESCRIPTION
        "Represents by which way the AP is categorized."
    ::= { hh3cDot11WIPSDctAPEntry 3 }

hh3cDot11WIPSDctAPClassifyType OBJECT-TYPE
    SYNTAX Hh3cDot11WIPSAPClassifyType
    MAX-ACCESS read-only
    STATUS current
    DESCRIPTION
        "Represents the category of the AP."
    ::= { hh3cDot11WIPSDctAPEntry 4 }

hh3cDot11WIPSDctAPSeverityLevel OBJECT-TYPE
    SYNTAX Unsigned32 (0..100)
    MAX-ACCESS read-only
    STATUS current
    DESCRIPTION
        "Represents the security level of the detected AP."
    ::= { hh3cDot11WIPSDctAPEntry 5 }

hh3cDot11WIPSDctAPStatus OBJECT-TYPE
    SYNTAX Hh3cDot11WIPSDevStatus
    MAX-ACCESS read-only
    STATUS current
    DESCRIPTION
        "Represents the status of the AP detected by WIPS."
    ::= { hh3cDot11WIPSDctAPEntry 6 }

hh3cDot11WIPSDctAPStatusDut OBJECT-TYPE
    SYNTAX TimeTicks
    MAX-ACCESS read-only
    STATUS current
    DESCRIPTION
        "Represents the duration of the AP status."
    ::= { hh3cDot11WIPSDctAPEntry 7 }

hh3cDot11WIPSDctAPVendor OBJECT-TYPE
    SYNTAX OCTET STRING (SIZE (0..127))
    MAX-ACCESS read-only
    STATUS current
    DESCRIPTION
        "Represents the vendor of the AP detected by WIPS."
    ::= { hh3cDot11WIPSDctAPEntry 8 }

hh3cDot11WIPSDctAPSSID OBJECT-TYPE
    SYNTAX OCTET STRING (SIZE (0..32))
    MAX-ACCESS read-only
    STATUS current
    DESCRIPTION
        "Represents the SSID that is broadcast by the AP."
    ::= { hh3cDot11WIPSDctAPEntry 9 }

hh3cDot11WIPSDctAPSecurity OBJECT-TYPE
    SYNTAX Hh3cDot11WIPSAPSecurityType
    MAX-ACCESS read-only
    STATUS current
    DESCRIPTION
        "Represents the security suites of the detected AP."
    ::= { hh3cDot11WIPSDctAPEntry 10 }

hh3cDot11WIPSDctAPEncryptMethod OBJECT-TYPE
    SYNTAX Hh3cDot11WIPSEncryptMethod
    MAX-ACCESS read-only
    STATUS current
    DESCRIPTION
        "Represents the encryption method used by the detected AP."
    ::= { hh3cDot11WIPSDctAPEntry 11 }

hh3cDot11WIPSDctAPAuthMethod OBJECT-TYPE
    SYNTAX Hh3cDot11WIPSAuthMethod
    MAX-ACCESS read-only
    STATUS current
    DESCRIPTION
        "Represents the authentication method used by the detected AP."
    ::= { hh3cDot11WIPSDctAPEntry 12 }

hh3cDot11WIPSDctAPRadioType OBJECT-TYPE
    SYNTAX Hh3cDot11WIPSRadioType
    MAX-ACCESS read-only
    STATUS current
    DESCRIPTION
        "Represents the radio type used by the detected AP."
    ::= { hh3cDot11WIPSDctAPEntry 13 }

hh3cDot11WIPSDctAPWorkChannel OBJECT-TYPE
    SYNTAX Hh3cDot11WIPSChannel
    MAX-ACCESS read-only
    STATUS current
    DESCRIPTION
        "Represents the radio channel on which the detected AP operates."
    ::= { hh3cDot11WIPSDctAPEntry 14 }

hh3cDot11WIPSDctAPIsCountered OBJECT-TYPE
    SYNTAX TruthValue
    MAX-ACCESS read-only
    STATUS current
    DESCRIPTION
        "Represents whether WIPS has taken countermeasures on the detected AP."
    ::= { hh3cDot11WIPSDctAPEntry 15 }

hh3cDot11WIPSDctAPAttachStaNum OBJECT-TYPE
    SYNTAX Integer32
    MAX-ACCESS read-only
    STATUS current
    DESCRIPTION
        "Represents the number of clients associated with the detected AP."
    ::= { hh3cDot11WIPSDctAPEntry 16 }

hh3cDot11WIPSDctAPRptSensorNum OBJECT-TYPE
    SYNTAX Integer32
    MAX-ACCESS read-only
    STATUS current
    DESCRIPTION
        "Represents the number of sensors that have detected the AP."
    ::= { hh3cDot11WIPSDctAPEntry 17 }

hh3cDot11WIPSDctAPIsBdcastSSID OBJECT-TYPE
    SYNTAX TruthValue
    MAX-ACCESS read-only
    STATUS current
    DESCRIPTION
        "Represents whether the detected AP is broadcasting the SSID."
    ::= { hh3cDot11WIPSDctAPEntry 18 }

hh3cDot11WIPSDctAPType OBJECT-TYPE
    SYNTAX Hh3cDot11WIPSAPType
    MAX-ACCESS read-only
    STATUS current
    DESCRIPTION
        "Represents the type of the detected AP."
    ::= { hh3cDot11WIPSDctAPEntry 19 }

hh3cDot11WIPSDctAPIsQosSported OBJECT-TYPE
    SYNTAX TruthValue
    MAX-ACCESS read-only
    STATUS current
    DESCRIPTION
        "Represents the support of the detected AP for QoS."
    ::= { hh3cDot11WIPSDctAPEntry 20 }

hh3cDot11WIPSDctAPBeaconItv OBJECT-TYPE
    SYNTAX Integer32
    MAX-ACCESS read-only
    STATUS current
    DESCRIPTION
        "Represents the beacon interval of the detected AP."
    ::= { hh3cDot11WIPSDctAPEntry 21 }

hh3cDot11WIPSDctAPUpDuration OBJECT-TYPE
    SYNTAX TimeTicks
    MAX-ACCESS read-only
    STATUS current
    DESCRIPTION
        "Represents the amount of time that has elapsed since AP
        started to work, which is calculated by using beacon/probe
        response frame."
    ::= { hh3cDot11WIPSDctAPEntry 22 }

hh3cDot11WIPSDctStaTable OBJECT-TYPE
    SYNTAX SEQUENCE OF Hh3cDot11WIPSDctStaEntry
    MAX-ACCESS not-accessible
    STATUS current
    DESCRIPTION
        "The table contains information about stations detected by WIPS."
    ::= { hh3cDot11WIPSDataGroup 2 }

hh3cDot11WIPSDctStaEntry OBJECT-TYPE
    SYNTAX Hh3cDot11WIPSDctStaEntry
    MAX-ACCESS not-accessible
    STATUS current
    DESCRIPTION
        "Each entry contains information about a station
        detected by WIPS."
    INDEX { hh3cDot11WIPSDctStaVSD, hh3cDot11WIPSDctStaMac }
    ::= { hh3cDot11WIPSDctStaTable 1 }

Hh3cDot11WIPSDctStaEntry ::= SEQUENCE {
        hh3cDot11WIPSDctStaVSD               OCTET STRING,
        hh3cDot11WIPSDctStaMac               MacAddress,
        hh3cDot11WIPSDctStaAssocBSSID        MacAddress,
        hh3cDot11WIPSDctStaClassifyWay       Hh3cDot11WIPSDevClassifyWay,
        hh3cDot11WIPSDctStaClassifyType      Hh3cDot11WIPSStaClassifyType,
        hh3cDot11WIPSDctStaSeverityLevel     Unsigned32,
        hh3cDot11WIPSDctStaIsDissociate      TruthValue,
        hh3cDot11WIPSDctStaStatus            Hh3cDot11WIPSDevStatus,
        hh3cDot11WIPSDctStaStatusDurat       TimeTicks,
        hh3cDot11WIPSDctStaVendor            OCTET STRING,
        hh3cDot11WIPSDctStaRadioType         Hh3cDot11WIPSRadioType,
        hh3cDot11WIPSDctStaRptSensorNum      Integer32,
        hh3cDot11WIPSDctStaWorkChannel       Hh3cDot11WIPSChannel,
        hh3cDot11WIPSDctStaIsCountered       TruthValue
     }

hh3cDot11WIPSDctStaVSD OBJECT-TYPE
    SYNTAX OCTET STRING (SIZE (1..63))
    MAX-ACCESS not-accessible
    STATUS current
    DESCRIPTION
        "Represents the virtual security domain in
         which the station was detected."
    ::= { hh3cDot11WIPSDctStaEntry 1 }

hh3cDot11WIPSDctStaMac OBJECT-TYPE
    SYNTAX MacAddress
    MAX-ACCESS not-accessible
    STATUS current
    DESCRIPTION
        "Represents the MAC address of the station."
    ::= { hh3cDot11WIPSDctStaEntry 2 }

hh3cDot11WIPSDctStaAssocBSSID OBJECT-TYPE
    SYNTAX MacAddress
    MAX-ACCESS read-only
    STATUS current
    DESCRIPTION
        "Represents the BSSID with which the station is associated."
    ::= { hh3cDot11WIPSDctStaEntry 3 }

hh3cDot11WIPSDctStaClassifyWay OBJECT-TYPE
    SYNTAX Hh3cDot11WIPSDevClassifyWay
    MAX-ACCESS read-only
    STATUS current
    DESCRIPTION
        "Represents the method that the client is categorized."
    ::= { hh3cDot11WIPSDctStaEntry 4 }

hh3cDot11WIPSDctStaClassifyType OBJECT-TYPE
    SYNTAX Hh3cDot11WIPSStaClassifyType
    MAX-ACCESS read-only
    STATUS current
    DESCRIPTION
        "Represents the category of the client."
    ::= { hh3cDot11WIPSDctStaEntry 5 }

hh3cDot11WIPSDctStaSeverityLevel OBJECT-TYPE
    SYNTAX Unsigned32 (0..100)
    MAX-ACCESS read-only
    STATUS current
    DESCRIPTION
        "Represents the security level of the detected client."
    ::= { hh3cDot11WIPSDctStaEntry 6 }

hh3cDot11WIPSDctStaIsDissociate OBJECT-TYPE
    SYNTAX TruthValue
    MAX-ACCESS read-only
    STATUS current
    DESCRIPTION
        "Represents whether the detected client is dissociated."
    ::= { hh3cDot11WIPSDctStaEntry 7 }

hh3cDot11WIPSDctStaStatus OBJECT-TYPE
    SYNTAX Hh3cDot11WIPSDevStatus
    MAX-ACCESS read-only
    STATUS current
    DESCRIPTION
        "Represents the status of the station detected by WIPS."
    ::= { hh3cDot11WIPSDctStaEntry 8 }

hh3cDot11WIPSDctStaStatusDurat OBJECT-TYPE
    SYNTAX TimeTicks
    MAX-ACCESS read-only
    STATUS current
    DESCRIPTION
        "Represents the duration of the client status."
    ::= { hh3cDot11WIPSDctStaEntry 9 }

hh3cDot11WIPSDctStaVendor OBJECT-TYPE
    SYNTAX OCTET STRING (SIZE (0..127))
    MAX-ACCESS read-only
    STATUS current
    DESCRIPTION
        "Represents the vendor of the station detected by WIPS."
    ::= { hh3cDot11WIPSDctStaEntry 10 }

hh3cDot11WIPSDctStaRadioType OBJECT-TYPE
    SYNTAX Hh3cDot11WIPSRadioType
    MAX-ACCESS read-only
    STATUS current
    DESCRIPTION
        "Represents the radio type used by the detected station."
    ::= { hh3cDot11WIPSDctStaEntry 11 }

hh3cDot11WIPSDctStaRptSensorNum OBJECT-TYPE
    SYNTAX Integer32
    MAX-ACCESS read-only
    STATUS current
    DESCRIPTION
        "Represents the number of sensors that have detected the station."
    ::= { hh3cDot11WIPSDctStaEntry 12 }

hh3cDot11WIPSDctStaWorkChannel OBJECT-TYPE
    SYNTAX Hh3cDot11WIPSChannel
    MAX-ACCESS read-only
    STATUS current
    DESCRIPTION
        "Represents on which radio channel that the WIPS sensor detected
        the station."
    ::= { hh3cDot11WIPSDctStaEntry 13 }

hh3cDot11WIPSDctStaIsCountered OBJECT-TYPE
    SYNTAX TruthValue
    MAX-ACCESS read-only
    STATUS current
    DESCRIPTION
        "Represents whether WIPS has taken countermeasures
         on the detected client."
    ::= { hh3cDot11WIPSDctStaEntry 14 }

--
-- ApAssociatecltTable data3
--
hh3cDot11WIPSApAssoCltTable OBJECT-TYPE
    SYNTAX SEQUENCE OF Hh3cDot11WIPSApAssoCltEntry
    MAX-ACCESS not-accessible
    STATUS current
    DESCRIPTION
        "The table contains information about associated client by WIPS."
    ::= { hh3cDot11WIPSDataGroup 3 }

hh3cDot11WIPSApAssoCltEntry OBJECT-TYPE
    SYNTAX Hh3cDot11WIPSApAssoCltEntry
    MAX-ACCESS not-accessible
    STATUS current
    DESCRIPTION
        "Each entry contains information about a associated client by WIPS."
    INDEX { hh3cDot11WIPSApAssoCltVSDName,
            hh3cDot11WIPSApAssoCltApMacAddr,
            hh3cDot11WIPSApAssoCltClMacAddr }
    ::= { hh3cDot11WIPSApAssoCltTable 1 }

Hh3cDot11WIPSApAssoCltEntry ::= SEQUENCE {
        hh3cDot11WIPSApAssoCltVSDName                    OCTET STRING,
        hh3cDot11WIPSApAssoCltApMacAddr                  MacAddress,
        hh3cDot11WIPSApAssoCltClMacAddr                  MacAddress,
        hh3cDot11WIPSApAssoCltIsAsso                     TruthValue
     }

hh3cDot11WIPSApAssoCltVSDName OBJECT-TYPE
    SYNTAX OCTET STRING (SIZE (1..63))
    MAX-ACCESS not-accessible
    STATUS current
    DESCRIPTION
        "Represents the virtual security domain in
         which the client had Associated."
    ::= { hh3cDot11WIPSApAssoCltEntry 1 }

hh3cDot11WIPSApAssoCltApMacAddr OBJECT-TYPE
    SYNTAX MacAddress
    MAX-ACCESS not-accessible
    STATUS current
    DESCRIPTION
        "Represents the MAC address of the AP."
    ::= { hh3cDot11WIPSApAssoCltEntry 2 }

hh3cDot11WIPSApAssoCltClMacAddr OBJECT-TYPE
    SYNTAX MacAddress
    MAX-ACCESS not-accessible
    STATUS current
    DESCRIPTION
        "Represents the MAC address of the Client."
    ::= { hh3cDot11WIPSApAssoCltEntry 3 }

hh3cDot11WIPSApAssoCltIsAsso OBJECT-TYPE
    SYNTAX TruthValue
    MAX-ACCESS read-only
    STATUS current
    DESCRIPTION
        "Represents whether WIPS had taken associated on the detected client."
    ::= { hh3cDot11WIPSApAssoCltEntry 4 }

hh3cDot11WIPSApRpSenTable OBJECT-TYPE
    SYNTAX SEQUENCE OF Hh3cDot11WIPSApRpSenEntry
    MAX-ACCESS not-accessible
    STATUS current
    DESCRIPTION
        "This table contains information about AP report sensors."
    ::= { hh3cDot11WIPSDataGroup 4 }

hh3cDot11WIPSApRpSenEntry OBJECT-TYPE
    SYNTAX Hh3cDot11WIPSApRpSenEntry
    MAX-ACCESS not-accessible
    STATUS current
    DESCRIPTION
        "Each entry contains information about one device in a VSD."
    INDEX { hh3cDot11WIPSApRpSenVsdName,
            hh3cDot11WIPSApRpSenMacAddr,
            hh3cDot11WIPSApRpSenName }
    ::= { hh3cDot11WIPSApRpSenTable 1 }

Hh3cDot11WIPSApRpSenEntry ::= SEQUENCE {
        hh3cDot11WIPSApRpSenVsdName             OCTET STRING,
        hh3cDot11WIPSApRpSenMacAddr             MacAddress,
        hh3cDot11WIPSApRpSenName                OCTET STRING,
        hh3cDot11WIPSApRpSenRadioID             Integer32,
        hh3cDot11WIPSApRpSenRssi                Integer32,
        hh3cDot11WIPSApRpSenChannel             Integer32,
        hh3cDot11WIPSApRpSenFirstRpTime         OCTET STRING,
        hh3cDot11WIPSApRpSenLastRpTime          OCTET STRING
     }

hh3cDot11WIPSApRpSenVsdName OBJECT-TYPE
    SYNTAX OCTET STRING (SIZE (1..63))
    MAX-ACCESS not-accessible
    STATUS current
    DESCRIPTION
        "Represents the name of the VSD."
    ::= { hh3cDot11WIPSApRpSenEntry 1 }

hh3cDot11WIPSApRpSenMacAddr OBJECT-TYPE
    SYNTAX MacAddress
    MAX-ACCESS not-accessible
    STATUS current
    DESCRIPTION
        "Represents the MAC address of the sensor."
    ::= { hh3cDot11WIPSApRpSenEntry 2 }

hh3cDot11WIPSApRpSenName OBJECT-TYPE
    SYNTAX OCTET STRING (SIZE (1..64))
    MAX-ACCESS not-accessible
    STATUS current
    DESCRIPTION
        "Represents the name of the sensor."
    ::= { hh3cDot11WIPSApRpSenEntry 3 }

hh3cDot11WIPSApRpSenRadioID  OBJECT-TYPE
    SYNTAX Integer32
    MAX-ACCESS read-only
    STATUS current
    DESCRIPTION
        "Represents the radio ID."
    ::= { hh3cDot11WIPSApRpSenEntry 4 }

hh3cDot11WIPSApRpSenRssi  OBJECT-TYPE
    SYNTAX Integer32
    MAX-ACCESS read-only
    STATUS current
    DESCRIPTION
        "Represents the rssi of AP."
    ::= { hh3cDot11WIPSApRpSenEntry 5 }

hh3cDot11WIPSApRpSenChannel  OBJECT-TYPE
    SYNTAX Integer32
    MAX-ACCESS read-only
    STATUS current
    DESCRIPTION
        "Represents the channel of AP."
    ::= { hh3cDot11WIPSApRpSenEntry 6 }

hh3cDot11WIPSApRpSenFirstRpTime  OBJECT-TYPE
    SYNTAX OCTET STRING (SIZE (1..256))
    MAX-ACCESS read-only
    STATUS current
    DESCRIPTION
        "Represents the first report time of AP."
    ::= { hh3cDot11WIPSApRpSenEntry 7 }

hh3cDot11WIPSApRpSenLastRpTime  OBJECT-TYPE
    SYNTAX OCTET STRING (SIZE (1..256))
    MAX-ACCESS read-only
    STATUS current
    DESCRIPTION
        "Represents the last report time of AP."
    ::= { hh3cDot11WIPSApRpSenEntry 8 }

hh3cDot11WIPSCtmRecTable OBJECT-TYPE
    SYNTAX SEQUENCE OF Hh3cDot11WIPSCtmRecEntry
    MAX-ACCESS not-accessible
    STATUS current
    DESCRIPTION
        "The table provides information about virtual security domains (VSDs)."
    ::= { hh3cDot11WIPSDataGroup 5 }

hh3cDot11WIPSCtmRecEntry OBJECT-TYPE
    SYNTAX Hh3cDot11WIPSCtmRecEntry
    MAX-ACCESS not-accessible
    STATUS current
    DESCRIPTION
        "Each entry contains information about one VSD."
    INDEX { hh3cDot11WIPSCtmRecVsdName,
            hh3cDot11WIPSCtmRecMacAddress,
            hh3cDot11WIPSCtmRecCount }
    ::= { hh3cDot11WIPSCtmRecTable 1 }

Hh3cDot11WIPSCtmRecEntry ::= SEQUENCE {
        hh3cDot11WIPSCtmRecVsdName                  OCTET STRING,
        hh3cDot11WIPSCtmRecMacAddress               MacAddress,
        hh3cDot11WIPSCtmRecCount                    Integer32,
        hh3cDot11WIPSCtmRecSensorName               OCTET STRING,
        hh3cDot11WIPSCtmRecDeviceType               Hh3cDot11WIPSDeviceType,
        hh3cDot11WIPSCtmRecClassifyType             Hh3cDot11WIPSClassifyType,
        hh3cDot11WIPSCtmRecRadioId                  Integer32,
        hh3cDot11WIPSCtmRecCounterTime              OCTET STRING
    }

hh3cDot11WIPSCtmRecVsdName OBJECT-TYPE
    SYNTAX OCTET STRING (SIZE (1..63))
    MAX-ACCESS not-accessible
    STATUS current
    DESCRIPTION
        "Represents the name of the virtual security domain."
    ::= { hh3cDot11WIPSCtmRecEntry 1 }

hh3cDot11WIPSCtmRecMacAddress OBJECT-TYPE
    SYNTAX MacAddress
    MAX-ACCESS not-accessible
    STATUS current
    DESCRIPTION
        "Represents the MAC address."
    ::= { hh3cDot11WIPSCtmRecEntry 2 }

hh3cDot11WIPSCtmRecCount OBJECT-TYPE
    SYNTAX Integer32 (1..1024)
    MAX-ACCESS not-accessible
    STATUS current
    DESCRIPTION
        "Represents the count of countermeasure record."
    ::= { hh3cDot11WIPSCtmRecEntry 3 }

hh3cDot11WIPSCtmRecSensorName OBJECT-TYPE
    SYNTAX OCTET STRING (SIZE (1..64))
    MAX-ACCESS read-only
    STATUS current
    DESCRIPTION
        "Represents the name of countermeasure sensor."
    ::= { hh3cDot11WIPSCtmRecEntry 4 }

hh3cDot11WIPSCtmRecDeviceType OBJECT-TYPE
    SYNTAX Hh3cDot11WIPSDeviceType
    MAX-ACCESS read-only
    STATUS current
    DESCRIPTION
        "Represents the type of device."
    ::= { hh3cDot11WIPSCtmRecEntry 5 }

hh3cDot11WIPSCtmRecClassifyType OBJECT-TYPE
    SYNTAX Hh3cDot11WIPSClassifyType
    MAX-ACCESS read-only
    STATUS current
    DESCRIPTION
        "Represents the type of device classification."
    ::= { hh3cDot11WIPSCtmRecEntry 6 }

hh3cDot11WIPSCtmRecRadioId OBJECT-TYPE
    SYNTAX Integer32
    MAX-ACCESS read-only
    STATUS current
    DESCRIPTION
        "Represents the radio ID of countermeasure sensor."
    ::= { hh3cDot11WIPSCtmRecEntry 7 }

hh3cDot11WIPSCtmRecCounterTime OBJECT-TYPE
    SYNTAX OCTET STRING (SIZE (1..256))
    MAX-ACCESS read-only
    STATUS current
    DESCRIPTION
        "Represents the time of countermeasure."
    ::= { hh3cDot11WIPSCtmRecEntry 8 }

hh3cDot11WIPSDevTable OBJECT-TYPE
    SYNTAX SEQUENCE OF Hh3cDot11WIPSDevEntry
    MAX-ACCESS not-accessible
    STATUS current
    DESCRIPTION
        "The table contains variedly devices type information."
    ::= { hh3cDot11WIPSDataGroup 7 }

hh3cDot11WIPSDevEntry OBJECT-TYPE
    SYNTAX Hh3cDot11WIPSDevEntry
    MAX-ACCESS not-accessible
    STATUS current
    DESCRIPTION
        "Each entry contains one type of devices information."
    INDEX { hh3cDot11WIPSDevVSDName }
    ::= { hh3cDot11WIPSDevTable 1 }

Hh3cDot11WIPSDevEntry ::= SEQUENCE {
        hh3cDot11WIPSDevVSDName                 OCTET STRING,
        hh3cDot11WIPSDevTotalApNum              Integer32,
        hh3cDot11WIPSDevTotalClinetNum          Integer32,
        hh3cDot11WIPSDevAuthApNum               Integer32,
        hh3cDot11WIPSDevMisConfigApNum          Integer32,
        hh3cDot11WIPSDevRogueApNum              Integer32,
        hh3cDot11WIPSDevExternalApNum           Integer32,
        hh3cDot11WIPSDevAdhocNum                Integer32,
        hh3cDot11WIPSDevMeshApNum               Integer32,
        hh3cDot11WIPSDevpotenAuthApNum          Integer32,
        hh3cDot11WIPSDevpotenRogueApNum         Integer32,
        hh3cDot11WIPSDevPotenExtApNum           Integer32,
        hh3cDot11WIPSDevUncateApNum             Integer32,
        hh3cDot11WIPSDevAuthClinetNum           Integer32,
        hh3cDot11WIPSDevUnauthClinetNum         Integer32,
        hh3cDot11WIPSDevMisAssocltNum           Integer32,
        hh3cDot11WIPSDevUncatecltNum            Integer32
     }

hh3cDot11WIPSDevVSDName OBJECT-TYPE
    SYNTAX OCTET STRING (SIZE (1..63))
    MAX-ACCESS not-accessible
    STATUS current
    DESCRIPTION
        "Represents the virtual security domain in one type device."
    ::= { hh3cDot11WIPSDevEntry 1 }

hh3cDot11WIPSDevTotalApNum OBJECT-TYPE
    SYNTAX Integer32
    MAX-ACCESS read-only
    STATUS current
    DESCRIPTION
        "Represents the total number of detected AP."
    ::= { hh3cDot11WIPSDevEntry 2 }

hh3cDot11WIPSDevTotalClinetNum OBJECT-TYPE
    SYNTAX Integer32
    MAX-ACCESS read-only
    STATUS current
    DESCRIPTION
        "Represents the total number of detected client."
    ::= { hh3cDot11WIPSDevEntry 3 }

hh3cDot11WIPSDevAuthApNum OBJECT-TYPE
    SYNTAX Integer32
    MAX-ACCESS read-only
    STATUS current
    DESCRIPTION
        "Represents the number of detected authenticated AP."
    ::= { hh3cDot11WIPSDevEntry 4 }

hh3cDot11WIPSDevMisConfigApNum OBJECT-TYPE
    SYNTAX Integer32
    MAX-ACCESS read-only
    STATUS current
    DESCRIPTION
        "Represents the number of detected misconfiguration AP."
    ::= { hh3cDot11WIPSDevEntry 5 }

hh3cDot11WIPSDevRogueApNum OBJECT-TYPE
    SYNTAX Integer32
    MAX-ACCESS read-only
    STATUS current
    DESCRIPTION
        "Represents the number of detected rouge AP."
    ::= { hh3cDot11WIPSDevEntry 6 }

hh3cDot11WIPSDevExternalApNum OBJECT-TYPE
    SYNTAX Integer32
    MAX-ACCESS read-only
    STATUS current
    DESCRIPTION
        "Represents the number of detected external AP."
    ::= { hh3cDot11WIPSDevEntry 7 }

hh3cDot11WIPSDevAdhocNum OBJECT-TYPE
    SYNTAX Integer32
    MAX-ACCESS read-only
    STATUS current
    DESCRIPTION
        "Represents the number of detected ad-hoc AP."
    ::= { hh3cDot11WIPSDevEntry 8 }

hh3cDot11WIPSDevMeshApNum OBJECT-TYPE
    SYNTAX Integer32
    MAX-ACCESS read-only
    STATUS current
    DESCRIPTION
        "Represents the number of detected mesh-AP."
    ::= { hh3cDot11WIPSDevEntry 9 }

hh3cDot11WIPSDevpotenAuthApNum OBJECT-TYPE
    SYNTAX Integer32
    MAX-ACCESS read-only
    STATUS current
    DESCRIPTION
        "Represents the number of detected potential authenticated AP."
    ::= { hh3cDot11WIPSDevEntry 10 }

hh3cDot11WIPSDevpotenRogueApNum OBJECT-TYPE
    SYNTAX Integer32
    MAX-ACCESS read-only
    STATUS current
    DESCRIPTION
        "Represents the number of detected potential rogue AP."
    ::= { hh3cDot11WIPSDevEntry 11 }

hh3cDot11WIPSDevPotenExtApNum OBJECT-TYPE
    SYNTAX Integer32
    MAX-ACCESS read-only
    STATUS current
    DESCRIPTION
        "Represents the number of detected potential external AP."
    ::= { hh3cDot11WIPSDevEntry 12 }

hh3cDot11WIPSDevUncateApNum OBJECT-TYPE
    SYNTAX Integer32
    MAX-ACCESS read-only
    STATUS current
    DESCRIPTION
        "Represents the number of detected uncategorized AP."
    ::= { hh3cDot11WIPSDevEntry 13 }

hh3cDot11WIPSDevAuthClinetNum OBJECT-TYPE
    SYNTAX Integer32
    MAX-ACCESS read-only
    STATUS current
    DESCRIPTION
        "Represents the number of detected authenticated clinet."
    ::= { hh3cDot11WIPSDevEntry 14 }

hh3cDot11WIPSDevUnauthClinetNum OBJECT-TYPE
    SYNTAX Integer32
    MAX-ACCESS read-only
    STATUS current
    DESCRIPTION
        "Represents the number of detected unauthenticated client."
    ::= { hh3cDot11WIPSDevEntry 15 }

hh3cDot11WIPSDevMisAssocltNum OBJECT-TYPE
    SYNTAX Integer32
    MAX-ACCESS read-only
    STATUS current
    DESCRIPTION
        "Represents the number of detected misassociated client."
    ::= { hh3cDot11WIPSDevEntry 16 }

hh3cDot11WIPSDevUncatecltNum OBJECT-TYPE
    SYNTAX Integer32
    MAX-ACCESS read-only
    STATUS current
    DESCRIPTION
        "Represents the number of detected uncategorized client."
    ::= { hh3cDot11WIPSDevEntry 17 }


hh3cDot11WIPSCtmDevTable OBJECT-TYPE
    SYNTAX SEQUENCE OF Hh3cDot11WIPSCtmDevEntry
    MAX-ACCESS not-accessible
    STATUS current
    DESCRIPTION
        "This table contains information about countermeasure device in a VSD."
    ::= { hh3cDot11WIPSDataGroup 8 }

hh3cDot11WIPSCtmDevEntry OBJECT-TYPE
    SYNTAX Hh3cDot11WIPSCtmDevEntry
    MAX-ACCESS not-accessible
    STATUS current
    DESCRIPTION
        "Each entry contains countermeasure information about device in a VSD."
    INDEX { hh3cDot11WIPSCtmDevVsdName }
    ::= { hh3cDot11WIPSCtmDevTable 1 }

Hh3cDot11WIPSCtmDevEntry ::= SEQUENCE {
        hh3cDot11WIPSCtmDevVsdName                  OCTET STRING,
        hh3cDot11WIPSCtmDevTotalApNum               Integer32,
        hh3cDot11WIPSCtmDevTotalStaNum              Integer32,
        hh3cDot11WIPSCtmDevMisCfgApNum              Integer32,
        hh3cDot11WIPSCtmDevRogueApNum               Integer32,
        hh3cDot11WIPSCtmDevExternalApNum            Integer32,
        hh3cDot11WIPSCtmDevpotAuthApNum             Integer32,
        hh3cDot11WIPSCtmDevpotRguApNum              Integer32,
        hh3cDot11WIPSCtmDevpotenExtApNum            Integer32,
        hh3cDot11WIPSCtmDevUncateApNum              Integer32,
        hh3cDot11WIPSCtmDevUnauthStaNum             Integer32,
        hh3cDot11WIPSCtmDevMisAssCltNum             Integer32,
        hh3cDot11WIPSCtmDevUncatecltNum             Integer32,
        hh3cDot11WIPSCtmDevAttackerNum              Integer32,
        hh3cDot11WIPSCtmDevManuNum                  Integer32,
        hh3cDot11WIPSCtmDevStaCauseByAP             Integer32
     }

hh3cDot11WIPSCtmDevVsdName OBJECT-TYPE
    SYNTAX OCTET STRING (SIZE (1..63))
    MAX-ACCESS not-accessible
    STATUS current
    DESCRIPTION
        "Represents the vsd name."
    ::= { hh3cDot11WIPSCtmDevEntry 1 }

hh3cDot11WIPSCtmDevTotalApNum OBJECT-TYPE
    SYNTAX Integer32
    MAX-ACCESS read-only
    STATUS current
    DESCRIPTION
        "Represents the total number of coutermeasured AP."
    ::= { hh3cDot11WIPSCtmDevEntry 2 }

hh3cDot11WIPSCtmDevTotalStaNum OBJECT-TYPE
    SYNTAX Integer32
    MAX-ACCESS read-only
    STATUS current
    DESCRIPTION
        "Represents the total number of coutermeasured client."
    ::= { hh3cDot11WIPSCtmDevEntry 3 }

hh3cDot11WIPSCtmDevMisCfgApNum OBJECT-TYPE
    SYNTAX Integer32
    MAX-ACCESS read-only
    STATUS current
    DESCRIPTION
        "Represents the number of coutermeasured misconfiguration AP."
    ::= { hh3cDot11WIPSCtmDevEntry 4 }

hh3cDot11WIPSCtmDevRogueApNum OBJECT-TYPE
    SYNTAX Integer32
    MAX-ACCESS read-only
    STATUS current
    DESCRIPTION
        "Represents the number of coutermeasured rouge AP."
    ::= { hh3cDot11WIPSCtmDevEntry 5 }

hh3cDot11WIPSCtmDevExternalApNum OBJECT-TYPE
    SYNTAX Integer32
    MAX-ACCESS read-only
    STATUS current
    DESCRIPTION
        "Represents the number of coutermeasured external AP."
    ::= { hh3cDot11WIPSCtmDevEntry 6 }

hh3cDot11WIPSCtmDevpotAuthApNum OBJECT-TYPE
    SYNTAX Integer32
    MAX-ACCESS read-only
    STATUS current
    DESCRIPTION
        "Represents the number of coutermeasured potential authenticated AP."
    ::= { hh3cDot11WIPSCtmDevEntry 7 }

hh3cDot11WIPSCtmDevpotRguApNum OBJECT-TYPE
    SYNTAX Integer32
    MAX-ACCESS read-only
    STATUS current
    DESCRIPTION
        "Represents the number of coutermeasured potential rogue AP."
    ::= { hh3cDot11WIPSCtmDevEntry 8 }

hh3cDot11WIPSCtmDevpotenExtApNum OBJECT-TYPE
    SYNTAX Integer32
    MAX-ACCESS read-only
    STATUS current
    DESCRIPTION
        "Represents the number of coutermeasured potential external AP."
    ::= { hh3cDot11WIPSCtmDevEntry 9 }

hh3cDot11WIPSCtmDevUncateApNum OBJECT-TYPE
    SYNTAX Integer32
    MAX-ACCESS read-only
    STATUS current
    DESCRIPTION
        "Represents the number of coutermeasured uncategorized AP."
    ::= { hh3cDot11WIPSCtmDevEntry 10 }

hh3cDot11WIPSCtmDevUnauthStaNum OBJECT-TYPE
    SYNTAX Integer32
    MAX-ACCESS read-only
    STATUS current
    DESCRIPTION
        "Represents the number of coutermeasured unauthenticated client."
    ::= { hh3cDot11WIPSCtmDevEntry 11 }

hh3cDot11WIPSCtmDevMisAssCltNum OBJECT-TYPE
    SYNTAX Integer32
    MAX-ACCESS read-only
    STATUS current
    DESCRIPTION
        "Represents the number of coutermeasured misassociated client."
    ::= { hh3cDot11WIPSCtmDevEntry 12 }

hh3cDot11WIPSCtmDevUncatecltNum OBJECT-TYPE
    SYNTAX Integer32
    MAX-ACCESS read-only
    STATUS current
    DESCRIPTION
        "Represents the number of coutermeasured uncategorized client."
    ::= { hh3cDot11WIPSCtmDevEntry 13 }

hh3cDot11WIPSCtmDevAttackerNum OBJECT-TYPE
    SYNTAX Integer32
    MAX-ACCESS read-only
    STATUS current
    DESCRIPTION
        "Represents the number of coutermeasured attackers."
    ::= { hh3cDot11WIPSCtmDevEntry 14 }

hh3cDot11WIPSCtmDevManuNum OBJECT-TYPE
    SYNTAX Integer32
    MAX-ACCESS read-only
    STATUS current
    DESCRIPTION
        "Represents the number of manual coutermeasure."
    ::= { hh3cDot11WIPSCtmDevEntry 15 }

hh3cDot11WIPSCtmDevStaCauseByAP OBJECT-TYPE
    SYNTAX Integer32
    MAX-ACCESS read-only
    STATUS current
    DESCRIPTION
        "Represents the number of station caused by coutermeasured AP."
    ::= { hh3cDot11WIPSCtmDevEntry 16 }

hh3cDot11WIPSCltRptApTable OBJECT-TYPE
    SYNTAX SEQUENCE OF Hh3cDot11WIPSCltRptApEntry
    MAX-ACCESS not-accessible
    STATUS current
    DESCRIPTION
        "The table contains information about stations Report by Sensor."
    ::= { hh3cDot11WIPSDataGroup 11 }

hh3cDot11WIPSCltRptApEntry OBJECT-TYPE
    SYNTAX Hh3cDot11WIPSCltRptApEntry
    MAX-ACCESS not-accessible
    STATUS current
    DESCRIPTION
        "Each entry contains information about a probe station."
    INDEX { hh3cDot11WIPSCltRptApVSDName,
            hh3cDot11WIPSCltRptApDevMac,
            hh3cDot11WIPSCltRptApSensorName }
    ::= { hh3cDot11WIPSCltRptApTable 1 }

Hh3cDot11WIPSCltRptApEntry ::= SEQUENCE {
        hh3cDot11WIPSCltRptApVSDName        OCTET STRING,
        hh3cDot11WIPSCltRptApDevMac         MacAddress,
        hh3cDot11WIPSCltRptApSensorName     OCTET STRING,
        hh3cDot11WIPSCltReportApRadioId     Integer32,
        hh3cDot11WIPSCltRptApRSSI           Integer32,
        hh3cDot11WIPSCltRptApWorkChannel    Hh3cDot11WIPSChannel,
        hh3cDot11WIPSCltRptApFirstTime      OCTET STRING,
        hh3cDot11WIPSCltRptApLastTime       OCTET STRING,
        hh3cDot11WIPSCltRptApAssocMac       MacAddress
     }

hh3cDot11WIPSCltRptApVSDName OBJECT-TYPE
    SYNTAX OCTET STRING (SIZE (1..63))
    MAX-ACCESS not-accessible
    STATUS current
    DESCRIPTION
        "Represents the virtual security domain in
         which the client was detected."
    ::= { hh3cDot11WIPSCltRptApEntry 1 }

hh3cDot11WIPSCltRptApDevMac OBJECT-TYPE
    SYNTAX MacAddress
    MAX-ACCESS not-accessible
    STATUS current
    DESCRIPTION
        "Represents the device MAC address of the client."
    ::= { hh3cDot11WIPSCltRptApEntry 2 }

hh3cDot11WIPSCltRptApSensorName OBJECT-TYPE
    SYNTAX OCTET STRING (SIZE (1..64))
    MAX-ACCESS not-accessible
    STATUS current
    DESCRIPTION
        "Represents the sensor name in which the client was detected."
    ::= { hh3cDot11WIPSCltRptApEntry 3 }

hh3cDot11WIPSCltReportApRadioId OBJECT-TYPE
    SYNTAX Integer32
    MAX-ACCESS read-only
    STATUS current
    DESCRIPTION
        "Represents the radio id that have detected the client."
    ::= { hh3cDot11WIPSCltRptApEntry 4 }

hh3cDot11WIPSCltRptApRSSI OBJECT-TYPE
    SYNTAX Integer32
    MAX-ACCESS read-only
    STATUS current
    DESCRIPTION
        "Represents the RSSI of the client."
    ::= { hh3cDot11WIPSCltRptApEntry 5 }

hh3cDot11WIPSCltRptApWorkChannel OBJECT-TYPE
    SYNTAX Hh3cDot11WIPSChannel
    MAX-ACCESS read-only
    STATUS current
    DESCRIPTION
        "Represents on which radio channel that
         the WIPS sensor detected the client."
    ::= { hh3cDot11WIPSCltRptApEntry 6 }

hh3cDot11WIPSCltRptApFirstTime OBJECT-TYPE
    SYNTAX OCTET STRING (SIZE (1..256))
    MAX-ACCESS read-only
    STATUS current
    DESCRIPTION
        "Represents the First Report Time of the client."
    ::= { hh3cDot11WIPSCltRptApEntry 7 }

hh3cDot11WIPSCltRptApLastTime OBJECT-TYPE
    SYNTAX OCTET STRING (SIZE (1..256))
    MAX-ACCESS read-only
    STATUS current
    DESCRIPTION
        "Represents the Last Report Time of the client."
    ::= { hh3cDot11WIPSCltRptApEntry 8 }

hh3cDot11WIPSCltRptApAssocMac OBJECT-TYPE
    SYNTAX MacAddress
    MAX-ACCESS read-only
    STATUS current
    DESCRIPTION
        "Represents the association MAC address of the client."
    ::= { hh3cDot11WIPSCltRptApEntry 9 }

hh3cDot11WIPSNatDtcCltTable OBJECT-TYPE
    SYNTAX SEQUENCE OF Hh3cDot11WIPSNatDtcCltEntry
    MAX-ACCESS not-accessible
    STATUS current
    DESCRIPTION
        "The table contains information about NAT client detected by WIPS."
    ::= { hh3cDot11WIPSDataGroup 12 }

hh3cDot11WIPSNatDtcCltEntry OBJECT-TYPE
    SYNTAX Hh3cDot11WIPSNatDtcCltEntry
    MAX-ACCESS not-accessible
    STATUS current
    DESCRIPTION
        "Each entry contains information about a NAT detect client."
    INDEX { hh3cDot11WIPSNatDtcCltMac }
    ::= { hh3cDot11WIPSNatDtcCltTable 1 }

Hh3cDot11WIPSNatDtcCltEntry ::= SEQUENCE {
        hh3cDot11WIPSNatDtcCltMac           MacAddress,
        hh3cDot11WIPSNatDtcCltFirstTime     OCTET STRING,
        hh3cDot11WIPSNatDtcCltLastTime      OCTET STRING,
        hh3cDot11WIPSNatDtcCltDuraTime      Integer32
     }

hh3cDot11WIPSNatDtcCltMac OBJECT-TYPE
    SYNTAX MacAddress
    MAX-ACCESS not-accessible
    STATUS current
    DESCRIPTION
        "Represents the MAC address of the NAT detect client."
    ::= { hh3cDot11WIPSNatDtcCltEntry 1 }

hh3cDot11WIPSNatDtcCltFirstTime OBJECT-TYPE
    SYNTAX OCTET STRING (SIZE (1..256))
    MAX-ACCESS read-only
    STATUS current
    DESCRIPTION
        "Represents the first report time of the NAT detect client."
    ::= { hh3cDot11WIPSNatDtcCltEntry 2 }

hh3cDot11WIPSNatDtcCltLastTime OBJECT-TYPE
    SYNTAX OCTET STRING (SIZE (1..256))
    MAX-ACCESS read-only
    STATUS current
    DESCRIPTION
        "Represents the last report time of the NAT detect client."
    ::= { hh3cDot11WIPSNatDtcCltEntry 3 }

hh3cDot11WIPSNatDtcCltDuraTime OBJECT-TYPE
    SYNTAX Integer32
    MAX-ACCESS read-only
    STATUS current
    DESCRIPTION
        "Represents the duration of the NAT detect client."
    ::= { hh3cDot11WIPSNatDtcCltEntry 4 }

hh3cDot11WIPSAckStaTable OBJECT-TYPE
    SYNTAX SEQUENCE OF Hh3cDot11WIPSAckStaEntry
    MAX-ACCESS not-accessible
    STATUS current
    DESCRIPTION
        "This table contains information about attack statistics."
    ::= { hh3cDot11WIPSDataGroup 13 }

hh3cDot11WIPSAckStaEntry OBJECT-TYPE
    SYNTAX Hh3cDot11WIPSAckStaEntry
    MAX-ACCESS not-accessible
    STATUS current
    DESCRIPTION
        "Each entry contains information about
         a attack statistics on the sensor."
    INDEX { hh3cDot11WIPSAckStaSensorName }
    ::= { hh3cDot11WIPSAckStaTable 1 }

Hh3cDot11WIPSAckStaEntry ::= SEQUENCE {
        hh3cDot11WIPSAckStaSensorName                   OCTET STRING,
        hh3cDot11WIPSAckStaAssReqFld                    Integer32,
        hh3cDot11WIPSAckStaAuthFld                      Integer32,
        hh3cDot11WIPSAckStaBeaconFld                    Integer32,
        hh3cDot11WIPSAckStaBlkAckFld                    Integer32,
        hh3cDot11WIPSAckStaCtsFld                       Integer32,
        hh3cDot11WIPSAckStaDeauthFld                    Integer32,
        hh3cDot11WIPSAckStaDisassFld                    Integer32,
        hh3cDot11WIPSAckStaEpolSatFld                   Integer32,
        hh3cDot11WIPSAckStaNullDataFld                  Integer32,
        hh3cDot11WIPSAckStaProReqFld                    Integer32,
        hh3cDot11WIPSAckStaReassFld                     Integer32,
        hh3cDot11WIPSAckStaRtsFld                       Integer32,
        hh3cDot11WIPSAckStaEapLgoffFld                  Integer32,
        hh3cDot11WIPSAckStaEapFailFld                   Integer32,
        hh3cDot11WIPSAckStaEapSucFld                    Integer32,
        hh3cDot11WIPSAckStaDupIeMalf                    Integer32,
        hh3cDot11WIPSAckStaFataJackMalf                 Integer32,
        hh3cDot11WIPSAckStaEssMalf                      Integer32,
        hh3cDot11WIPSAckStaInvComMalf                   Integer32,
        hh3cDot11WIPSAckStaInvAssReqMalf                Integer32,
        hh3cDot11WIPSAckStaInvAuthMalf                  Integer32,
        hh3cDot11WIPSAckStaInvDeauthMalf                Integer32,
        hh3cDot11WIPSAckStaInvDisMalf                   Integer32,
        hh3cDot11WIPSAckStaInvHtIeMalf                  Integer32,
        hh3cDot11WIPSAckStaInvIeLenMalf                 Integer32,
        hh3cDot11WIPSAckStaInvPktLthMalf                Integer32,
        hh3cDot11WIPSAckStaLgeDutMalf                   Integer32,
        hh3cDot11WIPSAckStaNProRespMalf                 Integer32,
        hh3cDot11WIPSAckStaOverflEapMalf                Integer32,
        hh3cDot11WIPSAckStaOverfSsidMalf                Integer32,
        hh3cDot11WIPSAckStaRedundIeMalf                 Integer32,
        hh3cDot11WIPSAckStaApSpoofAp                    Integer32,
        hh3cDot11WIPSAckStaApSpoofclt                   Integer32,
        hh3cDot11WIPSAckStaApSpoofAdhoc                 Integer32,
        hh3cDot11WIPSAckStaAdhocSpoofAp                 Integer32,
        hh3cDot11WIPSAckStacltSpoofAp                   Integer32,
        hh3cDot11WIPSAckStaWeakIv                       Integer32,
        hh3cDot11WIPSAckStaApRate                       Integer32,
        hh3cDot11WIPSAckStacltRate                      Integer32,
        hh3cDot11WIPSAckStaSignatureRule                Integer32,
        hh3cDot11WIPSAckSta40Mhz                        Integer32,
        hh3cDot11WIPSAckStaPowerSave                    Integer32,
        hh3cDot11WIPSAckStaWinBdg                       Integer32,
        hh3cDot11WIPSAckStaOmerta                       Integer32,
        hh3cDot11WIPSAckStaSoftAp                       Integer32,
        hh3cDot11WIPSAckStaBroadDis                     Integer32,
        hh3cDot11WIPSAckStaBroadDeauth                  Integer32,
        hh3cDot11WIPSAckStaApImp                        Integer32,
        hh3cDot11WIPSAckStaHtGreenField                 Integer32,
        hh3cDot11WIPSAckStaWireBdg                      Integer32,
        hh3cDot11WIPSAckStaApFld                        Integer32,
        hh3cDot11WIPSAckStaAssociaOverf                 Integer32
    }

hh3cDot11WIPSAckStaSensorName OBJECT-TYPE
    SYNTAX OCTET STRING (SIZE (1..64))
    MAX-ACCESS not-accessible
    STATUS current
    DESCRIPTION
        "Represents the sensor name."
    ::= { hh3cDot11WIPSAckStaEntry 1 }

hh3cDot11WIPSAckStaAssReqFld OBJECT-TYPE
    SYNTAX Integer32
    MAX-ACCESS read-only
    STATUS current
    DESCRIPTION
        "Represents the statistics number of association request packet flood."
    ::= { hh3cDot11WIPSAckStaEntry 2 }

hh3cDot11WIPSAckStaAuthFld OBJECT-TYPE
    SYNTAX Integer32
    MAX-ACCESS read-only
    STATUS current
    DESCRIPTION
        "Represents the statistics number of authentication packet flood."
    ::= { hh3cDot11WIPSAckStaEntry 3 }

hh3cDot11WIPSAckStaBeaconFld OBJECT-TYPE
    SYNTAX Integer32
    MAX-ACCESS read-only
    STATUS current
    DESCRIPTION
        "Represents the statistics number of beacon packet flood."
    ::= { hh3cDot11WIPSAckStaEntry 4 }

hh3cDot11WIPSAckStaBlkAckFld OBJECT-TYPE
    SYNTAX Integer32
    MAX-ACCESS read-only
    STATUS current
    DESCRIPTION
        "Represents the statistics number of block ack packet flood."
    ::= { hh3cDot11WIPSAckStaEntry 5 }

hh3cDot11WIPSAckStaCtsFld OBJECT-TYPE
    SYNTAX Integer32
    MAX-ACCESS read-only
    STATUS current
    DESCRIPTION
        "Represents the statistics number of cts packet flood."
    ::= { hh3cDot11WIPSAckStaEntry 6 }

hh3cDot11WIPSAckStaDeauthFld OBJECT-TYPE
    SYNTAX Integer32
    MAX-ACCESS read-only
    STATUS current
    DESCRIPTION
        "Represents the statistics number of deauthentication packet flood."
    ::= { hh3cDot11WIPSAckStaEntry 7 }

hh3cDot11WIPSAckStaDisassFld OBJECT-TYPE
    SYNTAX Integer32
    MAX-ACCESS read-only
    STATUS current
    DESCRIPTION
        "Represents the statistics number of disassociation packet flood."
    ::= { hh3cDot11WIPSAckStaEntry 8 }

hh3cDot11WIPSAckStaEpolSatFld OBJECT-TYPE
    SYNTAX Integer32
    MAX-ACCESS read-only
    STATUS current
    DESCRIPTION
        "Represents the statistics number of eapol-start packet flood."
    ::= { hh3cDot11WIPSAckStaEntry 9 }

hh3cDot11WIPSAckStaNullDataFld OBJECT-TYPE
    SYNTAX Integer32
    MAX-ACCESS read-only
    STATUS current
    DESCRIPTION
        "Represents the statistics number of null-data packet flood."
    ::= { hh3cDot11WIPSAckStaEntry 10 }
hh3cDot11WIPSAckStaProReqFld OBJECT-TYPE
    SYNTAX Integer32
    MAX-ACCESS read-only
    STATUS current
    DESCRIPTION
        "Represents the statistics number of probe request packet flood."
    ::= { hh3cDot11WIPSAckStaEntry 11 }

hh3cDot11WIPSAckStaReassFld OBJECT-TYPE
    SYNTAX Integer32
    MAX-ACCESS read-only
    STATUS current
    DESCRIPTION
        "Represents the statistics number of
         reassociation request packet flood."
    ::= { hh3cDot11WIPSAckStaEntry 12 }

hh3cDot11WIPSAckStaRtsFld OBJECT-TYPE
    SYNTAX Integer32
    MAX-ACCESS read-only
    STATUS current
    DESCRIPTION
        "Represents the statistics number of rts packet flood."
    ::= { hh3cDot11WIPSAckStaEntry 13 }

hh3cDot11WIPSAckStaEapLgoffFld OBJECT-TYPE
    SYNTAX Integer32
    MAX-ACCESS read-only
    STATUS current
    DESCRIPTION
        "Represents the statistics number of eapol-logoff packet flood."
    ::= { hh3cDot11WIPSAckStaEntry 14 }

hh3cDot11WIPSAckStaEapFailFld OBJECT-TYPE
    SYNTAX Integer32
    MAX-ACCESS read-only
    STATUS current
    DESCRIPTION
        "Represents the statistics number of eap-failure packet flood."
    ::= { hh3cDot11WIPSAckStaEntry 15 }

hh3cDot11WIPSAckStaEapSucFld OBJECT-TYPE
    SYNTAX Integer32
    MAX-ACCESS read-only
    STATUS current
    DESCRIPTION
        "Represents the statistics number of eap-success packet flood."
    ::= { hh3cDot11WIPSAckStaEntry 16 }

hh3cDot11WIPSAckStaDupIeMalf OBJECT-TYPE
    SYNTAX Integer32
    MAX-ACCESS read-only
    STATUS current
    DESCRIPTION
        "Represents the statistics number of duplicated IE malform."
    ::= { hh3cDot11WIPSAckStaEntry 17 }

hh3cDot11WIPSAckStaFataJackMalf OBJECT-TYPE
    SYNTAX Integer32
    MAX-ACCESS read-only
    STATUS current
    DESCRIPTION
        "Represents the statistics number of fata jack malform."
    ::= { hh3cDot11WIPSAckStaEntry 18 }

hh3cDot11WIPSAckStaEssMalf OBJECT-TYPE
    SYNTAX Integer32
    MAX-ACCESS read-only
    STATUS current
    DESCRIPTION
        "Represents the statistics number of illegal IBSS ESS malform."
    ::= { hh3cDot11WIPSAckStaEntry 19 }

hh3cDot11WIPSAckStaInvComMalf OBJECT-TYPE
    SYNTAX Integer32
    MAX-ACCESS read-only
    STATUS current
    DESCRIPTION
        "Represents the statistics number of
         invalid address combination malform."
    ::= { hh3cDot11WIPSAckStaEntry 20 }

hh3cDot11WIPSAckStaInvAssReqMalf OBJECT-TYPE
    SYNTAX Integer32
    MAX-ACCESS read-only
    STATUS current
    DESCRIPTION
        "Represents the statistics number of
         invalid authentication request malform."
    ::= { hh3cDot11WIPSAckStaEntry 21 }

hh3cDot11WIPSAckStaInvAuthMalf OBJECT-TYPE
    SYNTAX Integer32
    MAX-ACCESS read-only
    STATUS current
    DESCRIPTION
        "Represents the statistics number of invalid authentication malform."
    ::= { hh3cDot11WIPSAckStaEntry 22 }

hh3cDot11WIPSAckStaInvDeauthMalf OBJECT-TYPE
    SYNTAX Integer32
    MAX-ACCESS read-only
    STATUS current
    DESCRIPTION
        "Represents the statistics number of
         invalid deauthentication code malform."
    ::= { hh3cDot11WIPSAckStaEntry 23 }

hh3cDot11WIPSAckStaInvDisMalf OBJECT-TYPE
    SYNTAX Integer32
    MAX-ACCESS read-only
    STATUS current
    DESCRIPTION
        "Represents the statistics number of invalid disassocited code malform."
    ::= { hh3cDot11WIPSAckStaEntry 24 }

hh3cDot11WIPSAckStaInvHtIeMalf OBJECT-TYPE
    SYNTAX Integer32
    MAX-ACCESS read-only
    STATUS current
    DESCRIPTION
        "Represents the statistics number of invalid HT IE malform."
    ::= { hh3cDot11WIPSAckStaEntry 25 }

hh3cDot11WIPSAckStaInvIeLenMalf OBJECT-TYPE
    SYNTAX Integer32
    MAX-ACCESS read-only
    STATUS current
    DESCRIPTION
        "Represents the statistics number of invalid IE length malform."
    ::= { hh3cDot11WIPSAckStaEntry 26 }

hh3cDot11WIPSAckStaInvPktLthMalf OBJECT-TYPE
    SYNTAX Integer32
    MAX-ACCESS read-only
    STATUS current
    DESCRIPTION
        "Represents the statistics number of invalid packet length malform."
    ::= { hh3cDot11WIPSAckStaEntry 27 }

hh3cDot11WIPSAckStaLgeDutMalf OBJECT-TYPE
    SYNTAX Integer32
    MAX-ACCESS read-only
    STATUS current
    DESCRIPTION
        "Represents the statistics number of large duration malform."
    ::= { hh3cDot11WIPSAckStaEntry 28 }

hh3cDot11WIPSAckStaNProRespMalf OBJECT-TYPE
    SYNTAX Integer32
    MAX-ACCESS read-only
    STATUS current
    DESCRIPTION
        "Represents the statistics number of null probe response malform."
    ::= { hh3cDot11WIPSAckStaEntry 29 }

hh3cDot11WIPSAckStaOverflEapMalf OBJECT-TYPE
    SYNTAX Integer32
    MAX-ACCESS read-only
    STATUS current
    DESCRIPTION
        "Represents the statistics number of overflow eapol key malform."
    ::= { hh3cDot11WIPSAckStaEntry 30 }

hh3cDot11WIPSAckStaOverfSsidMalf OBJECT-TYPE
    SYNTAX Integer32
    MAX-ACCESS read-only
    STATUS current
    DESCRIPTION
        "Represents the statistics number of overflow SSID malform."
    ::= { hh3cDot11WIPSAckStaEntry 31 }

hh3cDot11WIPSAckStaRedundIeMalf OBJECT-TYPE
    SYNTAX Integer32
    MAX-ACCESS read-only
    STATUS current
    DESCRIPTION
        "Represents the statistics number of redundant IE malform."
    ::= { hh3cDot11WIPSAckStaEntry 32 }

hh3cDot11WIPSAckStaApSpoofAp OBJECT-TYPE
    SYNTAX Integer32
    MAX-ACCESS read-only
    STATUS current
    DESCRIPTION
        "Represents the statistics number of AP spoof AP."
    ::= { hh3cDot11WIPSAckStaEntry 33 }

hh3cDot11WIPSAckStaApSpoofclt OBJECT-TYPE
    SYNTAX Integer32
    MAX-ACCESS read-only
    STATUS current
    DESCRIPTION
        "Represents the statistics number of AP spoof client."
    ::= { hh3cDot11WIPSAckStaEntry 34 }

hh3cDot11WIPSAckStaApSpoofAdhoc OBJECT-TYPE
    SYNTAX Integer32
    MAX-ACCESS read-only
    STATUS current
    DESCRIPTION
        "Represents the statistics number of AP spoof adhoc."
    ::= { hh3cDot11WIPSAckStaEntry 35 }

hh3cDot11WIPSAckStaAdhocSpoofAp OBJECT-TYPE
    SYNTAX Integer32
    MAX-ACCESS read-only
    STATUS current
    DESCRIPTION
        "Represents the statistics number of adhoc spoof AP."
    ::= { hh3cDot11WIPSAckStaEntry 36 }

hh3cDot11WIPSAckStacltSpoofAp OBJECT-TYPE
    SYNTAX Integer32
    MAX-ACCESS read-only
    STATUS current
    DESCRIPTION
        "Represents the statistics number of client spoof AP."
    ::= { hh3cDot11WIPSAckStaEntry 37 }

hh3cDot11WIPSAckStaWeakIv OBJECT-TYPE
    SYNTAX Integer32
    MAX-ACCESS read-only
    STATUS current
    DESCRIPTION
        "Represents the statistics number of weak-iv."
    ::= { hh3cDot11WIPSAckStaEntry 38 }

hh3cDot11WIPSAckStaApRate OBJECT-TYPE
    SYNTAX Integer32
    MAX-ACCESS read-only
    STATUS current
    DESCRIPTION
        "Represents the statistics number of AP rate."
    ::= { hh3cDot11WIPSAckStaEntry 39 }

hh3cDot11WIPSAckStacltRate OBJECT-TYPE
    SYNTAX Integer32
    MAX-ACCESS read-only
    STATUS current
    DESCRIPTION
        "Represents the statistics number of client rate."
    ::= { hh3cDot11WIPSAckStaEntry 40 }

hh3cDot11WIPSAckStaSignatureRule OBJECT-TYPE
    SYNTAX Integer32
    MAX-ACCESS read-only
    STATUS current
    DESCRIPTION
        "Represents the statistics number of signature detect."
    ::= { hh3cDot11WIPSAckStaEntry 41 }

hh3cDot11WIPSAckSta40Mhz OBJECT-TYPE
    SYNTAX Integer32
    MAX-ACCESS read-only
    STATUS current
    DESCRIPTION
        "Represents the statistics number of 40MHZ detect."
    ::= { hh3cDot11WIPSAckStaEntry 42 }

hh3cDot11WIPSAckStaPowerSave OBJECT-TYPE
    SYNTAX Integer32
    MAX-ACCESS read-only
    STATUS current
    DESCRIPTION
        "Represents the statistics number of power save detect."
    ::= { hh3cDot11WIPSAckStaEntry 43 }

hh3cDot11WIPSAckStaWinBdg OBJECT-TYPE
    SYNTAX Integer32
    MAX-ACCESS read-only
    STATUS current
    DESCRIPTION
        "Represents the statistics number of window bridge detect."
    ::= { hh3cDot11WIPSAckStaEntry 44 }

hh3cDot11WIPSAckStaOmerta OBJECT-TYPE
    SYNTAX Integer32
    MAX-ACCESS read-only
    STATUS current
    DESCRIPTION
        "Represents the statistics number of omerta detect."
    ::= { hh3cDot11WIPSAckStaEntry 45 }

hh3cDot11WIPSAckStaSoftAp OBJECT-TYPE
    SYNTAX Integer32
    MAX-ACCESS read-only
    STATUS current
    DESCRIPTION
        "Represents the statistics number of soft AP detect."
    ::= { hh3cDot11WIPSAckStaEntry 46 }

hh3cDot11WIPSAckStaBroadDis OBJECT-TYPE
    SYNTAX Integer32
    MAX-ACCESS read-only
    STATUS current
    DESCRIPTION
        "Represents the statistics number of broadcast diassociated detect."
    ::= { hh3cDot11WIPSAckStaEntry 47 }

hh3cDot11WIPSAckStaBroadDeauth OBJECT-TYPE
    SYNTAX Integer32
    MAX-ACCESS read-only
    STATUS current
    DESCRIPTION
        "Represents the statistics number of broadcast deauthentication detect."
    ::= { hh3cDot11WIPSAckStaEntry 48 }

hh3cDot11WIPSAckStaApImp OBJECT-TYPE
    SYNTAX Integer32
    MAX-ACCESS read-only
    STATUS current
    DESCRIPTION
        "Represents the statistics number of AP impersonate."
    ::= { hh3cDot11WIPSAckStaEntry 49 }

hh3cDot11WIPSAckStaHtGreenField OBJECT-TYPE
    SYNTAX Integer32
    MAX-ACCESS read-only
    STATUS current
    DESCRIPTION
        "Represents the statistics number of HT green field."
    ::= { hh3cDot11WIPSAckStaEntry 50 }

hh3cDot11WIPSAckStaWireBdg OBJECT-TYPE
    SYNTAX Integer32
    MAX-ACCESS read-only
    STATUS current
    DESCRIPTION
        "Represents the statistics number of wireless bridge."
    ::= { hh3cDot11WIPSAckStaEntry 51 }

hh3cDot11WIPSAckStaApFld OBJECT-TYPE
    SYNTAX Integer32
    MAX-ACCESS read-only
    STATUS current
    DESCRIPTION
        "Represents the statistics number of AP flood."
    ::= { hh3cDot11WIPSAckStaEntry 52 }

hh3cDot11WIPSAckStaAssociaOverf OBJECT-TYPE
    SYNTAX Integer32
    MAX-ACCESS read-only
    STATUS current
    DESCRIPTION
        "Represents the statistics number of associated overflow."
    ::= { hh3cDot11WIPSAckStaEntry 53 }

END
