-- ==================================================================
-- Copyright (C) 2005 New H3C Tech. Co., Ltd. All rights reserved.
--
-- Description: MPLSOAM PS(protection switching) MIB
-- Reference:
-- Version: V1.0
-- History:
-- V1.0 2007-03-31 Created by LiXufu ID: 05023
-- ==================================================================
HH3C-MPLSOAM-PS-MIB DEFINITIONS ::= BEGIN

IMPORTS
        hh3cCommon
    FROM HH3C-OID-MIB
        Integer32, Unsigned32, OBJECT-TYPE, MODULE-IDENTITY, NOTIFICATION-TYPE
    FROM SNMPv2-SMI
        TruthValue, RowStatus
    FROM SNMPv2-TC;


hh3cMplsOamPs MODULE-IDENTITY
    LAST-UPDATED "200703310000Z"            -- March 31, 2007 at 00:00 GMT
    ORGANIZATION
        "New H3C Tech. Co., Ltd."
    CONTACT-INFO
        "Platform Team New H3C Tech. Co., Ltd.
        Hai-Dian District Beijing P.R. China
        http://www.h3c.com
        Zip:100085
        "
    DESCRIPTION
        "This MIB contains objects to configure mpls
        protect-switch module."
    ::= { hh3cCommon 80 }


-- ==================================================================
--
-- ======================= definition begin =========================
--
-- ==================================================================
hh3cMplsOamPsScalarGroup OBJECT IDENTIFIER ::= { hh3cMplsOamPs 1 }

hh3cMplsOamPsTrapOpen OBJECT-TYPE
    SYNTAX      TruthValue
    MAX-ACCESS  read-write
    STATUS      current
    DESCRIPTION
        "Whether mpls protect-switch trap is globally enabled.
        false: disable;
        true: enable"
    DEFVAL  { false }
    ::= { hh3cMplsOamPsScalarGroup 1 }

hh3cMplsOamPsTable OBJECT IDENTIFIER ::= { hh3cMplsOamPs 2 }

hh3cMplsPsTable OBJECT-TYPE
    SYNTAX      SEQUENCE OF Hh3cMplsPsEntry
    MAX-ACCESS  not-accessible
    STATUS      current
    DESCRIPTION
        "This table specifies per-protection-group MPLS PS
        capability and associated information."
    ::= { hh3cMplsOamPsTable 1 }

hh3cMplsPsEntry OBJECT-TYPE
    SYNTAX      Hh3cMplsPsEntry
    MAX-ACCESS  not-accessible
    STATUS      current
    DESCRIPTION
        "An entry in this table is created by an LSR for every
        protection group capable of supporting mpls ps."
    INDEX
        {
            hh3cMplsPsIndex
        }
    ::= { hh3cMplsPsTable 1 }

Hh3cMplsPsEntry ::= SEQUENCE
    {
        hh3cMplsPsIndex                 Integer32,
        hh3cMplsPsGroupID               Integer32,
        hh3cMplsPsWorkLspName           OCTET STRING,
        hh3cMplsPsProtectLspName        OCTET STRING,
        hh3cMplsPsRevertiveMode         Integer32,
        hh3cMplsPsWTR                   Integer32,
        hh3cMplsPsHoldOff               Integer32,
        hh3cMplsPsSwitchCondition       Integer32,
        hh3cMplsPsWorkLspDetectState    Integer32,
        hh3cMplsPsWorkLspUpDownState    Integer32,
        hh3cMplsPsProtLspDetectState    Integer32,
        hh3cMplsPsProtLspUpDownState    Integer32,
        hh3cMplsPsSwitchResult          Integer32,
        hh3cMplsPsRowStatus             RowStatus
    }

hh3cMplsPsIndex OBJECT-TYPE
    SYNTAX      Integer32
    MAX-ACCESS  not-accessible
    STATUS      current
    DESCRIPTION
        "This is a unique index for an entry in the mplspsEntry."
    ::= { hh3cMplsPsEntry 1 }

hh3cMplsPsGroupID OBJECT-TYPE
    SYNTAX      Integer32
    MAX-ACCESS  read-create
    STATUS      current
    DESCRIPTION
        "This is a unique group id for an entry in the mplspsEntry.
        One protect-switch group is composed of one working static-lsp
        and one protection static-lsp."
    ::= { hh3cMplsPsEntry 2 }

hh3cMplsPsWorkLspName OBJECT-TYPE
    SYNTAX      OCTET STRING
    MAX-ACCESS  read-create
    STATUS      current
    DESCRIPTION
        "The name of the working static-lsp."
    ::= { hh3cMplsPsEntry 3 }

hh3cMplsPsProtectLspName OBJECT-TYPE
    SYNTAX      OCTET STRING
    MAX-ACCESS  read-create
    STATUS      current
    DESCRIPTION
        "The name of the protection static-lsp."
    ::= { hh3cMplsPsEntry 4 }

hh3cMplsPsRevertiveMode OBJECT-TYPE
    SYNTAX      Integer32(1..2)
    MAX-ACCESS  read-create
    STATUS      current
    DESCRIPTION
        "Revertive mode is a protection switching mode where revertive
        action (switch back to the working LSP) is taken after the
        working LSP is repaired. And switching does not occur in a
        non-revertive mode.
        1: revertive;
        2: non-revertive;"
    ::= { hh3cMplsPsEntry 5 }

hh3cMplsPsWTR OBJECT-TYPE
    SYNTAX      Integer32
    UNITS       "30s"
    MAX-ACCESS  read-create
    STATUS      current
    DESCRIPTION
        "Wait to Restore timer is only applicable for the revertive mode
        and applies to a working LSP, it prevents reversion back to
        select the working LSP until the Wait to Restore timer has
        expired.
        The default value is 12 minutes. step is 30s."
    ::= { hh3cMplsPsEntry 6 }

hh3cMplsPsHoldOff OBJECT-TYPE
    SYNTAX      Integer32
    UNITS       "100ms"
    MAX-ACCESS  read-create
    STATUS      current
    DESCRIPTION
        "The time between declaration of signal degrade or signal fail,
        and the initialization of the protection switching algorithm.
        Step is 100ms, maximum is 10s."
    ::= { hh3cMplsPsEntry 7 }

hh3cMplsPsSwitchCondition OBJECT-TYPE
    SYNTAX      Integer32(1..9)
    MAX-ACCESS  read-create
    STATUS      current
    DESCRIPTION
        "The current switch condition of the protection group.
        1: clear, this command clears all of the externally
        initiated switch commands listed below;
        2: lockout of protection, fix the selector position on the
        working LSP, Prevents the selector from switching to the
        protection LSP when it is selecting the working LSP.
        Switches the selector from the protection to the working LSP
        when it is selecting the protection LSP;
        3: forced protection, switches the selector from the working LSP
        to the protection LSP (unless a higher priority switch
        request (i.e., LoP) is in effect);
        4: signal fail, for 1:1, Signal Fail (SF) is declared when the
        source of the protection domain enters the Defect State by
        receiving a BDI packet (from the return LSP or out of band).
        5: manual switch for working-lsp, switches the selector from the
        working LSP to the protection LSP (unless an equal or higher
        priority switch request (i.e., LoP, FS, SF or MS) is in
        effect);
        6: manual switch for protection-lsp, switches the selector from
        the protection LSP to the working LSP (unless an equal or
        higher priority switch request (i.e., LoP, FS, SF or MS) is
        in effect).
        7: WTR-timer, a configurable timer which is used to delay before
        reversion;
        8: HoldOff-timer, the time between declaration of signal degrade
        or signal fail, and the initialization of the protection
        switching algorithm;
        9: Others;
        The pripority of the commands are:
        clear > lockout of protection > force switch > manual switch for working
        lsp = manual switch for protection lsp"
    ::= { hh3cMplsPsEntry 8 }

hh3cMplsPsWorkLspDetectState OBJECT-TYPE
    SYNTAX      Integer32(1..2)
    MAX-ACCESS  read-only
    STATUS      current
    DESCRIPTION
        "The state of working static-lsp state in one protection group,
        whether it is in defect:
        1: it is out of defect;
        2: it enters defect."
    ::= { hh3cMplsPsEntry 9 }

hh3cMplsPsWorkLspUpDownState OBJECT-TYPE
    SYNTAX      Integer32(1..2)
    MAX-ACCESS  read-only
    STATUS      current
    DESCRIPTION
        "The state of working static-lsp state in one protection group,
        whether it is up or down:
        1: it is in up state;
        2: it is in down state."
    ::= { hh3cMplsPsEntry 10 }

hh3cMplsPsProtLspDetectState OBJECT-TYPE
    SYNTAX      Integer32(1..2)
    MAX-ACCESS  read-only
    STATUS      current
    DESCRIPTION
        "The state of protection static-lsp state in one protection group,
        whether it is in detection:
        1: it is out of defect;
        2: it enters defect."
    ::= { hh3cMplsPsEntry 11 }

hh3cMplsPsProtLspUpDownState OBJECT-TYPE
    SYNTAX      Integer32(1..2)
    MAX-ACCESS  read-only
    STATUS      current
    DESCRIPTION
        "The state of protection static-lsp state in one protection group,
        whether it is up or down:
        1: it is in up state;
        2: it is in down state."
    ::= { hh3cMplsPsEntry 12 }

hh3cMplsPsSwitchResult OBJECT-TYPE
    SYNTAX      Integer32(1..2)
    MAX-ACCESS  read-only
    STATUS      current
    DESCRIPTION
        "Which tunnel is used to transfer the data stream.
        1: working static-lsp;
        2: protection static-lsp."
    ::= { hh3cMplsPsEntry 13 }

hh3cMplsPsRowStatus OBJECT-TYPE
    SYNTAX      RowStatus
    MAX-ACCESS  read-create
    STATUS      current
    DESCRIPTION
        "This object is responsible for managing the creation,
        deletion and modification of rows, which support active
        status and CreatAndGo, destroy operation.
        To create a new row, hh3cMplsPsGroupID, hh3cMplsPsWorkLspName,
        hh3cMplsPsProtectLspName, hh3cMplsPsRevertiveMode, hh3cMplsPsWTR
        and hh3cMplsPsHoldOff must be specified."
    ::= { hh3cMplsPsEntry 14 }

hh3cMplsOamPsNotifications OBJECT IDENTIFIER ::= { hh3cMplsOamPs 3 }

hh3cMplsPsSwitchPtoW NOTIFICATION-TYPE
    OBJECTS
        {
            hh3cMplsPsWorkLspName,
            hh3cMplsPsProtectLspName,
            hh3cMplsPsSwitchResult
        }
    STATUS      current
    DESCRIPTION
        "This notification is generated when switching from
        protection-lsp to working-lsp occured."
    ::= { hh3cMplsOamPsNotifications 1 }

hh3cMplsPsSwitchWtoP NOTIFICATION-TYPE
    OBJECTS
        {
            hh3cMplsPsWorkLspName,
            hh3cMplsPsProtectLspName,
            hh3cMplsPsSwitchResult
        }
    STATUS      current
    DESCRIPTION
        "This notification is generated when switching from woking-lsp
        to protection-lsp occured."
    ::= { hh3cMplsOamPsNotifications 2 }

END
