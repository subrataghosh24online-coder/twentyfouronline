-- ==========================================================================
-- Copyright (c) 2004-2017 New H3C Tech. Co., Ltd. All rights reserved.
--
-- Description: The purpose of this MIB file is to provide object definition
--              of WLAN radio resource management (RRM).
-- Reference:
-- Version: V1.9
-- History:
-- V1.0 2008-07-16 Initial version, created by ChenWei
-- V1.1 2009-04-16 modified by WangChunsheng
-- Add new table of hh3cDot11MonitorDetectedDevTable for hh3cDot11MonitorDetectedGroup.
-- Add new table of hh3cDot11RRMAPCfgTable for hh3cDot11RRMConfigGroup.
-- V1.2 2009-05-07 modified by Wang Shaojie, wangchunsheng
--      Add hh3cDot11APInterfNumThreshhd, hh3cDot11StaInterfNumThreshhd
--      to hh3cDot11GlobeConfigGroup.
--      Modify hh3cDot11RRMCfgIntrvl
-- V1.3 2009-05-07 modified by Wang Shaojie
--      Add new node hh3cDot11MonitorDevSNR to hh3cDot11MonitorDetectedDevTable
-- V1.4 2010-02-22 modified by Wang Chunsheng
--      Add new table hh3cDot11RRMSDRadioGroupTable to hh3cDot11RRMConfigGroup
--      2010-03-18 Modified by Wang Lu
--      Add hh3cDot11RRMAPCfg2Table
-- V1.5 2010-09-21 Modified by wu xiaopeng
--      Add new node hh3cDot11RRMCoChlIntfTrapThhd, hh3cDot11RRMAdjChlIntfTrapThhd
--      to hh3cDot11RRMAPCfg2Table
--      2011-03-23 Modified by NiuJian
--      Add new node hh3cDot11RrmNbrSSID
--      to hh3cDot11RRMNbrInfoTable
-- V1.6 2013-03-23 Modified by GaoFei
--      Change SYNTAX of hh3cDot11RRMCfgPERThres,hh3cDot11RRMCfgToleranceFctr
-- V1.7 2013-09-02 Modified by Zhang Siyu
--      Add new table hh3cDot11RRMRadioNbrInfoTable to hh3cDot11RRMDetectGroup
--      2013-11-19 Modified by wubin
--      Add new node hh3cDot11RRM11nMultiCastMcs
--      to hh3cDot11RRMGlobalCfgPara
--      2013-12-21 Modified by wubin
--      Add new node hh3cDot11RRM11acMadtMaxNss, hh3cDot11RRM11acSuptMaxNss,
--      hh3cDot11RRM11acMultiCastNss, hh3cDot11RRM11acMultiCastVhtMcs
--      to hh3cDot11RRMGlobalCfgPara
-- V1.8 2014-05-07 Modified by yubo
--      Change SYNTAX of hh3cDot11RRMCfgIntrfThres.
-- V1.9 2017-05-22 Modified by weizhiguang
--      Add new node hh3cDot11RrmNbrSNR, hh3cDot11RrmNbrNF
--      to Hh3cDot11RRMNbrInfoEntry
-- ==========================================================================
HH3C-DOT11-RRM-MIB DEFINITIONS ::= BEGIN

IMPORTS
    Hh3cDot11RadioType, Hh3cDot11ChannelScopeType, Hh3cDot11RadioElementIndex,
    Hh3cDot11RadioScopeType, hh3cDot11APElementIndex
        FROM HH3C-DOT11-REF-MIB
    Integer32, Unsigned32, OBJECT-TYPE, MODULE-IDENTITY,
    NOTIFICATION-TYPE
        FROM SNMPv2-SMI
    TruthValue, MacAddress, DateAndTime, RowStatus
        FROM SNMPv2-TC
    hh3cDot11,
    Hh3cDot11ObjectIDType,
    Hh3cDot11SSIDStringType
        FROM HH3C-DOT11-REF-MIB;

hh3cDot11RRM MODULE-IDENTITY
    LAST-UPDATED "201705221600Z"        -- May 22, 2017 at 16:00 GMT
    ORGANIZATION
        "New H3C Technologies Co., Ltd."
    CONTACT-INFO
        "Platform Team New H3C Technologies Co., Ltd.
         Hai-Dian District Beijing P.R.China
         Http://www.h3c.com
         Zip: 100085"
    DESCRIPTION
        "This MIB file is to provide the object definition of
        WLAN radio resource management (RRM)."

    REVISION "201705221600Z"        -- May 22, 2017 at 16:00 GMT
    DESCRIPTION
        "Modified to add new nodes."
    REVISION "201009251800Z"        -- Sep 25, 2010 at 18:00 GMT
    DESCRIPTION
        "Modified to add new nodes."
    REVISION "201002231800Z"        -- Feb 23, 2010 at 18:00 GMT
    DESCRIPTION
        "Modified to add new nodes."
    REVISION "200908012000Z"        -- Aug 1, 2009 at 20:00 GMT
    DESCRIPTION
        "Modified to add new nodes and new table."
    REVISION "200905072000Z"        -- May 7, 2009 at 20:00 GMT
    DESCRIPTION
        "Modified to add new nodes and new table."
    REVISION "200904172000Z"        -- April 17, 2009 at 20:00 GMT
    DESCRIPTION
        "Modified to add new table and new group."
    REVISION "200807141429Z"
    DESCRIPTION
        "The initial revision of this MIB module."
    ::= { hh3cDot11 8 }

--
-- Node definitions
--

hh3cDot11RRMConfigGroup OBJECT IDENTIFIER ::= { hh3cDot11RRM 1 }

hh3cDot11RRMGlobalCfgPara OBJECT IDENTIFIER ::= { hh3cDot11RRMConfigGroup 1 }

hh3cDot11RRM11nMadtMaxMcs OBJECT-TYPE
    SYNTAX Integer32 (0..76 | 255)
    MAX-ACCESS read-write
    STATUS current
    DESCRIPTION
        "Specify the maximum modulation and coding scheme (MCS) index for
        802.11n mandatory rates.
        The value 255 indicates that no maximum MCS index
        is specified.  No maximum MCS index is specified for 802.11n
        mandatory rates by default.
        Besides 255, the specified maximum MCS index for 802.11n supported
        rates must be no less than the specified maximum MCS index for 802.11n
        mandatory rates."
    DEFVAL { 255 }
    ::= { hh3cDot11RRMGlobalCfgPara 1 }

hh3cDot11RRM11nSuptMaxMcs OBJECT-TYPE
    SYNTAX Integer32 (0..76)
    MAX-ACCESS read-write
    STATUS current
    DESCRIPTION
        "Specify the maximum Modulation and Coding Scheme (MCS) index for
        802.11n supported rates.
        The specified maximum MCS index for 802.11n supported rates must be no
        less than the specified maximum MCS index for 802.11n mandatory rates."
    DEFVAL { 76 }
    ::= { hh3cDot11RRMGlobalCfgPara 2 }

hh3cDot11RRM11gProtect OBJECT-TYPE
    SYNTAX TruthValue
    MAX-ACCESS read-write
    STATUS current
    DESCRIPTION
        "Enable/Disable dot11g protection."
    DEFVAL { false }
    ::= { hh3cDot11RRMGlobalCfgPara 3 }

hh3cDot11RRM11aPwrConstrt OBJECT-TYPE
    SYNTAX Integer32
    UNITS "dBm"
    MAX-ACCESS read-write
    STATUS current
    DESCRIPTION
        "Configure the power constraint for all 802.11a radios.
        The configured power constraint is advertised in beacons if spectrum
        management is enabled.
        The range of power constraint is 0 to MAX-POWER-1 (where the MAX-POWER
        is defined by the regulatory domain)."
    DEFVAL { 0 }
    ::= { hh3cDot11RRMGlobalCfgPara 4 }

hh3cDot11RRM11aSpectrumManag OBJECT-TYPE
    SYNTAX TruthValue
    MAX-ACCESS read-write
    STATUS current
    DESCRIPTION
        "Enable/Disable spectrum management for 802.11a radios.
        When spectrum management is enabled, the WLAN sub-system advertises
        power capabilities of the AP and power constraints applicable to all
        devices in the BSS based on regulatory domain specification."
    DEFVAL { false }
    ::= { hh3cDot11RRMGlobalCfgPara 5 }

hh3cDot11RRMAutoChlAvoid11h OBJECT-TYPE
    SYNTAX TruthValue
    MAX-ACCESS read-write
    STATUS current
    DESCRIPTION
        "Configure the auto-channel set as non-dot11h channels, this is,
        only the non-dot11h channels belonging to the country code are scanned
        during initial channel selection and one of them is selected."
    DEFVAL { false }
    ::= { hh3cDot11RRMGlobalCfgPara 6 }

hh3cDot11RRMScanChl OBJECT-TYPE
    SYNTAX INTEGER
        {
        auto(1),
        all(2)
        }
    MAX-ACCESS read-write
    STATUS current
    DESCRIPTION
        "Set the scan mode.
        auto: When this option is set, all channels of the country code being
              set are scanned.
        all: When this option is set, all the channels of the radio band are
             scanned."
    DEFVAL { auto }
    ::= { hh3cDot11RRMGlobalCfgPara 7 }

hh3cDot11RRMScanRptIntvel OBJECT-TYPE
    SYNTAX Integer32 (5..120)
    UNITS "second"
    MAX-ACCESS read-write
    STATUS current
    DESCRIPTION
        "Set the scan report interval."
    DEFVAL { 10 }
    ::= { hh3cDot11RRMGlobalCfgPara 8 }

hh3cDot11APInterfNumThreshhd OBJECT-TYPE
    SYNTAX      Integer32
    MAX-ACCESS  read-write
    STATUS      current
    DESCRIPTION
        "Represents threshold of AP interference .
         If the value of AP interference exceeds this threshold,
         AP interference trap will be sent.  If the value of this node
         is zero, AP interference trap will be sent immediately."

    DEFVAL      { 0 }
    ::= { hh3cDot11RRMGlobalCfgPara 9 }

hh3cDot11StaInterfNumThreshhd OBJECT-TYPE
    SYNTAX      Integer32
    MAX-ACCESS  read-write
    STATUS      current
    DESCRIPTION
        "Represents threshold of STA interference.
         If the value of STA interference exceeds this threshold,
         STA interference trap will be sent.  If the value of this
         node is zero, STA interference trap will be sent immediately.
         "
    DEFVAL      { 0 }
    ::= { hh3cDot11RRMGlobalCfgPara 10 }

hh3cDot11RRM11nMultiCastMcs OBJECT-TYPE
    SYNTAX Unsigned32 (0..76 | 4294967295)
    MAX-ACCESS read-write
    STATUS current
    DESCRIPTION
        "Specify the modulation and coding scheme (MCS) index for 802.11n
        multicast rates.
        The value 4294967295 indicates that no MCS index is specified.
        No MCS index is specified for 802.11n multicast rates by default.
        Besides 4294967295, the specified MCS index for 802.11n multicast
        rates must be no less than the specified maximum MCS index for 802.11n
        mandatory rates.
        Before configure the MCS index for 802.11n multicast rates, the maximum
        MCS index for 802.11n mandatory rates must be configured"
    DEFVAL { 4294967295 }
    ::= { hh3cDot11RRMGlobalCfgPara 11 }

hh3cDot11RRM11acMadtMaxNss OBJECT-TYPE
    SYNTAX Integer32 (0..8)
    MAX-ACCESS read-write
    STATUS current
    DESCRIPTION
        "Specify the maximum NSS index for 802.11ac mandatory rates.
        The value 0 indicates that no maximum NSS index is specified.
        No maximum NSS index is specified for 802.11ac mandatory rates by default.
        The specified maximum NSS index for 802.11ac supported rates must be no less
        than the specified maximum NSS index for 802.11ac mandatory rates."
    DEFVAL { 0 }
    ::= { hh3cDot11RRMGlobalCfgPara 12 }

hh3cDot11RRM11acSuptMaxNss OBJECT-TYPE
    SYNTAX Integer32 (1..8)
    MAX-ACCESS read-write
    STATUS current
    DESCRIPTION
        "Specify the maximum NSS index for 802.11ac supported rates.
        The specified maximum NSS index for 802.11ac supported rates must be no
        less than the specified maximum NSS index for 802.11ac mandatory rates."
    DEFVAL { 8 }
    ::= { hh3cDot11RRMGlobalCfgPara 13 }

hh3cDot11RRM11acMultiCastNss OBJECT-TYPE
    SYNTAX Integer32 (0..8)
    MAX-ACCESS read-write
    STATUS current
    DESCRIPTION
        "Specify the NSS index for 802.11ac multicast rates.
        The value 0 indicates that no NSS index is specified.
        No NSS index is specified for 802.11ac multicast rates by default.
        The specified NSS index for 802.11ac multicast rates must be no less
        than the specified maximum NSS index for 802.11ac mandatory rates.
        Before configuring the NSS index for 802.11ac multicast rates, the maximum
        NSS index for 802.11ac mandatory rates must be configured.
        Besides, it must be configured together with the node below."
    DEFVAL { 0 }
    ::= { hh3cDot11RRMGlobalCfgPara 14 }

hh3cDot11RRM11acMultiCastVhtMcs OBJECT-TYPE
    SYNTAX Integer32 (0..9 | 255)
    MAX-ACCESS read-write
    STATUS current
    DESCRIPTION
        "Specify the MCS index for 802.11ac multicast rates.
        The value 255 indicates that no MCS index is specified.
        No MCS index is specified for 802.11ac multicast rates by default.
        Besides, it must be configured together with the node above."
    DEFVAL { 255 }
    ::= { hh3cDot11RRMGlobalCfgPara 15 }

hh3cDot11RRMRadioCfgTable OBJECT-TYPE
    SYNTAX SEQUENCE OF Hh3cDot11RRMRadioCfgEntry
    MAX-ACCESS not-accessible
    STATUS current
    DESCRIPTION
        "Configure WLAN RRM based radio type.
        When 802.11b parameter is modified, 802.11g parameter will be
        changed at the same time.
        In the same way, when 802.11g parameter is modified, 802.11b parameter
        will be changed at the same time."
    ::= { hh3cDot11RRMConfigGroup 2 }

hh3cDot11RRMRadioCfgEntry OBJECT-TYPE
    SYNTAX Hh3cDot11RRMRadioCfgEntry
    MAX-ACCESS not-accessible
    STATUS current
    DESCRIPTION
        "Configure WLAN RRM based radio type.
        When 802.11b parameter is modified, 802.11g parameter will be
        changed at the same time.
        In the same way, when 802.11g parameter is modified, 802.11b parameter
        will be changed at the same time."
    INDEX { hh3cDot11RRMRadioType }
    ::= { hh3cDot11RRMRadioCfgTable 1 }

Hh3cDot11RRMRadioCfgEntry ::=
    SEQUENCE {
        hh3cDot11RRMRadioType
            Hh3cDot11RadioType,
        hh3cDot11RRMCfgChlState
            TruthValue,
        hh3cDot11RRMCfgChlMode
            INTEGER,
        hh3cDot11RRMChlProntoRadioElmt
            Unsigned32,
        hh3cDot11RRMCfgPwrState
            TruthValue,
        hh3cDot11RRMCfgPwrMode
            INTEGER,
        hh3cDot11RRMPwrProntoRadioElmt
            Unsigned32,
        hh3cDot11RRMCfgIntrvl
            Integer32,
        hh3cDot11RRMCfgIntrfThres
            Integer32,
        hh3cDot11RRMCfgNoiseThres
            Integer32,
        hh3cDot11RRMCfgPERThres
            Integer32,
        hh3cDot11RRMCfgToleranceFctr
            Integer32,
        hh3cDot11RRMCfgAdjacencyFctr
            Integer32
     }

hh3cDot11RRMRadioType OBJECT-TYPE
    SYNTAX Hh3cDot11RadioType
    MAX-ACCESS not-accessible
    STATUS current
    DESCRIPTION
        "802.11 radio type."
    ::= { hh3cDot11RRMRadioCfgEntry 1 }

hh3cDot11RRMCfgChlState OBJECT-TYPE
    SYNTAX TruthValue
    MAX-ACCESS read-write
    STATUS current
    DESCRIPTION
        "Enable/Disable dynamic channel selection."
    DEFVAL { false }
    ::= { hh3cDot11RRMRadioCfgEntry 2 }

hh3cDot11RRMCfgChlMode OBJECT-TYPE
    SYNTAX INTEGER
        {
        selfDecisive(1),
        userTriggered(2)
        }
    MAX-ACCESS read-write
    STATUS current
    DESCRIPTION
        "Configure the mode of channel selection.
        This node can be configured only when dynamic channel selection
        is enabled."
    DEFVAL { userTriggered }
    ::= { hh3cDot11RRMRadioCfgEntry 3 }

hh3cDot11RRMChlProntoRadioElmt OBJECT-TYPE
    SYNTAX Unsigned32
    MAX-ACCESS read-write
    STATUS current
    DESCRIPTION
        "Specify the AP and radio that will change channel at next
        calibration cycle.
        0 is returned when getting the value of this node.
        This node can be configured only when the mode of channel selection
        control is user-triggered.
        When configuring, the higher 24 bits stand for the AP index,
        and the last 8 bits stand for the radio index.
        4294967295 stand for configuring each radio on all APs."
    DEFVAL { 0 }
    ::= { hh3cDot11RRMRadioCfgEntry 4 }

hh3cDot11RRMCfgPwrState OBJECT-TYPE
    SYNTAX TruthValue
    MAX-ACCESS read-write
    STATUS current
    DESCRIPTION
        "Enable/Disable dynamic power selection for the band."
    DEFVAL { false }
    ::= { hh3cDot11RRMRadioCfgEntry 5 }

hh3cDot11RRMCfgPwrMode OBJECT-TYPE
    SYNTAX INTEGER
        {
        selfDecisive(1),
        userTriggered(2)
        }
    MAX-ACCESS read-write
    STATUS current
    DESCRIPTION
        "Configure the mode of transmit power control.
        This node can be configured only when dynamic power selection
        is enabled."
    DEFVAL { userTriggered }
    ::= { hh3cDot11RRMRadioCfgEntry 6 }

hh3cDot11RRMPwrProntoRadioElmt OBJECT-TYPE
    SYNTAX Unsigned32
    MAX-ACCESS read-write
    STATUS current
    DESCRIPTION
        "Specify the AP and radio that will change power at next
        calibration cycle.
        0 is returned when getting the value of this node.
        This node can be configured only when the mode of transmit power
        control is user-triggered.
        When configuring, the higher 24 bits stand for the AP index,
        and the last 8 bits stand for the radio index.
        4294967295 stand for configuring each radio on all APs."
    DEFVAL { 0 }
    ::= { hh3cDot11RRMRadioCfgEntry 7 }

hh3cDot11RRMCfgIntrvl OBJECT-TYPE
    SYNTAX Integer32
    UNITS "minute"
    MAX-ACCESS read-write
    STATUS current
    DESCRIPTION
        "Configure the calibration interval."
    DEFVAL { 8 }
    ::= { hh3cDot11RRMRadioCfgEntry 8 }

hh3cDot11RRMCfgIntrfThres OBJECT-TYPE
    SYNTAX Integer32 (1..100)
    UNITS "percent"
    MAX-ACCESS read-write
    STATUS current
    DESCRIPTION
        "Configure the interface threshold.
        By default, interference observed on an operating channel is considered
        during dynamic frequency selection and transmit power control.  If the
        interference percentage on the channel reaches the set threshold, RRM
        will perform resource adjustment to control the situation."
    DEFVAL { 50 }
    ::= { hh3cDot11RRMRadioCfgEntry 9 }

hh3cDot11RRMCfgNoiseThres OBJECT-TYPE
    SYNTAX Integer32 (-127..127)
    MAX-ACCESS read-write
    STATUS current
    DESCRIPTION
        "Configure the noise threshold."
    DEFVAL { -70 }
    ::= { hh3cDot11RRMRadioCfgEntry 10 }

hh3cDot11RRMCfgPERThres OBJECT-TYPE
    SYNTAX Integer32 (1..100)
    UNITS "percent"
    MAX-ACCESS read-write
    STATUS current
    DESCRIPTION
        "Configure the CRC error threshold.
        If the percentage of CRC errors reaches the threshold, RRM will perform
        resource adjustment to control the situation."
    DEFVAL { 20 }
    ::= { hh3cDot11RRMRadioCfgEntry 11 }

hh3cDot11RRMCfgToleranceFctr OBJECT-TYPE
    SYNTAX Integer32 (1..45)
    UNITS "percent"
    MAX-ACCESS read-write
    STATUS current
    DESCRIPTION
        "Configure the tolerance level.
        During dynamic frequency selection (DFS), the channel will be changed
        only if there is a better channel having lesser interference and packet
        error rate than those specified by the user."
    DEFVAL { 20 }
    ::= { hh3cDot11RRMRadioCfgEntry 12 }

hh3cDot11RRMCfgAdjacencyFctr OBJECT-TYPE
    SYNTAX Integer32 (1..16)
    MAX-ACCESS read-write
    STATUS current
    DESCRIPTION
        "Configure the adjacency factor for the band.
        If transmit power control (TPC) is configured, power will be adjusted
        when the nth neighbor is detected.  The value n is the adjacency factor."
    DEFVAL { 3 }
    ::= { hh3cDot11RRMRadioCfgEntry 13 }

hh3cDot11RRMAPCfgTable OBJECT-TYPE
    SYNTAX SEQUENCE OF Hh3cDot11RRMAPCfgEntry
    MAX-ACCESS not-accessible
    STATUS current
    DESCRIPTION
        "This table defines the RRM parameters for AP."
    ::= { hh3cDot11RRMConfigGroup 3 }

hh3cDot11RRMAPCfgEntry OBJECT-TYPE
    SYNTAX Hh3cDot11RRMAPCfgEntry
    MAX-ACCESS not-accessible
    STATUS current
    DESCRIPTION
        "Each entry contains information of RRM parameters for AP."
    INDEX { hh3cDot11APElementIndex }
    ::= { hh3cDot11RRMAPCfgTable 1 }

Hh3cDot11RRMAPCfgEntry ::=
    SEQUENCE {
        hh3cDot11RRMAPWorkMode
          INTEGER
    }

hh3cDot11RRMAPWorkMode OBJECT-TYPE
    SYNTAX INTEGER
        {
        normal(1),
        monitor(2),
        hybrid(3)
        }
    MAX-ACCESS read-write
    STATUS current
    DESCRIPTION
        "AP work mode."
    ::= { hh3cDot11RRMAPCfgEntry 1 }

hh3cDot11RRMSDRadioGroupTable OBJECT-TYPE
    SYNTAX SEQUENCE OF Hh3cDot11RRMSDRadioGroupEntry
    MAX-ACCESS not-accessible
    STATUS current
    DESCRIPTION
        "This table defines RRM self-decisive radio group."
    ::= { hh3cDot11RRMConfigGroup 4 }

hh3cDot11RRMSDRadioGroupEntry OBJECT-TYPE
    SYNTAX      Hh3cDot11RRMSDRadioGroupEntry
    MAX-ACCESS  not-accessible
    STATUS      current
    DESCRIPTION
        "Each entry contains information of one RRM self-decisive radio group."
    INDEX
        {
            hh3cDot11RRMSDRadioGroupId
        }
    ::= { hh3cDot11RRMSDRadioGroupTable 1 }

Hh3cDot11RRMSDRadioGroupEntry ::= SEQUENCE
    {
        hh3cDot11RRMSDRadioGroupId             Unsigned32,
        hh3cDot11RRMSDRadioGroupDesc           OCTET STRING,
        hh3cDot11RRMSDRdGrpChlHolddownTm       Unsigned32,
        hh3cDot11RRMSDRdGrpPwrHolddownTm       Unsigned32,
        hh3cDot11RRMSDRdGroupRowStatus         RowStatus
    }

hh3cDot11RRMSDRadioGroupId OBJECT-TYPE
    SYNTAX      Unsigned32
    MAX-ACCESS  not-accessible
    STATUS      current
    DESCRIPTION
        "Represents RRM self-decisive radio group ID."
    ::= { hh3cDot11RRMSDRadioGroupEntry 1 }

hh3cDot11RRMSDRadioGroupDesc OBJECT-TYPE
    SYNTAX      OCTET STRING
    MAX-ACCESS  read-create
    STATUS      current
    DESCRIPTION
        "Represents the description of RRM self-decisive radio group."
    ::= { hh3cDot11RRMSDRadioGroupEntry 2 }

hh3cDot11RRMSDRdGrpChlHolddownTm OBJECT-TYPE
    SYNTAX      Unsigned32
    UNITS       "minute"
    MAX-ACCESS  read-create
    STATUS      current
    DESCRIPTION
        "Represents the channel holddown time of RRM self-decisive radio group."
    ::= { hh3cDot11RRMSDRadioGroupEntry 3 }

hh3cDot11RRMSDRdGrpPwrHolddownTm OBJECT-TYPE
    SYNTAX      Unsigned32
    UNITS       "minute"
    MAX-ACCESS  read-create
    STATUS      current
    DESCRIPTION
        "Represents the power holddown time of RRM self-decisive radio group."
    ::= { hh3cDot11RRMSDRadioGroupEntry 4 }

hh3cDot11RRMSDRdGroupRowStatus OBJECT-TYPE
    SYNTAX      RowStatus
    MAX-ACCESS  read-create
    STATUS      current
    DESCRIPTION
        "The row status of this table entry."
    ::= { hh3cDot11RRMSDRadioGroupEntry 5 }

hh3cDot11RRMAPCfg2Table OBJECT-TYPE
    SYNTAX SEQUENCE OF Hh3cDot11RRMAPCfg2Entry
    MAX-ACCESS not-accessible
    STATUS current
    DESCRIPTION
        "This table defines the RRM parameters for AP."
    ::= { hh3cDot11RRMConfigGroup 5 }

hh3cDot11RRMAPCfg2Entry OBJECT-TYPE
    SYNTAX Hh3cDot11RRMAPCfg2Entry
    MAX-ACCESS not-accessible
    STATUS current
    DESCRIPTION
        "Each entry contains information of RRM parameters for AP."
    INDEX { hh3cDot11RRMAPSerialID }
    ::= { hh3cDot11RRMAPCfg2Table 1 }

Hh3cDot11RRMAPCfg2Entry ::=
    SEQUENCE {
        hh3cDot11RRMAPSerialID
            Hh3cDot11ObjectIDType,
        hh3cDot11RRMAPIntfThreshold
            Integer32,
        hh3cDot11RRMStaIntfThreshold
            Integer32,
        hh3cDot11RRMCoChlIntfTrapThhd
            Integer32,
        hh3cDot11RRMAdjChlIntfTrapThhd
            Integer32
    }

hh3cDot11RRMAPSerialID OBJECT-TYPE
    SYNTAX Hh3cDot11ObjectIDType
    MAX-ACCESS not-accessible
    STATUS current
    DESCRIPTION
        "Serial ID of the AP."
    ::= { hh3cDot11RRMAPCfg2Entry 1 }

hh3cDot11RRMAPIntfThreshold OBJECT-TYPE
    SYNTAX Integer32
    MAX-ACCESS read-write
    STATUS current
    DESCRIPTION
        "Represents threshold of AP interference .
         If the number of AP interference exceeds this threshold,
         AP interference trap will be sent."
    ::= { hh3cDot11RRMAPCfg2Entry 2 }

hh3cDot11RRMStaIntfThreshold OBJECT-TYPE
    SYNTAX Integer32
    MAX-ACCESS read-write
    STATUS current
    DESCRIPTION
        "Represents threshold of STA interference.
         If the number of STA interference exceeds this threshold,
         station interference trap will be sent."
    ::= { hh3cDot11RRMAPCfg2Entry 3 }

hh3cDot11RRMCoChlIntfTrapThhd OBJECT-TYPE
    SYNTAX      Integer32
    UNITS       "dbm"
    MAX-ACCESS  read-write
    STATUS      current
    DESCRIPTION
        "Represents threshold of interference trap with current ap.
        If signal strength of the device exceeds this threshold,
        corresponding trap will be sent."
    ::= { hh3cDot11RRMAPCfg2Entry 4 }


hh3cDot11RRMAdjChlIntfTrapThhd OBJECT-TYPE
    SYNTAX      Integer32
    UNITS       "dbm"
    MAX-ACCESS  read-write
    STATUS      current
    DESCRIPTION
        "Represents threshold of adjacent interference trap with current ap.
        If signal strength of the device exceeds this threshold,
        corresponding trap will be sent."
    ::= { hh3cDot11RRMAPCfg2Entry 5 }

hh3cDot11RRMDetectGroup OBJECT IDENTIFIER ::= { hh3cDot11RRM 2 }

hh3cDot11RRMChlRptTable OBJECT-TYPE
    SYNTAX SEQUENCE OF Hh3cDot11RRMChlRptEntry
    MAX-ACCESS not-accessible
    STATUS current
    DESCRIPTION
        "This table shows the RRM channel information of each radio
        on all APs."
    ::= { hh3cDot11RRMDetectGroup 1 }

hh3cDot11RRMChlRptEntry OBJECT-TYPE
    SYNTAX Hh3cDot11RRMChlRptEntry
    MAX-ACCESS not-accessible
    STATUS current
    DESCRIPTION
        "Each entry contains information of RRM channel information
        of the radio on the AP."
    INDEX { hh3cDot11RRMRadioIndex, hh3cDot11RRMChlRptChlNum }
    ::= { hh3cDot11RRMChlRptTable 1 }

Hh3cDot11RRMChlRptEntry ::=
    SEQUENCE {
        hh3cDot11RRMRadioIndex
            Hh3cDot11RadioElementIndex,
        hh3cDot11RRMChlRptChlNum
            Integer32,
        hh3cDot11RRMChlRptChlType
            INTEGER,
        hh3cDot11RRMChlRptChlQlty
            INTEGER,
        hh3cDot11RRMChlRptNbrCnt
            Integer32,
        hh3cDot11RRMChlRptLoad
            Integer32,
        hh3cDot11RRMChlRptUtlz
            Integer32,
        hh3cDot11RRMChlRptIntrf
            Integer32,
        hh3cDot11RRMChlRptPER
            Integer32,
        hh3cDot11RRMChlRptRetryRate
            Integer32,
        hh3cDot11RRMChlRptNoise
            Integer32,
        hh3cDot11RRMChlRptRadarIndtcr
            INTEGER
     }

hh3cDot11RRMRadioIndex OBJECT-TYPE
    SYNTAX Hh3cDot11RadioElementIndex
    MAX-ACCESS accessible-for-notify
    STATUS current
    DESCRIPTION
        "Represents index of the radio."
    ::= { hh3cDot11RRMChlRptEntry 1 }

hh3cDot11RRMChlRptChlNum OBJECT-TYPE
    SYNTAX Integer32
    MAX-ACCESS accessible-for-notify
    STATUS current
    DESCRIPTION
        "Channel number."
    ::= { hh3cDot11RRMChlRptEntry 2 }

hh3cDot11RRMChlRptChlType OBJECT-TYPE
    SYNTAX INTEGER
        {
        primeChannel(1),
        offChannel(2)
        }
    MAX-ACCESS read-only
    STATUS current
    DESCRIPTION
        "Channel type."
    ::= { hh3cDot11RRMChlRptEntry 3 }

hh3cDot11RRMChlRptChlQlty OBJECT-TYPE
    SYNTAX INTEGER
        {
        good(1),
        bad(2)
        }
    MAX-ACCESS read-only
    STATUS current
    DESCRIPTION
        "Channel quality."
    ::= { hh3cDot11RRMChlRptEntry 4 }

hh3cDot11RRMChlRptNbrCnt OBJECT-TYPE
    SYNTAX Integer32
    MAX-ACCESS read-only
    STATUS current
    DESCRIPTION
        "Number of neighbors found on the channel."
    ::= { hh3cDot11RRMChlRptEntry 5 }

hh3cDot11RRMChlRptLoad OBJECT-TYPE
    SYNTAX Integer32 (0..100)
    UNITS "percent"
    MAX-ACCESS read-only
    STATUS current
    DESCRIPTION
        "Load observed on the channel in percentage."
    ::= { hh3cDot11RRMChlRptEntry 6 }

hh3cDot11RRMChlRptUtlz OBJECT-TYPE
    SYNTAX Integer32 (0..100)
    UNITS "percent"
    MAX-ACCESS read-only
    STATUS current
    DESCRIPTION
        "Utilization of the channel in percentage."
    ::= { hh3cDot11RRMChlRptEntry 7 }

hh3cDot11RRMChlRptIntrf OBJECT-TYPE
    SYNTAX Integer32 (0..100)
    UNITS "percent"
    MAX-ACCESS read-only
    STATUS current
    DESCRIPTION
        "Interference observed on the channel in percentage."
    ::= { hh3cDot11RRMChlRptEntry 8 }

hh3cDot11RRMChlRptPER OBJECT-TYPE
    SYNTAX Integer32 (0..100)
    UNITS "percent"
    MAX-ACCESS read-only
    STATUS current
    DESCRIPTION
        "Packet error rate observed on the channel in percentage."
    ::= { hh3cDot11RRMChlRptEntry 9 }

hh3cDot11RRMChlRptRetryRate OBJECT-TYPE
    SYNTAX Integer32 (0..100)
    UNITS "percent"
    MAX-ACCESS read-only
    STATUS current
    DESCRIPTION
        "Percentage of retransmission happened on the channel."
    ::= { hh3cDot11RRMChlRptEntry 10 }

hh3cDot11RRMChlRptNoise OBJECT-TYPE
    SYNTAX Integer32
    MAX-ACCESS read-only
    STATUS current
    DESCRIPTION
        "Noise observed on the channel."
    ::= { hh3cDot11RRMChlRptEntry 11 }

hh3cDot11RRMChlRptRadarIndtcr OBJECT-TYPE
    SYNTAX INTEGER
        {
        detected(1),
        notDetected(2)
        }
    MAX-ACCESS read-write
    STATUS current
    DESCRIPTION
        "Radar detection status."
    ::= { hh3cDot11RRMChlRptEntry 12 }

hh3cDot11RRMNbrInfoTable OBJECT-TYPE
    SYNTAX SEQUENCE OF Hh3cDot11RRMNbrInfoEntry
    MAX-ACCESS not-accessible
    STATUS current
    DESCRIPTION
        "This table shows the RRM neighbor information of each radio
        on all APs."
    ::= { hh3cDot11RRMDetectGroup 2 }

hh3cDot11RRMNbrInfoEntry OBJECT-TYPE
    SYNTAX Hh3cDot11RRMNbrInfoEntry
    MAX-ACCESS not-accessible
    STATUS current
    DESCRIPTION
        "Each entry contains information of RRM neighbor information
        of the radio on an AP."
    INDEX { hh3cDot11RRMRadioIndex, hh3cDot11RrmNbrBSSID }
    ::= { hh3cDot11RRMNbrInfoTable 1 }

Hh3cDot11RRMNbrInfoEntry ::=
    SEQUENCE {
        hh3cDot11RrmNbrBSSID
            MacAddress,
        hh3cDot11RrmNbrChl
            Hh3cDot11ChannelScopeType,
        hh3cDot11RRMNbrIntrf
            Integer32,
        hh3cDot11RrmNbrRSSI
            Integer32,
        hh3cDot11RrmNbrType
            INTEGER,
        hh3cDot11RrmNbrSSID
            Hh3cDot11SSIDStringType,
        hh3cDot11RrmNbrSNR
            Integer32,
        hh3cDot11RrmNbrNF
            Integer32
     }

hh3cDot11RrmNbrBSSID OBJECT-TYPE
    SYNTAX MacAddress
    MAX-ACCESS not-accessible
    STATUS current
    DESCRIPTION
        "MAC address of the AP."
    ::= { hh3cDot11RRMNbrInfoEntry 1 }

hh3cDot11RrmNbrChl OBJECT-TYPE
    SYNTAX Hh3cDot11ChannelScopeType
    MAX-ACCESS read-only
    STATUS current
    DESCRIPTION
        "Channel number on which the neighbor was found."
    ::= { hh3cDot11RRMNbrInfoEntry 2 }

hh3cDot11RRMNbrIntrf OBJECT-TYPE
    SYNTAX Integer32 (0..100)
    UNITS "percent"
    MAX-ACCESS read-only
    STATUS current
    DESCRIPTION
        "Interference observed on the channel in percentage by neighbor."
    ::= { hh3cDot11RRMNbrInfoEntry 3 }

hh3cDot11RrmNbrRSSI OBJECT-TYPE
    SYNTAX Integer32
    UNITS "dBm"
    MAX-ACCESS read-only
    STATUS current
    DESCRIPTION
        "Signal strength of the AP in dBm."
    ::= { hh3cDot11RRMNbrInfoEntry 4 }

hh3cDot11RrmNbrType OBJECT-TYPE
    SYNTAX INTEGER
        {
        managed(1),
        unmanaged(2)
        }
    MAX-ACCESS read-only
    STATUS current
    DESCRIPTION
        "Type of the AP, managed or unmanaged."
    ::= { hh3cDot11RRMNbrInfoEntry 5 }

hh3cDot11RrmNbrSSID OBJECT-TYPE
    SYNTAX Hh3cDot11SSIDStringType
    MAX-ACCESS read-only
    STATUS current
    DESCRIPTION
        "SSID of the Neighbor."
    ::= { hh3cDot11RRMNbrInfoEntry 6 }

hh3cDot11RrmNbrSNR OBJECT-TYPE
    SYNTAX Integer32
    UNITS "dB"
    MAX-ACCESS read-only
    STATUS current
    DESCRIPTION
        "Signal to noise ratio of the AP in dB."
    ::= { hh3cDot11RRMNbrInfoEntry 7 }

hh3cDot11RrmNbrNF OBJECT-TYPE
    SYNTAX Integer32
    UNITS "dBm"
    MAX-ACCESS read-only
    STATUS current
    DESCRIPTION
        "Noise floor of the AP in dBm."
    ::= { hh3cDot11RRMNbrInfoEntry 8 }

hh3cDot11RRMHistoryTable OBJECT-TYPE
    SYNTAX SEQUENCE OF Hh3cDot11RRMHistoryEntry
    MAX-ACCESS not-accessible
    STATUS current
    DESCRIPTION
        "This table shows the details of the latest three channel changes
        and power changes applied on all APs, including time of change,
        reason of the change and the channel, power, interference parameters."
    ::= { hh3cDot11RRMDetectGroup 3 }

hh3cDot11RRMHistoryEntry OBJECT-TYPE
    SYNTAX Hh3cDot11RRMHistoryEntry
    MAX-ACCESS not-accessible
    STATUS current
    DESCRIPTION
        "Each entry shows the details of channel and power changes."
    INDEX { hh3cDot11RRMRadioIndex,
            hh3cDot11RRMHistoryId,
            hh3cDot11RRMHistoryRecIndctr }
    ::= { hh3cDot11RRMHistoryTable 1 }

Hh3cDot11RRMHistoryEntry ::=
    SEQUENCE {
        hh3cDot11RRMHistoryId
            Integer32,
        hh3cDot11RRMHistoryRecIndctr
            INTEGER,
        hh3cDot11RRMHistoryChl
            Hh3cDot11ChannelScopeType,
        hh3cDot11RRMHistoryPwr
            Integer32,
        hh3cDot11RRMHistoryLoad
            Integer32,
        hh3cDot11RRMHistoryUtlz
            Integer32,
        hh3cDot11RRMHistoryIntrf
            Integer32,
        hh3cDot11RRMHistoryNoise
            Integer32,
        hh3cDot11RRMHistoryPER
            Integer32,
        hh3cDot11RRMHistoryRetryRate
            Integer32,
        hh3cDot11RRMHistoryChgReason
            BITS,
        hh3cDot11RRMHistoryChgDateTime
            DateAndTime
     }

hh3cDot11RRMHistoryId OBJECT-TYPE
    SYNTAX Integer32
    MAX-ACCESS not-accessible
    STATUS current
    DESCRIPTION
        "History number of the change."
    ::= { hh3cDot11RRMHistoryEntry 1 }

hh3cDot11RRMHistoryRecIndctr OBJECT-TYPE
    SYNTAX INTEGER
        {
        before(1),
        after(2)
        }
    MAX-ACCESS not-accessible
    STATUS current
    DESCRIPTION
        "History record type of the change."
    ::= { hh3cDot11RRMHistoryEntry 2 }

hh3cDot11RRMHistoryChl OBJECT-TYPE
    SYNTAX Hh3cDot11ChannelScopeType
    MAX-ACCESS read-only
    STATUS current
    DESCRIPTION
        "Channel on which the radio operates before/after the change
        of channel or power."
    ::= { hh3cDot11RRMHistoryEntry 3 }

hh3cDot11RRMHistoryPwr OBJECT-TYPE
    SYNTAX Integer32
    UNITS "dBm"
    MAX-ACCESS read-only
    STATUS current
    DESCRIPTION
        "Power of the radio before/after the change of channel or
        power."
    ::= { hh3cDot11RRMHistoryEntry 4 }

hh3cDot11RRMHistoryLoad OBJECT-TYPE
    SYNTAX Integer32 (0..100)
    UNITS "percent"
    MAX-ACCESS read-only
    STATUS current
    DESCRIPTION
        "Load observed on the radio in percentage before/after the
        change of channel or power."
    ::= { hh3cDot11RRMHistoryEntry 5 }

hh3cDot11RRMHistoryUtlz OBJECT-TYPE
    SYNTAX Integer32 (0..100)
    UNITS "percent"
    MAX-ACCESS read-only
    STATUS current
    DESCRIPTION
        "Utilization of the radio in percentage before/after the
        change of channel or power."
    ::= { hh3cDot11RRMHistoryEntry 6 }

hh3cDot11RRMHistoryIntrf OBJECT-TYPE
    SYNTAX Integer32 (0..100)
    UNITS "percent"
    MAX-ACCESS read-only
    STATUS current
    DESCRIPTION
        "Interference observed on the radio in percentage
        before/after the change of channel or power."
    ::= { hh3cDot11RRMHistoryEntry 7 }

hh3cDot11RRMHistoryNoise OBJECT-TYPE
    SYNTAX Integer32
    MAX-ACCESS read-only
    STATUS current
    DESCRIPTION
        "Noise observed on the radio before/after the change
        of channel or power."
    ::= { hh3cDot11RRMHistoryEntry 8 }

hh3cDot11RRMHistoryPER OBJECT-TYPE
    SYNTAX Integer32 (0..100)
    UNITS "percent"
    MAX-ACCESS read-only
    STATUS current
    DESCRIPTION
        "Packet error rate observed on the radio in percentage
        before/after the change of channel or power."
    ::= { hh3cDot11RRMHistoryEntry 9 }

hh3cDot11RRMHistoryRetryRate OBJECT-TYPE
    SYNTAX Integer32 (0..100)
    UNITS "percent"
    MAX-ACCESS read-only
    STATUS current
    DESCRIPTION
        "Percentage of retransmission happened on the radio
        before/after the change of channel or power."
    ::= { hh3cDot11RRMHistoryEntry 10 }

hh3cDot11RRMHistoryChgReason OBJECT-TYPE
    SYNTAX BITS
        {
        others(0),
        coverage(1),
        radar(2),
        retransmission(3),
        packetsDiscarded(4),
        interference(5)
        }
    MAX-ACCESS read-only
    STATUS current
    DESCRIPTION
        "Reason for the change of channel or power.
        The various bit positions are:
        |0        |Others                    |
        |1        |Coverage                  |
        |2        |Radar                     |
        |3        |Retransmission            |
        |4        |Packets discarded         |
        |5        |Interference              |
        0 is returned when the history record type is after."
    ::= { hh3cDot11RRMHistoryEntry 11 }

hh3cDot11RRMHistoryChgDateTime OBJECT-TYPE
    SYNTAX DateAndTime
    MAX-ACCESS read-only
    STATUS current
    DESCRIPTION
        "The time when the channel or power change occurred."
    ::= { hh3cDot11RRMHistoryEntry 12 }

hh3cDot11RRMRadioNbrInfoTable OBJECT-TYPE
    SYNTAX SEQUENCE OF Hh3cDot11RRMRadioNbrInfoEntry
    MAX-ACCESS not-accessible
    STATUS current
    DESCRIPTION
        "This table shows the RRM neighbor information of each radio
        on all APs."
    ::= { hh3cDot11RRMDetectGroup 4 }

hh3cDot11RRMRadioNbrInfoEntry OBJECT-TYPE
    SYNTAX Hh3cDot11RRMRadioNbrInfoEntry
    MAX-ACCESS not-accessible
    STATUS current
    DESCRIPTION
        "Each entry contains information of RRM neighbor information
        of the radio on an AP."
    INDEX { hh3cDot11RRMRadioNbrAPID, hh3cDot11RRMRadioNbrRadioID }
    ::= { hh3cDot11RRMRadioNbrInfoTable 1 }

Hh3cDot11RRMRadioNbrInfoEntry ::=
    SEQUENCE {
        hh3cDot11RRMRadioNbrAPID
            Hh3cDot11ObjectIDType,
        hh3cDot11RRMRadioNbrRadioID
            Hh3cDot11RadioScopeType,
        hh3cDot11RRMRadioNbrSSID
            OCTET STRING
     }

hh3cDot11RRMRadioNbrAPID OBJECT-TYPE
    SYNTAX Hh3cDot11ObjectIDType
    MAX-ACCESS not-accessible
    STATUS current
    DESCRIPTION
        "AP serial id."
    ::= { hh3cDot11RRMRadioNbrInfoEntry 1 }

hh3cDot11RRMRadioNbrRadioID OBJECT-TYPE
    SYNTAX Hh3cDot11RadioScopeType
    MAX-ACCESS not-accessible
    STATUS current
    DESCRIPTION
        "Radio Id on AP."
    ::= { hh3cDot11RRMRadioNbrInfoEntry 2 }

hh3cDot11RRMRadioNbrSSID OBJECT-TYPE
    SYNTAX  OCTET STRING
    MAX-ACCESS read-only
    STATUS current
    DESCRIPTION
        "All neighbour SSIDs scanned by the selected radio."
    ::= { hh3cDot11RRMRadioNbrInfoEntry 3 }

hh3cDot11RRMNotifyGroup OBJECT IDENTIFIER ::= { hh3cDot11RRM 3 }

hh3cDot11RRMChlQltyNotifications OBJECT IDENTIFIER ::= { hh3cDot11RRMNotifyGroup 1 }

hh3cDot11RRMChlQltyNtfPrefix OBJECT IDENTIFIER ::= { hh3cDot11RRMChlQltyNotifications 0 }

hh3cDot11RRMIntrfLimit NOTIFICATION-TYPE
    OBJECTS { hh3cDot11RRMChlRptIntrf }
    STATUS current
    DESCRIPTION
        "This notification will be sent when interference on the radio
        exceeds the limit."
    ::= { hh3cDot11RRMChlQltyNtfPrefix 1 }

hh3cDot11RRMPERLimit NOTIFICATION-TYPE
    OBJECTS { hh3cDot11RRMChlRptPER }
    STATUS current
    DESCRIPTION
        "This notification will be sent when packet error rate on the
        radio exceeds the limit."
    ::= { hh3cDot11RRMChlQltyNtfPrefix 2 }

hh3cDot11RRMNoiseLimit NOTIFICATION-TYPE
    OBJECTS { hh3cDot11RRMChlRptNoise }
    STATUS current
    DESCRIPTION
        "This notification will be sent when noise on the radio exceeds
        the limit."
    ::= { hh3cDot11RRMChlQltyNtfPrefix 3 }

hh3cDot11RRMResChgNotifications OBJECT IDENTIFIER ::= { hh3cDot11RRMNotifyGroup 2 }

hh3cDot11RRMResChgNtfPrefix OBJECT IDENTIFIER ::= { hh3cDot11RRMResChgNotifications 0 }

hh3cDot11RRMPowerChange NOTIFICATION-TYPE
    OBJECTS { hh3cDot11RRMRadioIndex, hh3cDot11NewPower, hh3cDot11OldPower }
    STATUS current
    DESCRIPTION
        "This notification will be sent when power changed on the radio
        automatically."
    ::= { hh3cDot11RRMResChgNtfPrefix 1 }

hh3cDot11RRMNotificationsVar OBJECT IDENTIFIER ::= { hh3cDot11RRMNotifyGroup 3 }

hh3cDot11NewPower OBJECT-TYPE
    SYNTAX Integer32
    MAX-ACCESS accessible-for-notify
    STATUS current
    DESCRIPTION
        "Power of the radio after the change of power."
    ::= { hh3cDot11RRMNotificationsVar 1 }

hh3cDot11OldPower OBJECT-TYPE
    SYNTAX Integer32
    MAX-ACCESS accessible-for-notify
    STATUS current
    DESCRIPTION
        "Power of the radio before the change of power."
    ::= { hh3cDot11RRMNotificationsVar 2 }

hh3cDot11MonitorDetectedGroup OBJECT IDENTIFIER ::= { hh3cDot11RRM 4 }

hh3cDot11MonitorDetectedDevTable OBJECT-TYPE
    SYNTAX SEQUENCE OF Hh3cDot11MonitorDetectedDevEntry
    MAX-ACCESS not-accessible
    STATUS current
    DESCRIPTION
        "This table shows the devices of AP detected"
    ::= { hh3cDot11MonitorDetectedGroup 1 }

hh3cDot11MonitorDetectedDevEntry OBJECT-TYPE
    SYNTAX      Hh3cDot11MonitorDetectedDevEntry
    MAX-ACCESS  not-accessible
    STATUS      current
    DESCRIPTION
        "Each entry contains information of detected devices."
    INDEX
        {
            hh3cDot11MonitorDevMAC, hh3cDot11APElementIndex
        }
    ::= { hh3cDot11MonitorDetectedDevTable 1 }

Hh3cDot11MonitorDetectedDevEntry ::=
    SEQUENCE {
        hh3cDot11MonitorDevMAC
            MacAddress,
        hh3cDot11MonitorDevType
            INTEGER,
        hh3cDot11MonitorDevVendor
            OCTET STRING,
        hh3cDot11MonitorDevSSID
            OCTET STRING,
        hh3cDot11MonitorDevBSSID
            MacAddress,
        hh3cDot11MonitorDevChannel
            Hh3cDot11ChannelScopeType,
        hh3cDot11MonitorRadioId
            Hh3cDot11RadioScopeType,
        hh3cDot11MonitorDevMaxRSSI
            Integer32,
        hh3cDot11MonitorDevBeaconIntvl
            Integer32,
        hh3cDot11MonitorDevFstDctTime
            DateAndTime,
        hh3cDot11MonitorDevLstDctTime
            DateAndTime,
        hh3cDot11MonitorDevClear
            TruthValue,
        hh3cDot11MonitorDevSNR
            Integer32
     }

hh3cDot11MonitorDevMAC OBJECT-TYPE
    SYNTAX      MacAddress
    MAX-ACCESS  not-accessible
    STATUS      current
    DESCRIPTION
        "Represents MAC address of the device detected."
    ::= { hh3cDot11MonitorDetectedDevEntry 1 }

hh3cDot11MonitorDevType OBJECT-TYPE
    SYNTAX      INTEGER
                {
                    client(1),
                    ap(2),
                    adhoc(3),
                    wirelessBridge(4),
                    unknown(5)
                }
    MAX-ACCESS  read-only
    STATUS      current
    DESCRIPTION
        "Represents type of the device detected."
    ::= { hh3cDot11MonitorDetectedDevEntry 2 }

hh3cDot11MonitorDevVendor OBJECT-TYPE
    SYNTAX      OCTET STRING
    MAX-ACCESS  read-only
    STATUS      current
    DESCRIPTION
        "Represents vendor of the detected device."
    ::= { hh3cDot11MonitorDetectedDevEntry 3 }

hh3cDot11MonitorDevSSID OBJECT-TYPE
    SYNTAX      OCTET STRING
    MAX-ACCESS  read-only
    STATUS      current
    DESCRIPTION
        "Represents the service set identifier for the ESS of the device which
         type is ap or adhoc."
    ::= { hh3cDot11MonitorDetectedDevEntry 4 }

hh3cDot11MonitorDevBSSID OBJECT-TYPE
    SYNTAX      MacAddress
    MAX-ACCESS  read-only
    STATUS      current
    DESCRIPTION
        "Represents the basic service set identifier of the detected device."
    ::= { hh3cDot11MonitorDetectedDevEntry 5 }

hh3cDot11MonitorDevChannel OBJECT-TYPE
    SYNTAX      Hh3cDot11ChannelScopeType
    MAX-ACCESS  read-only
    STATUS      current
    DESCRIPTION
        "Represents the channel in which the device was last detected.  AP will
         choose the channel which has maximum signal strength as effective
         channel, as there is interference between adjacent channels."
    ::= { hh3cDot11MonitorDetectedDevEntry 6 }

hh3cDot11MonitorRadioId OBJECT-TYPE
    SYNTAX      Hh3cDot11RadioScopeType
    MAX-ACCESS  read-only
    STATUS      current
    DESCRIPTION
        "Represents the radio ID of the AP that detected the device."
    ::= { hh3cDot11MonitorDetectedDevEntry 7 }

hh3cDot11MonitorDevMaxRSSI OBJECT-TYPE
    SYNTAX      Integer32
    UNITS       "dbm"
    MAX-ACCESS  read-only
    STATUS      current
    DESCRIPTION
        "Represents the maximum detected RSSI of the device in a scan report cycle."
    ::= { hh3cDot11MonitorDetectedDevEntry 8 }

hh3cDot11MonitorDevBeaconIntvl OBJECT-TYPE
    SYNTAX      Integer32
    UNITS       "millisecond"
    MAX-ACCESS  read-only
    STATUS      current
    DESCRIPTION
        "Represents the beacon interval for the detected device(not include
         the device which type is client)."
    ::= { hh3cDot11MonitorDetectedDevEntry 9 }

hh3cDot11MonitorDevFstDctTime OBJECT-TYPE
    SYNTAX      DateAndTime
    MAX-ACCESS  read-only
    STATUS      current
    DESCRIPTION
        "Represents the time at which the device was first detected."
    ::= { hh3cDot11MonitorDetectedDevEntry 10 }

hh3cDot11MonitorDevLstDctTime OBJECT-TYPE
    SYNTAX      DateAndTime
    MAX-ACCESS  read-only
    STATUS      current
    DESCRIPTION
        "Represents the time at which the device was detected last time."
    ::= { hh3cDot11MonitorDetectedDevEntry 11 }

hh3cDot11MonitorDevClear OBJECT-TYPE
    SYNTAX      TruthValue
    MAX-ACCESS  read-write
    STATUS      current
    DESCRIPTION
        "This object is used to clear the information of the device detected
         in the WLAN.
         It will return false for get operation."
    ::= { hh3cDot11MonitorDetectedDevEntry 12 }

hh3cDot11MonitorDevSNR OBJECT-TYPE
    SYNTAX      Integer32
    MAX-ACCESS  read-only
    STATUS      current
    DESCRIPTION
        "Represents the SNR of the device in a scan report cycle."
    ::= { hh3cDot11MonitorDetectedDevEntry 13 }

END
