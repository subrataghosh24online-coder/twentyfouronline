-- ===========================================================================================================
-- Copyright (c) 2004-2018 New H3C Tech. Co., Ltd.  All rights reserved.
--
-- Description: ISSU MIB
-- Reference:
-- Version: V1.2
-- History:
--  Revision 1.0 2012-12-20 created by Wang Feng
--               2013-4-20 modified by Zhu Liuxing
--  Revision 1.1 2014-01-10 change hh3cIssuUpgradeImageIndex and
--               hh3cIssuUpgradeImageURL range by z03030
--  Revision 1.2 2018-04-08 change hh3cIssuUpgradeImageType by l07660
-- ============================================================================================================

HH3C-ISSU-MIB DEFINITIONS ::= BEGIN

IMPORTS
    hh3cCommon
        FROM HH3C-OID-MIB
    Integer32, OBJECT-TYPE, MODULE-IDENTITY, NOTIFICATION-TYPE
        FROM SNMPv2-SMI
    DisplayString, RowStatus, TruthValue
        FROM SNMPv2-TC;

hh3cIssuUpgrade MODULE-IDENTITY
    LAST-UPDATED "201301151536Z"        -- January 15, 2013 at 15:36 GMT
    ORGANIZATION
        "New H3C Tech. Co., Ltd."
    CONTACT-INFO
        "Platform Team New H3C Tech. Co., Ltd.
        Haidian District Beijing P.R. China
        http://www.h3c.com
        Zip:_100085"
    DESCRIPTION
        "This MIB provides objects for upgrading images on modules in the
        system, objects for showing the result of an upgrade operation,
        and objects for showing the result of a test operation.

        To perform an upgrade operation, a management application
        must first read the hh3cIssuUpgradeImageTable table and use the
        information in other tables, as explained below.  You can
        configure a new image name for each image type as listed in
        hh3cIssuUpgradeImageTable.  The system will use this image on the
        particular module at the next reboot.

        The management application used to perform an upgrade
        operation must first check if an upgrade operation is already
        in progress in the system.  This is done by reading the
        hh3cIssuOpType ('none' indicates that
        no other upgrade operation is in progress.  Any other value
        indicates that an upgrade is already in progress and a new upgrade
        operation is not allowed.  To start an 'install' operation,
        the user must first perform a 'test' operation to examine the
        version compatibility between the given set of images
        and the running images.  Only if the result of the 'test'
        operation is 'success' can the user proceed to do an install
        operation.  The table hh3cIssuTestResultTable
        provides the result of the 'test' operation performed by using hh3cIssuOpType.
        The table hh3cIssuUpgradeResultTable provides the result of the 'install' operation
        performed by using hh3cIssuOpType.
        "
    REVISION "201301151536Z"        -- January 15, 2013 at 15:36 GMT
    DESCRIPTION
        "Initial version of this MIB module.
        Added hh3cIssuUpgradeImageTable hh3cIssuOp hh3cIssuCompatibleResult
        hh3cIssuTestResultTable hh3cIssuUpgradeResultTable"
    ::= { hh3cCommon 133 }

--
-- Node definitions
--

hh3cIssuUpgradeMibObjects OBJECT IDENTIFIER ::= { hh3cIssuUpgrade 1 }


hh3cIssuUpgradeGroup OBJECT IDENTIFIER ::= { hh3cIssuUpgradeMibObjects 1 }


hh3cIssuUpgradeImageTable OBJECT-TYPE
    SYNTAX SEQUENCE OF Hh3cIssuUpgradeImageEntry
    MAX-ACCESS not-accessible
    STATUS current
    DESCRIPTION
        "A table listing the image variable types that
        exist in the device."
    ::= { hh3cIssuUpgradeGroup 1 }


hh3cIssuUpgradeImageEntry OBJECT-TYPE
    SYNTAX Hh3cIssuUpgradeImageEntry
    MAX-ACCESS not-accessible
    STATUS current
    DESCRIPTION
        "An hh3cIssuUpgradeImageEntry entry.  Each entry provides an
        image variable type that exists in the device."
    INDEX { hh3cIssuUpgradeImageIndex }
    ::= { hh3cIssuUpgradeImageTable 1 }


Hh3cIssuUpgradeImageEntry ::=
    SEQUENCE {
        hh3cIssuUpgradeImageIndex
            Integer32,
        hh3cIssuUpgradeImageType
            INTEGER,
        hh3cIssuUpgradeImageURL
            DisplayString,
        hh3cIssuUpgradeImageRowStatus
            RowStatus
     }

hh3cIssuUpgradeImageIndex OBJECT-TYPE
    SYNTAX Integer32 (1..2147483647)
    MAX-ACCESS not-accessible
    STATUS current
    DESCRIPTION
        "Index of each image."
    ::= { hh3cIssuUpgradeImageEntry 1 }


hh3cIssuUpgradeImageType OBJECT-TYPE
    SYNTAX INTEGER
        {
        boot(1),
        system(2),
        feature(3),
        ipe(4),
        patch(5)
        }
    MAX-ACCESS read-create
    STATUS current
    DESCRIPTION
        "Types of images that the system can run.  The value of
        this object has five image variable names:
        'boot', 'system', 'feature', 'ipe' and 'patch'.  This table will then
        list these five strings as follows:

              hh3cIssuUpgradeImageType
                  boot
                  system
                  feature
                  IPE
                  patch

              The user can assign images (using hh3cIssuUpgradeImageURL)
              to these variables and the system will use the assigned
              images to boot."
    ::= { hh3cIssuUpgradeImageEntry 2 }


hh3cIssuUpgradeImageURL OBJECT-TYPE
    SYNTAX DisplayString (SIZE (1..127))
    MAX-ACCESS read-create
    STATUS current
    DESCRIPTION
        "This object contains the path of the image
        of this entity."
    ::= { hh3cIssuUpgradeImageEntry 3 }


hh3cIssuUpgradeImageRowStatus OBJECT-TYPE
    SYNTAX RowStatus
    MAX-ACCESS read-create
    STATUS current
    DESCRIPTION
        "Row-status of image table."
    ::= { hh3cIssuUpgradeImageEntry 4 }


hh3cIssuOp OBJECT IDENTIFIER ::= { hh3cIssuUpgradeGroup 2 }


hh3cIssuOpType OBJECT-TYPE
    SYNTAX INTEGER
        {
        none(1),
        done(2),
        test(3),
        install(4),
        rollback(5)
        }
    MAX-ACCESS read-write
    STATUS current
    DESCRIPTION
        "Command to be executed.
        The 'test' command must be performed before the 'install'
        command can be executed.  The 'install'
        command is allowed only if a read of
        this object returns 'test' and the value of object
        hh3cIssuOpStatus is 'success'.

        Command                 Remarks

        none      If the user sets this object to 'none', the agent will return a success
                  without performing an upgrade operation.
        done      If this object returns any value other than
                  'none', setting this to 'done' will do
                  the required cleanup of the previous upgrade
                  operation and get the system ready for a new
                  upgrade operation.
        test      Check the version compatibility and upgrade method
                  for the given set of image files.
        install   For all the image entities listed in the
                  hh3cIssuUpgradeImageTable, perform the required
                  upgrade operation listed in that table.
        rollback  Abort the current 'install' operation and roll back
                  to the previous version.
          "
    DEFVAL { none }
    ::= { hh3cIssuOp 1 }


hh3cIssuImageFileOverwrite OBJECT-TYPE
    SYNTAX TruthValue
    MAX-ACCESS read-write
    STATUS current
    DESCRIPTION
        "If you want to overwrite the existing file, set the value of
        this object to enable.  Otherwise, set the value of this
        object to disable."
    DEFVAL { true }
    ::= { hh3cIssuOp 2 }


hh3cIssuOpTrapEnable OBJECT-TYPE
    SYNTAX TruthValue
    MAX-ACCESS read-write
    STATUS current
    DESCRIPTION
        "If you want to enable the trap, set the value of
        this object to enable.  Otherwise, set the value of this
        object to disable."
    DEFVAL { true }
    ::= { hh3cIssuOp 3 }


hh3cIssuOpStatus OBJECT-TYPE
    SYNTAX INTEGER
        {
        none(1),
        failure(2),
        inProgress(3),
        success(4),
        rollbackInProgress(5),
        rollbackSuccess(6)
        }
    MAX-ACCESS read-only
    STATUS current
    DESCRIPTION
        "Status of the specified operation.
        none                - No operation was performed.
        failure             - Specified operation has failed.
        inProgress          - Specified operation is in progress.
        success             - Specified operation completed successfully.
        rollbackInProgress     - Rollback operation is in progress.
        rollbackSuccess        - Rollback operation completed successfully.
          "
    DEFVAL { none }
    ::= { hh3cIssuOp 4 }


hh3cIssuFailedReason OBJECT-TYPE
    SYNTAX DisplayString (SIZE (0..255))
    MAX-ACCESS read-only
    STATUS current
    DESCRIPTION
        "Indicates the the cause of 'failure' state
        of the object 'hh3cIssuOpStatus'.
        This object would be a null string if the value of
        'hh3cIssuOpStatus' is not 'failure'."
    ::= { hh3cIssuOp 5 }


hh3cIssuOpTimeCompleted OBJECT-TYPE
    SYNTAX DisplayString (SIZE (0..255))
    MAX-ACCESS read-only
    STATUS current
    DESCRIPTION
        "Indicates the time when the upgrade operation was completed.
        This object would be a null string if hh3cIssuOpType is
        'none'. "
    ::= { hh3cIssuOp 6 }


hh3cIssuLastOpType OBJECT-TYPE
    SYNTAX INTEGER
        {
        none(1),
        done(2),
        test(3),
        install(4),
        rollback(5)
        }
    MAX-ACCESS read-only
    STATUS current
    DESCRIPTION
        "This object indicates the previous hh3cIssuOp value.
        It will be updated after a new hh3cIssuOp is set and delivered
        to the upgrade process.

        Command                 Remarks

        none      If the user sets this object to 'none', agent will return a success
                  without performing an upgrade operation.
        done      If this object returns any value other than
                  'none', setting this to 'done' will do
                  the required cleanup of the previous upgrade
                  operation and get the system ready for a new
                  upgrade operation.
        test      Check the version compatibility and upgrade method
                  for the given set of image files.
        install   For all the image entities listed in the
                  hh3cIssuUpgradeImageTable, perform the required
                  upgrade operation listed in that table.
        rollback  Abort the current install operation and roll back
                  to the previous version.
        "
    DEFVAL { none }
    ::= { hh3cIssuOp 7 }


hh3cIssuLastOpStatus OBJECT-TYPE
    SYNTAX INTEGER
        {
        none(1),
        failure(2),
        inProgress(3),
        success(4),
        rollbackInProgress(5),
        rollbackSuccess(6)
        }
    MAX-ACCESS read-only
    STATUS current
    DESCRIPTION
        "This object indicates previous hh3cIssuOpStatus value.
        It will be updated after new hh3cIssuOp is set and delivered
        to upgrade process.
        none                - No operation was performed.
        failure             - Specified operation has failed.
        inProgress          - Specified operation is active.
        success             - Specified operation completed successfully.
        rollbackInProgress     - Rollback operation is in progress.
        rollbackSuccess        - Rollback operation completed successfully.
        "
    DEFVAL { none }
    ::= { hh3cIssuOp 8 }


hh3cIssuLastOpFailedReason OBJECT-TYPE
    SYNTAX DisplayString (SIZE (0..255))
    MAX-ACCESS read-only
    STATUS current
    DESCRIPTION
        "Indicates the cause of 'failure' state
        of the object 'hh3cIssuOpStatus'.
        This object would be a null string if the value of
        'hh3cIssuOpStatus' is not 'failure'.
        The value will be updated when new hh3cIssuOp is set
        and delivered to the upgrade process."
    ::= { hh3cIssuOp 9 }


hh3cIssuLastOpTimeCompleted OBJECT-TYPE
    SYNTAX DisplayString (SIZE (0..255))
    MAX-ACCESS read-only
    STATUS current
    DESCRIPTION
        "Indicates the previous hh3cIssuOpTimeCompleted value.
        The value will be updated when new hh3cIssuOp is set
        and delivered to the upgrade process."
    ::= { hh3cIssuOp 10 }


hh3cIssuUpgradeResultGroup OBJECT IDENTIFIER ::= { hh3cIssuUpgradeMibObjects 2 }


hh3cIssuCompatibleResult OBJECT IDENTIFIER ::= { hh3cIssuUpgradeResultGroup 1 }


hh3cIssuCompatibleResultStatus OBJECT-TYPE
    SYNTAX INTEGER
        {
        none(1),
        inCompatible(2),
        compatible(3),
        failure(4)
        }
    MAX-ACCESS read-only
    STATUS current
    DESCRIPTION
        "Specifies whether the images provided in
        hh3cIssuUpgradeImageTable are compatible with each other as
        far as this module is concerned.
        none            - No operation was performed.
        inCompatible    - The images provided are compatible
                          and can be run on this module.
        compatible      - The images provided are incompatible
                          and can be run on this module.
        failure         - Failed to get the compatibility.
        "
    DEFVAL { none }
    ::= { hh3cIssuCompatibleResult 1 }


hh3cIssuCompatibleResultFailedReason OBJECT-TYPE
    SYNTAX DisplayString (SIZE (0..255))
    MAX-ACCESS read-only
    STATUS current
    DESCRIPTION
        "Indicates the cause of 'failure' state
        of the object 'hh3cIssuCompatibleResultStatus'.
        This object would be a null string if the value of
        'hh3cIssuCompatibleResultStatus' is not 'failure'."
    ::= { hh3cIssuCompatibleResult 2 }


hh3cIssuTestResultTable OBJECT-TYPE
    SYNTAX SEQUENCE OF Hh3cIssuTestResultEntry
    MAX-ACCESS not-accessible
    STATUS current
    DESCRIPTION
        "Shows the result of the test operation, from which you can
        see the upgrade method."
    ::= { hh3cIssuUpgradeResultGroup 2 }


hh3cIssuTestResultEntry OBJECT-TYPE
    SYNTAX Hh3cIssuTestResultEntry
    MAX-ACCESS not-accessible
    STATUS current
    DESCRIPTION
        "An hh3cIssuTestResultEntry entry.  Each entry provides the
        test result of a card in the device."
    INDEX { hh3cIssuTestResultIndex }
    ::= { hh3cIssuTestResultTable 1 }


Hh3cIssuTestResultEntry ::=
    SEQUENCE {
        hh3cIssuTestResultIndex
            Integer32,
        hh3cIssuTestDeviceChassisID
            Integer32,
        hh3cIssuTestDeviceSlotID
            Integer32,
        hh3cIssuTestDeviceCpuID
            Integer32,
        hh3cIssuTestDeviceUpgradeWay
            INTEGER
     }

hh3cIssuTestResultIndex OBJECT-TYPE
    SYNTAX Integer32 (1..65535)
    MAX-ACCESS not-accessible
    STATUS current
    DESCRIPTION
        "Internal index, not accessible."
    ::= { hh3cIssuTestResultEntry 1 }


hh3cIssuTestDeviceChassisID OBJECT-TYPE
    SYNTAX Integer32 (0..255)
    MAX-ACCESS read-only
    STATUS current
    DESCRIPTION
        "Chassis ID of the card."
    ::= { hh3cIssuTestResultEntry 2 }


hh3cIssuTestDeviceSlotID OBJECT-TYPE
    SYNTAX Integer32 (0..255)
    MAX-ACCESS read-only
    STATUS current
    DESCRIPTION
        "Slot ID of the card."
    ::= { hh3cIssuTestResultEntry 3 }


hh3cIssuTestDeviceCpuID OBJECT-TYPE
    SYNTAX Integer32 (0..7)
    MAX-ACCESS read-only
    STATUS current
    DESCRIPTION
        "CPU ID of the card."
    ::= { hh3cIssuTestResultEntry 4 }


hh3cIssuTestDeviceUpgradeWay OBJECT-TYPE
    SYNTAX INTEGER
        {
        none(1),
        reboot(2),
        sequenceReboot(3),
        issuReboot(4),
        serviceUpgrade(5),
        fileUpgrade(6),
        incompatibleUpgrade(7)
        }
    MAX-ACCESS read-only
    STATUS current
    DESCRIPTION
        "Upgrade method of the device.
        none                   - No operation was performed.
        reboot                 - The upgrade method of this device is Reboot.
        sequenceReboot         - The upgrade method of this device is SequenceReboot.
        issuReboot             - The upgrade method of this device is IssuReboot.
        serviceUpgrade         - The upgrade method of this device is ServiceReboot.
        fileUpgrade            - The upgrade method of this device is FileReboot.
        incompatibleUpgrade    - The upgrade method of this device is IncompatibleUpgrade.
        "
    DEFVAL { none }
    ::= { hh3cIssuTestResultEntry 5 }


hh3cIssuUpgradeResultTable OBJECT-TYPE
    SYNTAX SEQUENCE OF Hh3cIssuUpgradeResultEntry
    MAX-ACCESS not-accessible
    STATUS current
    DESCRIPTION
        "Shows the result of the install operation."
    ::= { hh3cIssuUpgradeResultGroup 3 }


hh3cIssuUpgradeResultEntry OBJECT-TYPE
    SYNTAX Hh3cIssuUpgradeResultEntry
    MAX-ACCESS not-accessible
    STATUS current
    DESCRIPTION
        "An hh3cIssuUpgradeResultEntry entry.  Each entry provides the
        upgrade result of a card in the device."
    INDEX { hh3cIssuUpgradeResultIndex }
    ::= { hh3cIssuUpgradeResultTable 1 }


Hh3cIssuUpgradeResultEntry ::=
    SEQUENCE {
        hh3cIssuUpgradeResultIndex
            Integer32,
        hh3cIssuUpgradeDeviceChassisID
            Integer32,
        hh3cIssuUpgradeDeviceSlotID
            Integer32,
        hh3cIssuUpgradeDeviceCpuID
            Integer32,
        hh3cIssuUpgradeState
            INTEGER,
        hh3cIssuDeviceUpgradeWay
            INTEGER,
        hh3cIssuUpgradeDeviceStatus
            INTEGER,
        hh3cIssuUpgradeFailedReason
            DisplayString
     }

hh3cIssuUpgradeResultIndex OBJECT-TYPE
    SYNTAX Integer32 (1..65535)
    MAX-ACCESS not-accessible
    STATUS current
    DESCRIPTION
        "Internal Index, not accessible."
    ::= { hh3cIssuUpgradeResultEntry 1 }


hh3cIssuUpgradeDeviceChassisID OBJECT-TYPE
    SYNTAX Integer32 (0..255)
    MAX-ACCESS read-only
    STATUS current
    DESCRIPTION
        "Chassis ID of the card."
    ::= { hh3cIssuUpgradeResultEntry 2 }


hh3cIssuUpgradeDeviceSlotID OBJECT-TYPE
    SYNTAX Integer32 (0..255)
    MAX-ACCESS read-only
    STATUS current
    DESCRIPTION
        "Slot ID of the card."
    ::= { hh3cIssuUpgradeResultEntry 3 }


hh3cIssuUpgradeDeviceCpuID OBJECT-TYPE
    SYNTAX Integer32 (0..7)
    MAX-ACCESS read-only
    STATUS current
    DESCRIPTION
        "CPU ID of the card."
    ::= { hh3cIssuUpgradeResultEntry 4 }


hh3cIssuUpgradeState OBJECT-TYPE
    SYNTAX INTEGER
        {
        init(1),
        loading(2),
        loaded(3),
        switching(4),
        switchover(5),
        committing(6),
        committed(7),
        rollbacking(8),
        rollbacked(9)
        }
    MAX-ACCESS read-only
    STATUS current
    DESCRIPTION
        "Upgrade status of the device.
        init           -The current status of the device is Init.
        loading        -The current status of the device is Loading.
        loaded         -The current status of the device is Loaded.
        switching      -The current status of the device is Switching.
        switchover     -The current status of the device is Switchover.
        committing     -The current status of the device is Committing.
        committed      -The current status of the device is Committed.
        rollbacking    -The current status of the device is Rollbacking.
        rollbacked     -The current status of the device is Rollbacked.
        "
    ::= { hh3cIssuUpgradeResultEntry 5 }


hh3cIssuDeviceUpgradeWay OBJECT-TYPE
    SYNTAX INTEGER
        {
        none(1),
        reboot(2),
        sequenceReboot(3),
        issuReboot(4),
        serviceUpgrade(5),
        fileUpgrade(6),
        incompatibleUpgrade(7)
        }
    MAX-ACCESS read-only
    STATUS current
    DESCRIPTION
        "Upgrade method of the card.
        none                   - No operation was performed.
        reboot                 - The upgrade method of this device is Reboot.
        sequenceReboot         - The upgrade method of this device is SequenceReboot.
        issuReboot             - The upgrade method of this device is IssuReboot.
        serviceUpgrade         - The upgrade method of this device is ServiceReboot.
        fileUpgrade            - The upgrade method of this device is FileReboot.
        incompatibleUpgrade    - The upgrade method of this device is IncompatibleUpgrade.
        "
    ::= { hh3cIssuUpgradeResultEntry 6 }


hh3cIssuUpgradeDeviceStatus OBJECT-TYPE
    SYNTAX INTEGER
        {
        waitingUpgrade(1),
        inProcess(2),
        success(3),
        failure(4)
        }
    MAX-ACCESS read-only
    STATUS current
    DESCRIPTION
        "Upgrade status of the device."
    ::= { hh3cIssuUpgradeResultEntry 7 }


hh3cIssuUpgradeFailedReason OBJECT-TYPE
    SYNTAX DisplayString (SIZE (0..255))
    MAX-ACCESS read-only
    STATUS current
    DESCRIPTION
        "Indicates the cause of 'failure' state
        of the object 'hh3cIssuUpgradeDeviceStatus'.
        This object would be a null string if the value of
        'hh3cIssuCompatibleResultStatus' is not 'failure'."
    ::= { hh3cIssuUpgradeResultEntry 8 }


hh3cIssuUpgradeNotify OBJECT IDENTIFIER ::= { hh3cIssuUpgrade 2 }


hh3cIssuUpgradeTrapPrefix OBJECT IDENTIFIER ::= { hh3cIssuUpgradeNotify 0 }


hh3cIssuUpgradeOpCompletionNotify NOTIFICATION-TYPE
    OBJECTS { hh3cIssuOpType, hh3cIssuOpStatus, hh3cIssuFailedReason, hh3cIssuOpTimeCompleted }
    STATUS current
    DESCRIPTION
        "An hh3cIssuUpgradeOpCompletionNotify is sent at the
        completion of upgrade operation denoted by
        hh3cIssuOp object, if such a notification
        was requested when the operation was initiated.
        hh3cIssuOpType indicates the type of the
        operation.  hh3cIssuOpStatus indicates the
        result of the operation.  hh3cIssuFailedReason
        indicates the operation failure reason.
        hh3cIssuOpTimeCompleted indicates the time
        when the operation was completed."
    ::= { hh3cIssuUpgradeTrapPrefix 1 }



END
