-- =================================================================
-- Copyright (C) 2008 by New H3C Technologies Co., Ltd. All rights reserved.
--
-- Description: The purpose of this MIB is to provide the definition of
--              the DSP(Digital Signal Processing) status.
-- Reference:
-- Version: V1.1
-- History:
-- V1.0 2008-01-16 Initial version, created by Zhu Xinfeng
-- V1.1 2008-07-14 Add hh3cVPMStateChange and hh3cDSPStateChange by zhuxinfeng
-- =================================================================
HH3C-DSP-MIB DEFINITIONS ::= BEGIN

IMPORTS
        hh3cCommon
    FROM HH3C-OID-MIB
        PhysicalIndex
    FROM ENTITY-MIB
        OBJECT-TYPE, MODULE-IDENTITY, NOTIFICATION-TYPE, Integer32, TimeTicks
    FROM SNMPv2-SMI;

hh3cDSP MODULE-IDENTITY
    LAST-UPDATED "200801161300Z"
    ORGANIZATION
        "New H3C Technologies Co., Ltd."
    CONTACT-INFO
        "PLAT Team New H3C Technologies Co.,Ltd.
        Shang-Di Information Industry Base,
        Hai-Dian District Beijing P.R. China
        http://www.h3c.com
        Zip:100085"
    DESCRIPTION
        "This MIB is to provide the definition of the DSP(Digital Signal
        Processing) status."
    REVISION "200801161300Z"
    DESCRIPTION
        "The initial revision of this MIB module."
    ::= { hh3cCommon 89 }

-- ===========================================================================
--                            hh3cVPMStatusTable
--
-- ===========================================================================
hh3cVPMStatusTable OBJECT-TYPE
    SYNTAX      SEQUENCE OF Hh3cVPMStatusEntry
    MAX-ACCESS  not-accessible
    STATUS      current
    DESCRIPTION
        "The table contains status parameters of VPM(Voice Process
        Module) card."
    ::= { hh3cDSP 1 }


hh3cVPMStatusEntry OBJECT-TYPE
    SYNTAX      Hh3cVPMStatusEntry
    MAX-ACCESS  not-accessible
    STATUS      current
    DESCRIPTION
        "The entry of VPM status table."
    INDEX
        {
            hh3cVPMIndex
        }
    ::= { hh3cVPMStatusTable 1 }

Hh3cVPMStatusEntry ::= SEQUENCE
    {
        hh3cVPMIndex                  Integer32,
        hh3cVPMEnPhysicalIndex        PhysicalIndex,
        hh3cVPMState                  INTEGER,
        hh3cVPMResourceUtilization    Integer32,
        hh3cVPMHiWaterUtilization     Integer32,
        hh3cVPMMaxChannel             Integer32
    }

hh3cVPMIndex OBJECT-TYPE
    SYNTAX      Integer32(1..64)
    MAX-ACCESS  accessible-for-notify
    STATUS      current
    DESCRIPTION
        "The index for this entry. The sequence of VPM card in the chassis is
        from the top to bottom."
    ::= { hh3cVPMStatusEntry 1 }

hh3cVPMEnPhysicalIndex OBJECT-TYPE
    SYNTAX      PhysicalIndex
    MAX-ACCESS  read-only
    STATUS      current
    DESCRIPTION
        "The object corresponds to PhysicalIndex in the chassis."
    ::= { hh3cVPMStatusEntry 2 }

hh3cVPMState OBJECT-TYPE
    SYNTAX      INTEGER
        {
            normal(1),
            warning(2),
            fatal(3),
            offLine(4)
        }
    MAX-ACCESS  read-only
    STATUS      current
    DESCRIPTION
        "The object indicates the current state of VPM card being monitored.
        normal(1)  - VPM card in normal condition.
        warning(2) - VPM card has some problem and need attention.
        fatal(3)   - VPM card is not functional.
        offLine(4) - VPM card is in off-line maintenance state."
    ::= { hh3cVPMStatusEntry 3 }

hh3cVPMResourceUtilization OBJECT-TYPE
    SYNTAX      Integer32(0..100)
    MAX-ACCESS  read-only
    STATUS      current
    DESCRIPTION
        "The object indicates the percentage of current DSP resource utilization
        of the VPM card. The utilization is a ratio of number of busy DSP
        resources (for handling calls, transcoding, voice compression,...)
        to the total available DSP resources."
    ::= { hh3cVPMStatusEntry 4 }

hh3cVPMHiWaterUtilization OBJECT-TYPE
    SYNTAX      Integer32(0..100)
    MAX-ACCESS  read-only
    STATUS      current
    DESCRIPTION
        "The object indicates the highest percentage of DSP resource utilization
        of the VPM card that have been occured."
    ::= { hh3cVPMStatusEntry 5 }

hh3cVPMMaxChannel OBJECT-TYPE
    SYNTAX      Integer32
    MAX-ACCESS  read-only
    STATUS      current
    DESCRIPTION
        "The maximum number of channels can be supported in each VPM card."
    ::= { hh3cVPMStatusEntry 6 }

-- ===========================================================================
--                            hh3cDSPStatusTable
--
-- ===========================================================================
hh3cDSPStatusTable OBJECT-TYPE
    SYNTAX      SEQUENCE OF Hh3cDSPStatusEntry
    MAX-ACCESS  not-accessible
    STATUS      current
    DESCRIPTION
        "The table contains status parameters of DSP(Digital Signal
        Processing) card."
    ::= { hh3cDSP 2 }

hh3cDSPStatusEntry OBJECT-TYPE
    SYNTAX      Hh3cDSPStatusEntry
    MAX-ACCESS  not-accessible
    STATUS      current
    DESCRIPTION
        "The entry of DSP status table."
    INDEX
        {
            hh3cDSPIndex
        }
    ::= { hh3cDSPStatusTable 1 }

Hh3cDSPStatusEntry ::= SEQUENCE
    {
        hh3cDSPIndex              Integer32,
        hh3cDSPVPMIndex           Integer32,
        hh3cDSPEnPhysicalIndex    PhysicalIndex,
        hh3cDSPResetTime          TimeTicks,
        hh3cDSPMaxChannel         Integer32,
        hh3cDSPState              INTEGER,
        hh3cDSPInUseChannel       Integer32
    }

hh3cDSPIndex OBJECT-TYPE
    SYNTAX      Integer32(1..256)
    MAX-ACCESS  accessible-for-notify
    STATUS      current
    DESCRIPTION
        "The index for this entry. DSP is fixed on VPM card or chassis card.
        The sequence of DSP in the VPM card or chassis card is from right to left."
    ::= { hh3cDSPStatusEntry 1 }

hh3cDSPVPMIndex OBJECT-TYPE
    SYNTAX      Integer32(0..64)
    MAX-ACCESS  read-only
    STATUS      current
    DESCRIPTION
        "The object corresponds to VPMIndex in the chassis.
        If value of this object is non-zero, it is the index of VPM card.(DSP is in
        this VPM card.) If value of this object is 0, then the DSP is fixed in the
        chassis card."
    ::= { hh3cDSPStatusEntry 2 }

hh3cDSPEnPhysicalIndex OBJECT-TYPE
    SYNTAX      PhysicalIndex
    MAX-ACCESS  read-only
    STATUS      current
    DESCRIPTION
        "The object corresponds to PhysicalIndex in the chassis."
    ::= { hh3cDSPStatusEntry 3 }

hh3cDSPResetTime OBJECT-TYPE
    SYNTAX      TimeTicks
    MAX-ACCESS  read-only
    STATUS      current
    DESCRIPTION
        "The value of sysUpTime from the last DSP reset occurred."
    ::= { hh3cDSPStatusEntry 4 }

hh3cDSPMaxChannel OBJECT-TYPE
    SYNTAX      Integer32
    MAX-ACCESS  read-only
    STATUS      current
    DESCRIPTION
        "The maximum number of channels can be supported in each DSP.
        The value is chosen in an implementation-dependent manner by the
        DSP functionality."
    ::= { hh3cDSPStatusEntry 5 }

hh3cDSPState OBJECT-TYPE
    SYNTAX      INTEGER
        {
            normal(1),
            fatal(3),
            offLine(4)
        }
    MAX-ACCESS  read-only
    STATUS      current
    DESCRIPTION
        "The object indicates the current state of DSP being monitored.
        normal(1)  - DSP in normal condition.
        fatal(3)   - DSP is not functional.
        offLine(4) - DSP is in off-line maintenance state."
    ::= { hh3cDSPStatusEntry 6 }

hh3cDSPInUseChannel OBJECT-TYPE
    SYNTAX      Integer32
    MAX-ACCESS  read-only
    STATUS      current
    DESCRIPTION
        "The number of channels that are reserved for serving calls.
        The value is incremented when the DSP channel is reserved for call setup
        and is decremented after the DSP channel is free due to call disconnection."
    ::= { hh3cDSPStatusEntry 7 }

-- ===========================================================================
--                            hh3cTrapGroup
--
-- ===========================================================================
-- Traps are defined below.

hh3cDSPTrap OBJECT IDENTIFIER ::= { hh3cDSP 3 }

hh3cDSPTrapPrex OBJECT IDENTIFIER ::= { hh3cDSPTrap 0 }

hh3cVPMStateChange NOTIFICATION-TYPE
    OBJECTS  { hh3cVPMIndex, hh3cVPMEnPhysicalIndex, hh3cVPMState }
    STATUS   current
    DESCRIPTION
        "This trap is sent when VPM state changes."
    ::= { hh3cDSPTrapPrex 1 }

hh3cDSPStateChange NOTIFICATION-TYPE
    OBJECTS  { hh3cDSPIndex, hh3cDSPVPMIndex, hh3cDSPEnPhysicalIndex, hh3cDSPState }
    STATUS   current
    DESCRIPTION
        "This trap is sent when DSP state changes."
    ::= { hh3cDSPTrapPrex 2 }

END
