--
-- NETBOTZV2-MIB       module definition
--
NETBOTZV2-MIB DEFINITIONS ::= BEGIN
IMPORTS
   MODULE-IDENTITY, OBJECT-TYPE,
      NOTIFICATION-TYPE, enterprises,
      Integer32          FROM SNMPv2-SMI
   TEXTUAL-CONVENTION, DisplayString,
        DateAndTime                FROM SNMPv2-TC;

netBotz-V2 MODULE-IDENTITY
    LAST-UPDATED "200309090000Z"
    ORGANIZATION "NetBotz Inc"
    CONTACT-INFO
            "Postal: NetBotz, Inc
                     11044 Research Blvd Suite C-100
                     Austin, TX 78759
                     US

                Tel: +1 512 439 5800

             E-mail: support@netbotz.com"
    DESCRIPTION
            "NetBotz BotzWare V2.x MIB"
    ::= { enterprises 5528 100 1 }

netBotz                 OBJECT IDENTIFIER ::= { enterprises 5528 }
netBotzV2               OBJECT IDENTIFIER ::= { netBotz 100 }
netBotzV2Traps          OBJECT IDENTIFIER ::= { netBotzV2 10 }
netBotzV2TrapParms      OBJECT IDENTIFIER ::= { netBotzV2 11 }
netBotzV2Products       OBJECT IDENTIFIER ::= { netBotzV2 20 }

netBotzV2GenericTraps   OBJECT IDENTIFIER ::= { netBotzV2Traps 1 }
netBotzV2SensorTraps    OBJECT IDENTIFIER ::= { netBotzV2Traps 2 }
netBotzV2PodTraps       OBJECT IDENTIFIER ::= { netBotzV2Traps 3 }
netBotzV2PortTraps      OBJECT IDENTIFIER ::= { netBotzV2Traps 4 }

netBotzV2TempSensorTraps        OBJECT IDENTIFIER ::= { netBotzV2SensorTraps 1 }
netBotzV2HumiditySensorTraps    OBJECT IDENTIFIER ::= { netBotzV2SensorTraps 2 }
netBotzV2DewPointSensorTraps    OBJECT IDENTIFIER ::= { netBotzV2SensorTraps 3 }
netBotzV2AirFlowSensorTraps     OBJECT IDENTIFIER ::= { netBotzV2SensorTraps 4 }
netBotzV2AudioSensorTraps       OBJECT IDENTIFIER ::= { netBotzV2SensorTraps 5 }
netBotzV2AmpDetectSensorTraps   OBJECT IDENTIFIER ::= { netBotzV2SensorTraps 6 }
netBotzV2DryContactSensorTraps  OBJECT IDENTIFIER ::= { netBotzV2SensorTraps 7 }
netBotzV2CameraMotionSensorTraps OBJECT IDENTIFIER ::= { netBotzV2SensorTraps 8 }
netBotzV2DoorSensorTraps        OBJECT IDENTIFIER ::= { netBotzV2SensorTraps 9 }
netBotzV2MicPlugSensorTraps     OBJECT IDENTIFIER ::= { netBotzV2SensorTraps 10 }
netBotzV2SpeakerPlugSensorTraps OBJECT IDENTIFIER ::= { netBotzV2SensorTraps 11 }
netBotzV2TVSignalSensorTraps    OBJECT IDENTIFIER ::= { netBotzV2SensorTraps 12 }
netBotzV2GPSPositionSensorTraps OBJECT IDENTIFIER ::= { netBotzV2SensorTraps 13 }
netBotzV2GPSMovementSensorTraps OBJECT IDENTIFIER ::= { netBotzV2SensorTraps 14 }
netBotzV2GPSStatusSensorTraps   OBJECT IDENTIFIER ::= { netBotzV2SensorTraps 15 }
netBotzV2WirelessStatusSensorTraps      OBJECT IDENTIFIER ::= { netBotzV2SensorTraps 22 }
netBotzV2PacketDropSensorTraps  OBJECT IDENTIFIER ::= { netBotzV2SensorTraps 23 }
netBotzV2SNMPCrawlerSensorTraps OBJECT IDENTIFIER ::= { netBotzV2SensorTraps 24 }
netBotzV2PlugModuleStatusSensorTraps    OBJECT IDENTIFIER ::= { netBotzV2SensorTraps 25 }
netBotzV2OutputControlSensorTraps       OBJECT IDENTIFIER ::= { netBotzV2SensorTraps 26 }
netBotzV2MultiRAESensorTraps            OBJECT IDENTIFIER ::= { netBotzV2SensorTraps 27 }
netBotzV2MultiRAESensorStatusTraps      OBJECT IDENTIFIER ::= { netBotzV2SensorTraps 28 }
netBotzV2MultiRAEDeviceStatusTraps      OBJECT IDENTIFIER ::= { netBotzV2SensorTraps 29 }

netBotzV2BasePodTraps   OBJECT IDENTIFIER ::= { netBotzV2PodTraps 1 }
netBotzV2SensorPodTraps OBJECT IDENTIFIER ::= { netBotzV2PodTraps 2 }
netBotzV2CameraPodTraps OBJECT IDENTIFIER ::= { netBotzV2PodTraps 3 }

netBotzV2Botz                   OBJECT IDENTIFIER ::= { netBotzV2Products 10 }

netBotzWallBotz500       OBJECT IDENTIFIER ::= { netBotzV2Botz 2000 }
netBotz420Wall           OBJECT IDENTIFIER ::= { netBotzV2Botz 2001 }
raeSystemsAreaConnect500 OBJECT IDENTIFIER ::= { netBotzV2Botz 2002 }
netBotz420Rack           OBJECT IDENTIFIER ::= { netBotzV2Botz 2003 }
netBotz320Wall           OBJECT IDENTIFIER ::= { netBotzV2Botz 2004 }
netBotz320Rack           OBJECT IDENTIFIER ::= { netBotzV2Botz 2005 }
netBotz420ERack          OBJECT IDENTIFIER ::= { netBotzV2Botz 2006 }
netBotz320ERack          OBJECT IDENTIFIER ::= { netBotzV2Botz 2007 }

--        MODULE-COMPLIANCE, OBJECT-GROUP,
--        NOTIFICATION-GROUP                     FROM SNMPv2-CONF;


OperStatus ::= TEXTUAL-CONVENTION
    STATUS current
    DESCRIPTION
        "The operational status of the device entity."
    SYNTAX INTEGER { disconnected(0), error(1), normal(2) }

ErrorStatus ::= TEXTUAL-CONVENTION
    STATUS current
    DESCRIPTION
        "The error status of the device entity.  If there are no error conditions
         reported for the entity, the status is normal.  Otherwise, the status is
         reported as the severity value of the highest severity error condition
         that is not resolved for the entity."
    SYNTAX INTEGER { normal(0), info(1), warning(2), error(3), critical(4), failure(5) }

BoolValue ::= TEXTUAL-CONVENTION
    STATUS current
    DESCRIPTION
        "A boolean value."
    SYNTAX INTEGER { no(0), yes(1), null(2) }

--BoolValue ::= TEXTUAL-CONVENTION
--    STATUS current
--    DESCRIPTION
--        "A boolean value."
--    SYNTAX INTEGER { no(0), yes(1), null(2) }

netBotzEnclosures        OBJECT IDENTIFIER ::= { netBotzV2 2 }
netBotzPorts             OBJECT IDENTIFIER ::= { netBotzV2 3 }
netBotzSensors           OBJECT IDENTIFIER ::= { netBotzV2 4 }
netBotzErrors            OBJECT IDENTIFIER ::= { netBotzV2 5 }

netBotzNumericSensors    OBJECT IDENTIFIER ::= { netBotzSensors 1 }
netBotzStateSensors      OBJECT IDENTIFIER ::= { netBotzSensors 2 }

--
-- Enclosures
--

enclosureTable OBJECT-TYPE
    SYNTAX     SEQUENCE OF EnclosureEntry
    MAX-ACCESS not-accessible
    STATUS     current
    DESCRIPTION
        "A list of enclosures (base enclosure and pods)."
    ::= { netBotzEnclosures 1 }

enclosureEntry OBJECT-TYPE
    SYNTAX     EnclosureEntry
    MAX-ACCESS not-accessible
    STATUS     current
    DESCRIPTION
        "Enclosure entry."
    INDEX { enclosureId }
    ::= { enclosureTable 1 }

EnclosureEntry ::= SEQUENCE {
    enclosureId                          DisplayString,
    enclosureStatus                      OperStatus,
    enclosureErrorStatus                 ErrorStatus,
    enclosureLabel                       DisplayString,
    enclosureParentEncId                 DisplayString,
    enclosureDockedToEncId               DisplayString
}

enclosureId OBJECT-TYPE
    SYNTAX     DisplayString (SIZE (0..127))
    MAX-ACCESS read-only
    STATUS     current
    DESCRIPTION
        "The id of the physical enclosure."
    ::= { enclosureEntry 1 }

enclosureStatus OBJECT-TYPE
    SYNTAX     OperStatus 
    MAX-ACCESS read-only
    STATUS     current
    DESCRIPTION
        "The operational status of the enclosure."
    ::= { enclosureEntry 2 }
    
enclosureErrorStatus OBJECT-TYPE
    SYNTAX     ErrorStatus
    MAX-ACCESS read-only
    STATUS     current
    DESCRIPTION
        "The error status of the enclosure.  If there are no error conditions
         reported for the enclosure, the status is normal.  Otherwise, the status is
         reported as the severity value of the highest severity error condition
         that is not resolved for the enclosure."
    ::= { enclosureEntry 3 }

enclosureLabel OBJECT-TYPE
    SYNTAX     DisplayString
    MAX-ACCESS read-only
    STATUS     current
    DESCRIPTION
        "The unique label assigned to the enclosure (or pod)."
    ::= { enclosureEntry 4 }

enclosureParentEncId OBJECT-TYPE
    SYNTAX     DisplayString (SIZE (0..127))
    MAX-ACCESS read-only
    STATUS     current
    DESCRIPTION
        "The id of the parent enclosure this enclosure is attached to."
    ::= { enclosureEntry 5 }
    
enclosureDockedToEncId OBJECT-TYPE
    SYNTAX     DisplayString (SIZE (0..127))
    MAX-ACCESS read-only
    STATUS     current
    DESCRIPTION
        "The id of the enclosure this enclosure is hard-docked with,
         i.e. as when sensor and camera pods are docked with the base
         system unit."
    ::= { enclosureEntry 6 }

--
-- Ports
--

dinPortTable OBJECT-TYPE
    SYNTAX     SEQUENCE OF DINPortEntry
    MAX-ACCESS not-accessible
    STATUS     current
    DESCRIPTION
        "A list of DIN port entries."
    ::= { netBotzPorts 1 }

dinPortEntry OBJECT-TYPE
    SYNTAX     DINPortEntry
    MAX-ACCESS not-accessible
    STATUS     current
    DESCRIPTION
        "DIN port entry."
    INDEX { dinPortId }
    ::= { dinPortTable 1 }

DINPortEntry ::= SEQUENCE {
    dinPortId                            DisplayString,
    dinPortStatus                        OperStatus,
    dinPortLabel                         DisplayString,
    dinPortEncId                         DisplayString,
    dinPortSensorIdSuffix                DisplayString,
    dinPortSupportsAverage               BoolValue,
    dinPortSupportsRMS                   BoolValue,
    dinPortSupportsDryContact            BoolValue
}

dinPortId OBJECT-TYPE
    SYNTAX     DisplayString (SIZE (0..127))
    MAX-ACCESS read-only
    STATUS     current
    DESCRIPTION
        "The unique id of the port."
    ::= { dinPortEntry 1 }

dinPortStatus OBJECT-TYPE
    SYNTAX     OperStatus 
    MAX-ACCESS read-only
    STATUS     current
    DESCRIPTION
        "The operational status of the port."
    ::= { dinPortEntry 2 }

dinPortLabel OBJECT-TYPE
    SYNTAX     DisplayString
    MAX-ACCESS read-only
    STATUS     current
    DESCRIPTION
        "The unique label assigned to the port."
    ::= { dinPortEntry 3 }

dinPortEncId OBJECT-TYPE
    SYNTAX     DisplayString (SIZE (0..127))
    MAX-ACCESS read-only
    STATUS     current
    DESCRIPTION
        "The id of the physical enclosure containing the port."
    ::= { dinPortEntry 4 }

dinPortSensorIdSuffix OBJECT-TYPE
    SYNTAX     DisplayString
    MAX-ACCESS read-only
    STATUS     current
    DESCRIPTION
        "The ID suffix added to a sensor plugged into the port.
         The ID suffix is combined with the sensor class ID when
         generating a local unique id for the DIN sensor."
    ::= { dinPortEntry 5 }

dinPortSupportsAverage OBJECT-TYPE
    SYNTAX     BoolValue
    MAX-ACCESS read-only
    STATUS     current
    DESCRIPTION
        "Whether the port supports returning the average voltage
         reading of the sensor.  This is used to determine which
         classes of sensors are supported by the port."
    ::= { dinPortEntry 6 }

dinPortSupportsRMS OBJECT-TYPE
    SYNTAX     BoolValue
    MAX-ACCESS read-only
    STATUS     current
    DESCRIPTION
        "Whether the port supports returning the AC RMS voltage
         reading of the sensor.  This is used to determine which
         classes of sensors are supported by the port."
    ::= { dinPortEntry 7 }

dinPortSupportsDryContact OBJECT-TYPE
    SYNTAX     BoolValue
    MAX-ACCESS read-only
    STATUS     current
    DESCRIPTION
        "Whether the port supports generating the 'open' and
         'closed' state of a dry contact sensor. This information
         is used to determine which classes of sensors are supported
         by the port."
    ::= { dinPortEntry 8 }

otherPortTable OBJECT-TYPE
    SYNTAX     SEQUENCE OF OtherPortEntry
    MAX-ACCESS not-accessible
    STATUS     current
    DESCRIPTION
        "A list of other port entries."
    ::= { netBotzPorts 10 }

otherPortEntry OBJECT-TYPE
    SYNTAX     OtherPortEntry
    MAX-ACCESS not-accessible
    STATUS     current
    DESCRIPTION
        "Other port entry."
    INDEX { otherPortId }
    ::= { otherPortTable 1 }

OtherPortEntry ::= SEQUENCE {
    otherPortId                            DisplayString,
    otherPortStatus                        OperStatus,
    otherPortLabel                         DisplayString,
    otherPortEncId                         DisplayString
}

otherPortId OBJECT-TYPE
    SYNTAX     DisplayString (SIZE (0..127))
    MAX-ACCESS read-only
    STATUS     current
    DESCRIPTION
        "The unique id of the port."
    ::= { otherPortEntry 1 }

otherPortStatus OBJECT-TYPE
    SYNTAX     OperStatus 
    MAX-ACCESS read-only
    STATUS     current
    DESCRIPTION
        "The operational status of the port."
    ::= { otherPortEntry 2 }

otherPortLabel OBJECT-TYPE
    SYNTAX     DisplayString
    MAX-ACCESS read-only
    STATUS     current
    DESCRIPTION
        "The unique label assigned to the port."
    ::= { otherPortEntry 3 }

otherPortEncId OBJECT-TYPE
    SYNTAX     DisplayString (SIZE (0..127))
    MAX-ACCESS read-only
    STATUS     current
    DESCRIPTION
        "The id of the physical enclosure containing the port."
    ::= { otherPortEntry 4 }

-- Numeric Sensors Group
-- This group defines sensors for which the concepts of "less than"
-- and "greater than" are meaningful.

tempSensorTable OBJECT-TYPE
    SYNTAX     SEQUENCE OF TempSensorEntry
    MAX-ACCESS not-accessible
    STATUS     current
    DESCRIPTION
        "A list of temperature sensor entries."
    ::= { netBotzNumericSensors 1 }

tempSensorEntry OBJECT-TYPE
    SYNTAX     TempSensorEntry
    MAX-ACCESS not-accessible
    STATUS     current
    DESCRIPTION
        "A temperature sensor entry."
    INDEX { tempSensorId }
    ::= { tempSensorTable 1 }

TempSensorEntry ::= SEQUENCE {
    tempSensorId                       DisplayString,
    tempSensorValue                    Integer32,
    tempSensorErrorStatus              ErrorStatus,
    tempSensorLabel                    DisplayString,
    tempSensorEncId                    DisplayString,
    tempSensorPortId                   DisplayString,
    tempSensorValueStr                 DisplayString,
    tempSensorValueInt                 Integer32,
    tempSensorValueIntF                Integer32
}

tempSensorId   OBJECT-TYPE
    SYNTAX     DisplayString (SIZE (0..127))
    MAX-ACCESS read-only
    STATUS     current
    DESCRIPTION
        "The unique id of the sensor."
    ::= { tempSensorEntry 1 }

tempSensorValue OBJECT-TYPE
    SYNTAX     Integer32 (-500..1000)
    MAX-ACCESS read-only
    STATUS     current
    DESCRIPTION
        "The temperature measured by the sensor in tenths of a degree Celsius."
    ::= { tempSensorEntry 2 }

tempSensorErrorStatus OBJECT-TYPE
    SYNTAX     ErrorStatus
    MAX-ACCESS read-only
    STATUS     current
    DESCRIPTION
        "The error status of the sensor.  If there are no error conditions
         reported for the sensor, the status is normal.  Otherwise, the status is
         reported as the severity value of the highest severity error condition
         that is not resolved for the sensor."
    ::= { tempSensorEntry 3 }

tempSensorLabel OBJECT-TYPE
    SYNTAX     DisplayString
    MAX-ACCESS read-only
    STATUS     current
    DESCRIPTION
        "The unique label assigned to the sensor."
    ::= { tempSensorEntry 4 }

tempSensorEncId OBJECT-TYPE
    SYNTAX     DisplayString (SIZE (0..127))
    MAX-ACCESS read-only
    STATUS     current
    DESCRIPTION
        "The id of the physical enclosure containing the sensor."
    ::= { tempSensorEntry 5 }

tempSensorPortId OBJECT-TYPE
    SYNTAX     DisplayString (SIZE (0..127))
    MAX-ACCESS read-only
    STATUS     current
    DESCRIPTION
        "The id of the port the sensor is plugged into (or empty string
         if it is not plugged into a port)."
    ::= { tempSensorEntry 6 }

tempSensorValueStr OBJECT-TYPE
    SYNTAX     DisplayString
    MAX-ACCESS read-only
    STATUS     current
    DESCRIPTION
        "The temperature reading, in degrees celsius, shown as a string (or empty string
         if it is not plugged into a port)."
    ::= { tempSensorEntry 7 }

tempSensorValueInt OBJECT-TYPE
    SYNTAX     Integer32 (-50..100)
    MAX-ACCESS read-only
    STATUS     current
    DESCRIPTION
        "The temperature measured by the sensor in degree Celsius."
    ::= { tempSensorEntry 8 }

tempSensorValueIntF OBJECT-TYPE
    SYNTAX     Integer32 (-50..212)
    MAX-ACCESS read-only
    STATUS     current
    DESCRIPTION
        "The temperature measured by the sensor in degree Farenheit."
    ::= { tempSensorEntry 9 }

humiSensorTable OBJECT-TYPE
    SYNTAX     SEQUENCE OF HumiSensorEntry
    MAX-ACCESS not-accessible
    STATUS     current
    DESCRIPTION
        "A list of humidity sensor entries."
    ::= { netBotzNumericSensors 2 }

humiSensorEntry OBJECT-TYPE
    SYNTAX     HumiSensorEntry
    MAX-ACCESS not-accessible
    STATUS     current
    DESCRIPTION
        "A humidity sensor entry."
    INDEX { humiSensorId }
    ::= { humiSensorTable 1 }

HumiSensorEntry ::= SEQUENCE {
    humiSensorId                       DisplayString,
    humiSensorValue                    Integer32,
    humiSensorErrorStatus              ErrorStatus,
    humiSensorLabel                    DisplayString,
    humiSensorEncId                    DisplayString,
    humiSensorPortId                   DisplayString,
    humiSensorValueStr                 DisplayString,
    humiSensorValueInt                 Integer32
}

humiSensorId   OBJECT-TYPE
    SYNTAX     DisplayString (SIZE (0..127))
    MAX-ACCESS read-only
    STATUS     current
    DESCRIPTION
        "The unique id of the sensor."
    ::= { humiSensorEntry 1 }

humiSensorValue OBJECT-TYPE
    SYNTAX     Integer32 (0..1000)
    MAX-ACCESS read-only
    STATUS     current
    DESCRIPTION
        "The relative humidity measured by the sensor in tenths of a percent."
    ::= { humiSensorEntry 2 }

humiSensorErrorStatus OBJECT-TYPE
    SYNTAX     ErrorStatus
    MAX-ACCESS read-only
    STATUS     current
    DESCRIPTION
        "The error status of the sensor.  If there are no error conditions
         reported for the sensor, the status is normal.  Otherwise, the status is
         reported as the severity value of the highest severity error condition
         that is not resolved for the sensor."
    ::= { humiSensorEntry 3 }

humiSensorLabel OBJECT-TYPE
    SYNTAX     DisplayString
    MAX-ACCESS read-only
    STATUS     current
    DESCRIPTION
        "The unique label assigned to the sensor."
    ::= { humiSensorEntry 4 }

humiSensorEncId OBJECT-TYPE
    SYNTAX     DisplayString (SIZE (0..127))
    MAX-ACCESS read-only
    STATUS     current
    DESCRIPTION
        "The id of the physical enclosure containing the sensor."
    ::= { humiSensorEntry 5 }

humiSensorPortId OBJECT-TYPE
    SYNTAX     DisplayString (SIZE (0..127))
    MAX-ACCESS read-only
    STATUS     current
    DESCRIPTION
        "The id of the port the sensor is plugged into (or empty string
         if it is not plugged into a port)."
    ::= { humiSensorEntry 6 }

humiSensorValueStr OBJECT-TYPE
    SYNTAX     DisplayString
    MAX-ACCESS read-only
    STATUS     current
    DESCRIPTION
        "The humidity reading, in percent, shown as a string (or empty string
         if it is not plugged into a port)."
    ::= { humiSensorEntry 7 }

humiSensorValueInt OBJECT-TYPE
    SYNTAX     Integer32 (0..100)
    MAX-ACCESS read-only
    STATUS     current
    DESCRIPTION
        "The relative humidity measured by the sensor in percent."
    ::= { humiSensorEntry 8 }

dewPointSensorTable OBJECT-TYPE
    SYNTAX     SEQUENCE OF DewPointSensorEntry
    MAX-ACCESS not-accessible
    STATUS     current
    DESCRIPTION
        "A list of dew point sensor entries."
    ::= { netBotzNumericSensors 3 }

dewPointSensorEntry OBJECT-TYPE
    SYNTAX     DewPointSensorEntry
    MAX-ACCESS not-accessible
    STATUS     current
    DESCRIPTION
        "An ampere sensor entry."
    INDEX { dewPointSensorId }
    ::= { dewPointSensorTable 1 }

DewPointSensorEntry ::= SEQUENCE {
    dewPointSensorId                      DisplayString,
    dewPointSensorValue                   Integer32,
    dewPointSensorErrorStatus             ErrorStatus,
    dewPointSensorLabel                   DisplayString,
    dewPointSensorEncId                   DisplayString,
    dewPointSensorPortId                  DisplayString,
    dewPointSensorValueStr                DisplayString,
    dewPointSensorValueInt                Integer32
}

dewPointSensorId OBJECT-TYPE
    SYNTAX     DisplayString (SIZE (0..127))
    MAX-ACCESS read-only
    STATUS     current
    DESCRIPTION
        "The unique id of the sensor."
    ::= { dewPointSensorEntry 1 }

dewPointSensorValue OBJECT-TYPE
    SYNTAX     Integer32 (-500..1000)
    MAX-ACCESS read-only
    STATUS     current
    DESCRIPTION
        "The dew point value measured by the sensor in tenths of a degree Celsius."
    ::= { dewPointSensorEntry 2 }

dewPointSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { dewPointSensorEntry 3 }

dewPointSensorLabel OBJECT-TYPE
    SYNTAX     DisplayString
    MAX-ACCESS read-only
    STATUS     current
    DESCRIPTION
        "The unique label assigned to the sensor."
    ::= { dewPointSensorEntry 4 }

dewPointSensorEncId OBJECT-TYPE
    SYNTAX     DisplayString (SIZE (0..127))
    MAX-ACCESS read-only
    STATUS     current
    DESCRIPTION
        "The id of the physical enclosure containing the sensor."
    ::= { dewPointSensorEntry 5 }

dewPointSensorPortId OBJECT-TYPE
    SYNTAX     DisplayString (SIZE (0..127))
    MAX-ACCESS read-only
    STATUS     current
    DESCRIPTION
        "The id of the port the sensor is plugged into (or empty string
         if it is not plugged into a port)."
    ::= { dewPointSensorEntry 6 }

dewPointSensorValueStr OBJECT-TYPE
    SYNTAX     DisplayString
    MAX-ACCESS read-only
    STATUS     current
    DESCRIPTION
        "The dew point reading, in degrees celsius, shown as a string (or empty string
         if it is not plugged into a port)."
    ::= { dewPointSensorEntry 7 }

dewPointSensorValueInt OBJECT-TYPE
    SYNTAX     Integer32 (-50..100)
    MAX-ACCESS read-only
    STATUS     current
    DESCRIPTION
        "The dew point value measured by the sensor in degrees Celsius."
    ::= { dewPointSensorEntry 8 }

audioSensorTable OBJECT-TYPE
    SYNTAX     SEQUENCE OF AudioSensorEntry
    MAX-ACCESS not-accessible
    STATUS     current
    DESCRIPTION
        "A list of audio sensor entries."
    ::= { netBotzNumericSensors 4 }

audioSensorEntry OBJECT-TYPE
    SYNTAX     AudioSensorEntry
    MAX-ACCESS not-accessible
    STATUS     current
    DESCRIPTION
        "An audio sensor entry."
    INDEX { audioSensorId }
    ::= { audioSensorTable 1 }

AudioSensorEntry ::= SEQUENCE {
    audioSensorId                      DisplayString,
    audioSensorValue                   Integer32,
    audioSensorErrorStatus             ErrorStatus,
    audioSensorLabel                   DisplayString,
    audioSensorEncId                   DisplayString,
    audioSensorPortId                  DisplayString,
    audioSensorValueStr                DisplayString,
    audioSensorValueInt                Integer32
}

audioSensorId  OBJECT-TYPE
    SYNTAX     DisplayString (SIZE (0..127))
    MAX-ACCESS read-only
    STATUS     current
    DESCRIPTION
        "The unique id of the sensor."
    ::= { audioSensorEntry 1 }

audioSensorValue OBJECT-TYPE
    SYNTAX     Integer32
    MAX-ACCESS read-only
    STATUS     current
    DESCRIPTION
        "The (unitless) audio level measured by the sensor."
    ::= { audioSensorEntry 2 }

audioSensorErrorStatus OBJECT-TYPE
    SYNTAX     ErrorStatus
    MAX-ACCESS read-only
    STATUS     current
    DESCRIPTION
        "The error status of the sensor.  If there are no error conditions
         reported for the sensor, the status is normal.  Otherwise, the status is
         reported as the severity value of the highest severity error condition
         that is not resolved for the sensor."
    ::= { audioSensorEntry 3 }

audioSensorLabel OBJECT-TYPE
    SYNTAX     DisplayString
    MAX-ACCESS read-only
    STATUS     current
    DESCRIPTION
        "The unique label assigned to the sensor."
   ::= { audioSensorEntry 4 }

audioSensorEncId OBJECT-TYPE
    SYNTAX     DisplayString (SIZE (0..127))
    MAX-ACCESS read-only
    STATUS     current
    DESCRIPTION
        "The id of the physical enclosure containing the sensor."
    ::= { audioSensorEntry 5 }

audioSensorPortId OBJECT-TYPE
    SYNTAX     DisplayString (SIZE (0..127))
    MAX-ACCESS read-only
    STATUS     current
    DESCRIPTION
        "The id of the port the sensor is plugged into (or empty string
         if it is not plugged into a port)."
    ::= { audioSensorEntry 6 }

audioSensorValueStr OBJECT-TYPE
    SYNTAX     DisplayString
    MAX-ACCESS read-only
    STATUS     current
    DESCRIPTION
        "The audio reading shown as a string (or empty string
         if it is not plugged into a port)."
    ::= { audioSensorEntry 7 }

audioSensorValueInt OBJECT-TYPE
    SYNTAX     Integer32
    MAX-ACCESS read-only
    STATUS     current
    DESCRIPTION
        "The (unitless) audio level measured by the sensor (1/10 of audioSensorValue)."
    ::= { audioSensorEntry 8 }

airFlowSensorTable OBJECT-TYPE
    SYNTAX     SEQUENCE OF AirFlowSensorEntry
    MAX-ACCESS not-accessible
    STATUS     current
    DESCRIPTION
        "A list of airflow sensor entries."
    ::= { netBotzNumericSensors 5 }

airFlowSensorEntry OBJECT-TYPE
    SYNTAX     AirFlowSensorEntry
    MAX-ACCESS not-accessible
    STATUS     current
    DESCRIPTION
        "An air flow sensor entry."
    INDEX { airFlowSensorId }
    ::= { airFlowSensorTable 1 }

AirFlowSensorEntry ::= SEQUENCE {
    airFlowSensorId                      DisplayString,
    airFlowSensorValue                   Integer32,
    airFlowSensorErrorStatus             ErrorStatus,
    airFlowSensorLabel                   DisplayString,
    airFlowSensorEncId                   DisplayString,
    airFlowSensorPortId                  DisplayString,
    airFlowSensorValueStr                DisplayString,
    airFlowSensorValueInt                Integer32
}

airFlowSensorId OBJECT-TYPE
    SYNTAX     DisplayString (SIZE (0..127))
    MAX-ACCESS read-only
    STATUS     current
    DESCRIPTION
        "The unique id of the sensor."
    ::= { airFlowSensorEntry 1 }

airFlowSensorValue OBJECT-TYPE
    SYNTAX     Integer32 (0..10000)
    MAX-ACCESS read-only
    STATUS     current
    DESCRIPTION
        "The air flow measured by the sensor in tenths of a meter per minute."
    ::= { airFlowSensorEntry 2 }

airFlowSensorErrorStatus OBJECT-TYPE
    SYNTAX     ErrorStatus
    MAX-ACCESS read-only
    STATUS     current
    DESCRIPTION
        "The error status of the sensor.  If there are no error conditions
         reported for the sensor, the status is normal.  Otherwise, the status is
         reported as the severity value of the highest severity error condition
         that is not resolved for the sensor."
    ::= { airFlowSensorEntry 3 }

airFlowSensorLabel OBJECT-TYPE
    SYNTAX     DisplayString
    MAX-ACCESS read-only
    STATUS     current
    DESCRIPTION
        "The unique label assigned to the sensor."
    ::= { airFlowSensorEntry 4 }

airFlowSensorEncId OBJECT-TYPE
    SYNTAX     DisplayString (SIZE (0..127))
    MAX-ACCESS read-only
    STATUS     current
    DESCRIPTION
        "The id of the physical enclosure containing the sensor."
    ::= { airFlowSensorEntry 5 }

airFlowSensorPortId OBJECT-TYPE
    SYNTAX     DisplayString (SIZE (0..127))
    MAX-ACCESS read-only
    STATUS     current
    DESCRIPTION
        "The id of the port the sensor is plugged into (or empty string
         if it is not plugged into a port)."
    ::= { airFlowSensorEntry 6 }

airFlowSensorValueStr OBJECT-TYPE
    SYNTAX     DisplayString
    MAX-ACCESS read-only
    STATUS     current
    DESCRIPTION
        "The airflow reading, in meters per minute, shown as a string (or empty string
         if it is not plugged into a port)."
    ::= { airFlowSensorEntry 7 }

airFlowSensorValueInt OBJECT-TYPE
    SYNTAX     Integer32 (0..1000)
    MAX-ACCESS read-only
    STATUS     current
    DESCRIPTION
        "The air flow measured by the sensor in meters per minute."
    ::= { airFlowSensorEntry 8 }

ampDetectSensorTable OBJECT-TYPE
    SYNTAX     SEQUENCE OF AmpDetectSensorEntry
    MAX-ACCESS not-accessible
    STATUS     current
    DESCRIPTION
        "A list of amp detect sensor entries."
    ::= { netBotzNumericSensors 6 }

ampDetectSensorEntry OBJECT-TYPE
    SYNTAX     AmpDetectSensorEntry
    MAX-ACCESS not-accessible
    STATUS     current
    DESCRIPTION
        "An ampere sensor entry."
    INDEX { ampDetectSensorId }
    ::= { ampDetectSensorTable 1 }

AmpDetectSensorEntry ::= SEQUENCE {
    ampDetectSensorId                      DisplayString,
    ampDetectSensorValue                   Integer32,
    ampDetectSensorErrorStatus             ErrorStatus,
    ampDetectSensorLabel                   DisplayString,
    ampDetectSensorEncId                   DisplayString,
    ampDetectSensorPortId                  DisplayString,
    ampDetectSensorValueStr                DisplayString,
    ampDetectSensorValueInt                Integer32
}

ampDetectSensorId OBJECT-TYPE
    SYNTAX     DisplayString (SIZE (0..127))
    MAX-ACCESS read-only
    STATUS     current
    DESCRIPTION
        "The unique id of the sensor."
    ::= { ampDetectSensorEntry 1 }

ampDetectSensorValue OBJECT-TYPE
    SYNTAX     Integer32 (0..65535)
    MAX-ACCESS read-only
    STATUS     current
    DESCRIPTION
        "The value measured by the sensor in tenths of an ampere."
    ::= { ampDetectSensorEntry 2 }

ampDetectSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { ampDetectSensorEntry 3 }

ampDetectSensorLabel OBJECT-TYPE
    SYNTAX     DisplayString
    MAX-ACCESS read-only
    STATUS     current
    DESCRIPTION
        "The unique label assigned to the sensor."
    ::= { ampDetectSensorEntry 4 }

ampDetectSensorEncId OBJECT-TYPE
    SYNTAX     DisplayString (SIZE (0..127))
    MAX-ACCESS read-only
    STATUS     current
    DESCRIPTION
        "The id of the physical enclosure containing the sensor."
    ::= { ampDetectSensorEntry 5 }

ampDetectSensorPortId OBJECT-TYPE
    SYNTAX     DisplayString (SIZE (0..127))
    MAX-ACCESS read-only
    STATUS     current
    DESCRIPTION
        "The id of the port the sensor is plugged into (or empty string
         if it is not plugged into a port)."
    ::= { ampDetectSensorEntry 6 }

ampDetectSensorValueStr OBJECT-TYPE
    SYNTAX     DisplayString
    MAX-ACCESS read-only
    STATUS     current
    DESCRIPTION
        "The amp detect reading, in amperes, shown as a string (or empty string
         if it is not plugged into a port)."
    ::= { ampDetectSensorEntry 7 }

ampDetectSensorValueInt OBJECT-TYPE
    SYNTAX     Integer32 (0..6554)
    MAX-ACCESS read-only
    STATUS     current
    DESCRIPTION
        "The value measured by the sensor in amperes."
    ::= { ampDetectSensorEntry 8 }

otherNumericSensorTable OBJECT-TYPE
    SYNTAX     SEQUENCE OF OtherNumericSensorEntry
    MAX-ACCESS not-accessible
    STATUS     current
    DESCRIPTION
        "A list of other numeric sensor entries."
    ::= { netBotzNumericSensors 10 }

otherNumericSensorEntry OBJECT-TYPE
    SYNTAX     OtherNumericSensorEntry
    MAX-ACCESS not-accessible
    STATUS     current
    DESCRIPTION
        "Other numeric sensor entry."
    INDEX { otherNumericSensorId }
    ::= { otherNumericSensorTable 1 }

OtherNumericSensorEntry ::= SEQUENCE {
    otherNumericSensorId                      DisplayString,
    otherNumericSensorValue                   Integer32,
    otherNumericSensorErrorStatus             ErrorStatus,
    otherNumericSensorLabel                   DisplayString,
    otherNumericSensorEncId                   DisplayString,
    otherNumericSensorPortId                  DisplayString,
    otherNumericSensorValueStr                DisplayString,
    otherNumericSensorValueInt                Integer32,
    otherNumericSensorUnits                   DisplayString,
    otherNumericSensorValueIntX1000           Integer32,
    otherNumericSensorValueIntX1000000           Integer32
}

otherNumericSensorId OBJECT-TYPE
    SYNTAX     DisplayString (SIZE (0..127))
    MAX-ACCESS read-only
    STATUS     current
    DESCRIPTION
        "The unique id of the sensor."
    ::= { otherNumericSensorEntry 1 }

otherNumericSensorValue OBJECT-TYPE
    SYNTAX     Integer32
    MAX-ACCESS read-only
    STATUS     current
    DESCRIPTION
        "The value measured by the sensor in tenths of the unit of measure."
    ::= { otherNumericSensorEntry 2 }

otherNumericSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { otherNumericSensorEntry 3 }

otherNumericSensorLabel OBJECT-TYPE
    SYNTAX     DisplayString
    MAX-ACCESS read-only
    STATUS     current
    DESCRIPTION
        "The unique label assigned to the sensor."
    ::= { otherNumericSensorEntry 4 }

otherNumericSensorEncId OBJECT-TYPE
    SYNTAX     DisplayString (SIZE (0..127))
    MAX-ACCESS read-only
    STATUS     current
    DESCRIPTION
        "The id of the physical enclosure containing the sensor."
    ::= { otherNumericSensorEntry 5 }

otherNumericSensorPortId OBJECT-TYPE
    SYNTAX     DisplayString (SIZE (0..127))
    MAX-ACCESS read-only
    STATUS     current
    DESCRIPTION
        "The id of the port the sensor is plugged into (or empty string
         if it is not plugged into a port)."
    ::= { otherNumericSensorEntry 6 }

otherNumericSensorValueStr OBJECT-TYPE
    SYNTAX     DisplayString
    MAX-ACCESS read-only
    STATUS     current
    DESCRIPTION
        "The sensor reading shown as a string (or empty string
         if it is not plugged into a port)."
    ::= { otherNumericSensorEntry 7 }

otherNumericSensorValueInt OBJECT-TYPE
    SYNTAX     Integer32
    MAX-ACCESS read-only
    STATUS     current
    DESCRIPTION
        "The value measured by the sensor in the unit of measure (1/10 of otherNumericSensorValue)"
    ::= { otherNumericSensorEntry 8 }

otherNumericSensorUnits OBJECT-TYPE
    SYNTAX     DisplayString
    MAX-ACCESS read-only
    STATUS     current
    DESCRIPTION
        "The unit of measure for the sensor value."
    ::= { otherNumericSensorEntry 9 }

otherNumericSensorValueIntX1000 OBJECT-TYPE
    SYNTAX     Integer32
    MAX-ACCESS read-only
    STATUS     current
    DESCRIPTION
        "The value measured by the sensor in thousandths of the unit of measure (100 times otherNumericSensorValue)"
    ::= { otherNumericSensorEntry 10 }

otherNumericSensorValueIntX1000000 OBJECT-TYPE
    SYNTAX     Integer32
    MAX-ACCESS read-only
    STATUS     current
    DESCRIPTION
        "The value measured by the sensor in millionths of the unit of measure (100000 times otherNumericSensorValue)"
    ::= { otherNumericSensorEntry 11 }
        
-- State Sensors Group
-- This group defines sensors having an integer value which is
-- a defined state id or index.

dryContactSensorTable OBJECT-TYPE
    SYNTAX     SEQUENCE OF DryContactSensorEntry
    MAX-ACCESS not-accessible
    STATUS     current
    DESCRIPTION
        "A list of dry contact sensor entries."
    ::= { netBotzStateSensors 1 }

dryContactSensorEntry OBJECT-TYPE
    SYNTAX     DryContactSensorEntry
    MAX-ACCESS not-accessible
    STATUS     current
    DESCRIPTION
        "Dry contact sensor entry."
    INDEX { dryContactSensorId }
    ::= { dryContactSensorTable 1 }

DryContactSensorEntry ::= SEQUENCE {
    dryContactSensorId                      DisplayString,
    dryContactSensorValue                   INTEGER,
    dryContactSensorErrorStatus             ErrorStatus,
    dryContactSensorLabel                   DisplayString,
    dryContactSensorEncId                   DisplayString,
    dryContactSensorPortId                  DisplayString,
    dryContactSensorValueStr              DisplayString
}

dryContactSensorId OBJECT-TYPE
    SYNTAX     DisplayString (SIZE (0..127))
    MAX-ACCESS read-only
    STATUS     current
    DESCRIPTION
        "The unique id of the sensor."
    ::= { dryContactSensorEntry 1 }

dryContactSensorValue OBJECT-TYPE
    SYNTAX     INTEGER { null(-1), open(0), closed(1) }
    MAX-ACCESS read-only
    STATUS     current
    DESCRIPTION
        "Whether the dry sensor contact is open or closed."
    ::= { dryContactSensorEntry 2 }

dryContactSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { dryContactSensorEntry 3 }

dryContactSensorLabel OBJECT-TYPE
    SYNTAX     DisplayString
    MAX-ACCESS read-only
    STATUS     current
    DESCRIPTION
        "The unique label assigned to the sensor."
    ::= { dryContactSensorEntry 4 }

dryContactSensorEncId OBJECT-TYPE
    SYNTAX     DisplayString (SIZE (0..127))
    MAX-ACCESS read-only
    STATUS     current
    DESCRIPTION
        "The id of the physical enclosure containing the sensor."
    ::= { dryContactSensorEntry 5 }

dryContactSensorPortId OBJECT-TYPE
    SYNTAX     DisplayString (SIZE (0..127))
    MAX-ACCESS read-only
    STATUS     current
    DESCRIPTION
        "The id of the port the sensor is plugged into (or empty string
         if it is not plugged into a port)."
    ::= { dryContactSensorEntry 6 }

dryContactSensorValueStr OBJECT-TYPE
    SYNTAX     DisplayString
    MAX-ACCESS read-only
    STATUS     current
    DESCRIPTION
        "The enum value label for the state reported by the sensor."
    ::= { dryContactSensorEntry 7 }

doorSwitchSensorTable OBJECT-TYPE
    SYNTAX     SEQUENCE OF DoorSwitchSensorEntry
    MAX-ACCESS not-accessible
    STATUS     current
    DESCRIPTION
        "A list of door switch sensor entries."
    ::= { netBotzStateSensors 2 }

doorSwitchSensorEntry OBJECT-TYPE
    SYNTAX     DoorSwitchSensorEntry
    MAX-ACCESS not-accessible
    STATUS     current
    DESCRIPTION
        "Door switch sensor entry."
    INDEX { doorSwitchSensorId }
    ::= { doorSwitchSensorTable 1 }

DoorSwitchSensorEntry ::= SEQUENCE {
    doorSwitchSensorId                      DisplayString,
    doorSwitchSensorValue                   INTEGER,
    doorSwitchSensorErrorStatus             ErrorStatus,
    doorSwitchSensorLabel                   DisplayString,
    doorSwitchSensorEncId                   DisplayString,
    doorSwitchSensorPortId                  DisplayString,
    doorSwitchSensorValueStr              DisplayString
}

doorSwitchSensorId OBJECT-TYPE
    SYNTAX     DisplayString (SIZE (0..127))
    MAX-ACCESS read-only
    STATUS     current
    DESCRIPTION
        "The unique id of the sensor."
    ::= { doorSwitchSensorEntry 1 }

doorSwitchSensorValue OBJECT-TYPE
    SYNTAX     INTEGER { null(-1), open(0), closed(1) }
    MAX-ACCESS read-only
    STATUS     current
    DESCRIPTION
        "Whether the door is open or closed."
    ::= { doorSwitchSensorEntry 2 }

doorSwitchSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { doorSwitchSensorEntry 3 }

doorSwitchSensorLabel OBJECT-TYPE
    SYNTAX     DisplayString
    MAX-ACCESS read-only
    STATUS     current
    DESCRIPTION
        "The unique label assigned to the sensor."
    ::= { doorSwitchSensorEntry 4 }

doorSwitchSensorEncId OBJECT-TYPE
    SYNTAX     DisplayString (SIZE (0..127))
    MAX-ACCESS read-only
    STATUS     current
    DESCRIPTION
        "The id of the physical enclosure containing the sensor."
    ::= { doorSwitchSensorEntry 5 }

doorSwitchSensorPortId OBJECT-TYPE
    SYNTAX     DisplayString (SIZE (0..127))
    MAX-ACCESS read-only
    STATUS     current
    DESCRIPTION
        "The id of the port the sensor is plugged into (or empty string
         if it is not plugged into a port)."
    ::= { doorSwitchSensorEntry 6 }

doorSwitchSensorValueStr OBJECT-TYPE
    SYNTAX     DisplayString
    MAX-ACCESS read-only
    STATUS     current
    DESCRIPTION
        "The enum value label for the state reported by the sensor."
    ::= { doorSwitchSensorEntry 7 }

cameraMotionSensorTable OBJECT-TYPE
    SYNTAX     SEQUENCE OF CameraMotionSensorEntry
    MAX-ACCESS not-accessible
    STATUS     current
    DESCRIPTION
        "A list of camera motion sensor entries."
    ::= { netBotzStateSensors 3 }

cameraMotionSensorEntry OBJECT-TYPE
    SYNTAX     CameraMotionSensorEntry
    MAX-ACCESS not-accessible
    STATUS     current
    DESCRIPTION
        "Camera motion sensor entry."
    INDEX { cameraMotionSensorId }
    ::= { cameraMotionSensorTable 1 }

CameraMotionSensorEntry ::= SEQUENCE {
    cameraMotionSensorId                      DisplayString,
    cameraMotionSensorValue                   INTEGER,
    cameraMotionSensorErrorStatus             ErrorStatus,
    cameraMotionSensorLabel                   DisplayString,
    cameraMotionSensorEncId                   DisplayString,
    cameraMotionSensorPortId                  DisplayString,
    cameraMotionSensorValueStr                DisplayString
}

cameraMotionSensorId OBJECT-TYPE
    SYNTAX     DisplayString (SIZE (0..127))
    MAX-ACCESS read-only
    STATUS     current
    DESCRIPTION
        "The unique id of the sensor."
    ::= { cameraMotionSensorEntry 1 }

cameraMotionSensorValue OBJECT-TYPE
    SYNTAX     INTEGER { null(-1), noMotion(0), motionDetected(1) }
    MAX-ACCESS read-only
    STATUS     current
    DESCRIPTION
        "Whether motion is detected by the camera sensor."
    ::= { cameraMotionSensorEntry 2 }

cameraMotionSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { cameraMotionSensorEntry 3 }

cameraMotionSensorLabel OBJECT-TYPE
    SYNTAX     DisplayString
    MAX-ACCESS read-only
    STATUS     current
    DESCRIPTION
        "The unique label assigned to the sensor."
    ::= { cameraMotionSensorEntry 4 }

cameraMotionSensorEncId OBJECT-TYPE
    SYNTAX     DisplayString (SIZE (0..127))
    MAX-ACCESS read-only
    STATUS     current
    DESCRIPTION
        "The id of the physical enclosure containing the sensor."
    ::= { cameraMotionSensorEntry 5 }

cameraMotionSensorPortId OBJECT-TYPE
    SYNTAX     DisplayString (SIZE (0..127))
    MAX-ACCESS read-only
    STATUS     current
    DESCRIPTION
        "The id of the port the sensor is plugged into (or empty string
         if it is not plugged into a port)."
    ::= { cameraMotionSensorEntry 6 }

cameraMotionSensorValueStr OBJECT-TYPE
    SYNTAX     DisplayString
    MAX-ACCESS read-only
    STATUS     current
    DESCRIPTION
        "The enum value label for the state reported by the sensor."
    ::= { cameraMotionSensorEntry 7 }

otherStateSensorTable OBJECT-TYPE
    SYNTAX     SEQUENCE OF OtherStateSensorEntry
    MAX-ACCESS not-accessible
    STATUS     current
    DESCRIPTION
        "A list of other state sensor entries."
    ::= { netBotzStateSensors 10 }

otherStateSensorEntry OBJECT-TYPE
    SYNTAX     OtherStateSensorEntry
    MAX-ACCESS not-accessible
    STATUS     current
    DESCRIPTION
        "Other state sensor entry."
    INDEX { otherStateSensorId }
    ::= { otherStateSensorTable 1 }

OtherStateSensorEntry ::= SEQUENCE {
    otherStateSensorId                      DisplayString,
    otherStateSensorValue                   INTEGER,
    otherStateSensorErrorStatus             ErrorStatus,
    otherStateSensorLabel                   DisplayString,
    otherStateSensorEncId                   DisplayString,
    otherStateSensorPortId                  DisplayString,
    otherStateSensorValueStr              DisplayString
}

otherStateSensorId OBJECT-TYPE
    SYNTAX     DisplayString (SIZE (0..127))
    MAX-ACCESS read-only
    STATUS     current
    DESCRIPTION
        "The unique id of the sensor."
    ::= { otherStateSensorEntry 1 }

otherStateSensorValue OBJECT-TYPE
    SYNTAX     INTEGER
    MAX-ACCESS read-only
    STATUS     current
    DESCRIPTION
        "State value reported by the sensor."
    ::= { otherStateSensorEntry 2 }
    
otherStateSensorErrorStatus OBJECT-TYPE
    SYNTAX     ErrorStatus
    MAX-ACCESS read-only
    STATUS     current
    DESCRIPTION
        "The operational status of the sensor.  If there are no error conditions
         reported for the sensor, the status is normal.  Otherwise, the status is
         reported as the severity value of the highest severity error condition
         that is not resolved for the sensor."
    ::= { otherStateSensorEntry 3 }

otherStateSensorLabel OBJECT-TYPE
    SYNTAX     DisplayString
    MAX-ACCESS read-only
    STATUS     current
    DESCRIPTION
        "The unique label assigned to the sensor."
    ::= { otherStateSensorEntry 4 }

otherStateSensorEncId OBJECT-TYPE
    SYNTAX     DisplayString (SIZE (0..127))
    MAX-ACCESS read-only
    STATUS     current
    DESCRIPTION
        "The id of the physical enclosure containing the sensor."
    ::= { otherStateSensorEntry 5 }

otherStateSensorPortId OBJECT-TYPE
    SYNTAX     DisplayString (SIZE (0..127))
    MAX-ACCESS read-only
    STATUS     current
    DESCRIPTION
        "The id of port the sensor is plugged into (or empty string
         if it is not plugged into a port)."
    ::= { otherStateSensorEntry 6 }

otherStateSensorValueStr OBJECT-TYPE
    SYNTAX     DisplayString
    MAX-ACCESS read-only
    STATUS     current
    DESCRIPTION
        "The enum value label for the state reported by the sensor."
    ::= { otherStateSensorEntry 7 }

-- Error Conditions Group
--

errorCondTable OBJECT-TYPE
    SYNTAX     SEQUENCE OF ErrorCondEntry
    MAX-ACCESS not-accessible
    STATUS     current
    DESCRIPTION
        "A list of active and resolved error conditions."
    ::= { netBotzErrors 1 }

errorCondEntry OBJECT-TYPE
    SYNTAX     ErrorCondEntry
    MAX-ACCESS not-accessible
    STATUS     current
    DESCRIPTION
        "Error condition entry."
    INDEX { errorCondId }
    ::= { errorCondTable 1 }

ErrorCondEntry ::= SEQUENCE {
    errorCondId                          DisplayString,
    errorCondSeverity                    ErrorStatus,
    errorCondTypeId                      DisplayString,
    errorCondStartTime                   DateAndTime,
    errorCondStartTimeStr                DisplayString,
    errorCondResolved                    BoolValue,
    errorCondResolvedTime                DateAndTime,
    errorCondResolvedTimeStr             DisplayString,
    errorCondEncId                       DisplayString,
    errorCondPortId                      DisplayString,
    errorCondSensorId                    DisplayString
}

errorCondId    OBJECT-TYPE
    SYNTAX     DisplayString (SIZE (0..127))
    MAX-ACCESS read-only
    STATUS     current
    DESCRIPTION
        "The unique id of the error condition."
    ::= { errorCondEntry 1 }

errorCondSeverity OBJECT-TYPE
    SYNTAX     ErrorStatus
    MAX-ACCESS read-only
    STATUS     current
    DESCRIPTION
        "The relative severity of the error condition."
    ::= { errorCondEntry 2 }

errorCondTypeId  OBJECT-TYPE
    SYNTAX     DisplayString (SIZE (0..127))
    MAX-ACCESS read-only
    STATUS     current
    DESCRIPTION
        "The error type id reported for the error condition."
    ::= { errorCondEntry 3 }

errorCondStartTime OBJECT-TYPE
    SYNTAX     DateAndTime
    MAX-ACCESS read-only
    STATUS     current
    DESCRIPTION
        "The start time of the error condition, in msec since 1/1/1970."
    ::= { errorCondEntry 4 }

errorCondStartTimeStr OBJECT-TYPE
    SYNTAX     DisplayString
    MAX-ACCESS read-only
    STATUS     current
    DESCRIPTION
        "The start time of the error condition, as ISO date-time formatted string (UTC)."
    ::= { errorCondEntry 5 }

errorCondResolved OBJECT-TYPE
    SYNTAX     BoolValue
    MAX-ACCESS read-only
    STATUS     current
    DESCRIPTION
        "Whether the error condition was resolved."
    ::= { errorCondEntry 6 }

errorCondResolvedTime OBJECT-TYPE
    SYNTAX     DateAndTime
    MAX-ACCESS read-only
    STATUS     current
    DESCRIPTION
        "The time the error condition was resolved (if it was resolved), in msec since 1/1/1970."
    ::= { errorCondEntry 7 }

errorCondResolvedTimeStr OBJECT-TYPE
    SYNTAX     DisplayString
    MAX-ACCESS read-only
    STATUS     current
    DESCRIPTION
        "The time the error condition was resolved (if it was resolved), as ISO date-time formatted string (UTC)."
    ::= { errorCondEntry 8 }

errorCondEncId OBJECT-TYPE
    SYNTAX     DisplayString (SIZE (0..127))
    MAX-ACCESS read-only
    STATUS     current
    DESCRIPTION
        "The id of the physical enclosure associated with the error."
    ::= { errorCondEntry 9 }

errorCondPortId OBJECT-TYPE
    SYNTAX     DisplayString (SIZE (0..127))
    MAX-ACCESS read-only
    STATUS     current
    DESCRIPTION
        "The id of the port associated with the error (or empty string
         if the error is not associated with a port)."
    ::= { errorCondEntry 10 }

errorCondSensorId OBJECT-TYPE
    SYNTAX     DisplayString (SIZE (0..127))
    MAX-ACCESS read-only
    STATUS     current
    DESCRIPTION
        "The id of the sensor associated with the error (or empty string
         if the error is not associated with a sensor.)"
    ::= { errorCondEntry 11 }


-- Alert specific definitions
--

netBotzV2TrapErrorID    OBJECT-TYPE
        SYNTAX          DisplayString (SIZE (0..127))
        MAX-ACCESS              read-only
        STATUS          current
        DESCRIPTION     "Unique ID of error condition that produced the trap"
        ::= { netBotzV2TrapParms 1 }

netBotzV2TrapErrorType  OBJECT-TYPE
        SYNTAX          DisplayString (SIZE (0..127))
        MAX-ACCESS              read-only
        STATUS          current
        DESCRIPTION     "Symbolic ID of error type"
        ::= { netBotzV2TrapParms 2 }


netBotzV2TrapErrorTypeLabel     OBJECT-TYPE
        SYNTAX          DisplayString
        MAX-ACCESS              read-only
        STATUS          current
        DESCRIPTION     "Label for error type"
        ::= { netBotzV2TrapParms 3 }


netBotzV2TrapSensorID   OBJECT-TYPE
        SYNTAX          DisplayString (SIZE (0..127))
        MAX-ACCESS              read-only
        STATUS          current
        DESCRIPTION     "ID of sensor associated with error condition that produced the trap"
        ::= { netBotzV2TrapParms 4 }

netBotzV2TrapSensorLabel        OBJECT-TYPE
        SYNTAX          DisplayString
        MAX-ACCESS              read-only
        STATUS          current
        DESCRIPTION     "Label of sensor associated with error condition that produced the trap"
        ::= { netBotzV2TrapParms 5 }

netBotzV2TrapPodID      OBJECT-TYPE
        SYNTAX          DisplayString (SIZE (0..127))
        MAX-ACCESS              read-only
        STATUS          current
        DESCRIPTION     "ID of pod associated with error condition that produced the trap"
        ::= { netBotzV2TrapParms 6 }

netBotzV2TrapPodLabel   OBJECT-TYPE
        SYNTAX          DisplayString
        MAX-ACCESS              read-only
        STATUS          current
        DESCRIPTION     "Label of pod associated with error condition that produced the trap"
        ::= { netBotzV2TrapParms 7 }

netBotzV2TrapPortID     OBJECT-TYPE
        SYNTAX          DisplayString (SIZE (0..127))
        MAX-ACCESS              read-only
        STATUS          current
        DESCRIPTION     "ID of port associated with error condition that produced the trap"
        ::= { netBotzV2TrapParms 8 }

netBotzV2TrapPortLabel  OBJECT-TYPE
        SYNTAX          DisplayString
        MAX-ACCESS              read-only
        STATUS          current
        DESCRIPTION     "Label of port associated with error condition that produced the trap"
        ::= { netBotzV2TrapParms 9 }

netBotzV2TrapStartTime  OBJECT-TYPE
        SYNTAX          INTEGER
        MAX-ACCESS              read-only
        STATUS          current
        DESCRIPTION     "Start time (in UTC seconds) for error that produced the trap"
        ::= { netBotzV2TrapParms 10 }

netBotzV2TrapNotifyTime OBJECT-TYPE
        SYNTAX          INTEGER
        MAX-ACCESS              read-only
        STATUS          current
        DESCRIPTION     "Notification time (in UTC seconds) for error that produced the trap"
        ::= { netBotzV2TrapParms 11 }

netBotzV2TrapResolveTime        OBJECT-TYPE
        SYNTAX          INTEGER
        MAX-ACCESS              read-only
        STATUS          current
        DESCRIPTION     "Resolve time (in UTC seconds) for error that produced the trap"
        ::= { netBotzV2TrapParms 12 }

netBotzV2TrapSeverity   OBJECT-TYPE
        SYNTAX          INTEGER {
                        information(0),
                        warning(1),
                        error(2),
                        critical(3),
                        failure(4)
                        }
        MAX-ACCESS              read-only
        STATUS          current
        DESCRIPTION     "Severity of error that produced the trap"
        ::= { netBotzV2TrapParms 13 }

netBotzV2TrapSensorValue        OBJECT-TYPE
        SYNTAX          DisplayString
        MAX-ACCESS              read-only
        STATUS          current
        DESCRIPTION     "String presentation of value of sensor"
        ::= { netBotzV2TrapParms 14 }

netBotzV2TrapSensorValueInt     OBJECT-TYPE
        SYNTAX          INTEGER
        MAX-ACCESS              read-only
        STATUS          current
        DESCRIPTION     "Whole integer representation of value of sensor (without decimal portion)"
        ::= { netBotzV2TrapParms 15 }

netBotzV2TrapSensorValueFraction        OBJECT-TYPE
        SYNTAX          INTEGER
        MAX-ACCESS              read-only
        STATUS          current
        DESCRIPTION     "Fractional portion of value of sensor (multiplied by 1000000)"
        ::= { netBotzV2TrapParms 16 }


netBotzTempTooHigh NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION "Temperature sensor value too high."
        ::= { netBotzV2TempSensorTraps 0 2 }

netBotzTempTooHighRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION "Temperature sensor value is not longer too high."
        ::= { netBotzV2TempSensorTraps 0 102 }

netBotzTempTooLow NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION "Temperature sensor value too low."
        ::= { netBotzV2TempSensorTraps 0 3 }

netBotzTempTooLowRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION "Temperature sensor value is no longer too low."
        ::= { netBotzV2TempSensorTraps 0 103 }

netBotzTempTooHighTooLong NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Temperature sensor value too high for too long."
        ::= { netBotzV2TempSensorTraps 0 4 }

netBotzTempTooHighTooLongRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Temperature sensor value is not longer too high for too long."
        ::= { netBotzV2TempSensorTraps 0 104 }

netBotzTempTooLowTooLong NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Temperature sensor value too low for too long."
        ::= { netBotzV2TempSensorTraps 0 5 }

netBotzTempTooLowForTooLongRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Temperature sensor value is no longer too low for too long."
        ::= { netBotzV2TempSensorTraps 0 105 }

netBotzTempUnplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Temperature sensor unplugged."
        ::= { netBotzV2TempSensorTraps 0 6 }

netBotzTempReplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Temperature sensor no longer unplugged."
        ::= { netBotzV2TempSensorTraps 0 106 }

netBotzTempIncreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Temperature sensor value increasing too quickly."
        ::= { netBotzV2TempSensorTraps 0 8 }

netBotzTempNotIncreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Temperature sensor value no longer increasing too quickly."
        ::= { netBotzV2TempSensorTraps 0 108 }

netBotzTempDecreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Temperature sensor value decreasing too quickly."
        ::= { netBotzV2TempSensorTraps 0 9 }

netBotzTempNotDecreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Temperature sensor value no longer decreasing too quickly."
        ::= { netBotzV2TempSensorTraps 0 109 }

netBotzTempError NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Temperature sensor error."
        ::= { netBotzV2TempSensorTraps 0 1 }

netBotzTempErrorRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Temperature sensor error resolved."
        ::= { netBotzV2TempSensorTraps 0 101 }

netBotzHumidityTooHigh NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Humidity sensor value too high."
        ::= { netBotzV2HumiditySensorTraps 0 2 }

netBotzHumidityTooHighRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Humidity sensor value is not longer too high."
        ::= { netBotzV2HumiditySensorTraps 0 102 }

netBotzHumidityTooLow NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Humidity sensor value too low."
        ::= { netBotzV2HumiditySensorTraps 0 3 }

netBotzHumidityTooLowRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Humidity sensor value is no longer too low."
        ::= { netBotzV2HumiditySensorTraps 0 103 }

netBotzHumidityTooHighTooLong NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Humidity sensor value too high for too long."
        ::= { netBotzV2HumiditySensorTraps 0 4 }

netBotzHumidityTooHighTooLongRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Humidity sensor value is not longer too high for too long."
        ::= { netBotzV2HumiditySensorTraps 0 104 }

netBotzHumidityTooLowTooLong NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Humidity sensor value too low for too long."
        ::= { netBotzV2HumiditySensorTraps 0 5 }

netBotzHumidityTooLowForTooLongRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Humidity sensor value is no longer too low for too long."
        ::= { netBotzV2HumiditySensorTraps 0 105 }

netBotzHumidityUnplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Humidity sensor unplugged."
        ::= { netBotzV2HumiditySensorTraps 0 6 }

netBotzHumidityReplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Humidity sensor no longer unplugged."
        ::= { netBotzV2HumiditySensorTraps 0 106 }

netBotzHumidityIncreasingTooQuickly NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Humidity sensor value increasing too quickly."
        ::= { netBotzV2HumiditySensorTraps 0 8 }

netBotzHumidityNotIncreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Humidity sensor value no longer increasing too quickly."
        ::= { netBotzV2HumiditySensorTraps 0 108 }

netBotzHumidityDecreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Humidity sensor value decreasing too quickly."
        ::= { netBotzV2HumiditySensorTraps 0 9 }

netBotzHumidityNotDecreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Humidity sensor value no longer decreasing too quickly."
        ::= { netBotzV2HumiditySensorTraps 0 109 }

netBotzHumidityError NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Humidity sensor error."
        ::= { netBotzV2HumiditySensorTraps 0 1 }

netBotzHumidityErrorRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Humidity sensor error resolved."
        ::= { netBotzV2HumiditySensorTraps 0 101 }

netBotzDewPointTooHigh NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "DewPoint sensor value too high."
        ::= { netBotzV2DewPointSensorTraps 0 2 }

netBotzDewPointTooHighRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "DewPoint sensor value is not longer too high."
        ::= { netBotzV2DewPointSensorTraps 0 102 }

netBotzDewPointTooLow NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "DewPoint sensor value too low."
        ::= { netBotzV2DewPointSensorTraps 0 3 }

netBotzDewPointTooLowRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "DewPoint sensor value is no longer too low."
        ::= { netBotzV2DewPointSensorTraps 0 103 }

netBotzDewPointTooHighTooLong NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "DewPoint sensor value too high for too long."
        ::= { netBotzV2DewPointSensorTraps 0 4 }

netBotzDewPointTooHighTooLongRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "DewPoint sensor value is not longer too high for too long."
        ::= { netBotzV2DewPointSensorTraps 0 104 }

netBotzDewPointTooLowTooLong NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "DewPoint sensor value too low for too long."
        ::= { netBotzV2DewPointSensorTraps 0 5 }

netBotzDewPointTooLowForTooLongRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "DewPoint sensor value is no longer too low for too long."
        ::= { netBotzV2DewPointSensorTraps 0 105 }

netBotzDewPointUnplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "DewPoint sensor unplugged."
        ::= { netBotzV2DewPointSensorTraps 0 6 }

netBotzDewPointReplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "DewPoint sensor no longer unplugged."
        ::= { netBotzV2DewPointSensorTraps 0 106 }

netBotzDewPointIncreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "DewPoint sensor value increasing too quickly."
        ::= { netBotzV2DewPointSensorTraps 0 8 }

netBotzDewPointNotIncreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "DewPoint sensor value no longer increasing too quickly."
        ::= { netBotzV2DewPointSensorTraps 0 108 }

netBotzDewPointDecreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "DewPoint sensor value decreasing too quickly."
        ::= { netBotzV2DewPointSensorTraps 0 9 }

netBotzDewPointNotDecreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "DewPoint sensor value no longer decreasing too quickly."
        ::= { netBotzV2DewPointSensorTraps 0 109 }

netBotzDewPointError NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "DewPoint sensor error."
        ::= { netBotzV2DewPointSensorTraps 0 1 }

netBotzDewPointErrorRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "DewPoint sensor error resolved."
        ::= { netBotzV2DewPointSensorTraps 0 101 }

netBotzAirFlowTooHigh NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "AirFlow sensor value too high."
        ::= { netBotzV2AirFlowSensorTraps 0 2 }

netBotzAirFlowTooHighRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "AirFlow sensor value is not longer too high."
        ::= { netBotzV2AirFlowSensorTraps 0 102 }

netBotzAirFlowTooLow NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "AirFlow sensor value too low."
        ::= { netBotzV2AirFlowSensorTraps 0 3 }

netBotzAirFlowTooLowRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "AirFlow sensor value is no longer too low."
        ::= { netBotzV2AirFlowSensorTraps 0 103 }

netBotzAirFlowTooHighTooLong NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "AirFlow sensor value too high for too long."
        ::= { netBotzV2AirFlowSensorTraps 0 4 }

netBotzAirFlowTooHighTooLongRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "AirFlow sensor value is not longer too high for too long."
        ::= { netBotzV2AirFlowSensorTraps 0 104 }

netBotzAirFlowTooLowTooLong NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "AirFlow sensor value too low for too long."
        ::= { netBotzV2AirFlowSensorTraps 0 5 }

netBotzAirFlowTooLowForTooLongRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "AirFlow sensor value is no longer too low for too long."
        ::= { netBotzV2AirFlowSensorTraps 0 105 }

netBotzAirFlowUnplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "AirFlow sensor unplugged."
        ::= { netBotzV2AirFlowSensorTraps 0 6 }

netBotzAirFlowReplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "AirFlow sensor no longer unplugged."
        ::= { netBotzV2AirFlowSensorTraps 0 106 }

netBotzAirFlowIncreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "AirFlow sensor value increasing too quickly."
        ::= { netBotzV2AirFlowSensorTraps 0 8 }

netBotzAirFlowNotIncreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "AirFlow sensor value no longer increasing too quickly."
        ::= { netBotzV2AirFlowSensorTraps 0 108 }

netBotzAirFlowDecreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "AirFlow sensor value decreasing too quickly."
        ::= { netBotzV2AirFlowSensorTraps 0 9 }

netBotzAirFlowNotDecreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "AirFlow sensor value no longer decreasing too quickly."
        ::= { netBotzV2AirFlowSensorTraps 0 109 }

netBotzAirFlowError NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "AirFlow sensor error."
        ::= { netBotzV2AirFlowSensorTraps 0 1 }

netBotzAirFlowErrorRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "AirFlow sensor error resolved."
        ::= { netBotzV2AirFlowSensorTraps 0 101 }

netBotzAudioTooHigh NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Audio sensor value too high."
        ::= { netBotzV2AudioSensorTraps 0 2 }

netBotzAudioTooHighRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Audio sensor value is not longer too high."
        ::= { netBotzV2AudioSensorTraps 0 102 }

netBotzAudioTooLow NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Audio sensor value too low."
        ::= { netBotzV2AudioSensorTraps 0 3 }

netBotzAudioTooLowRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Audio sensor value is no longer too low."
        ::= { netBotzV2AudioSensorTraps 0 103 }

netBotzAudioTooHighTooLong NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Audio sensor value too high for too long."
        ::= { netBotzV2AudioSensorTraps 0 4 }

netBotzAudioTooHighTooLongRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Audio sensor value is not longer too high for too long."
        ::= { netBotzV2AudioSensorTraps 0 104 }

netBotzAudioTooLowTooLong NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Audio sensor value too low for too long."
        ::= { netBotzV2AudioSensorTraps 0 5 }

netBotzAudioTooLowForTooLongRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Audio sensor value is no longer too low for too long."
        ::= { netBotzV2AudioSensorTraps 0 105 }

netBotzAudioUnplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Audio sensor unplugged."
        ::= { netBotzV2AudioSensorTraps 0 6 }

netBotzAudioReplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Audio sensor no longer unplugged."
        ::= { netBotzV2AudioSensorTraps 0 106 }

netBotzAudioIncreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Audio sensor value increasing too quickly."
        ::= { netBotzV2AudioSensorTraps 0 8 }

netBotzAudioNotIncreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Audio sensor value no longer increasing too quickly."
        ::= { netBotzV2AudioSensorTraps 0 108 }

netBotzAudioDecreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Audio sensor value decreasing too quickly."
        ::= { netBotzV2AudioSensorTraps 0 9 }

netBotzAudioNotDecreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Audio sensor value no longer decreasing too quickly."
        ::= { netBotzV2AudioSensorTraps 0 109 }

netBotzAudioError NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Audio sensor error."
        ::= { netBotzV2AudioSensorTraps 0 1 }

netBotzAudioErrorRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Audio sensor error resolved."
        ::= { netBotzV2AudioSensorTraps 0 101 }

netBotzAmpDetectTooHigh NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Amp Detectsensor value too high."
        ::= { netBotzV2AmpDetectSensorTraps 0 2 }

netBotzAmpDetectTooHighRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Amp Detectsensor value is not longer too high."
        ::= { netBotzV2AmpDetectSensorTraps 0 102 }

netBotzAmpDetectTooLow NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Amp Detectsensor value too low."
        ::= { netBotzV2AmpDetectSensorTraps 0 3 }

netBotzAmpDetectTooLowRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Amp Detectsensor value is no longer too low."
        ::= { netBotzV2AmpDetectSensorTraps 0 103 }

netBotzAmpDetectTooHighTooLong NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Amp Detectsensor value too high for too long."
        ::= { netBotzV2AmpDetectSensorTraps 0 4 }

netBotzAmpDetectTooHighTooLongRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Amp Detectsensor value is not longer too high for too long."
        ::= { netBotzV2AmpDetectSensorTraps 0 104 }

netBotzAmpDetectTooLowTooLong NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Amp Detectsensor value too low for too long."
        ::= { netBotzV2AmpDetectSensorTraps 0 5 }

netBotzAmpDetectTooLowForTooLongRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Amp Detectsensor value is no longer too low for too long."
        ::= { netBotzV2AmpDetectSensorTraps 0 105 }

netBotzAmpDetectUnplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Amp Detectsensor unplugged."
        ::= { netBotzV2AmpDetectSensorTraps 0 6 }

netBotzAmpDetectReplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Amp Detectsensor no longer unplugged."
        ::= { netBotzV2AmpDetectSensorTraps 0 106 }

netBotzAmpDetectIncreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Amp Detectsensor value increasing too quickly."
        ::= { netBotzV2AmpDetectSensorTraps 0 8 }

netBotzAmpDetectNotIncreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Amp Detectsensor value no longer increasing too quickly."
        ::= { netBotzV2AmpDetectSensorTraps 0 108 }

netBotzAmpDetectDecreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Amp Detectsensor value decreasing too quickly."
        ::= { netBotzV2AmpDetectSensorTraps 0 9 }

netBotzAmpDetectNotDecreasingTooQuickly NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Amp Detectsensor value no longer decreasing too quickly."
        ::= { netBotzV2AmpDetectSensorTraps 0 109 }

netBotzAmpDetectError NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Amp Detectsensor error."
        ::= { netBotzV2AmpDetectSensorTraps 0 1 }

netBotzAmpDetectErrorRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Amp Detectsensor error resolved."
        ::= { netBotzV2AmpDetectSensorTraps 0 101 }

netBotzDryContactUnplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Dry Contact sensor unplugged."
        ::= { netBotzV2DryContactSensorTraps 0 6 }

netBotzDryContactReplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Dry Contact sensor no longer unplugged."
        ::= { netBotzV2DryContactSensorTraps 0 106 }

netBotzDryContactError NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Dry Contact sensor error."
        ::= { netBotzV2DryContactSensorTraps 0 1 }

netBotzDryContactErrorRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Dry Contact sensor error resolved."
        ::= { netBotzV2DryContactSensorTraps 0 101 }

netBotzDryContactValueError NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Dry Contact sensor value error."
        ::= { netBotzV2DryContactSensorTraps 0 10 }

netBotzDryContactValueErrorRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Dry Contact sensor value error resolved."
        ::= { netBotzV2DryContactSensorTraps 0 110 }

netBotzCameraMotionSensorUnplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Camera Motion Sensor sensor unplugged."
        ::= { netBotzV2CameraMotionSensorTraps 0 6 }

netBotzCameraMotionSensorReplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Camera Motion Sensor sensor no longer unplugged."
        ::= { netBotzV2CameraMotionSensorTraps 0 106 }

netBotzCameraMotionSensorError NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Camera Motion Sensor sensor error."
        ::= { netBotzV2CameraMotionSensorTraps 0 1 }

netBotzCameraMotionSensorErrorRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Camera Motion Sensor sensor error resolved."
        ::= { netBotzV2CameraMotionSensorTraps 0 101 }

netBotzCameraMotionSensorValueError NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Camera Motion Sensor sensor value error."
        ::= { netBotzV2CameraMotionSensorTraps 0 10 }

netBotzCameraMotionSensorValueErrorRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Camera Motion Sensor sensor value error resolved."
        ::= { netBotzV2CameraMotionSensorTraps 0 110 }

netBotzDoorSensorUnplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Door Sensor sensor unplugged."
        ::= { netBotzV2DoorSensorTraps 0 6 }

netBotzDoorSensorReplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Door Sensor sensor no longer unplugged."
        ::= { netBotzV2DoorSensorTraps 0 106 }

netBotzDoorSensorError NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Door Sensor sensor error."
        ::= { netBotzV2DoorSensorTraps 0 1 }

netBotzDoorSensorErrorRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Door Sensor sensor error resolved."
        ::= { netBotzV2DoorSensorTraps 0 101 }

netBotzDoorSensorValueError NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Door Sensor sensor value error."
        ::= { netBotzV2DoorSensorTraps 0 10 }

netBotzDoorSensorValueErrorRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Door Sensor sensor value error resolved."
        ::= { netBotzV2DoorSensorTraps 0 110 }

netBotzMicPlugSensorUnplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "MicPlug Sensor sensor unplugged."
        ::= { netBotzV2MicPlugSensorTraps 0 6 }

netBotzMicPlugSensorReplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "MicPlug Sensor sensor no longer unplugged."
        ::= { netBotzV2MicPlugSensorTraps 0 106 }

netBotzMicPlugSensorError NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "MicPlug Sensor sensor error."
        ::= { netBotzV2MicPlugSensorTraps 0 1 }

netBotzMicPlugSensorErrorRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "MicPlug Sensor sensor error resolved."
        ::= { netBotzV2MicPlugSensorTraps 0 101 }

netBotzMicPlugSensorValueError NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "MicPlug Sensor sensor value error."
        ::= { netBotzV2MicPlugSensorTraps 0 10 }

netBotzMicPlugSensorValueErrorRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "MicPlug Sensor sensor value error resolved."
        ::= { netBotzV2MicPlugSensorTraps 0 110 }

netBotzSpeakerPlugSensorUnplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "SpeakerPlug Sensor sensor unplugged."
        ::= { netBotzV2SpeakerPlugSensorTraps 0 6 }

netBotzSpeakerPlugSensorReplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "SpeakerPlug Sensor sensor no longer unplugged."
        ::= { netBotzV2SpeakerPlugSensorTraps 0 106 }

netBotzSpeakerPlugSensorError NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "SpeakerPlug Sensor sensor error."
        ::= { netBotzV2SpeakerPlugSensorTraps 0 1 }

netBotzSpeakerPlugSensorErrorRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "SpeakerPlug Sensor sensor error resolved."
        ::= { netBotzV2SpeakerPlugSensorTraps 0 101 }

netBotzSpeakerPlugSensorValueError NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "SpeakerPlug Sensor sensor value error."
        ::= { netBotzV2SpeakerPlugSensorTraps 0 10 }

netBotzSpeakerPlugSensorValueErrorRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "SpeakerPlug Sensor sensor value error resolved."
        ::= { netBotzV2SpeakerPlugSensorTraps 0 110 }


netBotzTVSignalSensorUnplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "TVSignal Sensor sensor unplugged."
        ::= { netBotzV2TVSignalSensorTraps 0 6 }

netBotzTVSignalSensorReplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "TVSignal Sensor sensor no longer unplugged."
        ::= { netBotzV2TVSignalSensorTraps 0 106 }

netBotzTVSignalSensorError NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "TVSignal Sensor sensor error."
        ::= { netBotzV2TVSignalSensorTraps 0 1 }

netBotzTVSignalSensorErrorRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "TVSignal Sensor sensor error resolved."
        ::= { netBotzV2TVSignalSensorTraps 0 101 }

netBotzTVSignalSensorValueError NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "TVSignal Sensor sensor value error."
        ::= { netBotzV2TVSignalSensorTraps 0 10 }

netBotzTVSignalSensorValueErrorRTN NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "TVSignal Sensor sensor value error resolved."
        ::= { netBotzV2TVSignalSensorTraps 0 110 }

netBotzPodUnplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Pod unplugged."
        ::= { netBotzV2PodTraps 0 7 }

netBotzPodReplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Pod no longer unplugged."
        ::= { netBotzV2PodTraps 0 107 }

netBotzSensorPodUnplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Sensor Pod unplugged."
        ::= { netBotzV2SensorPodTraps 0 7 }

netBotzSensorPodReplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Sensor Pod no longer unplugged."
        ::= { netBotzV2SensorPodTraps 0 107 }

netBotzCameraPodUnplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Camera Pod unplugged."
        ::= { netBotzV2CameraPodTraps 0 7 }

netBotzCameraPodReplugged NOTIFICATION-TYPE
        OBJECTS {
                netBotzV2TrapErrorID,   
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION 
        "Camera Pod no longer unplugged."
        ::= { netBotzV2CameraPodTraps 0 107 }

netBotzLogonError NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Multiple failed logon attempts."
        ::= { netBotzV2PodTraps 0 11 }

netBotzLogonErrorResolved NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Failed logon attempts stopped, or logon succeeded."
        ::= { netBotzV2PodTraps 0 111 }

netBotzDriveNotFoundError NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Configured add-on drive not found or has malfunctioned."
        ::= { netBotzV2PodTraps 0 12 }

netBotzDriveNotFoundErrorResolved NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Missing add-on drive has bee found."
        ::= { netBotzV2PodTraps 0 112 }


netBotzGPSPositionTooHigh NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Position sensor value too high."
        ::= { netBotzV2GPSPositionSensorTraps 0 2 }

netBotzGPSPositionTooHighRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Position sensor value is not longer too high."
        ::= { netBotzV2GPSPositionSensorTraps 0 102 }

netBotzGPSPositionTooLow NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Position sensor value too low."
        ::= { netBotzV2GPSPositionSensorTraps 0 3 }

netBotzGPSPositionTooLowRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Position sensor value is no longer too low."
        ::= { netBotzV2GPSPositionSensorTraps 0 103 }

netBotzGPSPositionTooHighTooLong NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Position sensor value too high for too long."
        ::= { netBotzV2GPSPositionSensorTraps 0 4 }

netBotzGPSPositionTooHighTooLongRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Position sensor value is not longer too high for too long."
        ::= { netBotzV2GPSPositionSensorTraps 0 104 }

netBotzGPSPositionTooLowTooLong NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Position ensor value too low for too long."
        ::= { netBotzV2GPSPositionSensorTraps 0 5 }

netBotzGPSPositionTooLowForTooLongRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Position sensor value is no longer too low for too long."
        ::= { netBotzV2GPSPositionSensorTraps 0 105 }

netBotzGPSPositionUnplugged NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Position sensor unplugged."
        ::= { netBotzV2GPSPositionSensorTraps 0 6 }

netBotzGPSPositionReplugged NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Position sensor no longer unplugged."
        ::= { netBotzV2GPSPositionSensorTraps 0 106 }

netBotzGPSPositionIncreasingTooQuickly NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Position sensor value increasing too quickly."
        ::= { netBotzV2GPSPositionSensorTraps 0 8 }

netBotzGPSPositionNotIncreasingTooQuickly NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Position sensor value no longer increasing too quickly."
        ::= { netBotzV2GPSPositionSensorTraps 0 108 }

netBotzGPSPositionDecreasingTooQuickly NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Position sensor value decreasing too quickly."
        ::= { netBotzV2GPSPositionSensorTraps 0 9 }

netBotzGPSPositionNotDecreasingTooQuickly NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Position sensor value no longer decreasing too quickly."
        ::= { netBotzV2GPSPositionSensorTraps 0 109 }

netBotzGPSPositionError NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Position sensor error."
        ::= { netBotzV2GPSPositionSensorTraps 0 1 }

netBotzGPSPositionErrorRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Position sensor error resolved."
        ::= { netBotzV2GPSPositionSensorTraps 0 101 }

netBotzGPSMovementTooHigh NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Movement sensor value too high."
        ::= { netBotzV2GPSMovementSensorTraps 0 2 }

netBotzGPSMovementTooHighRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Movement sensor value is not longer too high."
        ::= { netBotzV2GPSMovementSensorTraps 0 102 }

netBotzGPSMovementTooLow NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Movement sensor value too low."
        ::= { netBotzV2GPSMovementSensorTraps 0 3 }

netBotzGPSMovementTooLowRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Movement sensor value is no longer too low."
        ::= { netBotzV2GPSMovementSensorTraps 0 103 }

netBotzGPSMovementTooHighTooLong NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Movement sensor value too high for too long."
        ::= { netBotzV2GPSMovementSensorTraps 0 4 }

netBotzGPSMovementTooHighTooLongRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Movement sensor value is not longer too high for too long."
        ::= { netBotzV2GPSMovementSensorTraps 0 104 }

netBotzGPSMovementTooLowTooLong NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Movement ensor value too low for too long."
        ::= { netBotzV2GPSMovementSensorTraps 0 5 }

netBotzGPSMovementTooLowForTooLongRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Movement sensor value is no longer too low for too long."
        ::= { netBotzV2GPSMovementSensorTraps 0 105 }

netBotzGPSMovementUnplugged NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Movement sensor unplugged."
        ::= { netBotzV2GPSMovementSensorTraps 0 6 }

netBotzGPSMovementReplugged NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Movement sensor no longer unplugged."
        ::= { netBotzV2GPSMovementSensorTraps 0 106 }

netBotzGPSMovementIncreasingTooQuickly NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Movement sensor value increasing too quickly."
        ::= { netBotzV2GPSMovementSensorTraps 0 8 }

netBotzGPSMovementNotIncreasingTooQuickly NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Movement sensor value no longer increasing too quickly."
        ::= { netBotzV2GPSMovementSensorTraps 0 108 }

netBotzGPSMovementDecreasingTooQuickly NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Movement sensor value decreasing too quickly."
        ::= { netBotzV2GPSMovementSensorTraps 0 9 }

netBotzGPSMovementNotDecreasingTooQuickly NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Movement sensor value no longer decreasing too quickly."
        ::= { netBotzV2GPSMovementSensorTraps 0 109 }

netBotzGPSMovementError NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Movement sensor error."
        ::= { netBotzV2GPSMovementSensorTraps 0 1 }

netBotzGPSMovementErrorRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Movement sensor error resolved."
        ::= { netBotzV2GPSMovementSensorTraps 0 101 }

netBotzPacketDropTooHigh NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Packet Drop sensor value too high."
        ::= { netBotzV2PacketDropSensorTraps 0 2 }

netBotzPacketDropTooHighRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Packet Drop sensor value is not longer too high."
        ::= { netBotzV2PacketDropSensorTraps 0 102 }

netBotzPacketDropTooLow NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Packet Drop sensor value too low."
        ::= { netBotzV2PacketDropSensorTraps 0 3 }

netBotzPacketDropTooLowRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Packet Drop sensor value is no longer too low."
        ::= { netBotzV2PacketDropSensorTraps 0 103 }

netBotzPacketDropTooHighTooLong NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Packet Drop sensor value too high for too long."
        ::= { netBotzV2PacketDropSensorTraps 0 4 }

netBotzPacketDropTooHighTooLongRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Packet Drop sensor value is not longer too high for too long."
        ::= { netBotzV2PacketDropSensorTraps 0 104 }

netBotzPacketDropTooLowTooLong NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Packet Drop ensor value too low for too long."
        ::= { netBotzV2PacketDropSensorTraps 0 5 }

netBotzPacketDropTooLowForTooLongRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Packet Drop sensor value is no longer too low for too long."
        ::= { netBotzV2PacketDropSensorTraps 0 105 }

netBotzPacketDropUnplugged NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Packet Drop sensor unplugged."
        ::= { netBotzV2PacketDropSensorTraps 0 6 }

netBotzPacketDropReplugged NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Packet Drop sensor no longer unplugged."
        ::= { netBotzV2PacketDropSensorTraps 0 106 }

netBotzPacketDropIncreasingTooQuickly NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Packet Drop sensor value increasing too quickly."
        ::= { netBotzV2PacketDropSensorTraps 0 8 }

netBotzPacketDropNotIncreasingTooQuickly NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Packet Drop sensor value no longer increasing too quickly."
        ::= { netBotzV2PacketDropSensorTraps 0 108 }

netBotzPacketDropDecreasingTooQuickly NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Packet Drop sensor value decreasing too quickly."
        ::= { netBotzV2PacketDropSensorTraps 0 9 }

netBotzPacketDropNotDecreasingTooQuickly NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Packet Drop sensor value no longer decreasing too quickly."
        ::= { netBotzV2PacketDropSensorTraps 0 109 }

netBotzPacketDropError NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Packet Drop sensor error."
        ::= { netBotzV2PacketDropSensorTraps 0 1 }

netBotzPacketDropErrorRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Packet Drop sensor error resolved."
        ::= { netBotzV2PacketDropSensorTraps 0 101 }

netBotzSNMPCrawlerTooHigh NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "SNMP Crawler sensor value too high."
        ::= { netBotzV2SNMPCrawlerSensorTraps 0 2 }

netBotzSNMPCrawlerTooHighRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "SNMP Crawler sensor value is not longer too high."
        ::= { netBotzV2SNMPCrawlerSensorTraps 0 102 }

netBotzSNMPCrawlerTooLow NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "SNMP Crawler sensor value too low."
        ::= { netBotzV2SNMPCrawlerSensorTraps 0 3 }

netBotzSNMPCrawlerTooLowRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "SNMP Crawler sensor value is no longer too low."
        ::= { netBotzV2SNMPCrawlerSensorTraps 0 103 }

netBotzSNMPCrawlerTooHighTooLong NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "SNMP Crawler sensor value too high for too long."
        ::= { netBotzV2SNMPCrawlerSensorTraps 0 4 }

netBotzSNMPCrawlerTooHighTooLongRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "SNMP Crawler sensor value is not longer too high for too long."
        ::= { netBotzV2SNMPCrawlerSensorTraps 0 104 }

netBotzSNMPCrawlerTooLowTooLong NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "SNMP Crawler ensor value too low for too long."
        ::= { netBotzV2SNMPCrawlerSensorTraps 0 5 }

netBotzSNMPCrawlerTooLowForTooLongRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "SNMP Crawler sensor value is no longer too low for too long."
        ::= { netBotzV2SNMPCrawlerSensorTraps 0 105 }

netBotzSNMPCrawlerUnplugged NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "SNMP Crawler sensor unplugged."
        ::= { netBotzV2SNMPCrawlerSensorTraps 0 6 }

netBotzSNMPCrawlerReplugged NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "SNMP Crawler sensor no longer unplugged."
        ::= { netBotzV2SNMPCrawlerSensorTraps 0 106 }

netBotzSNMPCrawlerIncreasingTooQuickly NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "SNMP Crawler sensor value increasing too quickly."
        ::= { netBotzV2SNMPCrawlerSensorTraps 0 8 }

netBotzSNMPCrawlerNotIncreasingTooQuickly NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "SNMP Crawler sensor value no longer increasing too quickly."
        ::= { netBotzV2SNMPCrawlerSensorTraps 0 108 }

netBotzSNMPCrawlerDecreasingTooQuickly NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "SNMP Crawler sensor value decreasing too quickly."
        ::= { netBotzV2SNMPCrawlerSensorTraps 0 9 }

netBotzSNMPCrawlerNotDecreasingTooQuickly NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "SNMP Crawler sensor value no longer decreasing too quickly."
        ::= { netBotzV2SNMPCrawlerSensorTraps 0 109 }

netBotzSNMPCrawlerError NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "SNMP Crawler sensor error."
        ::= { netBotzV2SNMPCrawlerSensorTraps 0 1 }

netBotzSNMPCrawlerErrorRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "SNMP Crawler sensor error resolved."
        ::= { netBotzV2SNMPCrawlerSensorTraps 0 101 }

netBotzSNMPCrawlerSensorValueError NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "SNMP Crawler Sensor sensor value error."
        ::= { netBotzV2SNMPCrawlerSensorTraps 0 10 }

netBotzSNMPCrawlerSensorValueErrorRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "SNMP Crawler Sensor sensor value error resolved."
        ::= { netBotzV2SNMPCrawlerSensorTraps 0 110 }

netBotzGPSStatusSensorUnplugged NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Status Sensor sensor unplugged."
        ::= { netBotzV2GPSStatusSensorTraps 0 6 }

netBotzGPSStatusSensorReplugged NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Status Sensor sensor no longer unplugged."
        ::= { netBotzV2GPSStatusSensorTraps 0 106 }

netBotzGPSStatusSensorError NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Status Sensor sensor error."
        ::= { netBotzV2GPSStatusSensorTraps 0 1 }

netBotzGPSStatusSensorErrorRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Status Sensor sensor error resolved."
        ::= { netBotzV2GPSStatusSensorTraps 0 101 }

netBotzGPSStatusSensorValueError NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Status Sensor sensor value error."
        ::= { netBotzV2GPSStatusSensorTraps 0 10 }

netBotzGPSStatusSensorValueErrorRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "GPS Status Sensor sensor value error resolved."
        ::= { netBotzV2GPSStatusSensorTraps 0 110 }

netBotzWirelessStatusSensorUnplugged NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Wireless Status Sensor sensor unplugged."
        ::= { netBotzV2WirelessStatusSensorTraps 0 6 }

netBotzWirelessStatusSensorReplugged NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Wireless Status Sensor sensor no longer unplugged."
        ::= { netBotzV2WirelessStatusSensorTraps 0 106 }

netBotzWirelessStatusSensorError NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Wireless Status Sensor sensor error."
        ::= { netBotzV2WirelessStatusSensorTraps 0 1 }

netBotzWirelessStatusSensorErrorRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Wireless Status Sensor sensor error resolved."
        ::= { netBotzV2WirelessStatusSensorTraps 0 101 }

netBotzWirelessStatusSensorValueError NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Wireless Status Sensor sensor value error."
        ::= { netBotzV2WirelessStatusSensorTraps 0 10 }

netBotzWirelessStatusSensorValueErrorRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Wireless Status Sensor sensor value error resolved."
        ::= { netBotzV2WirelessStatusSensorTraps 0 110 }

netBotzOutputControlSensorUnplugged NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Output Control Sensor unplugged."
        ::= { netBotzV2OutputControlSensorTraps 0 6 }

netBotzOutputControlSensorReplugged NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Output Control Sensor no longer unplugged."
        ::= { netBotzV2OutputControlSensorTraps 0 106 }

netBotzOutputControlSensorError NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Output Control Sensor error."
        ::= { netBotzV2OutputControlSensorTraps 0 1 }

netBotzOutputControlSensorErrorRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Output Control Sensor error resolved."
        ::= { netBotzV2OutputControlSensorTraps 0 101 }

netBotzOutputControlSensorValueError NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Output Control Sensor value error."
        ::= { netBotzV2OutputControlSensorTraps 0 10 }

netBotzOutputControlSensorValueErrorRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "Output Control Sensor value error resolved."
        ::= { netBotzV2OutputControlSensorTraps 0 110 }


netBotzMultiRAESensorTooHigh NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE sensor value too high."
        ::= { netBotzV2MultiRAESensorTraps 0 2 }

netBotzMultiRAESensorTooHighRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE sensor value is not longer too high."
        ::= { netBotzV2MultiRAESensorTraps 0 102 }

netBotzMultiRAESensorTooLow NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE sensor value too low."
        ::= { netBotzV2MultiRAESensorTraps 0 3 }

netBotzMultiRAESensorTooLowRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE sensor value is no longer too low."
        ::= { netBotzV2MultiRAESensorTraps 0 103 }

netBotzMultiRAESensorTooHighTooLong NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE sensor value too high for too long."
        ::= { netBotzV2MultiRAESensorTraps 0 4 }

netBotzMultiRAESensorTooHighTooLongRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE sensor value is not longer too high for too long."
        ::= { netBotzV2MultiRAESensorTraps 0 104 }

netBotzMultiRAESensorTooLowTooLong NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE ensor value too low for too long."
        ::= { netBotzV2MultiRAESensorTraps 0 5 }

netBotzMultiRAESensorTooLowForTooLongRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE sensor value is no longer too low for too long."
        ::= { netBotzV2MultiRAESensorTraps 0 105 }

netBotzMultiRAESensorUnplugged NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE sensor unplugged."
        ::= { netBotzV2MultiRAESensorTraps 0 6 }

netBotzMultiRAESensorReplugged NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE sensor no longer unplugged."
        ::= { netBotzV2MultiRAESensorTraps 0 106 }

netBotzMultiRAESensorIncreasingTooQuickly NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE sensor value increasing too quickly."
        ::= { netBotzV2MultiRAESensorTraps 0 8 }

netBotzMultiRAESensorNotIncreasingTooQuickly NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE sensor value no longer increasing too quickly."
        ::= { netBotzV2MultiRAESensorTraps 0 108 }

netBotzMultiRAESensorDecreasingTooQuickly NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE sensor value decreasing too quickly."
        ::= { netBotzV2MultiRAESensorTraps 0 9 }

netBotzMultiRAESensorNotDecreasingTooQuickly NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE sensor value no longer decreasing too quickly."
        ::= { netBotzV2MultiRAESensorTraps 0 109 }

netBotzMultiRAESensorError NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE sensor error."
        ::= { netBotzV2MultiRAESensorTraps 0 1 }

netBotzMultiRAESensorErrorRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE sensor error resolved."
        ::= { netBotzV2MultiRAESensorTraps 0 101 }

netBotzMultiRAESensorSensorValueError NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE Sensor sensor value error."
        ::= { netBotzV2MultiRAESensorTraps 0 10 }

netBotzMultiRAESensorSensorValueErrorRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE Sensor sensor value error resolved."
        ::= { netBotzV2MultiRAESensorTraps 0 110 }
                

netBotzMultiRAESensorStatusUnplugged NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE Sensor Status unplugged."
        ::= { netBotzV2MultiRAESensorStatusTraps 0 6 }

netBotzMultiRAESensorStatusReplugged NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE Sensor Status no longer unplugged."
        ::= { netBotzV2MultiRAESensorStatusTraps 0 106 }

netBotzMultiRAESensorStatusError NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE Sensor Status error."
        ::= { netBotzV2MultiRAESensorStatusTraps 0 1 }

netBotzMultiRAESensorStatusErrorRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE Sensor Status error resolved."
        ::= { netBotzV2MultiRAESensorStatusTraps 0 101 }

netBotzMultiRAESensorStatusValueError NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE Sensor Status value error."
        ::= { netBotzV2MultiRAESensorStatusTraps 0 10 }

netBotzMultiRAESensorStatusValueErrorRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE Sensor Status value error resolved."
        ::= { netBotzV2MultiRAESensorStatusTraps 0 110 }


netBotzMultiRAEDeviceStatusUnplugged NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE Device Status unplugged."
        ::= { netBotzV2MultiRAEDeviceStatusTraps 0 6 }

netBotzMultiRAEDeviceStatusReplugged NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE Device Status no longer unplugged."
        ::= { netBotzV2MultiRAEDeviceStatusTraps 0 106 }

netBotzMultiRAEDeviceStatusError NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE Device Status error."
        ::= { netBotzV2MultiRAEDeviceStatusTraps 0 1 }

netBotzMultiRAEDeviceStatusErrorRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE Device Status error resolved."
        ::= { netBotzV2MultiRAEDeviceStatusTraps 0 101 }

netBotzMultiRAEDeviceStatusValueError NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE Device Status value error."
        ::= { netBotzV2MultiRAEDeviceStatusTraps 0 10 }

netBotzMultiRAEDeviceStatusValueErrorRTN NOTIFICATION-TYPE
        OBJECTS {
                netBotzV2TrapErrorID,
                netBotzV2TrapErrorType,
                netBotzV2TrapErrorTypeLabel,
                netBotzV2TrapSensorID,
                netBotzV2TrapSensorLabel,
                netBotzV2TrapPodID,
                netBotzV2TrapPodLabel,
                netBotzV2TrapPortID,
                netBotzV2TrapPortLabel,
                netBotzV2TrapStartTime,
                netBotzV2TrapNotifyTime,
                netBotzV2TrapResolveTime,
                netBotzV2TrapSeverity,
                netBotzV2TrapSensorValue,
                netBotzV2TrapSensorValueInt,
                netBotzV2TrapSensorValueFraction
                }
        STATUS          current
        DESCRIPTION
        "MultiRAE Device Status value error resolved."
        ::= { netBotzV2MultiRAEDeviceStatusTraps 0 110 }
        
END
