-- *********************************************************************
-- *********************************************************************
-- ** Filename: PRVT-NETWORK-LOOPBACK-TEST-MIB
-- ** Project: Network Loopback Tester 
-- ** Purpose: Private MIB
-- *********************************************************************
-- (c) Copyright, 2001, BATM Advanced Communications. All rights reserved.
-- WARNING:
--
-- BY UTILIZING THIS FILE, YOU AGREE TO THE FOLLOWING:
--
-- This file is the property of BATM Advanced Communications.
-- BATM Advanced Communications retains all title and
-- ownership in the Specification, including any revisions.

-- BATM Advanced Communications grants all interested parties a non-exclusive
-- license to use and distribute an unmodified copy of this
-- Specification in connection with management of BATM Advanced Communications 
-- and Telco Systems products, and without fee, provided that the following
-- conditions are met:
-- 1. Redistributions of this specification must retain the above copyright
-- notice, this list of conditions and the following disclaimer.
-- 2. Redistributions in binary form must reproduce the above copyright
-- notice, this list of conditions and the following disclaimer in the
-- documentation and/or other materials provided with the distribution.
-- 3. The name of the BATM Advanced Communications MAY NOT be used to endorse
-- or promote products derived from this specification without specific prior written
-- permission.
--
-- EXCEPT AS RESTRICTED BY LAW, OR AS PROVIDED IN BATM'S LIMITED
-- WARRANTY, THE SPECIFICATIONS CONTAINED IN THIS FILE ARE
-- PROVIDED "AS IS" WITHOUT WARRANTY OF ANY KIND, EITHER EXPRESSED
-- OR IMPLIED, INCLUDING BUT NOT LIMITED TO, ANY IMPLIED WARRANTIES
-- OF MERCHANTABILITY OR FITNESS FOR A PARTICULAR PURPOSE.
-- IN NO EVENT SHALL BATM BE LIABLE FOR ANY DAMAGES WHATSOEVER
-- INCLUDING, WITHOUT LIMITATION, DAMAGES FOR LOSS OF BUSINESS
-- PROFITS, BUSINESS INTERRUPTION, LOSS OF BUSINESS INFORMATION OR
-- OTHER CONSEQUENTIAL DAMAGES ARISING OUT OF THE USE, OR INABILITY
-- TO USE, THE SPECIFICATION CONTAINED IN THIS FILE.
PRVT-NETWORK-LOOPBACK-TEST-MIB DEFINITIONS ::= BEGIN

IMPORTS
MODULE-IDENTITY,
OBJECT-TYPE
FROM SNMPv2-SMI         

ifIndex
FROM IF-MIB     

MODULE-COMPLIANCE,
OBJECT-GROUP,
NOTIFICATION-GROUP
FROM SNMPv2-CONF

TimeStamp,
RowStatus
FROM SNMPv2-TC 

NOTIFICATION-TYPE
FROM SNMPv2-SMI                    -- [RFC2578]

   
accessListControlListGroup
FROM  PRVT-SWITCH-ACCESS-LIST-MIB

ipSwitch FROM PRVT-SWITCH-MIB; 

-- The NETWORK LOOPBACK TEST MIB
prvtNetworkLoopbackTestMib MODULE-IDENTITY

LAST-UPDATED "201008310000Z"
ORGANIZATION "BATM Advanced Communication"
CONTACT-INFO
"BATM/Telco Systems Support team
Email: 
For North America: techsupport@telco.com
For North Europe: support@batm.de, info@batm.de
For the rest of the world: techsupport@telco.com"

DESCRIPTION
"This MIB contains managed objects definitions for
encapsulating Loopback Tester feature that enables or disables
embedded mechanisms for network troubleshooting, diagnostics and measurement."
             
REVISION "201008310000Z"
DESCRIPTION
"Initial version."  

::= { ipSwitch 7 }     

prvtNetworkLoopbackTestNotifications OBJECT IDENTIFIER  ::= { prvtNetworkLoopbackTestMib 0 } 
prvtNetworkLoopbackTestObjects OBJECT IDENTIFIER 		::= { prvtNetworkLoopbackTestMib 1 } 
prvtNetworkLoopbackTestConformance OBJECT IDENTIFIER 	::= { prvtNetworkLoopbackTestMib 2 }

prvtNetworkLoopbackTestTable OBJECT-TYPE
SYNTAX SEQUENCE OF PrvtNetworkLoopbackTestEntry
MAX-ACCESS not-accessible
STATUS current
DESCRIPTION
"This table contains object for configuring and display information about Network Loopback Tester."
::= { prvtNetworkLoopbackTestObjects 1 }

prvtNetworkLoopbackTestEntry OBJECT-TYPE
SYNTAX PrvtNetworkLoopbackTestEntry
MAX-ACCESS not-accessible
STATUS current
DESCRIPTION
"An entry in the prvtNetworkLoopbackTestTable table"
INDEX { ifIndex, accessListControlListGroup }
::= { prvtNetworkLoopbackTestTable 1 }

PrvtNetworkLoopbackTestEntry ::=  SEQUENCE {  
prvtNetworkLoopTestDuration  INTEGER,
prvtNetworkLoopStartDuration TimeStamp,
prvtNetworkLoopEndDuration   TimeStamp,
prvtNetworkLoopRowStatus     RowStatus
} 

prvtNetworkLoopTestDuration  OBJECT-TYPE
SYNTAX INTEGER (0..100000) 
MAX-ACCESS read-write   
STATUS current
DESCRIPTION
"An integer that  identifies the duration in seconds of Loopback test.
For infinite Loopback tests object will have the value 0."        
::= {prvtNetworkLoopbackTestEntry 1}

prvtNetworkLoopStartDuration OBJECT-TYPE
SYNTAX TimeStamp 
MAX-ACCESS read-only
STATUS current
DESCRIPTION
"Star time of Loopback test.
For infinite Loopback tests object will have the value 0."         
::= {prvtNetworkLoopbackTestEntry 2}         

prvtNetworkLoopEndDuration OBJECT-TYPE
SYNTAX TimeStamp 
MAX-ACCESS read-only
STATUS current
DESCRIPTION
"End time of Loopback test.
For infinite Loopback tests object will have the value 0."      
::= {prvtNetworkLoopbackTestEntry 3} 

prvtNetworkLoopRowStatus OBJECT-TYPE
SYNTAX RowStatus  
MAX-ACCESS read-create   
STATUS current
DESCRIPTION
"Network Loopback Test RowStatus.
 Both createAndGo(4) and createAndWait(5) are available. 
 CreateAndGo(4) is used for enable a Loopback test unlimited in time and CreateAndWait(4) 
 for enable a Loopback Test on a period specified by prvtNetworkLoopTestDuration."      
::= {prvtNetworkLoopbackTestEntry 4}   
          
-- ----------------------------------------------------------------------------
-- Notifications
-- ----------------------------------------------------------------------------
                               
prvtNetworkLoopbackTestFinish NOTIFICATION-TYPE
OBJECTS { ifIndex, accessListControlListGroup }
STATUS current
DESCRIPTION
"This notification is sent  when a Network Loopback Test is complete."
::= {prvtNetworkLoopbackTestNotifications 1}       

-- ----------------------------------------------------------------------------
-- Conformance Information
-- ----------------------------------------------------------------------------
prvtNetworkLoopTestCompliances  OBJECT IDENTIFIER ::= {prvtNetworkLoopbackTestConformance 1}
prvtNetworkLoopTestGroups OBJECT IDENTIFIER ::= {prvtNetworkLoopbackTestConformance 2}

-- compliance statements
prvtNetworkLoopTestCompliance MODULE-COMPLIANCE
STATUS current
DESCRIPTION
"The compliance statement for Network Loopback Tester."
MODULE -- this module
MANDATORY-GROUPS {
prvtNetworkLoopTestGroup,
prvtNetworkLoopTestNotificationsGroup
}      
::= {prvtNetworkLoopTestCompliances 1}  

prvtNetworkLoopTestGroup  OBJECT-GROUP
OBJECTS {prvtNetworkLoopTestDuration,
prvtNetworkLoopStartDuration,
prvtNetworkLoopEndDuration,
prvtNetworkLoopRowStatus
}
STATUS current
DESCRIPTION   
"The group of objects regarding Network Looback Tester feature."
::= {prvtNetworkLoopTestGroups 1}     

prvtNetworkLoopTestNotificationsGroup NOTIFICATION-GROUP
NOTIFICATIONS{
prvtNetworkLoopbackTestFinish
}  
STATUS current
DESCRIPTION   
"The collection of Notifications used to indicate general status information
 of Network Looback Tester feature."
::= {prvtNetworkLoopTestGroups 2} 

END
