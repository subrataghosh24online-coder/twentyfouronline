-- ----------------------------------------------------------------------------
--
--  SIAE MICROELETTRONICA s.p.a.
--
--  Via Michelangelo Buonarroti, 21
--  20093 - Cologno Monzese
--  Milano
--  ITALY
--
-- ----------------------------------------------------------------------------
-- ----------------------------------------------------------------------------

SIAE-HC-MIB
        DEFINITIONS ::= BEGIN

        IMPORTS
             MODULE-IDENTITY, OBJECT-TYPE,
             Integer32
        FROM SNMPv2-SMI
             RowStatus
        FROM SNMPv2-TC
             siaeMib
        FROM SIAE-TREE-MIB;

     headerCompression MODULE-IDENTITY
        LAST-UPDATED "201410070000Z"
        ORGANIZATION "SIAE MICROELETTRONICA spa"
        CONTACT-INFO
            "SIAE MICROELETTONICA s.p.a.
             Via Michelangelo Buonarroti, 21
             20093 - Cologno Monzese
             Milano - ITALY
             Phone :  +39-02-27325-1
             E-mail: tbd@siaemic.com
            "
        DESCRIPTION
            "Management information for equipment header compression.
            "
        REVISION "201410070000Z"
        DESCRIPTION
            "Changed MAX-ACCESS clause of some objects in
             headerCompressionTable
            "
        REVISION "201403310000Z"
        DESCRIPTION
            "Initial version 01.00.00
            "
    ::= { siaeMib 79 }

----------------------------------------------------------------------------------
--  Header Compression Management information
----------------------------------------------------------------------------------
--
--  This MIB is used to describe header compression management of the equipment.
--  
----------------------------------------------------------------------------------

------ Beginning --------------------------------------------------------------

    headerCompressionMibVersion  OBJECT-TYPE
        SYNTAX      INTEGER
        MAX-ACCESS  read-only
        STATUS      current
        DESCRIPTION
            "Numerical version of this module.
             The string version of this MIB have the following format:
                XX.YY.ZZ
             so, for example, the value 1 should be interpreted as 00.00.01
             and the value 10001 should be interpreted as 01.00.01."
    ::= {headerCompression 1}

-------  Begin of  headerCompressionTable
--

    headerCompressionTable OBJECT-TYPE
        SYNTAX      SEQUENCE OF  HeaderCompressionEntry
        MAX-ACCESS  not-accessible
        STATUS      current
        DESCRIPTION
            "Table with header compression entries"
    ::= {headerCompression 2}

    headerCompressionEntry OBJECT-TYPE
        SYNTAX      HeaderCompressionEntry
        MAX-ACCESS  not-accessible
        STATUS      current
        DESCRIPTION
            "Header compression records"
        INDEX       {headerCompressionIndex}
    ::= {headerCompressionTable 1}

    HeaderCompressionEntry  ::=
        SEQUENCE  {
             headerCompressionIndex             Integer32,
             headerCompressionAdminStatus       INTEGER,
             headerCompressionContextDepth      INTEGER,
             headerCompressionParsingMode       INTEGER,
             headerCompressionTagEnable         INTEGER,
             headerCompressionRowStatus         RowStatus
         }

    headerCompressionIndex OBJECT-TYPE
        SYNTAX      Integer32
        MAX-ACCESS  read-only
        STATUS      current
        DESCRIPTION
            "Header compression index."
    ::= {headerCompressionEntry 1}

    headerCompressionAdminStatus   OBJECT-TYPE
        SYNTAX      INTEGER  {
                               up   (1),
                               down (2)
                             }
        MAX-ACCESS  read-create
        STATUS      current
        DESCRIPTION
            "This object is used to enable instance of header compression."
    ::= {headerCompressionEntry 2}

    headerCompressionContextDepth OBJECT-TYPE
        SYNTAX      INTEGER  {
                               ctx16bytes  (1),
                               ctx32bytes  (2),
                               ctx64byets  (3),
                               ctx128bytes (4)
                             }
        MAX-ACCESS  read-create
        STATUS      current
        DESCRIPTION
            "This object is used to set context depth of the specified instance
             of header compression."
    ::= {headerCompressionEntry 3}

    headerCompressionParsingMode OBJECT-TYPE
        SYNTAX      INTEGER  {
                               auto         (1),
                               semiMpls     (2),
                               semiIPv4IPv6 (3)
                             }
        MAX-ACCESS  read-create
        STATUS      current
        DESCRIPTION
            "This object is used to specify the mode of parsing packets."
    ::= {headerCompressionEntry 4}

    headerCompressionTagEnable OBJECT-TYPE
        SYNTAX      INTEGER   {
                               disable    (1),
                               enable     (2)
                              }
        MAX-ACCESS  read-create
        STATUS      current
        DESCRIPTION
            "This object is used to enable or disable TAG management."
    ::= {headerCompressionEntry 5}

    headerCompressionRowStatus OBJECT-TYPE
        SYNTAX      RowStatus
        MAX-ACCESS  read-create
        STATUS      current
        DESCRIPTION
            "Row Status object of the header compression table."
    ::= {headerCompressionEntry 6}

--
-------  End of headerCompressionTable


------ End group -----------------------------------------------------------------

END
