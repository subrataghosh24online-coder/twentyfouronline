SEH-PSRV-MIB DEFINITIONS ::= BEGIN

    -- Title:         SEH-PSRV-MIB
    --
    --                This Private MIB supports the following SEH print servers:
    --                InterCon Print Server II / III
    -- Version:       ms 1.167 Fr 15. Okt 09:23:15 CEST 2021
    --
    -- Author:        Matthias Wolff, mw@seh.de
    --
    -- Comments:      SEH agents also support the following Public MIBs:
    --                - MIB-II  ( RFC1213 )
    
    IMPORTS
        IpAddress, enterprises     FROM RFC1155-SMI
        OBJECT-TYPE                FROM RFC-1212
        DisplayString, PhysAddress FROM RFC1213-MIB
        TRAP-TYPE                  FROM RFC-1215;
    
    seh         OBJECT IDENTIFIER ::= { enterprises 1229  }
    
    -- Print Server II tree
    -- groups for Print Server 2 / 3 / 4 in SEH-MIB:
    
    sehDevice        OBJECT IDENTIFIER ::= { seh     1  }
    sehPSrv          OBJECT IDENTIFIER ::= { seh     2  }
    sehGeneral       OBJECT IDENTIFIER ::= { sehPSrv 1  }
    sehPprinter      OBJECT IDENTIFIER ::= { sehPSrv 2  }
    sehLprinter      OBJECT IDENTIFIER ::= { sehPSrv 3  }
    sehIp            OBJECT IDENTIFIER ::= { sehPSrv 4  }
    sehNovell        OBJECT IDENTIFIER ::= { sehPSrv 5  }
    sehApple         OBJECT IDENTIFIER ::= { sehPSrv 6  }
    sehSnmp          OBJECT IDENTIFIER ::= { sehPSrv 7  }
    sehActions       OBJECT IDENTIFIER ::= { sehPSrv 8  }
    sehTokenRing     OBJECT IDENTIFIER ::= { sehPSrv 10 }
    sehWireless      OBJECT IDENTIFIER ::= { sehPSrv 11 }
    sehWin           OBJECT IDENTIFIER ::= { sehPSrv 20 }
    sehTime          OBJECT IDENTIFIER ::= { sehPSrv 21 }
    sehPrintjob      OBJECT IDENTIFIER ::= { sehPSrv 22 }
    sehNotification  OBJECT IDENTIFIER ::= { sehPSrv 25 }
    sehMail          OBJECT IDENTIFIER ::= { sehNotification 8 }
    sehNat           OBJECT IDENTIFIER ::= { sehPSrv 26 }
    sehNatDrop       OBJECT IDENTIFIER ::= { sehPSrv 27 }
    sehTpg           OBJECT IDENTIFIER ::= { sehPSrv 30 }
    sehLrs           OBJECT IDENTIFIER ::= { sehPSrv 31 }
    sehProtection    OBJECT IDENTIFIER ::= { sehPSrv 40 }
    sehUser          OBJECT IDENTIFIER ::= { sehPSrv 41 }
    sehIPsec         OBJECT IDENTIFIER ::= { sehPSrv 42 }
    sehIpVLan        OBJECT IDENTIFIER ::= { sehPSrv 43 }
    sehUtn           OBJECT IDENTIFIER ::= { sehPSrv 50 }
    sehUtnEvent      OBJECT IDENTIFIER ::= { sehPSrv 51 }
    sehSnd           OBJECT IDENTIFIER ::= { seh     10 }
    sehPPS           OBJECT IDENTIFIER ::= { seh     11 }
    sehSndUser       OBJECT IDENTIFIER ::= { sehSnd  1  }
    sehSndSender     OBJECT IDENTIFIER ::= { sehSnd  2  }
    sehSndFFilter    OBJECT IDENTIFIER ::= { sehSnd  3  }
    sehSndSDCard     OBJECT IDENTIFIER ::= { sehSnd  4  }
    sehTSE           OBJECT IDENTIFIER ::= { seh     12 }
    
    -- the sehDevice group
    
    sehDevInfo OBJECT-TYPE
        SYNTAX  DisplayString (SIZE (0..64))
        ACCESS  read-write
        STATUS  mandatory
        DESCRIPTION
            "This parameter specifies a full device description."
        ::= { sehDevice 1 }
    
    -- the sehGeneral group
    
    sehSysInfo OBJECT-TYPE
        SYNTAX  DisplayString (SIZE (0..128))
        ACCESS  read-only
        STATUS  mandatory
        DESCRIPTION
            "This parameter specifies information about
            the print server."
        ::= { sehGeneral 1 }
    
    sehDefName OBJECT-TYPE
        SYNTAX  DisplayString (SIZE (1..15))
        ACCESS  read-only
        STATUS  mandatory
        DESCRIPTION
            "This parameter specifies the default name
            of the SEH print server."
        ::= { sehGeneral 2 }
    
    sehPhysAddr OBJECT-TYPE
        SYNTAX  PhysAddress (SIZE (6))
        ACCESS  read-only
        STATUS  mandatory
        DESCRIPTION
            "This parameter specifies the hardware address
            of the SEH print server."
        ::= { sehGeneral 3 }
    
    sehHwPn OBJECT-TYPE
        SYNTAX  INTEGER
        ACCESS  read-only
        STATUS  mandatory
        DESCRIPTION
            "This parameter specifies the hardware project number
            of the SEH print server."
        ::= { sehGeneral 4 }
    
    sehBiosId OBJECT-TYPE
        SYNTAX  INTEGER {
        ic53(1),
        ic60(2),
        ic55(3),
        ic57(4),
        ic59(5),
        ic73(6),
        ic53f(7),
        ic77(8),
        nc57(9),
        nb53(10),
        nb53f(11),
        nb60(12),
        ic56(13),
        nc77(14),
        nb73(15),
        pm55(16),
        ic69(17),
        ic79(18),
        ic59f(19),
        nb59(20),
        ic55f(21),
        nb59f(22),
        nb69(23),
        nb79(24),
        ic67(25),
        nc67(26),
        ic55t(27),
        ic104(51),
        ic105(52),
        ic106(53),
        ic107(54),
        ic109(55),
        ic126(56),
        ic129(57),
        ic99(58),
        ic127(59),
        ic146(60),
        ic147(61),
        ic149(62),
        ic166(63),
        ic167(64),
        ic169(65),
        sb109(66),
        sb129(67),
        sb149(68),
        sb169(69),
        ic124(70),
        ic144(71),
        pm102(72),
        ic102(73),
        ro102(74),
        nc109(75),
        ic175(76),
        ic177(77),
        ic179(78),
        sb179(79),
        ic189(80),
        sb189(81),
        xb105(82),
        xb104(83),
        xb124(84),
        xb144(85),
        ro105(86),
        ic159(87),
        ic154(88),
        sb159(89),
        ic156(90),
        ic111(91),
        ic190(92),
        ic191(93),
        ic134(94),
        ic157(95),
        ic178(96),
        ic152(97),
        wl105(98),
        ic155(99),
        pm152(100),
        eb105(101),
        ci102(102),
        ci152(103),
        ic125(107),
        ic112(108),
        cl105(109),
        bl650(110),
        wl109(111),
        ic103(112),
        wl154(113)
        }
        ACCESS  read-only
        STATUS  mandatory
        DESCRIPTION
            "This parameter specifies the BIOS identity
            of the SEH print server."
        ::= { sehGeneral 5 }
    
    sehBiosVer OBJECT-TYPE
        SYNTAX  INTEGER
        ACCESS  read-only
        STATUS  mandatory
        DESCRIPTION
            "This parameter specifies the BIOS version
            of the SEH print server."
        ::= { sehGeneral 6 }
    
    sehCmpId OBJECT-TYPE
        SYNTAX  INTEGER {
        kyocera(1),
        epson(2),
        pocket(3),
        kyocera2(4),
        hp(5),
        box(6),
        seh(7),
        oki(8)
        }
        ACCESS  read-only
        STATUS  mandatory
        DESCRIPTION
            "This parameter specifies the compatibility identity
            of the SEH print server."
        ::= { sehGeneral 7 }
    
    sehCmplevel OBJECT-TYPE
        SYNTAX  INTEGER
        ACCESS  read-only
        STATUS  mandatory
        DESCRIPTION
            "This parameter specifies the compatibility level
            of the SEH print server."
        ::= { sehGeneral 8 }
    
    sehSerNum OBJECT-TYPE
        SYNTAX  INTEGER
        ACCESS  read-only
        STATUS  mandatory
        DESCRIPTION
            "This parameter specifies the serial number
            of the SEH print server."
        ::= { sehGeneral 9 }
    
    sehPrdYear OBJECT-TYPE
        SYNTAX  INTEGER
        ACCESS  read-only
        STATUS  mandatory
        DESCRIPTION
            "This parameter specifies the
            production year."
        ::= { sehGeneral 10 }
    
    sehPrdMonth OBJECT-TYPE
        SYNTAX  INTEGER
        ACCESS  read-only
        STATUS  mandatory
        DESCRIPTION
            "This parameter specifies the
            production month."
        ::= { sehGeneral 11 }
    
    sehSwVer OBJECT-TYPE
        SYNTAX  INTEGER
        ACCESS  read-only
        STATUS  mandatory
        DESCRIPTION
            "This parameter specifies the number of the software
            version of the SEH print server."
        ::= { sehGeneral 12 }
    
    sehSwRel OBJECT-TYPE
        SYNTAX  INTEGER
        ACCESS  read-only
        STATUS  mandatory
        DESCRIPTION
            "This parameter specifies the software release number
            of the SEH print server."
        ::= { sehGeneral 13 }
    
    sehSwSub OBJECT-TYPE
        SYNTAX  INTEGER
        ACCESS  read-only
        STATUS  mandatory
        DESCRIPTION
            "This parameter specifies the software subrelease number
            of the SEH print server."
        ::= { sehGeneral 14 }
    
    sehSpMode OBJECT-TYPE
        SYNTAX  INTEGER { ascii(0), postscript(1), prescribe(2), auto(5), datamax(6), zpl(7), escpages3(8), epl2(9) }
        ACCESS  read-write
        STATUS  mandatory
        DESCRIPTION
            "This parameter specifies the status page format."
        ::= { sehGeneral 15 }
    
    sehHwMajor OBJECT-TYPE
        SYNTAX  INTEGER
        ACCESS  read-only
        STATUS  mandatory
        DESCRIPTION
            "This parameter specifies the major hardware revision
            number of the SEH print server."
        ::= { sehGeneral 16 }
    
    sehHwMinor OBJECT-TYPE
        SYNTAX  INTEGER
        ACCESS  read-only
        STATUS  mandatory
        DESCRIPTION
            "This parameter specifies the minor hardware revision
            number of the SEH print server."
        ::= { sehGeneral 17 }
    
    sehPassword OBJECT-TYPE
        SYNTAX  DisplayString (SIZE (0..16))
        ACCESS  read-write
        STATUS  mandatory
        DESCRIPTION
            "This parameter specifies the password of the print server.
            If set the password must be used as SNMP community
            for write access."
        ::= { sehGeneral 18 }
    
    sehAccessControl OBJECT-TYPE
        SYNTAX  INTEGER { disabled(0), enabled(1) }
        ACCESS  read-write
        STATUS  mandatory
        DESCRIPTION
            "This parameter enables or disables the access to the print
            server parameters. If a password is assigned and access control
            is enabled, the parameters are read-protected. "
        ::= { sehGeneral 19 }
    
    sehDealer OBJECT-TYPE
        SYNTAX  DisplayString (SIZE (0..64))
        ACCESS  read-write
        STATUS  mandatory
        DESCRIPTION
            "This parameter specifies a string containing e.g. the name
            of the printer dealer."
        ::= { sehGeneral 20 }
    
    sehDealerURL OBJECT-TYPE
        SYNTAX  DisplayString (SIZE (0..64))
        ACCESS  read-write
        STATUS  mandatory
        DESCRIPTION
            "This parameter specifies a string containing e.g. the URL
            of the printer dealer."
        ::= { sehGeneral 21 }
    
    sehLocalisation OBJECT-TYPE
        SYNTAX  DisplayString (SIZE (0..2))
        ACCESS  read-write
        STATUS  mandatory
        DESCRIPTION
            "This parameter specifies the country code."
        ::= { sehGeneral 22 }
    
    sehHpJetAdminCompatibility OBJECT-TYPE
        SYNTAX  INTEGER { disabled(0), enabled(1) }
        ACCESS  read-write
        STATUS  mandatory
        DESCRIPTION
            "This parameter enables/disables the HP JetAdmin compatibility mode."
        ::= { sehGeneral 23 }
    
    -- todo : only for box and pocket !
    
    sehEnpcSupport OBJECT-TYPE
        SYNTAX  INTEGER { none(0), basic(1), full(2) }
        ACCESS  read-write
        STATUS  mandatory
        DESCRIPTION
            "This parameter enables/disables ENPC support on parallel interfaces."
        ::= { sehGeneral 24 }
    
    -- todo
    
    sehAdminGroup OBJECT-TYPE
        SYNTAX  DisplayString (SIZE (0..128))
        ACCESS  read-write
        STATUS  mandatory
        DESCRIPTION
            "This parameter specifies the workgroup for the admin tool."
        ::= { sehGeneral 25 }
    
    sehUpdateState OBJECT-TYPE
        SYNTAX  INTEGER {
        idle(0),
        active(1),
        failed(2)
        }
        ACCESS  read-only
        STATUS  mandatory
        DESCRIPTION
            "This parameter specifies if a software update
            is running or has been failed."
        ::= { sehGeneral 26 }
    
    sehJobRecvTimeout OBJECT-TYPE
        SYNTAX  INTEGER
        ACCESS  read-write
        STATUS  mandatory
        DESCRIPTION
            "This parameter specifies the receive timeout (in seconds)
            for TCP based print jobs. A print job will be aborted
            if there are no data received for the specified time."
        ::= { sehGeneral 27 }
    
    -- EthernetFullDuplex OBJECT-TYPE
    --    SYNTAX  INTEGER { disabled(0), enabled(1) }
    --    ACCESS  read-write
    --    STATUS  mandatory
    --    DESCRIPTION
    --        "This parameter sets the ethernet link to full duplex mode.
    --        This should only be set for 100BaseFX connections
    --        (which don't support auto negotiating) when the other
    --        side is configured to full duplex mode, too."
    --    ::= { sehGeneral 28 }
    
    sehThinPrintPort OBJECT-TYPE
        SYNTAX  INTEGER
        ACCESS  read-write
        STATUS  mandatory
        DESCRIPTION
            "This parameter specifies the ThinPrint port number."
        ::= { sehGeneral 29 }
    
    sehHpHttpDaemon OBJECT-TYPE
        SYNTAX  INTEGER { disabled(0), enabled(1) }
        ACCESS  read-write
        STATUS  mandatory
        DESCRIPTION
            "This parameter enables/disables an HTTP daemon on HP printers."
        ::= { sehGeneral 30 }
    
    sehBaseLine OBJECT-TYPE
        SYNTAX  INTEGER { disabled(0), enabled(1) }
        ACCESS  read-only
        STATUS  mandatory
        DESCRIPTION
            "This parameter specifies if the device is 
            an SEH Baseline device with reduced functionality."
        ::= { sehGeneral 31 }
    
    sehEthernetConfig OBJECT-TYPE
        SYNTAX  INTEGER {
        auto(0),
        tenbasehalf(1),
        tenbasefull(2),
        hundredbasehalf(3),
        hundredbasefull(4) }
        ACCESS  read-write
        STATUS  mandatory
        DESCRIPTION
            "This parameter sets the configuration of the ethernet link."
        ::= { sehGeneral 32 }
    
    sehSwId OBJECT-TYPE
        SYNTAX  INTEGER {
        full(1),
        tpg(2),
        vpn(3),
        tni(4),
        uds(6) }
        ACCESS  read-only
        STATUS  mandatory
        DESCRIPTION
            "This parameter specifies the software id of the SEH print server."
        ::= { sehGeneral 33 }
    
    sehNetworkType OBJECT-TYPE
        SYNTAX  INTEGER {
        ethernet10Mbit(1),
        ethernet100MbitTx(2),
        wireless54Mbit(3),
        ethernet100MbitFx(4),
        ethernet100MbitFxTx(5),
        tokenring(6),
        ethernetGbitTx(7) }
        ACCESS  read-only
        STATUS  mandatory
        DESCRIPTION
            "This parameter specifies the product network type."
        ::= { sehGeneral 34 }
    
    sehUtnPort OBJECT-TYPE
        SYNTAX  INTEGER
        ACCESS  read-write
        STATUS  mandatory
        DESCRIPTION
            "This parameter specifies the UTN port number."
        ::= { sehGeneral 35 }

    sehZebraPort OBJECT-TYPE
        SYNTAX  INTEGER
        ACCESS  read-write
        STATUS  mandatory
        DESCRIPTION
            "This parameter specifies the Zebra UDP port number."
        ::= { sehGeneral 36 }

    sehServiceInfo OBJECT-TYPE
        SYNTAX  DisplayString (SIZE (0..128))
        ACCESS  read-only
        STATUS  mandatory
        DESCRIPTION
            "This parameter returns the service-information string."
        ::= { sehGeneral 37 }



    sehButtonPressed OBJECT-TYPE
        SYNTAX  INTEGER
        ACCESS  read-only
        STATUS  mandatory
        DESCRIPTION
            "This parameter returns the count of pushes of the button."
        ::= { sehGeneral 40 }

    sehUtnSSLPort OBJECT-TYPE
        SYNTAX  INTEGER
        ACCESS  read-write
        STATUS  mandatory
        DESCRIPTION
            "This parameter specifies the UTN SSL port number."
        ::= { sehGeneral 45 }

    sehUtnCiphert OBJECT-TYPE
        SYNTAX  INTEGER { 
        rc4MD5(1),
        aes256SHA(2) }
        ACCESS  read-write
        STATUS  mandatory
        DESCRIPTION
            "This parameter specifies the UTN protocol encryption."
        ::= { sehGeneral 46 }

    sehSwFeatures OBJECT-TYPE
        SYNTAX  INTEGER
        ACCESS  read-only
        STATUS  mandatory
        DESCRIPTION
            "This parameter contains a bitfield of software internal features."
        ::= { sehGeneral 50 }

    -- the sehPprinter group
    -- This group specifies physical printer parameters of SEH print servers.
    
    pprtNumber OBJECT-TYPE
        SYNTAX  INTEGER
        ACCESS  read-only
        STATUS  mandatory
        DESCRIPTION
            "This parameter specifies the number of available printer
            ports/physical printers (regardless of their current state)."
        ::= { sehPprinter 1 }

    pprtTable OBJECT-TYPE
        SYNTAX  SEQUENCE OF PPrtEntryType
        ACCESS  not-accessible
        STATUS  mandatory
        DESCRIPTION
            "This object specifies a table containing a list of printer
            port/physical printer entries. The number of
            entries is given by the value of pprtNumber."
        ::= { sehPprinter 2 }

    pprtEntry OBJECT-TYPE
        SYNTAX  PPrtEntryType
        ACCESS  not-accessible
        STATUS  mandatory
        DESCRIPTION
            "Parameters regarding to physical printers"
        INDEX   { pprtIndex }
        ::= { pprtTable 1 }
    
    PPrtEntryType ::= SEQUENCE {
    pprtIndex               INTEGER,
    pprtError               INTEGER,
    pprtType                INTEGER,
    pprtEcp                 INTEGER,
    pprtPanel               INTEGER,
    pprtMailNotification1   INTEGER,
    pprtMailAddress1        DisplayString,
    pprtMailServer1         IpAddress,
    pprtMailMask1           INTEGER,
    pprtMailNotification2   INTEGER,
    pprtMailAddress2        DisplayString,
    pprtMailServer2         IpAddress,
    pprtMailMask2           INTEGER,
    pprtModel               DisplayString,
    pprtManufacturer        DisplayString,
    pprtEmulations          DisplayString,
    pprtFast                INTEGER,
    pprtBaudrate            INTEGER,
    pprtParity              DisplayString,
    pprtDatabits            INTEGER,
    pprtStopbits            INTEGER,
    pprtFlowControl         DisplayString,
    pprtDeviceID            DisplayString,
    pprtDot4                INTEGER,
    pprtPortMode            INTEGER,
    pprtPjl                 INTEGER
    }
    
    pprtIndex OBJECT-TYPE
        SYNTAX  INTEGER (0..256)
        ACCESS  read-only
        STATUS  mandatory
        DESCRIPTION
            "This object contains the index of the table being a unique
            value for each physical port/physical printer. Its value
            ranges between 1 and the value of pprtNumber."
        ::= { pprtEntry 1 }
    
    pprtError OBJECT-TYPE
        SYNTAX  INTEGER
        ACCESS  read-only
        STATUS  mandatory
        DESCRIPTION
            "This parameter specifies the printer errors.
            BITS       MEANING
            2^0        paper jam
            2^1        paper empty
            2^2        toner low
            2^3        cover open
            2^4        toner empty
            2^5        cassette not ready
            2^6        warming up
            2^7        offline
            2^8        engine error
            2^9        no select
            2^14       service call
            2^15       misc error"
        ::= { pprtEntry 2 }
    
    pprtType OBJECT-TYPE
        SYNTAX  INTEGER {
        parallel(0),
        serial(1),
        kyocera(2),
        mio(3),
        epson(4),
        kuio(5),
        eio(6),
        usb(7)
        }
        ACCESS  read-only
        STATUS  mandatory
        DESCRIPTION
            "This parameter specifies the type of the interface of the printer."
        ::= { pprtEntry 3 }
    
    pprtEcp OBJECT-TYPE
        SYNTAX  INTEGER { disabled(0), enabled(1) }
        ACCESS  read-write
        STATUS  mandatory
        DESCRIPTION
            "This parameter enables the ECP mode for Pocket print servers.
            It is only available for pprtType = parallel(0)."
        ::= { pprtEntry 4 }
    
    pprtPanel OBJECT-TYPE
        SYNTAX  INTEGER { disabled(0), enabled(1) }
        ACCESS  read-write
        STATUS  mandatory
        DESCRIPTION
            "This parameter enables the configuration via printer operating panel.
            It is only available for pprtType = kyocera(2)."
        ::= { pprtEntry 5 }
    
    pprtMailNotification1 OBJECT-TYPE
        SYNTAX  INTEGER { disabled(0), enabled(1) }
        ACCESS  read-write
        STATUS  mandatory
        DESCRIPTION
            "This parameter enables or disables the e-mail
            notification for recipient 1."
        ::= { pprtEntry 7 }
    
    pprtMailAddress1 OBJECT-TYPE
        SYNTAX  DisplayString (SIZE (0..128))
        ACCESS  read-write
        STATUS  mandatory
        DESCRIPTION
            "This parameter specifies the IP address of the e-mail recipient 1."
        ::= { pprtEntry 8 }
    
    pprtMailServer1 OBJECT-TYPE
        SYNTAX  IpAddress
        ACCESS  read-write
        STATUS  mandatory
        DESCRIPTION
            "This parameter specifies the mail server for the e-mail
            notification of recipient 1."
        ::= { pprtEntry 9 }
    
    pprtMailMask1 OBJECT-TYPE
        SYNTAX  INTEGER
        ACCESS  read-write
        STATUS  mandatory
        DESCRIPTION
            "This parameter specifies the mail mask bits of the e-mail
            notification for recipient 1.
            BITS       MEANING
            2^0        paper jam
            2^1        paper empty
            2^2        toner low
            2^3        cover open
            2^4        toner empty
            2^5        cassette not ready
            2^6        warming up
            2^7        offline
            2^8        engine error
            2^9        noselect
            2^10       paper low
            2^14       service call
            2^15       misc error"
        ::= { pprtEntry 10 }
    
    pprtMailNotification2 OBJECT-TYPE
        SYNTAX  INTEGER { disabled(0), enabled(1) }
        ACCESS  read-write
        STATUS  mandatory
        DESCRIPTION
            "This parameter enables or disables the e-mail
            notification for recipient 2."
        ::= { pprtEntry 11 }
    
    pprtMailAddress2 OBJECT-TYPE
        SYNTAX  DisplayString (SIZE (0..128))
        ACCESS  read-write
        STATUS  mandatory
        DESCRIPTION
            "This parameter specifies the IP-address of the e-mail recipient 2."
        ::= { pprtEntry 12 }
    
    pprtMailServer2 OBJECT-TYPE
        SYNTAX  IpAddress
        ACCESS  read-write
        STATUS  mandatory
        DESCRIPTION
            "This parameter specifies the mail server for the e-mail
            notification of recipient 2."
        ::= { pprtEntry 13 }
    
    pprtMailMask2 OBJECT-TYPE
        SYNTAX  INTEGER
        ACCESS  read-write
        STATUS  mandatory
        DESCRIPTION
            "This parameter specifies the mail mask bits of the e-mail
            notification for recipient 2.
            BITS       MEANING
            2^0        paper jam
            2^1        paper empty
            2^2        toner low
            2^3        cover open
            2^4        toner empty
            2^5        cassette not ready
            2^6        warming up
            2^7        offline
            2^8        engine error
            2^9        no select
            2^14       service call
            2^15       misc error"
        ::= { pprtEntry 14 }
    
    pprtModel OBJECT-TYPE
        SYNTAX  DisplayString (SIZE (0..255))
        ACCESS  read-only
        STATUS  mandatory
        DESCRIPTION
            "This parameter specifies the printer model."
        ::= { pprtEntry 15 }
    
    pprtManufacturer OBJECT-TYPE
        SYNTAX  DisplayString (SIZE (0..255))
        ACCESS  read-only
        STATUS  mandatory
        DESCRIPTION
            "This parameter specifies the printer manufacturer."
        ::= { pprtEntry 16 }
    
    pprtEmulations OBJECT-TYPE
        SYNTAX  DisplayString (SIZE (0..255))
        ACCESS  read-only
        STATUS  mandatory
        DESCRIPTION
            "This parameter contains the printer emulations."
        ::= { pprtEntry 17 }
    
    pprtFast OBJECT-TYPE
        SYNTAX  INTEGER { disabled(0), enabled(1) }
        ACCESS  read-write
        STATUS  mandatory
        DESCRIPTION
            "This parameter enables the fast compatible mode for
            print servers with pprtType = parallel(0)."
        ::= { pprtEntry 18 }
    
    pprtBaudrate OBJECT-TYPE
        SYNTAX  INTEGER
        ACCESS  read-write
        STATUS  mandatory
        DESCRIPTION
            "This parameter specifies the baud rate
            for ports with pprtType = serial(1)."
        ::= { pprtEntry 19 }
    
    pprtParity OBJECT-TYPE
        SYNTAX  DisplayString (SIZE (1..31))
        ACCESS  read-write
        STATUS  mandatory
        DESCRIPTION
            "This parameter specifies the parity
            for ports with pprtType = serial(1).
            It may take the values none, even or odd."
        ::= { pprtEntry 20 }
    
    pprtDatabits OBJECT-TYPE
        SYNTAX  INTEGER
        ACCESS  read-write
        STATUS  mandatory
        DESCRIPTION
            "This parameter specifies the number of data bits
            for ports with pprtType = serial(1)."
        ::= { pprtEntry 21 }
    
    pprtStopbits OBJECT-TYPE
        SYNTAX  INTEGER
        ACCESS  read-write
        STATUS  mandatory
        DESCRIPTION
            "This parameter specifies the number of stop bits
            for ports with pprtType = serial(1)."
        ::= { pprtEntry 22 }
    
    pprtFlowControl OBJECT-TYPE
        SYNTAX  DisplayString (SIZE (1..31))
        ACCESS  read-write
        STATUS  mandatory
        DESCRIPTION
            "This parameter specifies the flow control
            for ports with pprtType = serial(1).
            It may take the values none, xon, dsr or both."
        ::= { pprtEntry 23 }
    
    pprtDeviceID OBJECT-TYPE
        SYNTAX  DisplayString (SIZE (0..512))
        ACCESS  read-only
        STATUS  mandatory
        DESCRIPTION
            "This parameter contains the printer device id."
        ::= { pprtEntry 24 }
    
    pprtDot4 OBJECT-TYPE
        SYNTAX  INTEGER { disabled(0), enabled(1) }
        ACCESS  read-write
        STATUS  mandatory
        DESCRIPTION
            "On print servers with external interfaces
            this parameter enables the IEEE 1284.4 protocol
            resp. the (similar) MLC protocol."
        ::= { pprtEntry 25 }
    
    -- todo : only for box and pocket !
    pprtPortMode OBJECT-TYPE
        SYNTAX  INTEGER { bidirectional(0), unidirectional(1), kmptgdi(2), utn(3)}
        ACCESS  read-write
        STATUS  mandatory
        DESCRIPTION
            "This parameter specifies how to handle the communication
            at the printer port. Beside uni and bidirectional there are
            modes for manufactor specific GDI printer."
        ::= { pprtEntry 26 }
    
    pprtPjl OBJECT-TYPE
        SYNTAX  INTEGER { disabled(0), enabled(1) }
        ACCESS  read-write
        STATUS  mandatory
        DESCRIPTION
            "On print servers with external interfaces
            this parameter enables the PJL (Printer Job Language) protocol."
        ::= { pprtEntry 27 }
    

    pprtDynUpdate OBJECT-TYPE
        SYNTAX  INTEGER { disabled(0), enabled(1) }
        ACCESS  read-write
        STATUS  mandatory
        DESCRIPTION
            "This parameter switches the printer dynamic update on or off."
        ::= { sehPprinter 10 }


    pprtDynUpdateUrl OBJECT-TYPE
        SYNTAX  DisplayString (SIZE (0..255))
        ACCESS  read-write
        STATUS  mandatory
        DESCRIPTION
            "This parameter specifies the printer firmware update ftp url."
        ::= { sehPprinter 11 }

    pprtDynUpdateUsr OBJECT-TYPE
        SYNTAX  DisplayString (SIZE (0..64))
        ACCESS  read-write
        STATUS  mandatory
        DESCRIPTION
            "This parameter specifies the printer firmware update ftp user."
        ::= { sehPprinter 12 }

    pprtDynUpdatePwd OBJECT-TYPE
        SYNTAX  DisplayString (SIZE (0..64))
        ACCESS  read-write
        STATUS  mandatory
        DESCRIPTION
            "This parameter specifies the printer firmware update ftp password."
        ::= { sehPprinter 13 }

    pprtDynStatusPath OBJECT-TYPE
        SYNTAX  DisplayString (SIZE (0..128))
        ACCESS  read-write
        STATUS  mandatory
        DESCRIPTION
            "This parameter specifies the printer status path and file name."
        ::= { sehPprinter 14 }

    pprtDynUpdateHour OBJECT-TYPE
        SYNTAX  INTEGER (0..24)
        ACCESS  read-write
        STATUS  mandatory
        DESCRIPTION
            "This parameter defines the hour for the daily printer firmware update.
             24 means the daily update is disabled. 
             The update is randomly delayed between 0 und 15 minutes to avoid traffic bursts."
        ::= { sehPprinter 20 }

    pprtDynReportMin OBJECT-TYPE
        SYNTAX  INTEGER (0..44640)
        ACCESS  read-write
        STATUS  mandatory
        DESCRIPTION
            "This parameter defines the minutes between the ftp committed printer status reports.
             0 means only report once after start." 
        ::= { sehPprinter 21 }

    -- the sehLprinter group
    
    -- This group specifies logical printer parameters of SEH print servers.
    
    
    lprtNumber OBJECT-TYPE
        SYNTAX  INTEGER
        ACCESS  read-only
        STATUS  mandatory
        DESCRIPTION
            "This parameter specifies the number of available logical
            printers (regardless of their current state)."
        ::= { sehLprinter 1 }
    
    lprtTable OBJECT-TYPE
        SYNTAX  SEQUENCE OF LPrtEntry
        ACCESS  not-accessible
        STATUS  mandatory
        DESCRIPTION
            "This object specifies a table containing a list of logical printer
            entries. The number of entries is given by the value of lprtNumber."
        ::= { sehLprinter 2 }
    
    lprtEntry OBJECT-TYPE
        SYNTAX  LPrtEntry
        ACCESS  not-accessible
        STATUS  mandatory
        DESCRIPTION
            "Parameters regarding to logical printers."
        INDEX   { lprtIndex }
        ::= { lprtTable 1 }
    
    LPrtEntry ::= SEQUENCE {
    lprtIndex       INTEGER,
    lprtStart       DisplayString,
    lprtEnd         DisplayString,
    lprtPhyPrt      INTEGER,
    lprtTCPPort     INTEGER,
    lprtCRLF        INTEGER,
    lprtHexDp       INTEGER,
    lprtBp          INTEGER,
    lprtAsPs        INTEGER,
    lprtMode        INTEGER,
    lprtRsoSpool    INTEGER,
    lprtSearch      DisplayString,
    lprtReplace     DisplayString,
    lprtBinaryPS    INTEGER
    }
    
    lprtIndex OBJECT-TYPE
        SYNTAX  INTEGER (0..256)
        ACCESS  read-only
        STATUS  mandatory
        DESCRIPTION
            "This object contains the index of the table being a
            unique value for each logical printer. Its value
            ranges between 1 and the value of lprtNumber."
        ::= { lprtEntry 1 }
    
    lprtStart OBJECT-TYPE
        SYNTAX  DisplayString (SIZE (1..63))
        ACCESS  read-write
        STATUS  mandatory
        DESCRIPTION
            "This parameter specifies the start sequence
            of a logical printer."
        ::= { lprtEntry 2 }
    
    lprtEnd OBJECT-TYPE
        SYNTAX  DisplayString (SIZE (1..63))
        ACCESS  read-write
        STATUS  mandatory
        DESCRIPTION
            "This parameter specifies the end sequence
            of a logical printer."
        ::= { lprtEntry 3 }
    
    lprtPhyPrt OBJECT-TYPE
        SYNTAX  INTEGER { port1(1), port2(2), port3(3), port4(4) }
        ACCESS  read-write
        STATUS  mandatory
        DESCRIPTION
            "This parameter assigns a physical port to a logical
            printer. It is only available for pprtNumber > 1."
        ::= { lprtEntry 4 }
    
    lprtTCPPort OBJECT-TYPE
        SYNTAX  INTEGER
        ACCESS  read-write
        STATUS  mandatory
        DESCRIPTION
            "This parameter specifies the TCP/IP port of the logical printer."
        ::= { lprtEntry 5 }
    
    lprtCRLF OBJECT-TYPE
        SYNTAX  INTEGER { disabled(0), enabled(1) }
        ACCESS  read-write
        STATUS  mandatory
        DESCRIPTION
            "If this parameter is enabled, LF is converted to CR+LF."
        ::= { lprtEntry 6 }
    
    lprtHexDp OBJECT-TYPE
        SYNTAX  INTEGER { disabled(0), enabled(1) }
        ACCESS  read-write
        STATUS  mandatory
        DESCRIPTION
            "This parameter enables or disables the hex dump mode."
        ::= { lprtEntry 7 }
    
    lprtBp OBJECT-TYPE
        SYNTAX  INTEGER { disabled(0), enabled(1) }
        ACCESS  read-write
        STATUS  mandatory
        DESCRIPTION
            "If this parameter is enabled a banner page is printed."
        ::= { lprtEntry 8 }
    
    lprtAsPs OBJECT-TYPE
        SYNTAX  INTEGER { disabled(0), enabled(1) }
        ACCESS  read-write
        STATUS  mandatory
        DESCRIPTION
            "This parameter converts ASCII to PostScript."
        ::= { lprtEntry 9 }
    
    lprtMode OBJECT-TYPE
        SYNTAX  INTEGER { ascii(0), postscript(1) }
        ACCESS  read-write
        STATUS  mandatory
        DESCRIPTION
            "This parameter specifies the format of the banner page."
        ::= { lprtEntry 10 }
    
    lprtRsoSpool OBJECT-TYPE
        SYNTAX  INTEGER { disabled(0), enabled(1) }
        ACCESS  read-write
        STATUS  mandatory
        DESCRIPTION
            "This parameter uses the RSO spooler on TCP socket connections."
        ::= { lprtEntry 11 }
    
    lprtSearch OBJECT-TYPE
        SYNTAX  DisplayString (SIZE (1..63))
        ACCESS  read-write
        STATUS  mandatory
        DESCRIPTION
            "Logical printer search string for search and replace."
        ::= { lprtEntry 13 }
    
    lprtReplace OBJECT-TYPE
        SYNTAX  DisplayString (SIZE (1..63))
        ACCESS  read-write
        STATUS  mandatory
        DESCRIPTION
            "Logical printer replace string for search and replace."
        ::= { lprtEntry 14 }
    
    lprtBinaryPS OBJECT-TYPE
        SYNTAX  INTEGER { disabled(0), enabled(1) }
        ACCESS  read-write
        STATUS  mandatory
        DESCRIPTION
            "This parameter enables support for binary PostScript data
            on TCP socket connections."
        ::= { lprtEntry 15 }

    -- the sehIp group
    -- This group specifies the TCP/IP parameters of the SEH print servers.
    
    ipIpAddr OBJECT-TYPE
        SYNTAX  IpAddress
        ACCESS  read-write
        STATUS  mandatory
        DESCRIPTION
            "This parameter specifies the IP address of the print server."
        ::= { sehIp 1 }
    
    ipNetMask OBJECT-TYPE
        SYNTAX  IpAddress
        ACCESS  read-write
        STATUS  mandatory
        DESCRIPTION
            "This parameter specifies the subnet mask."
        ::= { sehIp 2 }
    
    ipDefGate OBJECT-TYPE
        SYNTAX  IpAddress
        ACCESS  read-write
        STATUS  mandatory
        DESCRIPTION
            "This parameter specifies the IP address of the default gateway."
        ::= { sehIp 3 }
    
    ipBOOTP OBJECT-TYPE
        SYNTAX  INTEGER { disabled(0), enabled(1) }
        ACCESS  read-write
        STATUS  mandatory
        DESCRIPTION
            "This parameter enables the BOOTP protocol."
        ::= { sehIp 4 }
    
    ipRARP OBJECT-TYPE
        SYNTAX  INTEGER { disabled(0), enabled(1) }
        ACCESS  read-write
        STATUS  mandatory
        DESCRIPTION
            "This parameter enables the RARP protocol."
        ::= { sehIp 5 }
    
    ipAutoconf OBJECT-TYPE
        SYNTAX  INTEGER { disabled(0), enabled(1) }
        ACCESS  read-write
        STATUS  mandatory
        DESCRIPTION
            "This parameter enables ARP/PING to
            save the IP address in the print server."
        ::= { sehIp 6 }
    
    ipDHCP OBJECT-TYPE
        SYNTAX  INTEGER { disabled(0), enabled(1) }
        ACCESS  read-write
        STATUS  mandatory
        DESCRIPTION
            "This parameter enables the DHCP protocol."
        ::= { sehIp 7 }
    
    ipZeroConf OBJECT-TYPE
        SYNTAX  INTEGER { disabled(0), enabled(1) }
        ACCESS  read-write
        STATUS  mandatory
        DESCRIPTION
            "This parameter enables the ZeroConfig protocol."
        ::= { sehIp 8 }
    
    ipSetBy OBJECT-TYPE
        SYNTAX  INTEGER {
        unknown(0),
        snmp(1),
        bootp(2),
        dhcp(3),
        arpping(4),
        panel(5),
        zeroconfig(6),
        parameterfile(7),
        rarp(8),
        slp(9),
        epsonenpc(10),
        appleadm(11),
        http(12) }
        ACCESS  read-only
        STATUS  mandatory
        DESCRIPTION
            "This parameter informs who has set the current ip address"
        ::= { sehIp 9 }
    
    -- todo : obsolete begin
    
    ipWinsPrimarySrv OBJECT-TYPE
        SYNTAX  IpAddress
        ACCESS  read-write
        STATUS  mandatory
        DESCRIPTION
            "This parameter specifies the IP address of the primary WINS server."
        ::= { sehIp 10 }
    
    ipWinsSecondarySrv OBJECT-TYPE
        SYNTAX  IpAddress
        ACCESS  read-write
        STATUS  mandatory
        DESCRIPTION
            "This parameter specifies the IP address of the secondary WINS server."
        ::= { sehIp 11 }
    
    -- obsolete end
    
    ipTCP OBJECT-TYPE
        SYNTAX  INTEGER { disabled(0), enabled(1) }
        ACCESS  read-write
        STATUS  mandatory
        DESCRIPTION
            "This parameter enables or disables TCP/IP."
        ::= { sehIp 12 }
    
    ipDNS OBJECT-TYPE
        SYNTAX  INTEGER { disabled(0), enabled(1) }
        ACCESS  read-write
        STATUS  mandatory
        DESCRIPTION
            "This parameter enables the DNS name resolution."
        ::= { sehIp 13 }
    
    ipDomainName OBJECT-TYPE
        SYNTAX  DisplayString (SIZE (1..255))
        ACCESS  read-write
        STATUS  mandatory
        DESCRIPTION
            "This parameter specifies the domain name."
        ::= { sehIp 14 }
    
    ipDnsPrimarySrv OBJECT-TYPE
        SYNTAX  IpAddress
        ACCESS  read-write
        STATUS  mandatory
        DESCRIPTION
            "This parameter specifies the IP address of the primary DNS server."
        ::= { sehIp 15 }
    
    ipDnsSecondarySrv OBJECT-TYPE
        SYNTAX  IpAddress
        ACCESS  read-write
        STATUS  mandatory
        DESCRIPTION
            "This parameter specifies the IP address of the secondary DNS server."
        ::= { sehIp 16 }
    
    ipSenderNumber OBJECT-TYPE
        SYNTAX  INTEGER
        ACCESS  read-only
        STATUS  mandatory
        DESCRIPTION
            "Number of IP sender"
        ::= { sehIp 17 }
    
    ipSenderTable OBJECT-TYPE
        SYNTAX  SEQUENCE OF IpSenderEntry
        ACCESS  not-accessible
        STATUS  mandatory
        DESCRIPTION
            "Table of Ip senders"
        ::= { sehIp 18 }
    
    ipAutoGate OBJECT-TYPE
        SYNTAX  INTEGER { disabled(0), enabled(1) }
        ACCESS  read-write
        STATUS  mandatory
        DESCRIPTION
            "This parameter enables the use of a multicast router
            as the default gateway."
        ::= { sehIp 19 }
    
    ipZeroConfig OBJECT-TYPE
        SYNTAX  INTEGER { disabled(0), enabled(1) }
        ACCESS  read-write
        STATUS  mandatory
        DESCRIPTION
            "This parameter enables the ZeroConfig protocol. 
             Identical to sehIp 8 for compatibility reasons."
        ::= { sehIp 20 }
    
    ipHTTP OBJECT-TYPE
        SYNTAX  INTEGER { disabled(0), enabled(1) }
        ACCESS  read-write
        STATUS  mandatory
        DESCRIPTION
            "This parameter enables the HTTP daemon."
        ::= { sehIp 21 }
    
    ipIPv6 OBJECT-TYPE
        SYNTAX  INTEGER { disabled(0), enabled(1) }
        ACCESS  read-write
        STATUS mandatory
        DESCRIPTION
            "This parameter enables the IPv6 protocol."
        ::= { sehIp 22 }

    ipIPv6Addr OBJECT-TYPE
        SYNTAX  DisplayString (SIZE (1..40))
        ACCESS  read-write
        STATUS mandatory
        DESCRIPTION
            "This parameter set manual a IPv6-Address."
        ::= { sehIp 23 }

    ipIPv6Plen OBJECT-TYPE
        SYNTAX  INTEGER (0..64)
        ACCESS  read-write
        STATUS mandatory
        DESCRIPTION
            "This parameter set IPv6 prefix length."
        ::= { sehIp 24 }

    ipIPv6Gate OBJECT-TYPE
        SYNTAX  DisplayString (SIZE (1..40))
        ACCESS  read-write
        STATUS mandatory
        DESCRIPTION
            "This parameter set manual a IPv6-Route."
        ::= { sehIp 25 }

    ipIPv6Auto OBJECT-TYPE
        SYNTAX  INTEGER { disabled(0), enabled(1) }
        ACCESS  read-write
        STATUS mandatory
        DESCRIPTION
            "This parameter enables or disables the IPv6 Automatic configuration."
        ::= { sehIp 26 }

    ipFTP OBJECT-TYPE
        SYNTAX  INTEGER { disabled(0), enabled(1) }
        ACCESS  read-write
        STATUS mandatory
        DESCRIPTION
            "This parameter enables or disables the FPT daemon."
        ::= { sehIp 30 }


    ip4VLanNumber OBJECT-TYPE
        SYNTAX  INTEGER
        ACCESS  read-only
        STATUS  mandatory
        DESCRIPTION
            "Number of entries in the  Ip VLan table."
        ::= { sehIpVLan 1 }
    
    Ip4VLanEntryType ::= SEQUENCE {
    ip4VLanIndex   INTEGER,
    ip4VLanOnOff   INTEGER,
    ip4VLanAddr    DisplayString,
    ip4VLanMask    DisplayString,
    ip4VLanID      INTEGER,
    ip4VLanGate    DisplayString
    }

    ip4VLanTable OBJECT-TYPE
        SYNTAX  SEQUENCE OF Ip4VLanEntryType
        ACCESS  not-accessible
        STATUS  mandatory
        DESCRIPTION
            "This object specifies a table containing IP filter descriptions."
        ::= { sehIpVLan 2 }

    ip4VLanEntry OBJECT-TYPE
        SYNTAX  Ip4VLanEntryType
        ACCESS  not-accessible
        STATUS  mandatory
        DESCRIPTION
            "Entry of Ip4 VLan table."
        INDEX   { ip4VLanIndex }
        ::= { ip4VLanTable 1 }
    
    ip4VLanIndex OBJECT-TYPE
        SYNTAX  INTEGER (0..256)
        ACCESS  not-accessible
        STATUS  mandatory
        DESCRIPTION
            "This object contains the index of the table being a
            unique value for each IP vlan address."
        ::= { ip4VLanEntry 1 }
    
    ip4VLanOnOff OBJECT-TYPE
        SYNTAX  INTEGER { off(0), on(1) }
        ACCESS  read-write
        STATUS  mandatory
        DESCRIPTION
            "This parameter specifies wether the vlan address is active or not."
        ::= { ip4VLanEntry 2 }
 
    ip4VLanAddr OBJECT-TYPE
        SYNTAX  DisplayString (SIZE (1..64))
        ACCESS  read-write
        STATUS  mandatory
        DESCRIPTION
            "This parameter specifies the Ip vlan address."
        ::= { ip4VLanEntry 3 }

    ip4VLanMask OBJECT-TYPE
        SYNTAX  DisplayString (SIZE (1..64))
        ACCESS  read-write
        STATUS  mandatory
        DESCRIPTION
            "This parameter specifies the Ip mask for the vlan address."
        ::= { ip4VLanEntry 4 }

   ip4VLanID OBJECT-TYPE
        SYNTAX  INTEGER (1..4094)
        ACCESS  read-write
        STATUS  mandatory
        DESCRIPTION
            "This object contains the VLan ID for this VLan." 
        ::= { ip4VLanEntry 5 }
    
    ip4VLanGate OBJECT-TYPE
        SYNTAX  DisplayString (SIZE (1..64))
        ACCESS  read-write
        STATUS  mandatory
        DESCRIPTION
            "This parameter specifies the Ip gate for the vlan address."
        ::= { ip4VLanEntry 6 }


    ip4VLanWeb OBJECT-TYPE
        SYNTAX  INTEGER { disabled(0), enabled(1) }
        ACCESS  read-write
        STATUS mandatory
        DESCRIPTION
            "Obsolete - This parameter enables or disables Web access through vlan ports."
        ::= { sehIpVLan 3 }

    ip4VLanSNMP OBJECT-TYPE
        SYNTAX  INTEGER { disabled(0), enabled(1) }
        ACCESS  read-write
        STATUS mandatory
        DESCRIPTION
            "Obsolete - This parameter enables or disables Snmp access through vlan ports."
        ::= { sehIpVLan 4 }

    ip4VLanMgmt OBJECT-TYPE
        SYNTAX  INTEGER { disabled(0), enabled(1) }
        ACCESS  read-write
        STATUS  mandatory
        DESCRIPTION
            "This parameter enables or disables management access for all other vlans."
        ::= { sehIpVLan 10 }

    ip4VLanMgmtID OBJECT-TYPE
        SYNTAX  INTEGER (0..4096)
        ACCESS  read-write
        STATUS  mandatory
        DESCRIPTION
            "This object contains the VLan ID for the management VLan." 
        ::= { sehIpVLan 11 }
    
    ip4VLanMgmtAny OBJECT-TYPE
        SYNTAX  INTEGER { disabled(0), enabled(1) }
        ACCESS  read-write
        STATUS  mandatory
        DESCRIPTION
            "This parameter enables or disables management access for all other vlans."
        ::= { sehIpVLan 12 }
    
    ip4VLanMgmtUntag OBJECT-TYPE
        SYNTAX  INTEGER { disabled(0), enabled(1) }
        ACCESS  read-write
        STATUS  mandatory
        DESCRIPTION
            "This parameter enables or disables management access from unttaged lan beside VLan access."
        ::= { sehIpVLan 13 }
    
    ipSenderEntry OBJECT-TYPE
        SYNTAX  IpSenderEntry
        ACCESS  not-accessible
        STATUS  mandatory
        DESCRIPTION
            "Entry of IP sender table"
        INDEX   { ipSenderIndex }
        ::= { ipSenderTable 1 }
    
    IpSenderEntry ::= SEQUENCE {
    ipSenderIndex   INTEGER,
    ipSender        DisplayString
    }
    
    ipSenderIndex OBJECT-TYPE
        SYNTAX  INTEGER (0..256)
        ACCESS  read-only
        STATUS  mandatory
        DESCRIPTION
            "Index of IP sender table."
        ::= { ipSenderEntry 1 }
    
    ipSender OBJECT-TYPE
        SYNTAX  DisplayString (SIZE (1..255))
        ACCESS  read-write
        STATUS  mandatory
        DESCRIPTION
            "IP sender."
        ::= { ipSenderEntry 2 }
    
    -- the sehNovell group
    -- This group specifies Novell parameters of SEH print servers.
    
    nwName OBJECT-TYPE
        SYNTAX  DisplayString (SIZE (1..128))
        ACCESS  read-write
        STATUS  mandatory
        DESCRIPTION
            "This parameter specifies the Novell name
            of the SEH print server."
        ::= { sehNovell 1  }
    
    nwNDS OBJECT-TYPE
        SYNTAX  INTEGER { disabled(0), enabled(1) }
        ACCESS  read-write
        STATUS  mandatory
        DESCRIPTION
            "This parameter enables or disables the support
            for the Netware Directory Services."
        ::= { sehNovell 2 }
    
    nwBindery OBJECT-TYPE
        SYNTAX  INTEGER { disabled(0), enabled(1) }
        ACCESS  read-write
        STATUS  mandatory
        DESCRIPTION
            "This parameter enables or disables the support
            for the Netware Bindery Services."
        ::= { sehNovell 3 }
    
    nw8022 OBJECT-TYPE
        SYNTAX  INTEGER { disabled(0), enabled(1) }
        ACCESS  read-write
        STATUS  mandatory
        DESCRIPTION
            "This parameter enables or disables the
            frame header ETHERNET_802.2."
        ::= { sehNovell 4 }
    
    nw8023 OBJECT-TYPE
        SYNTAX  INTEGER { disabled(0), enabled(1) }
        ACCESS  read-write
        STATUS  mandatory
        DESCRIPTION
            "This parameter enables or disables the
            frame header ETHERNET_802.3."
        ::= { sehNovell 5 }
    
    nwEthII OBJECT-TYPE
        SYNTAX  INTEGER { disabled(0), enabled(1) }
        ACCESS  read-write
        STATUS  mandatory
        DESCRIPTION
            "This parameter enables or disables the
            frame header ETHERNET_II."
        ::= { sehNovell 6 }
    
    nwSNAP OBJECT-TYPE
        SYNTAX  INTEGER { disabled(0), enabled(1) }
        ACCESS  read-write
        STATUS  mandatory
        DESCRIPTION
            "This parameter enables or disables the
            frame header ETHERNET_SNAP."
        ::= { sehNovell 7 }
    
    
    nwUpdate OBJECT-TYPE
        SYNTAX  INTEGER { disabled(0), enabled(1) }
        ACCESS  read-write
        STATUS  mandatory
        DESCRIPTION
            "This parameters enables or disables the automatic network recognition."
        ::= { sehNovell 8 }
    
    
    nwUpdTime OBJECT-TYPE
        SYNTAX  INTEGER
        ACCESS  read-write
        STATUS  mandatory
        DESCRIPTION
            "This parameter specifies the time between two refresh cycles.
            Refreshes are at least important to restore lost connections."
        ::= { sehNovell 9 }
    
    
    nwPollTime OBJECT-TYPE
        SYNTAX  INTEGER
        ACCESS  read-write
        STATUS  mandatory
        DESCRIPTION
            "This parameter specifies the time between two poll cycles."
        ::= { sehNovell 10 }
    
    nwServer1 OBJECT-TYPE
        SYNTAX  DisplayString (SIZE (1..129))
        ACCESS  read-write
        STATUS  mandatory
        DESCRIPTION
            "This parameter specifies the first Novell server. If a string is
            entered, the print server does only see the file server with
            exacly this name (case sensitive).
            In additiion, this parameter is used by Pure IP to find this Novell
            Server, given by his IP address or, if DNS is configured, his full
            DNS name."
        ::= { sehNovell 11 }
    
    nwServer2 OBJECT-TYPE
        SYNTAX  DisplayString (SIZE (1..129))
        ACCESS  read-write
        STATUS  mandatory
        DESCRIPTION
            "This parameter specifies the second Novell server.
            If a string is entered, the print server does only see
            the file server with exacly this name (case sensitive).
            Use only if nwServer1 is also used.
            In additiion, this parameter is used by Pure IP to find this Novell
            Server, given by his IP address or, if DNS is configured, his full
            DNS name."
        ::= { sehNovell 12 }
    
    nwServer3 OBJECT-TYPE
        SYNTAX  DisplayString (SIZE (1..129))
        ACCESS  read-write
        STATUS  mandatory
        DESCRIPTION
            "This parameter specifies the third Novell server.
            If a string is entered, the print server does only see
            the file server with exacly this name (case sensitive).
            Use only if nwServer1 and 2 are also used.
            In additiion, this parameter is used by Pure IP to find this Novell
            Server, given by his IP address or, if DNS is configured, his full
            DNS name."
        ::= { sehNovell 13 }
    
    nwServer4 OBJECT-TYPE
        SYNTAX  DisplayString (SIZE (1..129))
        ACCESS  read-write
        STATUS  mandatory
        DESCRIPTION
            "This parameter specifies the 4th Novell server.
            If a string is entered, the print server does only see
            the file server with exacly this name (case sensitive).
            Use only if nwServer1, 2, and 3 are also used.
            In additiion, this parameter is used by Pure IP to find this Novell
            Server, given by his IP address or, if DNS is configured, his full
            DNS name."
        ::= { sehNovell 14 }
    
    nwNDSCommonName OBJECT-TYPE
        SYNTAX  DisplayString (SIZE (1..256))
        ACCESS  read-only
        STATUS  mandatory
        DESCRIPTION
            "This parameter specifies the NDS name."
        ::= { sehNovell 15 }
    
    nwNDSTreeFound OBJECT-TYPE
        SYNTAX  DisplayString (SIZE (1..32))
        ACCESS  read-only
        STATUS  mandatory
        DESCRIPTION
            "This parameter specifies the name of the  NDS tree
            containing the print server object"
        ::= { sehNovell 16 }
    
    nwNDSFound OBJECT-TYPE
        SYNTAX  INTEGER
        ACCESS  read-only
        STATUS  mandatory
        DESCRIPTION
            "This parameter specifies the number of objects
            with the same NDS name."
        ::= { sehNovell 17 }
    
    nwConnNumber OBJECT-TYPE
        SYNTAX  INTEGER
        ACCESS  read-only
        STATUS  mandatory
        DESCRIPTION
            "This parameter specifies the number of the available
            NetWare connections."
        ::= { sehNovell 18 }
    
    nwConnTable OBJECT-TYPE
        SYNTAX  SEQUENCE OF NWConnEntry
        ACCESS  not-accessible
        STATUS  mandatory
        DESCRIPTION
            "This object specifies a table containing a list of
            NetWare connections entries. The number of entries
            is given by the value of nwConnNumber."
        ::= { sehNovell 19 }
    
    nwConnEntry OBJECT-TYPE
        SYNTAX  NWConnEntry
        ACCESS  not-accessible
        STATUS  mandatory
        DESCRIPTION
            "Entry of NCP connection table."
        INDEX   { nwConnIndex }
        ::= { nwConnTable 1 }
    
    NWConnEntry ::= SEQUENCE {
    nwConnIndex         INTEGER,
    nwConnServer        DisplayString,
    nwConnState         INTEGER,
    nwConnLastError     INTEGER,
    nwConnServerState   INTEGER,
    nwConnHeader        INTEGER,
    nwConnNet           INTEGER
    }
    
    nwConnIndex OBJECT-TYPE
        SYNTAX  INTEGER (0..256)
        ACCESS  read-only
        STATUS  mandatory
        DESCRIPTION
            "This object contains the index of the table being a
            unique value for each NetWare connection.  Its value
            ranges between 1 and the value of nwConnNumber."
        ::= { nwConnEntry 1 }
    
    nwConnServer OBJECT-TYPE
        SYNTAX  DisplayString (SIZE (1..48))
        ACCESS  read-only
        STATUS  mandatory
        DESCRIPTION
            "This parameter specifies the NetWare server name."
        ::= { nwConnEntry 2 }
    
    nwConnState OBJECT-TYPE
        SYNTAX  INTEGER { notConnected(0),
        binderyLogin(2),
        binderyLoginSetPwd(3),
        attached(17),
        ndsLogin(32),
        ndsAuthenticated(48),
        ndsLocked(64),
        ndsLoginSetPwd(160) }
        ACCESS  read-only
        STATUS  mandatory
        DESCRIPTION
            "This parameter specifies the state of the
            NetWare connection."
        ::= { nwConnEntry 3 }
    
    nwConnLastError OBJECT-TYPE
        SYNTAX  INTEGER
        ACCESS  read-only
        STATUS  mandatory
        DESCRIPTION
            "This parameter specifies the last connection error.
            VALUE       MEANING
            0           No Error
            2           Bindery Login refused (Hint: If not connected - delete Password)
            3           Bindery ChangePassword failed
            32          NDS Login refused (Hint: If not connected - delete Password)
            48          NDS ChangePassword failed
            "
        ::= { nwConnEntry 4 }
    
    nwConnServerState OBJECT-TYPE
        SYNTAX  INTEGER  { idle(0), sleep(1), busy(2) }
        ACCESS  read-only
        STATUS  mandatory
        DESCRIPTION
            "This parameter specifies the server state."
        ::= { nwConnEntry 5 }
    
    nwConnHeader OBJECT-TYPE
        SYNTAX  INTEGER { ethernetII(1),
        ieee802-3(2),
        ieee802-2(4),
        snap(8),
        ieee802-5(16)}
        ACCESS  read-only
        STATUS  mandatory
        DESCRIPTION
            "This parameter specifies the frame header used in a connection."
        ::= { nwConnEntry 6 }
    
    nwConnNet OBJECT-TYPE
        SYNTAX  INTEGER
        ACCESS  read-only
        STATUS  mandatory
        DESCRIPTION
            "This parameter specifies the network number
            of the connected file server"
        ::= { nwConnEntry 7 }
    
    nwQueueNumber OBJECT-TYPE
        SYNTAX  INTEGER
        ACCESS  read-only
        STATUS  mandatory
        DESCRIPTION
            "This parameter specifies the number
            of available NetWare queues."
        ::= { sehNovell 20 }
    
    nwQueueTable OBJECT-TYPE
        SYNTAX  SEQUENCE OF NWQueueEntry
        ACCESS  not-accessible
        STATUS  mandatory
        DESCRIPTION
            "This object specifies a table containing a list of
            NetWare queue entries. The number of entries is
            given by the value of nwQueueNumber."
        ::= { sehNovell 21 }
    
    nwQueueEntry OBJECT-TYPE
        SYNTAX  NWQueueEntry
        ACCESS  not-accessible
        STATUS  mandatory
        DESCRIPTION
            "Entry of NCP queue table."
        INDEX   { nwQueueIndex }
        ::= { nwQueueTable 1 }
    
    NWQueueEntry ::= SEQUENCE {
    nwQueueIndex    INTEGER,
    nwQueueName     DisplayString,
    nwQueueConnId   INTEGER,
    nwQueuePort     INTEGER,
    nwQueueState    INTEGER
    }
    
    nwQueueIndex OBJECT-TYPE
        SYNTAX  INTEGER (0..256)
        ACCESS  read-only
        STATUS  mandatory
        DESCRIPTION
            "This object contains the index of the table being a
            unique value for each queue.  Its value ranges between 1
            and the value of nwQueueNumber."
        ::= { nwQueueEntry 1 }
    
    nwQueueName OBJECT-TYPE
        SYNTAX  DisplayString (SIZE (1..256))
        ACCESS  read-only
        STATUS  mandatory
        DESCRIPTION
            "This parameter specifies the NetWare queue name."
        ::= { nwQueueEntry 2 }
    
    nwQueueConnId OBJECT-TYPE
        SYNTAX  INTEGER
        ACCESS  read-only
        STATUS  mandatory
        DESCRIPTION
            "This parameter specifies the connection ID."
        ::= { nwQueueEntry 3 }
    
    nwQueuePort OBJECT-TYPE
        SYNTAX  INTEGER { lp1(1),
        lp2(2),
        lp3(4),
        lp4(8),
        lp5(16),
        lp6(32),
        lp7(64),
        lp8(128) }
        ACCESS  read-only
        STATUS  mandatory
        DESCRIPTION
            "This parameter specifies the logical printer used."
        ::= { nwQueueEntry 4 }
    
    nwQueueState OBJECT-TYPE
        SYNTAX  INTEGER { lost(5),
        attachError(16),
        printingError(32),
        pollingError(48),
        attached(133),
        printing(144),
        printingAbort(160) }
        ACCESS  read-only
        STATUS  mandatory
        DESCRIPTION
            "This parameter specifies the state of the queue."
        ::= { nwQueueEntry 5 }
    
    nwRprinterHeader OBJECT-TYPE
        SYNTAX  INTEGER { ethernetII(1),
        ieee802-3(2),
        ieee802-2(4),
        snap(8),
        ieee802-5(16)}
        ACCESS  read-only
        STATUS  mandatory
        DESCRIPTION
            "This parameter shows the used frame headers (remote printer mode)."
        ::= { sehNovell 22 }
    
    nwNDSPwd OBJECT-TYPE
        SYNTAX  INTEGER { disabled(0), enabled(1) }
        ACCESS  read-write
        STATUS  mandatory
        DESCRIPTION
            "This parameter enables the NDS password."
        ::= { sehNovell 23 }
    
    nwBinderyPwd OBJECT-TYPE
        SYNTAX  INTEGER { disabled(0), enabled(1) }
        ACCESS  read-write
        STATUS  mandatory
        DESCRIPTION
            "This parameter enables the Bindery password."
        ::= { sehNovell 24 }
    
    nw8025 OBJECT-TYPE
        SYNTAX  INTEGER { disabled(0), enabled(1) }
        ACCESS  read-write
        STATUS  mandatory
        DESCRIPTION
            "This parameter enables or disables the
            frame header TOKENRING_802.5."
        ::= { sehNovell 25 }
    
    -- only for print server generation 2 (Version 8.x.x)
    nwPserver OBJECT-TYPE
        SYNTAX  INTEGER { disabled(0), enabled(1) }
        ACCESS  read-write
        STATUS  mandatory
        DESCRIPTION
            "This parameter enables or disables the
            print server mode."
        ::= { sehNovell 26 }
    
    nwRprinter OBJECT-TYPE
        SYNTAX  INTEGER { disabled(0), enabled(1) }
        ACCESS  read-write
        STATUS  mandatory
        DESCRIPTION
            "This parameter enables or disables the
            remote printer mode."
        ::= { sehNovell 27 }
    
    nwAdvPserver OBJECT-TYPE
        SYNTAX  DisplayString (SIZE (1..48))
        ACCESS  read-write
        STATUS  mandatory
        DESCRIPTION
            "This parameter specifies the PSERVER
            name in remote printer mode."
        ::= { sehNovell 28 }
    
    nwLogPrinter OBJECT-TYPE
        SYNTAX  INTEGER { 
        lp1(1),
        lp2(2),
        lp3(3),
        lp4(4),
        lp5(5),
        lp6(6),
        lp7(7),
        lp8(8) 
        }
        ACCESS  read-write
        STATUS  mandatory
        DESCRIPTION
            "This parameter specifies the logical printer
            for PSERVER in remote printer mode."
        ::= { sehNovell 29 }
    
    nwSPXConnState OBJECT-TYPE
        SYNTAX  INTEGER { 
        close(0),
        preopen(1),
        open(2),
        listen(3)
        }
        ACCESS  read-only
        STATUS  mandatory
        DESCRIPTION
            "This parameter specifies the state of the SPX
            connection in remote printer mode."
        ::= { sehNovell 30 }
    
    nwNDSTree OBJECT-TYPE
        SYNTAX  DisplayString (SIZE (1..32))
        ACCESS  read-write
        STATUS  mandatory
        DESCRIPTION
            "This parameter specifies the optional NDS tree
            name. If a string is entered, the print server only
            sees the Novell servers within this tree."
        ::= { sehNovell 31 }
    
    nwIPX OBJECT-TYPE
        SYNTAX  INTEGER { disabled(0), enabled(1) }
        ACCESS  read-write
        STATUS  mandatory
        DESCRIPTION
            "This parameter enables or disables the IPX protocol."
        ::= { sehNovell 32 }
    
    nwMyNet OBJECT-TYPE
        SYNTAX  INTEGER
        ACCESS  read-only
        STATUS  mandatory
        DESCRIPTION
            "This parameter specifies the network number of the print server."
        ::= { sehNovell 33 }
    
    nwPureIp OBJECT-TYPE
        SYNTAX  INTEGER { off(0),udp(1), tcp(2) }
        ACCESS  read-write
        STATUS  mandatory
        DESCRIPTION
            "This parameter specifies the pure IP mode of the print server."
        ::= { sehNovell 34 }
    
    -- the sehApple group
    -- This group specifies Apple parameters of SEH print servers.
    
    appleTalk OBJECT-TYPE
        SYNTAX  INTEGER { disabled(0), enabled(1) }
        ACCESS  read-write
        STATUS  mandatory
        DESCRIPTION
            "This parameter enables or disables AppleTalk."
        ::= { sehApple 1 }
    
    appleName OBJECT-TYPE
        SYNTAX  DisplayString (SIZE (1..32))
        ACCESS  read-write
        STATUS  mandatory
        DESCRIPTION
            "This parameter specifies the Apple name."
        ::= { sehApple 2 }
    
    appleZone OBJECT-TYPE
        SYNTAX  DisplayString (SIZE (1..32))
        ACCESS  read-write
        STATUS  mandatory
        DESCRIPTION
            "This parameter specifies the zone."
        ::= { sehApple 3 }
    
    applePrinter OBJECT-TYPE
        SYNTAX  DisplayString (SIZE (1..32))
        ACCESS  read-write
        STATUS  mandatory
        DESCRIPTION
            "This parameter specifies the printer type. It must be exactly
            the same as requested by the AppleServer, otherwise
            the Print Server would be ignored."
        ::= { sehApple 4 }
    
    appleCurrentName OBJECT-TYPE
        SYNTAX  DisplayString (SIZE (1..32))
        ACCESS  read-only
        STATUS  mandatory
        DESCRIPTION
            "This parameter specifies the current Apple name."
        ::= { sehApple 5 }
    
    appleCurrentZone OBJECT-TYPE
        SYNTAX  DisplayString (SIZE (1..32))
        ACCESS  read-only
        STATUS  mandatory
        DESCRIPTION
            "This parameter specifies the current zone."
        ::= { sehApple 6 }
    
    appleEntity OBJECT-TYPE
        SYNTAX  DisplayString (SIZE (1..256))
        ACCESS  read-only
        STATUS  mandatory
        DESCRIPTION
            "This parameter specifies the entity types."
        ::= { sehApple 7 }
    
    appleNet OBJECT-TYPE
        SYNTAX  INTEGER
        ACCESS  read-only
        STATUS  mandatory
        DESCRIPTION
            "This parameter specifies the network number
            of the network where the print server belongs to."
        ::= { sehApple 8 }
    
    appleNode OBJECT-TYPE
        SYNTAX  INTEGER
        ACCESS  read-only
        STATUS  mandatory
        DESCRIPTION
            "This parameter specifies the node
            number of the print server."
        ::= { sehApple 9 }
    
    appleRouterNet OBJECT-TYPE
        SYNTAX  INTEGER
        ACCESS  read-only
        STATUS  mandatory
        DESCRIPTION
            "This parameter specifies the network
            number of the router."
        ::= { sehApple 10 }
    
    appleRouterNode OBJECT-TYPE
        SYNTAX  INTEGER
        ACCESS  read-only
        STATUS  mandatory
        DESCRIPTION
            "This parameter specifies the node
            number of the router."
        ::= { sehApple 11 }
    
    
    -- todo : only for box and pocket !
    appleBidirectional OBJECT-TYPE
        SYNTAX  INTEGER { disabled(0), enabled(1) }
        ACCESS  read-write
        STATUS  mandatory
        DESCRIPTION
            "Enable bidirectional communication with the printer."
        ::= { sehApple 12 }
    
    -- todo : only for box and pocket !
    appleBinary OBJECT-TYPE
        SYNTAX  INTEGER {
        ascii(0),
        bcp1(2),
        bcp2(4),
        tbcp(8)
        }
        ACCESS  read-write
        STATUS  mandatory
        DESCRIPTION
            "Enable different Modes for Adobe
            Communication protocol."
        ::= { sehApple 13 }
    
    appleRendezvous OBJECT-TYPE
        SYNTAX  INTEGER { disabled(0), enabled(1) }
        ACCESS  read-write
        STATUS  mandatory
        DESCRIPTION
            "This parameter enables or disables Apple Rendezvous."
        ::= { sehApple 14 }
    
    -- only for box and pocket (print server 3, version > 9.1.x) !
    applePortNumber OBJECT-TYPE
        SYNTAX  INTEGER
        ACCESS  read-only
        STATUS  mandatory
        DESCRIPTION
            "Number of Apple ports"
        ::= { sehApple 20 }
    
    -- only for box and pocket (print server 3, version > 9.1.x) !
    applePortTable OBJECT-TYPE
        SYNTAX  SEQUENCE OF ApplePortTableEntry
        ACCESS  not-accessible
        STATUS  mandatory
        DESCRIPTION
            "Table of AppleTalk ports."
        ::= { sehApple 21 }
    
    -- only for box and pocket (print server 3, version > 9.1.x) !
    applePortEntry OBJECT-TYPE
        SYNTAX  ApplePortTableEntry
        ACCESS  not-accessible
        STATUS  mandatory
        DESCRIPTION
            "Table of AppleTalk ports."
        INDEX   { applePortIndex }
        ::= { applePortTable 1 }
    
    -- only for box and pocket (print server 3, version > 9.1.x) !
    ApplePortTableEntry ::= SEQUENCE {
    applePortIndex                  INTEGER,
    applePortBidirectional          INTEGER,
    applePortPrinter                DisplayString,
    applePortEntity                 DisplayString,
    applePortBinaryEncoding         INTEGER,
    applePortCurrentName            DisplayString,
    appleRendezvousPortName         DisplayString,
    appleRendezvousCurrentPortName  DisplayString
    }
    
    -- only for box and pocket (print server 3, version > 9.1.x) !
    applePortIndex OBJECT-TYPE
        SYNTAX  INTEGER (0..256)
        ACCESS  read-only
        STATUS  mandatory
        DESCRIPTION
            "This object contains the index of the table being a unique
            value for each Apple port. Its value ranges between 1
            and the value of applePortNumber."
        ::= { applePortEntry 1 }
    
    -- only for box and pocket (print server 3, version > 9.1.x) !
    applePortBidirectional OBJECT-TYPE
        SYNTAX  INTEGER { disabled(0), enabled(1) }
        ACCESS  read-write
        STATUS  mandatory
        DESCRIPTION
            "Enable bidirectional communication with the printer."
        ::= { applePortEntry 2 }
    
    -- only for box and pocket (print server 3, version > 9.1.x) !
    applePortPrinter OBJECT-TYPE
        SYNTAX  DisplayString (SIZE (1..256))
        ACCESS  read-write
        STATUS  mandatory
        DESCRIPTION
            "This parameter specifies the printer type. It must be exactly
            the same as requested by the AppleServer, otherwise
            the Print Server would be ignored."
        ::= { applePortEntry 3 }
    
    -- only for box and pocket (print server 3, version > 9.1.x) !
    applePortEntity OBJECT-TYPE
        SYNTAX  DisplayString (SIZE (1..256))
        ACCESS  read-only
        STATUS  mandatory
        DESCRIPTION
            "This parameter specifies the entity types."
        ::= { applePortEntry 4 }
    
    -- only for box and pocket (print server 3, version > 9.1.x) !
    applePortBinaryEncoding OBJECT-TYPE
        SYNTAX  INTEGER {
        ascii(0),
        bcp1(2),
        bcp2(4),
        tbcp(8)
        }
        ACCESS  read-write
        STATUS  mandatory
        DESCRIPTION
            "Enable different Modes for Adobe
            Communication protocol."
        ::= { applePortEntry 5 }
    
    applePortCurrentName OBJECT-TYPE
        SYNTAX  DisplayString (SIZE (1..32))
        ACCESS  read-only
        STATUS  mandatory
        DESCRIPTION
            "This parameter specifies the current Apple name."
        ::= { applePortEntry 6 }
    
    appleRendezvousPortName OBJECT-TYPE
        SYNTAX  DisplayString (SIZE (1..63))
        ACCESS  read-write
        STATUS  mandatory
        DESCRIPTION
            "This parameter specifies the Rendezvous port name."
        ::= { applePortEntry 10 }
    
    appleRendezvousCurrentPortName OBJECT-TYPE
        SYNTAX  DisplayString (SIZE (1..63))
        ACCESS  read-only
        STATUS  mandatory
        DESCRIPTION
            "This parameter specifies the current Rendezvous port name."
        ::= { applePortEntry 11 }
    
    -- the sehSnmp group
    -- This group specifies the SNMP parameters of the SEH print servers.
    
    -- todo obsolete for PS3 > 9.1.x
    
    snmpIpAddr1 OBJECT-TYPE
        SYNTAX  IpAddress
        ACCESS  read-write
        STATUS  mandatory
        DESCRIPTION
            "This parameter specifies the first Trap IP address."
        ::= { sehSnmp 1 }
    
    snmpIpAddr2 OBJECT-TYPE
        SYNTAX  IpAddress
        ACCESS  read-write
        STATUS  mandatory
        DESCRIPTION
            "This parameter specifies the second Trap IP address."
        ::= { sehSnmp 2 }
    
    snmpIpxAddr1 OBJECT-TYPE
        SYNTAX  PhysAddress (SIZE (10))
        ACCESS  read-write
        STATUS  mandatory
        DESCRIPTION
            "This parameter specifies the first Trap IPX address."
        ::= { sehSnmp 3 }
    
    snmpIpxAddr2 OBJECT-TYPE
        SYNTAX  PhysAddress (SIZE (10))
        ACCESS  read-write
        STATUS  mandatory
        DESCRIPTION
            "This parameter specifies the second Trap IPX address."
        ::= { sehSnmp 4 }
    
    snmpTrapComm OBJECT-TYPE
        SYNTAX  DisplayString (SIZE (1..16))
        ACCESS  read-write
        STATUS  mandatory
        DESCRIPTION
            "This parameter specifies the trap community."
        ::= { sehSnmp 5 }
    
    snmpAutTrap OBJECT-TYPE
        SYNTAX  INTEGER { disabled(0), enabled(1) }
        ACCESS  read-write
        STATUS  mandatory
        DESCRIPTION
            "This parameter enables authentication traps."
        ::= { sehSnmp 6 }
    
    snmpPrtTrap OBJECT-TYPE
        SYNTAX  INTEGER { disabled(0), enabled(1) }
        ACCESS  read-write
        STATUS  mandatory
        DESCRIPTION
            "This parameter enables printer traps."
        ::= { sehSnmp 7 }
    
    snmpTrapNumber OBJECT-TYPE
        SYNTAX  INTEGER
        ACCESS  read-only
        STATUS  mandatory
        DESCRIPTION
            "This parameter specifies the number of SNMP Traps."
        ::= { sehSnmp 8 }
    
    snmpTrapTable OBJECT-TYPE
        SYNTAX  SEQUENCE OF SnmpTrapEntry
        ACCESS  not-accessible
        STATUS  mandatory
        DESCRIPTION
            "This object specifies a table containing a list
            of SNMP Trap entries. The number of
            entries is given by the value of snmpTrapNumber."
        ::= { sehSnmp 9 }

    snmpTrapEntry OBJECT-TYPE
        SYNTAX  SnmpTrapEntry
        ACCESS  not-accessible
        STATUS  mandatory
        DESCRIPTION
            "Entry in SNMP trap table."
        INDEX   { snmpTrapIndex }
        ::= { snmpTrapTable 1 }
    
    SnmpTrapEntry ::= SEQUENCE {
    snmpTrapIndex           INTEGER,
    snmpTrapIpAddress       IpAddress,
    snmpTrapIpxAddress      PhysAddress,
    snmpTrapAuthentication  INTEGER,
    snmpTrapPrinter1        INTEGER,
    snmpTrapMask1           INTEGER,
    snmpTrapCommunity       DisplayString
    }
    
    snmpTrapIndex OBJECT-TYPE
        SYNTAX  INTEGER (0..256)
        ACCESS  read-only
        STATUS  mandatory
        DESCRIPTION
            "This object contains the index of the table being a unique
            value for each SNMP Trap. Its value ranges between 1
            and the value of snmpTrapNumber."
        ::= { snmpTrapEntry 1 }
    
    snmpTrapIpAddress OBJECT-TYPE
        SYNTAX  IpAddress
        ACCESS  read-write
        STATUS  mandatory
        DESCRIPTION
            "This parameter specifies the Trap IP address."
        ::= { snmpTrapEntry 2 }
    
    snmpTrapIpxAddress OBJECT-TYPE
        SYNTAX  PhysAddress (SIZE (10))
        ACCESS  read-write
        STATUS  mandatory
        DESCRIPTION
            "This parameter specifies the Trap IPX address."
        ::= { snmpTrapEntry 3 }
    
    snmpTrapAuthentication OBJECT-TYPE
        SYNTAX  INTEGER { disabled(0), enabled(1) }
        ACCESS  read-write
        STATUS  mandatory
        DESCRIPTION
            "This parameter enables authentication traps."
        ::= { snmpTrapEntry 4 }
    
    snmpTrapPrinter1 OBJECT-TYPE
        SYNTAX  INTEGER { disabled(0), enabled(1) }
        ACCESS  read-write
        STATUS  mandatory
        DESCRIPTION
            "This parameter enables printer traps."
        ::= { snmpTrapEntry 5 }
    
    snmpTrapMask1 OBJECT-TYPE
        SYNTAX  INTEGER
        ACCESS  read-write
        STATUS  mandatory
        DESCRIPTION
            "This parameter specifies the printer error bits.
            BITS       MEANING
            2^0        paper jam
            2^1        paper empty
            2^2        toner low
            2^3        cover open
            2^4        toner empty
            2^5        cassette not ready
            2^6        warming up
            2^7        offline
            2^8        engine error
            2^9        noselect
            2^14       service call
            2^15       misc error"
        ::= { snmpTrapEntry 6 }
    
    snmpTrapCommunity OBJECT-TYPE
        SYNTAX  DisplayString (SIZE (1..16))
        ACCESS  read-write
        STATUS  mandatory
        DESCRIPTION
            "This parameter specifies the trap community."
        ::= { snmpTrapEntry 7 }
    
    snmpCommunity OBJECT-TYPE
        SYNTAX  DisplayString (SIZE (1..16))
        ACCESS  read-write
        STATUS  mandatory
        DESCRIPTION
            "This parameter specifies the SNMP version 1 community."
        ::= { sehSnmp 20 }

    snmpV1 OBJECT-TYPE
        SYNTAX  INTEGER { disabled(0), enabled(1) }
        ACCESS  read-write
        STATUS  mandatory
        DESCRIPTION
            "This parameter enables the SNMP Version 1 support."
        ::= { sehSnmp 21 }

    snmpV1AccMode OBJECT-TYPE
        SYNTAX  INTEGER { readonly(0), readwrite(1) }
        ACCESS  read-write
        STATUS  mandatory
        DESCRIPTION
            "This parameter specifies the SNMP Version 1 access mode."
        ::= { sehSnmp 22 }


    snmpV3 OBJECT-TYPE
        SYNTAX  INTEGER { disabled(0), enabled(1) }
        ACCESS  read-write
        STATUS  mandatory
        DESCRIPTION
            "This parameter enables the SNMP Version 1 support."
        ::= { sehSnmp 31 }

    -- the sehActions group
    -- This group specifies actions available to SEH print servers.
    
    actAction OBJECT-TYPE
        SYNTAX  INTEGER {
        actionCompleted(0),
        restoreFactorySettings(9),
        restart(10),
        printStatuspageOnChannel1(11),
        printStatuspageOnChannel2(12),
        printStatuspageOnChannel3(13),
        printStatuspageOnChannel4(14),
        mail(64),
        tpReconnect(65),
        actionInprogress(254),
        actionError(255)
        }
        ACCESS  read-write
        STATUS  mandatory
        DESCRIPTION
            "This parameter specifies the actions available for the print server.
            The value restoreFactorySettings initiates the resetting of all
            parameters followed by a restart of the print server.
            The value restart initiates a restart of the print server.
            The value printStatusPage prints out a status page.
            The other values are return codes only."
        ::= { sehActions 1  }
    
    
    actUpdate OBJECT-TYPE
        SYNTAX  INTEGER { disabled(0), enabled(1) }
        ACCESS  read-write
        STATUS  mandatory
        DESCRIPTION
            "todo"
        ::= { sehActions 10 }
    
    actUpdateUrl OBJECT-TYPE
        SYNTAX  DisplayString (SIZE (1..255))
        ACCESS  read-write
        STATUS  mandatory
        DESCRIPTION
            "todo"
        ::= { sehActions 11 }
    
    actUpdateProxy OBJECT-TYPE
        SYNTAX  INTEGER { disabled(0), enabled(1) }
        ACCESS  read-write
        STATUS  mandatory
        DESCRIPTION
            "todo"
        ::= { sehActions 12 }
    
    actUpdateProxyName OBJECT-TYPE
        SYNTAX  DisplayString (SIZE (1..255))
        ACCESS  read-write
        STATUS  mandatory
        DESCRIPTION
            "todo"
        ::= { sehActions 13 }

    -- 
    -- seh printer firmware update stuff
    --

    actPrtUpdate OBJECT-TYPE
        SYNTAX  INTEGER { disabled(0), enabled(1) }
        ACCESS  read-write
        STATUS  mandatory
        DESCRIPTION
            "todo"
        ::= { sehActions 14 }
    
    actPrtUpdateUrl OBJECT-TYPE
        SYNTAX  DisplayString (SIZE (1..255))
        ACCESS  read-write
        STATUS  mandatory
        DESCRIPTION
            "todo"
        ::= { sehActions 15 }
    
    actPrtUpdateUsr OBJECT-TYPE
        SYNTAX  DisplayString (SIZE (1..64))
        ACCESS  read-write
        STATUS  mandatory
        DESCRIPTION
            "todo"
        ::= { sehActions 16 }
    
    actPrtUpdatePwd OBJECT-TYPE
        SYNTAX  DisplayString (SIZE (1..64))
        ACCESS  read-write
        STATUS  mandatory
        DESCRIPTION
            "todo"
        ::= { sehActions 17 }
    
    actPrtUpdateProxy OBJECT-TYPE
        SYNTAX  INTEGER { disabled(0), enabled(1) }
        ACCESS  read-write
        STATUS  mandatory
        DESCRIPTION
            "todo"
        ::= { sehActions 18 }
    
    actPrtUpdateProxyName OBJECT-TYPE
        SYNTAX  DisplayString (SIZE (1..255))
        ACCESS  read-write
        STATUS  mandatory
        DESCRIPTION
            "todo"
        ::= { sehActions 19 }
    
    -- the sehTokenRing group
    -- This group specifies the TokenRing parameters of SEH print servers.
    
    trEarlyTokRel OBJECT-TYPE
        SYNTAX  INTEGER { disabled(0), enabled(1) }
        ACCESS  read-write
        STATUS  mandatory
        DESCRIPTION
            "This parameter enables or disables the
            early token release in 16 Mbit/s networks."
        ::= { sehTokenRing 1 }
    
    trSourceRouting OBJECT-TYPE
        SYNTAX  INTEGER { disabled(0), enabled(1) }
        ACCESS  read-write
        STATUS  mandatory
        DESCRIPTION
            "This parameter enables or disables the source routing."
        ::= { sehTokenRing 2 }
    
    trPhysAddr OBJECT-TYPE
        SYNTAX  PhysAddress (SIZE (6))
        ACCESS  read-write
        STATUS  mandatory
        DESCRIPTION
            "This parameter specifies the locally
            administered address."
        ::= { sehTokenRing 3 }
    
    trRingSpeed OBJECT-TYPE
        SYNTAX  INTEGER { unknown(0),
        speed4Mbps(4),
        speed16Mbps(16)
        }
        ACCESS  read-only
        STATUS  mandatory
        DESCRIPTION
            "This parameter specifies the ring speed."
        ::= { sehTokenRing 4 }
    
    -- the sehWireless group
    -- This group specifies the Wireless and EAP authentication parameters 
    -- of SEH print servers.
    
    wlanMode OBJECT-TYPE
        SYNTAX  INTEGER { infrastructure(1), auto(2), ad-hoc(3), softAP(4) }
        ACCESS  read-write
        STATUS  mandatory
        DESCRIPTION
            "This parameter specifies the wireless mode."
        ::= { sehWireless 1 }
    
    wlanChannel OBJECT-TYPE
        SYNTAX  INTEGER
        ACCESS  read-write
        STATUS  mandatory
        DESCRIPTION
            "This parameter specifies the channel when in ad-hoc mode."
        ::= { sehWireless 2 }
    
    wlanNetworkName OBJECT-TYPE
        SYNTAX  DisplayString (SIZE (1..32))
        ACCESS  read-write
        STATUS  mandatory
        DESCRIPTION
            "This parameter specifies the name of the network."
        ::= { sehWireless 3 }
    
    wlanEncrypt OBJECT-TYPE
        SYNTAX  INTEGER { 
        none(0), 
        wep(1), 
        wep-sharedkey(2), 
        wpa-tkip(3), 
        wpa-aes(4), 
        wpa2-tkip(5), 
        wpa2-aes(6), 
        wpa-aes-tkip(7), 
        wpa2-aes-tkip(8), 
        wpa-auto(9) 
        }
        ACCESS  read-write
        STATUS  mandatory
        DESCRIPTION
            "This parameter specifies the encryption algorithm for wireless. 
            Default is NONE.
           (0 = None, 1 = WEP, 2 = WEP Shared Key, 3 = WPA-TKIP,
            4 = WPA-AES, 5 = WPA2-TKIP, 6 = WPA2-AES, 7 = WPA-AES-TKIP,
            8 = WPA2-AES-TKIP, 9 = WPA-AUTO)"
        ::= { sehWireless 5 }
    
    wlanWepKey1 OBJECT-TYPE
        SYNTAX  DisplayString (SIZE (0..28))
        ACCESS  read-write
        STATUS  mandatory
        DESCRIPTION
            "This parameter specifies the 1st WEP-key."
        ::= { sehWireless 6 }
    
    wlanDistance OBJECT-TYPE
        SYNTAX  INTEGER { large(1), medium(2), small(3) }
        ACCESS  read-write
        STATUS  mandatory
        DESCRIPTION
            "This parameter specifies the distance between APs."
        ::= { sehWireless 7 }
    
    wlanLevel OBJECT-TYPE
        SYNTAX  INTEGER
        ACCESS  read-only
        STATUS  mandatory
        DESCRIPTION
            "This parameter shows the level."
        ::= { sehWireless 8 }
    
    wlanSpeed OBJECT-TYPE
        SYNTAX  DisplayString (SIZE (1..4))
        ACCESS  read-only
        STATUS  mandatory
        DESCRIPTION
            "This parameter shows the current transmission speed."
        ::= { sehWireless 9 }
    
    wlanConnectionStatus OBJECT-TYPE
        SYNTAX  INTEGER { 
        disabled(1), 
        searching(2), 
        ad-hoc(3), 
        infrastructure(4), 
        out-of-range(5), 
        softAP(6)
        }
        ACCESS  read-only
        STATUS  mandatory
        DESCRIPTION
            "This parameter shows the connection status."
        ::= { sehWireless 10 }
    
    wlanManufacturer OBJECT-TYPE
        SYNTAX  DisplayString (SIZE (1..64))
        ACCESS  read-only
        STATUS  mandatory
        DESCRIPTION
            "This parameter shows the manufacturer of the wireless card."
        ::= { sehWireless 11 }
    
    wlanCurrentName OBJECT-TYPE
        SYNTAX  DisplayString (SIZE (1..32))
        ACCESS  read-only
        STATUS  mandatory
        DESCRIPTION
            "This parameter shows the current network-name of the wireless card."
        ::= { sehWireless 12 }
    
    wlanPcmciaSerial OBJECT-TYPE
        SYNTAX  DisplayString (SIZE (1..12))
        ACCESS  read-only
        STATUS  mandatory
        DESCRIPTION
            "This parameter shows the serial-no of the wireless card."
        ::= { sehWireless 13 }
    
    wlanKeyId OBJECT-TYPE
        SYNTAX  INTEGER
        ACCESS  read-write
        STATUS  mandatory
        DESCRIPTION
            "This parameter specifies the WepKey index used for transmission. (1..4)"
        ::= { sehWireless 14 }
    
    wlanWepKey2 OBJECT-TYPE
        SYNTAX  DisplayString (SIZE (0..28))
        ACCESS  read-write
        STATUS  mandatory
        DESCRIPTION
            "This parameter specifies the 2nd WEP-key."
        ::= { sehWireless 15 }
    
    wlanWepKey3 OBJECT-TYPE
        SYNTAX  DisplayString (SIZE (0..28))
        ACCESS  read-write
        STATUS  mandatory
        DESCRIPTION
            "This parameter specifies the 3rd WEP-key."
        ::= { sehWireless 16 }
    
    wlanWepKey4 OBJECT-TYPE
        SYNTAX  DisplayString (SIZE (0..28))
        ACCESS  read-write
        STATUS  mandatory
        DESCRIPTION
            "This parameter specifies the 4th WEP-key."
        ::= { sehWireless 17 }
    
    eapAuthType OBJECT-TYPE
        SYNTAX  INTEGER { 
        openSystem(1), 
        sharedSystem(2), 
        radiusMD5(3), 
        radiusTLS(4),
        ttl(5),
        peap(6),
        eapfast(7)
        }
        ACCESS  read-write
        STATUS  mandatory
        DESCRIPTION
            "This parameter specifies the authentication algorithm. 
            Default is open-system.
            For wired print server the syntax is different.
            (1 = no authentication, 2 = unsupported, 3 = MD5, 4 = TLS)"
        ::= { sehWireless 18 }
    
    eapAuthName OBJECT-TYPE
        SYNTAX  DisplayString (SIZE (0..64))
        ACCESS  read-write
        STATUS  mandatory
        DESCRIPTION
            "This parameter specifies the user name for EAP authentication."
        ::= { sehWireless 19 }
    
    eapAuthPwd OBJECT-TYPE
        SYNTAX  DisplayString (SIZE (0..64))
        ACCESS  read-write
        STATUS  mandatory
        DESCRIPTION
            "This parameter specifies the password for EAP authentication."
        ::= { sehWireless 20 }
    
    wlanPSK OBJECT-TYPE
        SYNTAX  DisplayString (SIZE (8..63))
        ACCESS  read-write
        STATUS  mandatory
        DESCRIPTION
            "This parameter specifies the Pre Shared Key for Wi-Fi Protected Access (WPA)."
        ::= { sehWireless 21 }
    
    wlanRoaming OBJECT-TYPE
        SYNTAX  INTEGER { disabled(0), enabled(1) }
        ACCESS  read-write
        STATUS  mandatory
        DESCRIPTION
            "Roaming between APs"
        ::= { sehWireless 22 }

    eapAuthExtern OBJECT-TYPE
        SYNTAX  INTEGER { 
        none(0),
        peaplabel0(1),
        peaplabel1(2),
        peapversion0(3),
        peapversion1(4),
        eapfastprovisioning(5)
        }
        ACCESS  read-write
        STATUS  mandatory
        DESCRIPTION
            "Authentication Types for the outer system config."
        ::= { sehWireless 23 }

    eapAuthIntern OBJECT-TYPE
        SYNTAX  INTEGER { 
        none(0),
        mschap(1),
        mschapv2(2),
        pap(3),
        chap(4),
        eapmd5(5),
        eapmschap(6),
        eapmschapv2(7),
        eaptls(8)
        }
        ACCESS  read-write
        STATUS  mandatory
        DESCRIPTION
            "Authentication Types for the inner system config."
        ::= { sehWireless 24 }

    eapAuthAnonymousName OBJECT-TYPE
        SYNTAX  DisplayString (SIZE (0..64))
        ACCESS  read-write
        STATUS  mandatory
        DESCRIPTION
            "Anonymous Name for the unencrypted Part of EAP."
        ::= { sehWireless 25 }
    
    eapAuthSupplicantAddOn OBJECT-TYPE
        SYNTAX  DisplayString (SIZE (0..255))
        ACCESS  read-write
        STATUS  mandatory
        DESCRIPTION
            "This parameter specifies extra Prameters for Authentication."
        ::= { sehWireless 26 }

    wlandBm2Roam OBJECT-TYPE
        SYNTAX  INTEGER
        ACCESS  read-write
        STATUS  mandatory
        DESCRIPTION
            "This parameter specifies the Level in -dBm to start Roaming."
        ::= { sehWireless 27 }
    
    wlandWps OBJECT-TYPE
        SYNTAX  INTEGER { disabled(0), enabled(1) }
        ACCESS  read-write
        STATUS  mandatory
        DESCRIPTION
            "This parameter specifies if WPS is enabled"
        ::= { sehWireless 28 }

    wlen OBJECT-TYPE
        SYNTAX  INTEGER { disabled(0), enabled(1) }
        ACCESS  read-write
        STATUS  mandatory
        DESCRIPTION
            "Enable or disable wireless networking"
        ::= { sehWireless 30 }
    
     wlan OBJECT-TYPE
        SYNTAX  INTEGER { disabled(0), enabled(1) }
        ACCESS  read-write
        STATUS  mandatory
        DESCRIPTION
            "Enables wireless functionality on hybrid devices."
        ::= { sehWireless 40 }

     onTheAir OBJECT-TYPE
        SYNTAX  INTEGER { wired(0), wireless(1) }
        ACCESS  read-only
        STATUS  mandatory
        DESCRIPTION
            "Working state for hybrid devices."
        ::= { sehWireless 41 }

    -- the sehWin group
    -- This group specifies the SMB parameters of SEH print servers.
    
    winSmb OBJECT-TYPE
        SYNTAX  INTEGER { disabled(0), enabled(1) }
        ACCESS  read-write
        STATUS  mandatory
        DESCRIPTION
            "todo"
        ::= { sehWin 1 }
    
    winNetbiosName OBJECT-TYPE
        SYNTAX  DisplayString (SIZE (1..15))
        ACCESS  read-write
        STATUS  mandatory
        DESCRIPTION
            "todo"
        ::= { sehWin 20 }
    
    winNetbiosDomain OBJECT-TYPE
        SYNTAX  DisplayString (SIZE (1..15))
        ACCESS  read-write
        STATUS  mandatory
        DESCRIPTION
            "todo"
        ::= { sehWin 21 }
    
    winNetbiosRefresh            OBJECT-TYPE
        SYNTAX  INTEGER
        ACCESS  read-write
        STATUS  mandatory
        DESCRIPTION
            "todo"
        ::= { sehWin 22}
    
    
    winWinsReg OBJECT-TYPE
        SYNTAX  INTEGER { disabled(0), enabled(1) }
        ACCESS  read-write
        STATUS  mandatory
        DESCRIPTION
            "This parameter enables the WINS registration via DHCP."
        ::= { sehWin 40 }
    
    winWinsDHCP OBJECT-TYPE
        SYNTAX  INTEGER { disabled(0), enabled(1) }
        ACCESS  read-write
        STATUS  mandatory
        DESCRIPTION
            "This parameter enables the transfer of the IP address
            of the WINS server from the DHCP server."
        ::= { sehWin 41 }
    
    winWinsPrimarySrv OBJECT-TYPE
        SYNTAX  DisplayString (SIZE (1..255))
        ACCESS  read-write
        STATUS  mandatory
        DESCRIPTION
            "This parameter specifies the IP address or DNS Name of the primary WINS server."
        ::= { sehWin 42}
    
    winWinsSecondarySrv OBJECT-TYPE
        SYNTAX  DisplayString (SIZE (1..255))
        ACCESS  read-write
        STATUS  mandatory
        DESCRIPTION
            "This parameter specifies the IP address or DNS Name of the secondary WINS server."
        ::= { sehWin 43}
    
    -- the sehTime group
    -- This group specifies the SNTP parameters of SEH print servers.
    
    timeSntp OBJECT-TYPE
        SYNTAX  INTEGER { disabled(0), enabled(1) }
        ACCESS  read-write
        STATUS  mandatory
        DESCRIPTION
            "This parameter enables or disables the simple network time protocol."
        ::= { sehTime 1 }
    
    timeServer OBJECT-TYPE
        SYNTAX  DisplayString (SIZE (1..255))
        ACCESS  read-write
        STATUS  mandatory
        DESCRIPTION
            "This parameter specifies the IP address or DNS Name of the SNTP server."
        ::= { sehTime 2 }
    
    timeZoneOffset  OBJECT-TYPE
        SYNTAX  INTEGER
        ACCESS  read-write
        STATUS  mandatory
        DESCRIPTION
            "This parameter specifies the time zone offset to UTC."
        ::= { sehTime 3 }
    
    timeDate OBJECT-TYPE
        SYNTAX  DisplayString (SIZE (0..64))
        ACCESS  read-only
        STATUS  mandatory
        DESCRIPTION
            "This parameter shows the actual date and time."
        ::= { sehTime 4 }
    
    timeZoneNameAndRule OBJECT-TYPE
        SYNTAX  DisplayString (SIZE (0..64))
        ACCESS  read-write
        STATUS  mandatory
        DESCRIPTION
            "This parameter specifies the name of the time zone
            and the rule for daylight saving.
            example: CET/CEST (EU)"
        ::= { sehTime 5 }
    
    
    -- the sehPrintjob group
    -- This group describes the print job history table of SEH print servers.
    
    pjobCount OBJECT-TYPE
        SYNTAX  INTEGER
        ACCESS  read-only
        STATUS  mandatory
        DESCRIPTION
            "This parameter specifies the number of available jobs
            in the print job history table."
        ::= { sehPrintjob 1 }
    
    pjobTable OBJECT-TYPE
        SYNTAX  SEQUENCE OF PjobEntry
        ACCESS  not-accessible
        STATUS  mandatory
        DESCRIPTION
            "This object specifies a table containing a list of jobs
            in the print job history table. The number of
            entries is given by the value of pjobCount."
        ::= { sehPrintjob 2 }
    
    pjobEntry OBJECT-TYPE
        SYNTAX  PjobEntry
        ACCESS  not-accessible
        STATUS  mandatory
        DESCRIPTION
            "Entry in the job history."
        INDEX   { pjobIndex }
        ::= { pjobTable 1 }
    
    PjobEntry ::= SEQUENCE {
    pjobIndex           INTEGER,
    pjobStatus          INTEGER,
    pjobProtocol        INTEGER,
    pjobName            DisplayString,
    pjobSender          DisplayString,
    pjobSize            INTEGER,
    pjobCreationTime    DisplayString,
    pjobDuration        INTEGER,
    pjobPport           INTEGER,
    pjobPages           INTEGER,
    pjobSizeType        INTEGER 
    }
    
    pjobIndex OBJECT-TYPE
        SYNTAX  INTEGER (0..256)
        ACCESS  read-only
        STATUS  mandatory
        DESCRIPTION
            "This object contains the index of the table being a unique
            value for each job."
        ::= { pjobEntry 1 }
    
    pjobStatus OBJECT-TYPE
        SYNTAX  INTEGER {
        initialized(1),
        pending(3),
        held(4),
        processing(5),
        stopped(6),
        canceled(7),
        aborted(8),
        completed(9)
        }
        ACCESS  read-only
        STATUS  mandatory
        DESCRIPTION
            "This parameter describes the status of the print job."
        ::= { pjobEntry 2 }
    
    pjobProtocol OBJECT-TYPE
        SYNTAX  INTEGER {
        ipp(0),
        tcp(1),
        lpr(2),
        nds(3),
        bindery(4),
        rnprinter(5),
        atalk(6),
        ftp(7),
        smb(8),
        http(9),
        thinprint(10),
        email(11),
        thinprintcs(12),
        unknown(13)
        }
        ACCESS  read-only
        STATUS  mandatory
        DESCRIPTION
            "This parameter describes the protocol of the print job."
        ::= { pjobEntry 3 }
    
    pjobName OBJECT-TYPE
        SYNTAX  DisplayString (SIZE (0..128))
        ACCESS  read-only
        STATUS  mandatory
        DESCRIPTION
            "This parameter describes the name of the print job."
        ::= { pjobEntry 4 }
    
    pjobSender OBJECT-TYPE
        SYNTAX  DisplayString (SIZE (0..128))
        ACCESS  read-only
        STATUS  mandatory
        DESCRIPTION
            "This parameter describes the sender of the print job."
        ::= { pjobEntry 5 }
    
    pjobSize OBJECT-TYPE
        SYNTAX  INTEGER
        ACCESS  read-only
        STATUS  mandatory
        DESCRIPTION
            "This parameter describes the size (in Bytes) of the print job.
            For jobs larger 2GB, the size is in KByte and the pJobSizeType is kbytes."
        ::= { pjobEntry 6 }
    
    pjobCreationTime OBJECT-TYPE
        SYNTAX  DisplayString (SIZE (0..128))
        ACCESS  read-only
        STATUS  mandatory
        DESCRIPTION
            "This parameter describes the creation time of the print job."
        ::= { pjobEntry 7 }
    
    pjobDuration OBJECT-TYPE
        SYNTAX  INTEGER
        ACCESS  read-only
        STATUS  mandatory
        DESCRIPTION
            "This parameter describes the duration (in seconds) of the print job."
        ::= { pjobEntry 8 }
    
    pjobPport OBJECT-TYPE
        SYNTAX  INTEGER
        ACCESS  read-only
        STATUS  mandatory
        DESCRIPTION
            "This parameter describes the printer port of the print job."
        ::= { pjobEntry 9 }
    
    pjobPages OBJECT-TYPE
        SYNTAX  INTEGER
        ACCESS  read-only
        STATUS  mandatory
        DESCRIPTION
            "This parameter describes the number of pages of the print job."
        ::= { pjobEntry 10 }
    
    pjobSizeType OBJECT-TYPE
        SYNTAX  INTEGER {
        bytes(0),
        kbytes(1)
        }
        ACCESS  read-only
        STATUS  mandatory
        DESCRIPTION
            "This parameter describes the job size."
        ::= { pjobEntry 11 }
    
    -- todo begin nur für PS3 mit 9.1.?
    
    nfSlotNumber OBJECT-TYPE
        SYNTAX  INTEGER
        ACCESS  read-only
        STATUS  mandatory
        DESCRIPTION
            "This parameter specifies the number of notification slots."
        ::= { sehNotification 1 }
    
    NFSlotTableEntry ::= SEQUENCE {
    nfSlotIndex             INTEGER,
    nfMailNotification      INTEGER,
    nfMailAddress           DisplayString,
    nfMailServer            DisplayString,
    nfTrapIpAddress         IpAddress,
    nfTrapIpxAddress        PhysAddress,
    nfTrapAuthentication    INTEGER,
    nfTrapPrinter           INTEGER,
    nfTrapCommunity         DisplayString,
    nfAccJobHist            INTEGER,
    nfAccJobHistTime        INTEGER,
    nfAccJobHistCntr        INTEGER
    }
    
    nfSlotTable OBJECT-TYPE
        SYNTAX  SEQUENCE OF NFSlotTableEntry
        ACCESS  not-accessible
        STATUS  mandatory
        DESCRIPTION
            "This object specifies a table containing a list
            of notification slot entries. The number of
            entries is given by the value of nfSlotNumber."
        ::= { sehNotification 2 }
    
    nfSlotEntry OBJECT-TYPE
        SYNTAX  NFSlotTableEntry
        ACCESS  not-accessible
        STATUS  mandatory
        DESCRIPTION
            " "
        INDEX   { nfSlotIndex }
        ::= { nfSlotTable 1 }
    
    nfSlotIndex OBJECT-TYPE
        SYNTAX  INTEGER (0..256)
        ACCESS  read-only
        STATUS  mandatory
        DESCRIPTION
            "This object contains the index of the table being a unique
            value for each notification slot. Its value ranges between 1
            and the value of nfSlotNumber."
        ::= { nfSlotEntry 1 }
    
    nfMailNotification OBJECT-TYPE
        SYNTAX  INTEGER { disabled(0), enabled(1) }
        ACCESS  read-write
        STATUS  mandatory
        DESCRIPTION
            "This parameter enables or disables the e-mail
            notification."
        ::= { nfSlotEntry 2 }
    
    nfMailAddress OBJECT-TYPE
        SYNTAX  DisplayString (SIZE (0..255))
        ACCESS  read-write
        STATUS  mandatory
        DESCRIPTION
            "This parameter specifies the IP address of the e-mail recipient 1."
        ::= { nfSlotEntry 3 }
    
    nfMailServer OBJECT-TYPE
        SYNTAX  DisplayString (SIZE (0..255))
        ACCESS  read-write
        STATUS  mandatory
        DESCRIPTION
            "This parameter specifies the mail server for the e-mail
            notification"
        ::= { nfSlotEntry 4 }
    
    nfTrapIpAddress OBJECT-TYPE
        SYNTAX  IpAddress
        ACCESS  read-write
        STATUS  mandatory
        DESCRIPTION
            "This parameter specifies the Trap IP address."
        ::= { nfSlotEntry 10 }
    
    nfTrapIpxAddress OBJECT-TYPE
        SYNTAX  PhysAddress (SIZE (10))
        ACCESS  read-write
        STATUS  mandatory
        DESCRIPTION
            "This parameter specifies the Trap IPX address."
        ::= { nfSlotEntry 11 }
    
    nfTrapAuthentication OBJECT-TYPE
        SYNTAX  INTEGER { disabled(0), enabled(1) }
        ACCESS  read-write
        STATUS  mandatory
        DESCRIPTION
            "This parameter enables authentication traps."
        ::= { nfSlotEntry 12 }
    
    nfTrapPrinter OBJECT-TYPE
        SYNTAX  INTEGER { disabled(0), enabled(1) }
        ACCESS  read-write
        STATUS  mandatory
        DESCRIPTION
            "This parameter enables printer traps."
        ::= { nfSlotEntry 13 }
    
    
    nfTrapCommunity OBJECT-TYPE
        SYNTAX  DisplayString (SIZE (1..16))
        ACCESS  read-write
        STATUS  mandatory
        DESCRIPTION
            "This parameter specifies the trap community."
        ::= { nfSlotEntry 14 }
    
    nfAccJobHist OBJECT-TYPE
        SYNTAX  INTEGER { disabled(0), enabled(1) }
        ACCESS  read-write
        STATUS  mandatory
        DESCRIPTION
            "This parameter enables printer mail notification for the 
            job history to the mail recipient."
        ::= { nfSlotEntry 15 }
    
    nfAccJobHistTime OBJECT-TYPE
        SYNTAX  INTEGER
        ACCESS  read-write
        STATUS  mandatory
        DESCRIPTION
            "This parameter set the time limit in hours to 
            send the job history to the mail recipient."
        ::= { nfSlotEntry 16 }
    
    nfAccJobHistCntr OBJECT-TYPE
        SYNTAX  INTEGER
        ACCESS  read-write
        STATUS  mandatory
        DESCRIPTION
            "This parameter set the job limit to 
            send the job history to the mail recipient.
            Range is 1 to 60"
        ::= { nfSlotEntry 17 }
    
    nfPortNumber OBJECT-TYPE
        SYNTAX  INTEGER
        ACCESS  read-only
        STATUS  mandatory
        DESCRIPTION
            "This parameter specifies the number of notification ports."
        ::= { sehNotification 5 }
    
    NFPortTableEntry ::= SEQUENCE {
    nfPortIndex             INTEGER,
    nfPortMailMask1         INTEGER,
    nfPortMailMask2         INTEGER,
    nfPortTrapMask1         INTEGER,
    nfPortTrapMask2         INTEGER,
    nfPortAccPageCntr1      INTEGER,
    nfPortAccPageCntr2      INTEGER,
    nfPortAccPageCntrTime1  INTEGER,
    nfPortAccPageCntrTime2  INTEGER,
    nfPortAccPageCntrCntr1  INTEGER,
    nfPortAccPageCntrCntr2  INTEGER,
    nfPortMailList1         DisplayString,
    nfPortMailList2         DisplayString,
    nfPortTrapList1         DisplayString,
    nfPortTrapList2         DisplayString,
    nfPortAccPageCntrIndex1 INTEGER,
    nfPortAccPageCntrIndex2 INTEGER
    }
    
    nfPortTable OBJECT-TYPE
        SYNTAX  SEQUENCE OF NFPortTableEntry
        ACCESS  not-accessible
        STATUS  mandatory
        DESCRIPTION
            "This object specifies a table containing a list
            of notification slot entries. The number of
            entries is given by the value of nfPortNumber."
        ::= { sehNotification 6 }
    
    nfPortEntry OBJECT-TYPE
        SYNTAX  NFPortTableEntry
        ACCESS  not-accessible
        STATUS  mandatory
        DESCRIPTION
            "Entry in the NFPort table."
        INDEX   { nfPortIndex }
        ::= { nfPortTable 1 }
    
    nfPortIndex OBJECT-TYPE
        SYNTAX  INTEGER (0..256)
        ACCESS  read-only
        STATUS  mandatory
        DESCRIPTION
            "This object contains the index of the table being a unique
            value for each physical port. Its value ranges between 1
            and the value of nfPortNumber."
        ::= { nfPortEntry 1 }
    
    nfPortMailMask1 OBJECT-TYPE
        SYNTAX  INTEGER
        ACCESS  read-write
        STATUS  mandatory
        DESCRIPTION
            "This parameter specifies the mail mask bits of the e-mail
            notification for recipient 1.
            BITS       MEANING
            2^0        paper jam
            2^1        paper empty
            2^2        toner low
            2^3        cover open
            2^4        toner empty
            2^5        cassette not ready
            2^6        warming up
            2^7        offline
            2^8        engine error
            2^9        noselect
            2^10       paper low
            2^14       service call
            2^15       misc error"
        ::= { nfPortEntry 2 }
    
    nfPortMailMask2 OBJECT-TYPE
        SYNTAX  INTEGER
        ACCESS  read-write
        STATUS  mandatory
        DESCRIPTION
            "This parameter specifies the mail mask bits of the e-mail
            notification for recipient 2.
            BITS       MEANING
            2^0        paper jam
            2^1        paper empty
            2^2        toner low
            2^3        cover open
            2^4        toner empty
            2^5        cassette not ready
            2^6        warming up
            2^7        offline
            2^8        engine error
            2^9        noselect
            2^10       paper low
            2^14       service call
            2^15       misc error"
        ::= { nfPortEntry 3 }
    
    nfPortTrapMask1 OBJECT-TYPE
        SYNTAX  INTEGER
        ACCESS  read-write
        STATUS  mandatory
        DESCRIPTION
            "This parameter specifies the printer error bits.
            BITS       MEANING
            2^0        paper jam
            2^1        paper empty
            2^2        toner low
            2^3        cover open
            2^4        toner empty
            2^5        cassette not ready
            2^6        warming up
            2^7        offline
            2^8        engine error
            2^9        noselect
            2^14       service call
            2^15       misc error"
        ::= { nfPortEntry 20 }
    
    nfPortTrapMask2 OBJECT-TYPE
        SYNTAX  INTEGER
        ACCESS  read-write
        STATUS  mandatory
        DESCRIPTION
            "This parameter specifies the printer error bits.
            BITS       MEANING
            2^0        paper jam
            2^1        paper empty
            2^2        toner low
            2^3        cover open
            2^4        toner empty
            2^5        cassette not ready
            2^6        warming up
            2^7        offline
            2^8        engine error
            2^9        noselect
            2^14       service call
            2^15       misc error"
        ::= { nfPortEntry 21 }
    
    -- only PS3 >= 9.2.x
    
    nfPortAccPageCntr1 OBJECT-TYPE
        SYNTAX  INTEGER { disabled(0), enabled(1) }
        ACCESS  read-write
        STATUS  mandatory
        DESCRIPTION
            "This object switches accounting control for the printer
            internal page counter and the first mail recipient on or off."
        ::= { nfPortEntry 22 }
    
    nfPortAccPageCntr2 OBJECT-TYPE
        SYNTAX  INTEGER { disabled(0), enabled(1) }
        ACCESS  read-write
        STATUS  mandatory
        DESCRIPTION
            "This object switches accounting control for the printer
            internal page counter and the second mail recipient on or off."
        ::= { nfPortEntry 23 }
    
    
    nfPortAccPageCntrTime1 OBJECT-TYPE
        SYNTAX  INTEGER
        ACCESS  read-write
        STATUS  mandatory
        DESCRIPTION
            "This value set the time in hours to send the printer internal
            page counter to the first mail recipient."
        ::= { nfPortEntry 24 }
    
    nfPortAccPageCntrTime2 OBJECT-TYPE
        SYNTAX  INTEGER
        ACCESS  read-write
        STATUS  mandatory
        DESCRIPTION
            "This value set the time in hours to send the printer internal
            page counter to the second mail recipient."
        ::= { nfPortEntry 25 }
    
    nfPortAccPageCntrCntr1 OBJECT-TYPE
        SYNTAX  INTEGER
        ACCESS  read-write
        STATUS  mandatory
        DESCRIPTION
            "This value set the limit of number of pages to send the 
            printer internal page counter to the first mail recipient."
        ::= { nfPortEntry 26 }
    
    nfPortAccPageCntrCntr2 OBJECT-TYPE
        SYNTAX  INTEGER
        ACCESS  read-write
        STATUS  mandatory
        DESCRIPTION
            "This value set the limit of number of pages to send the 
            printer internal page counter to the second mail recipient."
        ::= { nfPortEntry 27 }
    
    nfPortMailList1 OBJECT-TYPE
        SYNTAX  DisplayString (SIZE (0..64))
        ACCESS  read-write
        STATUS  mandatory
        DESCRIPTION
            " "
        ::= { nfPortEntry 31 }
    
    nfPortMailList2 OBJECT-TYPE
        SYNTAX  DisplayString (SIZE (0..64))
        ACCESS  read-write
        STATUS  mandatory
        DESCRIPTION
            " "
        ::= { nfPortEntry 32 }
    
    nfPortTrapList1 OBJECT-TYPE
        SYNTAX  DisplayString (SIZE (0..64))
        ACCESS  read-write
        STATUS  mandatory
        DESCRIPTION
            " "
        ::= { nfPortEntry 33 }
    
    nfPortTrapList2 OBJECT-TYPE
        SYNTAX  DisplayString (SIZE (0..64))
        ACCESS  read-write
        STATUS  mandatory
        DESCRIPTION
            " "
        ::= { nfPortEntry 34 }
    
    nfPortAccPageCntrIndex1 OBJECT-TYPE
        SYNTAX  INTEGER
        ACCESS  read-write
        STATUS  mandatory
        DESCRIPTION
            "This object chooses the printer internal counter
            (specified as the index of periCounterTable)
            for the first mail recipient."
        ::= { nfPortEntry 35 }
    
    nfPortAccPageCntrIndex2 OBJECT-TYPE
        SYNTAX  INTEGER
        ACCESS  read-write
        STATUS  mandatory
        DESCRIPTION
            "This object chooses the printer internal counter
            (specified as the index of periCounterTable)
            for the first mail recipient."
        ::= { nfPortEntry 36 }
    
    nfSmtpServer OBJECT-TYPE
        SYNTAX  DisplayString (SIZE (0..255))
        ACCESS  read-write
        STATUS  mandatory
        DESCRIPTION
            "This parameter specifies the smtp server for the e-mail
            notification."
        ::= { sehNotification 7 }
    
    nfPop3 OBJECT-TYPE
        SYNTAX  INTEGER { disabled(0), enabled(1) }
        ACCESS  read-write
        STATUS  mandatory
        DESCRIPTION
            "This parameter enables POP3 functionality for first configuration set."
        ::= { sehMail 1 }
    
    nfPop3Poll OBJECT-TYPE
        SYNTAX  INTEGER
        ACCESS  read-write
        STATUS  mandatory
        DESCRIPTION
            "This parameter specifies the POP3 poll intervall in minutes."
        ::= { sehMail 2 }
    
    nfPop3Srv OBJECT-TYPE
        SYNTAX  DisplayString (SIZE (0..128))
        ACCESS  read-write
        STATUS  mandatory
        DESCRIPTION
            "This parameter specifies the pop3 server DNS name or IP address."
        ::= { sehMail 3 }
    
    nfPop3SrvPort OBJECT-TYPE
        SYNTAX  INTEGER
        ACCESS  read-write
        STATUS  mandatory
        DESCRIPTION
            "This is the TCP port number of the pop3 server
            we want to connect to."
        ::= { sehMail 4 }
    
    nfPop3SmtpSrv OBJECT-TYPE
        SYNTAX  DisplayString (SIZE (0..128))
        ACCESS  read-write
        STATUS  mandatory
        DESCRIPTION
            "This parameter specifies the pop3 smtp server DNS name or IP address."
        ::= { sehMail 5 }
    
    nfPop3SmtpPort OBJECT-TYPE
        SYNTAX  INTEGER
        ACCESS  read-write
        STATUS  mandatory
        DESCRIPTION
            "This is the TCP port number of the smtp server
            we want to connect to."
        ::= { sehMail 6 }
    
    nfPop3Usr OBJECT-TYPE
        SYNTAX  DisplayString (SIZE (0..128))
        ACCESS  read-write
        STATUS  mandatory
        DESCRIPTION
            "This parameter specifies the pop3 server user name."
        ::= { sehMail 7 }
    
    nfPop3Pwd OBJECT-TYPE
        SYNTAX  DisplayString (SIZE (0..128))
        ACCESS  read-write
        STATUS  mandatory
        DESCRIPTION
            "This parameter specifies the pop3 server user passsword."
        ::= { sehMail 8 }
    
    nfPop3Security OBJECT-TYPE
        SYNTAX  INTEGER { none(0), apop(1), ssl(2) }
        ACCESS  read-write
        STATUS  mandatory
        DESCRIPTION
            "This parameter specifies which security protocol we want
            to use for mail and password exchange with the pop3 server,
            and, if ssl is selected, with the smtp server."
        ::= { sehMail 9 }
    
    nfPop3MDel OBJECT-TYPE
        SYNTAX  INTEGER { leaveMailOnServer(0), deleteMailFromServer(1) }
        ACCESS  read-write
        STATUS  mandatory
        DESCRIPTION
            "This parameter specifies to delete or leave
            fetched mail on the server."
        ::= { sehMail 10 }
    
    nfPop3Limit OBJECT-TYPE
        SYNTAX  INTEGER
        ACCESS  read-write
        STATUS  mandatory
        DESCRIPTION
            "This parameter describes the maximal byte count for
            mails to fetch, zero means unlimited."
        ::= { sehMail 11 }
    
    nfPop3Signature OBJECT-TYPE
        SYNTAX  DisplayString (SIZE (0..128))
        ACCESS  read-write
        STATUS  mandatory
        DESCRIPTION
            "This contains the multiline signature email replies."
        ::= { sehMail 12 }
    
    nfSmtpUsr OBJECT-TYPE
        SYNTAX  DisplayString (SIZE (0..128))
        ACCESS  read-write
        STATUS  mandatory
        DESCRIPTION
            "This parameter specifies the smtp server user name."
        ::= { sehMail 13 }
    
    nfSmtpPwd OBJECT-TYPE
        SYNTAX  DisplayString (SIZE (0..128))
        ACCESS  read-write
        STATUS  mandatory
        DESCRIPTION
            "This parameter specifies the smtp server user passsword."
        ::= { sehMail 14 }
    
    nfSmtpSndr OBJECT-TYPE
        SYNTAX  DisplayString (SIZE (0..128))
        ACCESS  read-write
        STATUS  mandatory
        DESCRIPTION
            "This parameter specifies the smtp email sender name."
        ::= { sehMail 15 }
    
    nfSmtpSsl OBJECT-TYPE
        SYNTAX  INTEGER { disabled(0), enabled(1) }
        ACCESS  read-write
        STATUS  mandatory
        DESCRIPTION
            "This parameter enables SSL security for the SMTP connection."
        ::= { sehMail 16 }
    
    nfSmtpAsPop3 OBJECT-TYPE
        SYNTAX  INTEGER { disabled(0), enabled(1) }
        ACCESS  read-write
        STATUS  mandatory
        DESCRIPTION
            "This parameter decides to use the same settings for
            SMTP Authentication for user and password as pop3."
        ::= { sehMail 17 }
    
    nfSmtpAuth OBJECT-TYPE
        SYNTAX  INTEGER { disabled(0), enabled(1) }
        ACCESS  read-write
        STATUS  mandatory
        DESCRIPTION
            "This parameter switches the SMTP Authentication on or off."
        ::= { sehMail 18 }
    
    
    MailConnState ::= INTEGER {
    -- p3NONE(0), just for completeness, never reached
    p3INIT(1),
    p3DNSDONE(2),
    p3CONNECT(3),
    p3CONTACT(4),
    p3LOGIN(5),
    p3WORK(6),
    p3CLOSED(7),
    -- failures are following:
    p3APOPLOGINFAIL(8),
    p3APOPMD5FAIL(9),
    p3CONNECTFAIL(10),
    p3DATAFAIL(11),
    p3DELFAIL(12),
    p3DNSFAIL(13),
    p3LISTFAIL(14),
    p3LOGINFAIL(15),
    p3MEMFAIL(16),
    p3MFROMFAIL(17),
    p3AUTHFAIL(18),
    p3POPFAIL(19),
    p3PWDFAIL(20),
    p3RCPTFAIL(21),
    p3RETRFAIL(22),
    p3SCANFAIL(23),
    p3SENTFAIL(24),
    p3STATFAIL(25),
    p3STATSCANFAIL(26),
    p3USERFAIL(27)
    }
    
    nfPop3P3His OBJECT-TYPE
        SYNTAX  MailConnState
        ACCESS  read-only
        STATUS  mandatory
        DESCRIPTION
            "This parameter contains the highest reached state
            of the Pop3 protocol stack."
        ::= { sehMail 20 }
    
    nfPop3SMTPHis OBJECT-TYPE
        SYNTAX  MailConnState
        ACCESS  read-only
        STATUS  mandatory
        DESCRIPTION
            "This parameter contains the highest reached state
            of the Pop3 Smtp protocol stack."
        ::= { sehMail 21 }
    
    nfPop3P3Ctr OBJECT-TYPE
        SYNTAX  INTEGER
        ACCESS  read-only
        STATUS  mandatory
        DESCRIPTION
            "This parameter contains the  count of fetched Pop3 emails."
        ::= { sehMail 22 }
    
    nfPop3SMTPCtr OBJECT-TYPE
        SYNTAX  INTEGER
        ACCESS  read-only
        STATUS  mandatory
        DESCRIPTION
            "This parameter contains the  count of sent Pop3 replies emails."
        ::= { sehMail 23 }
    
    nfPop3P3Err OBJECT-TYPE
        SYNTAX  MailConnState
        ACCESS  read-only
        STATUS  mandatory
        DESCRIPTION
            "This parameter contains the last occured Pop3 error."
        ::= { sehMail 24 }
    
    nfPop3SmtpErr OBJECT-TYPE
        SYNTAX  MailConnState
        ACCESS  read-only
        STATUS  mandatory
        DESCRIPTION
            "This parameter contains the last occured Smtp error for Pop3 replies."
        ::= { sehMail 25 }
    
    nfPop3P3Next OBJECT-TYPE
        SYNTAX  INTEGER
        ACCESS  read-only
        STATUS  mandatory
        DESCRIPTION
            "This parameter contains number of second till the next
            Pop3 looking for emails cycle."
        ::= { sehMail 26 }
    
    smtpSMIMESig OBJECT-TYPE
        SYNTAX  INTEGER { disabled(0), enabled(1) }
        ACCESS  read-write
        STATUS  mandatory
        DESCRIPTION
            "This parameter decides to use S/MIME signature/authentication for outgoing emails."
        ::= { sehMail 30 }

    smtpSMIMEAddKey OBJECT-TYPE
        SYNTAX  INTEGER { disabled(0), enabled(1) }
        ACCESS  read-write
        STATUS  mandatory
        DESCRIPTION
            "This parameter decides to attach our public key within the S/MIME signature"
        ::= { sehMail 31 }
    
    smtpSMIMEEnc OBJECT-TYPE
        SYNTAX  INTEGER { disabled(0), enabled(1) }
        ACCESS  read-write
        STATUS  mandatory
        DESCRIPTION
            "This parameter decides to use S/MIME encryption for outgoing emails."
        ::= { sehMail 35 }
    
    -- the sehNat groups
    -- sehNat is PS19, sehNatDrop is Heinz extension
    -- This group specifies NAT gateway parameters of SEH.
        
    natLocal OBJECT-TYPE
        SYNTAX  IpAddress
        ACCESS  read-write
        STATUS  mandatory
        DESCRIPTION
            "This parameter specifies the local IP Address of the NAT device"
        ::= { sehNat 1 }
    
    natRemote OBJECT-TYPE
        SYNTAX  IpAddress
        ACCESS  read-write
        STATUS  mandatory
        DESCRIPTION
            "This parameter specifies the remote IP Address of the NAT device"
        ::= { sehNat 2 }
    
    httpPort OBJECT-TYPE
        SYNTAX  INTEGER
        ACCESS  read-write
        STATUS  mandatory
        DESCRIPTION
            "This parameter specifies the local HTTP port of the device."
        ::= { sehNat 3 }
    

    natMasquerade OBJECT-TYPE
        SYNTAX  INTEGER { disabled(0), enabled(1) }
        ACCESS  read-write
        STATUS  mandatory
        DESCRIPTION
            "This parameter switches NAT Masquerading on or off for the NAT device"
        ::= { sehNat 4 }
    

    natIcmp OBJECT-TYPE
        SYNTAX  INTEGER { disabled(0), enabled(1) }
        ACCESS  read-write
        STATUS  mandatory
        DESCRIPTION
            "This parameter switches ICMP forwarding on or off for the NAT device"
        ::= { sehNat 5 }
    
    spagePort OBJECT-TYPE
        SYNTAX  INTEGER
        ACCESS  read-write
        STATUS  mandatory
        DESCRIPTION
            "This parameter specifies the TCP port on the remote device 
             to print out the status page. 
             Default is socket printing port 9100"
        ::= { sehNat 6 }
    
    httpsPort OBJECT-TYPE
        SYNTAX  INTEGER
        ACCESS  read-write
        STATUS  mandatory
        DESCRIPTION
            "This parameter specifies the local HTTPS port of the device."
        ::= { sehNatDrop 6 }
    
    ftpPort OBJECT-TYPE
        SYNTAX  INTEGER
        ACCESS  read-write
        STATUS  mandatory
        DESCRIPTION
            "This parameter specifies the local FTP command port of the device."
        ::= { sehNatDrop 7 }
    
    ftpDataPort OBJECT-TYPE
        SYNTAX  INTEGER
        ACCESS  read-write
        STATUS  mandatory
        DESCRIPTION
            "This parameter specifies the local FTP data port of the device."
        ::= { sehNatDrop 8 }

    snmpPort OBJECT-TYPE
        SYNTAX  INTEGER
        ACCESS  read-write
        STATUS  mandatory
        DESCRIPTION
            "This parameter specifies the local SNMP port of the device."
        ::= { sehNatDrop 9 }
    
    aicePort OBJECT-TYPE
        SYNTAX  INTEGER
        ACCESS  read-write
        STATUS  mandatory
        DESCRIPTION
            "This parameter specifies the local AICE port for MSE CardnCopy of the device."
        ::= { sehNatDrop 10 }
    
    natDropNumber OBJECT-TYPE
        SYNTAX  INTEGER
        ACCESS  read-only
        STATUS  mandatory
        DESCRIPTION
            "This parameter specifies the number of available NAT Drop entries"
        ::= { sehNatDrop 21 }
    
    natDropTable OBJECT-TYPE
        SYNTAX  SEQUENCE OF NatDropEntry
        ACCESS  not-accessible
        STATUS  mandatory
        DESCRIPTION
            "This object specifies a table containing a list of NAT Drop
            entries. The number of entries is given by the value of natDropNumber."
        ::= { sehNatDrop 22 }

    natDropEntry OBJECT-TYPE
        SYNTAX  NatDropEntry
        ACCESS  not-accessible
        STATUS  mandatory
        DESCRIPTION
            "Parameters regarding to NAT Drop entry."
        INDEX   { natDropIndex }
        ::= { natDropTable 1 }
    
    NatDropEntry ::= SEQUENCE {
    natDropIndex   INTEGER,
    natDropPort    INTEGER,
    natDropTcp     INTEGER,
    natDropUdp     INTEGER,
    natDropLan     INTEGER,
    natDropNat     INTEGER
    }
    
    natDropIndex OBJECT-TYPE
        SYNTAX  INTEGER (0..256)
        ACCESS  read-only
        STATUS  mandatory
        DESCRIPTION
            "This object contains the index of the table being a
            unique value for each Nat Drop rule. Its value
            ranges between 1 and the value of NatDropNumber."
        ::= { natDropEntry 1 }

    natDropPort OBJECT-TYPE
        SYNTAX  INTEGER
        ACCESS  read-write
        STATUS  mandatory
        DESCRIPTION
            "This object contains the port number of the NAT drop rule."
        ::= { natDropEntry 2 }

    natDropTcp OBJECT-TYPE
        SYNTAX  INTEGER { disabled(0), enabled(1) }
        ACCESS  read-write
        STATUS  mandatory
        DESCRIPTION
            "This object contains 1 if to rule should match TCP packets on this port."
        ::= { natDropEntry 3 }

    natDropUdp OBJECT-TYPE
        SYNTAX  INTEGER { disabled(0), enabled(1) }
        ACCESS  read-write
        STATUS  mandatory
        DESCRIPTION
            "This object contains 1 if to rule should match UDP packets on this port."
        ::= { natDropEntry 4 }


    natDropLan OBJECT-TYPE
        SYNTAX  INTEGER { disabled(0), enabled(1) }
        ACCESS  read-write
        STATUS  mandatory
        DESCRIPTION
            "This object contains 1 if to rule should match packets at the LAN interface."
        ::= { natDropEntry 5 }

    natDropNat OBJECT-TYPE
        SYNTAX  INTEGER { disabled(0), enabled(1) }
        ACCESS  read-write
        STATUS  mandatory
        DESCRIPTION
            "This object contains 1 if to rule should match packets at the MAT interface."
        ::= { natDropEntry 6 }

    
    -- the sehtpg group
    
    -- This group specifies ThinPrint gateway parameters of SEH TPG.
        
    tpgNumber OBJECT-TYPE
        SYNTAX  INTEGER
        ACCESS  read-only
        STATUS  mandatory
        DESCRIPTION
            "This parameter specifies the number of available ThinPrint gateway entries"
        ::= { sehTpg 1 }
    
    tpgTable OBJECT-TYPE
        SYNTAX  SEQUENCE OF TpgEntry
        ACCESS  not-accessible
        STATUS  mandatory
        DESCRIPTION
            "This object specifies a table containing a list of ThinPrint gateway
            entries. The number of entries is given by the value of tpgNumber."
        ::= { sehTpg 2 }
    
    tpgClientId OBJECT-TYPE
        SYNTAX  INTEGER
        ACCESS  read-write
        STATUS  mandatory
        DESCRIPTION
            "This object specifies the ThinPrint client ID for ThinPrint Connections Services."
        ::= { sehTpg 3 }
    
    tpgAuthKey OBJECT-TYPE
        SYNTAX  INTEGER
        ACCESS  read-write
        STATUS  mandatory
        DESCRIPTION
            "This object specifies the ThinPrint Authentication Key for ThinPrint Connections Services."
        ::= { sehTpg 4 }
    
    tpgBandwidth OBJECT-TYPE
        SYNTAX  INTEGER { disabled(0), enabled(1) }
        ACCESS  read-write
        STATUS  mandatory
        DESCRIPTION
            "This parameter enables the TPG bandwith commitment with tpgBandwidthVal."
        ::= { sehTpg 5 }

    tpgBandwidthVal OBJECT-TYPE
        SYNTAX  INTEGER
        ACCESS  read-write
        STATUS  mandatory
        DESCRIPTION
            "This object specifies the TPG Bandwidth value committed to host."
        ::= { sehTpg 6 }
    
    tpgConnServices OBJECT-TYPE
        SYNTAX  INTEGER { disabled(0), enabled(1) }
        ACCESS  read-write
        STATUS  mandatory
        DESCRIPTION
            "This parameter enables the TPG Connection Services support."
        ::= { sehTpg 7 }

    tpgConnServer OBJECT-TYPE
        SYNTAX  IpAddress
        ACCESS  read-write
        STATUS  mandatory
        DESCRIPTION
            "This parameter specifies the IP address of the TPG 
             Connection Server."
        ::= { sehTpg 8 }

    tpgConnServerPort OBJECT-TYPE
        SYNTAX  INTEGER
        ACCESS  read-write
        STATUS  mandatory
        DESCRIPTION
            "This parameter specifies the IP port of the TPG 
             Connection Server."
        ::= { sehTpg 9 }
    
    tpgConnRetry OBJECT-TYPE
        SYNTAX  INTEGER
        ACCESS  read-write
        STATUS  mandatory
        DESCRIPTION
            "This parameter specifies the Retry value in seconds 
             of the TPG Connection Services."
        ::= { sehTpg 10 }
    
    tpgKeepAlive OBJECT-TYPE
        SYNTAX  INTEGER
        ACCESS  read-write
        STATUS  mandatory
        DESCRIPTION
            "This parameter specifies the KeepAlive value in seconds of the TPG."
        ::= { sehTpg 11 }
    
    tpgSpagePrt OBJECT-TYPE
        SYNTAX  INTEGER
        ACCESS  read-write
        STATUS  mandatory
        DESCRIPTION
            "This parameter specifies the index of the Remote Printer, 
             which prints the TPG status page."
        ::= { sehTpg 12 }
    
    -- tpgPrtOpenTo is not used and only listed for completeness

    tpgPrtOpenToVal OBJECT-TYPE
        SYNTAX  INTEGER (0..86400)
        ACCESS  read-write
        STATUS  mandatory
        DESCRIPTION
            "This object specifies the TPG printer open timeout value in seconds.
             After the specified time period a unsuccessfully try to open
             a remote printer returns with an error.
             Value of 0 disables this timeout. Max value is equal to one day"
        ::= { sehTpg 16 }
    
    tpgJobSendTimeout OBJECT-TYPE
        SYNTAX  INTEGER (0..86400)
        ACCESS  read-write
        STATUS  mandatory
        DESCRIPTION
            "This object specifies the TPG job send timeout value in seconds.
             If over the specified time period no data could be written to the 
             remote printer, the connection to printer will be closed and 
             an error returned.
             Value of 0 disables this timeout. Max value is equal to one day"
        ::= { sehTpg 17 }
    
    tpgJobRecvTimeout OBJECT-TYPE
        SYNTAX  INTEGER (0..1440)
        ACCESS  read-write
        STATUS  mandatory
        DESCRIPTION
            "This object specifies the TPG job receive timeout value in minutes.
             If over the specified time period no data could be received from the 
             ThinePrint server, the connections to printer and server will be closed.
             Value of 0 disables this timeout. Max value is equal to one day"
        ::= { sehTpg 18 }
    
    tpgMonitorPoll OBJECT-TYPE
        SYNTAX  INTEGER
        ACCESS  read-write
        STATUS  mandatory
        DESCRIPTION
            "This object specifies the poll time in seconds for the remote monitoring functionality."
        ::= { sehTpg 20 }

    tpgMonitorPing OBJECT-TYPE
        SYNTAX  INTEGER { disabled(0), enabled(1) }
        ACCESS  read-write
        STATUS  mandatory
        DESCRIPTION
            "This parameter enables the TPG remote monitoring using PING packets."
        ::= { sehTpg 21 }

    tpgMonitorSnmp OBJECT-TYPE
        SYNTAX  INTEGER { disabled(0), enabled(1) }
        ACCESS  read-write
        STATUS  mandatory
        DESCRIPTION
            "This parameter enables the TPG remote monitoring using SNMP packets."
        ::= { sehTpg 22 }

    tpgConnState OBJECT-TYPE
        SYNTAX  INTEGER {
                tpgINIT(1),
                tpgCONNECT(2),
                tpgREJECT(3),
                tpgTIMEOUT(4)
                }  
        ACCESS  read-only
        STATUS  mandatory
        DESCRIPTION
            "This parameter contains the state of the TPG Connection Services."
        ::= { sehTpg 13 }

    tpgStreamCompr OBJECT-TYPE
        SYNTAX  INTEGER { disabled(0), enabled(1) }
        ACCESS  read-write
        STATUS  mandatory
        DESCRIPTION
            "This parameter enables the TPG StreamCompression Mode,
             used with ThinPrint Server Versions later or equal than 7.0."
        ::= { sehTpg 14 }

    tpgSpage OBJECT-TYPE
        SYNTAX  INTEGER { disabled(0), enabled(1) }
        ACCESS  read-write
        STATUS  mandatory
        DESCRIPTION
            "This parameter enables the TPG status page on printed to the remote device."
        ::= { sehTpg 15 }

    tpgEntry OBJECT-TYPE
        SYNTAX  TpgEntry
        ACCESS  not-accessible
        STATUS  mandatory
        DESCRIPTION
            "Parameters regarding to ThinPrint gateway entry."
        INDEX   { tpgIndex }
        ::= { tpgTable 1 }
    
    TpgEntry ::= SEQUENCE {
    tpgIndex       INTEGER,
    tpgPrtName     DisplayString,
    tpgPrtClass    DisplayString,
    tpgPrtDriver   DisplayString,
    tpgRemoteIp    DisplayString,
    tpgRemotePort  INTEGER,
    tpgRemoteStat  INTEGER,
    tpgRemoteQueue DisplayString,
    tpgRemoteLPD   INTEGER,
    tpgLpdModeRFC  INTEGER,
    tpgRemoteUrl   DisplayString,
    tpgRemoteIPPs  INTEGER,
    tpgRemoteStStr DisplayString
    }
    
    tpgIndex OBJECT-TYPE
        SYNTAX  INTEGER (0..256)
        ACCESS  read-only
        STATUS  mandatory
        DESCRIPTION
            "This object contains the index of the table being a
            unique value for each logical printer. Its value
            ranges between 1 and the value of tpgNumber.
            For the TPG this is also the ThinPrint printer ID."
        ::= { tpgEntry 1 }
    
    tpgPrtName OBJECT-TYPE
        SYNTAX  DisplayString (SIZE (1..32))
        ACCESS  read-write
        STATUS  mandatory
        DESCRIPTION
            "ThinPrint Gatewy Printer Name."
        ::= { tpgEntry 2 }
    
    tpgPrtClass OBJECT-TYPE
        SYNTAX  DisplayString (SIZE (1..8))
        ACCESS  read-write
        STATUS  mandatory
        DESCRIPTION
            "ThinPrint Gatewy Printer Class."
        ::= { tpgEntry 3 }
    
    tpgPrtDriver OBJECT-TYPE
        SYNTAX  DisplayString (SIZE (1..64))
        ACCESS  read-write
        STATUS  mandatory
        DESCRIPTION
            "ThinPrint Gatewy Printer Driver Name; for future purpose."
        ::= { tpgEntry 4 }
    
    tpgRemoteIp OBJECT-TYPE
        SYNTAX  DisplayString (SIZE (1..128))
        ACCESS  read-write
        STATUS  mandatory
        DESCRIPTION
            "This parameter specifies the TPG remote IP address of the index related printer."
        ::= { tpgEntry 5 }

    tpgRemotePort OBJECT-TYPE
        SYNTAX  INTEGER
        ACCESS  read-write
        STATUS  mandatory
        DESCRIPTION
            "This parameter specifies the TPG remote IP port of the index related printer."
        ::= { tpgEntry 6 }
    
    tpgRemoteStat OBJECT-TYPE
        SYNTAX  INTEGER {
                timeout(1),
                reachable(2),
                unrechable(3),
                unknown(4)
                }  
        ACCESS  read-only
        STATUS  mandatory
        DESCRIPTION
            "This parameter specifies the TPG connection status to the remote printer."
        ::= { tpgEntry 7 }
    
    tpgRemoteQueue OBJECT-TYPE
        SYNTAX  DisplayString (SIZE (1..64))
        ACCESS  read-write
        STATUS  mandatory
        DESCRIPTION
            "This parameter specifies the TPG remote queue name for LPD printing."
        ::= { tpgEntry 8 }

    tpgRemoteLPD OBJECT-TYPE
        SYNTAX  INTEGER { raw(0), lpd(1), ipp(2) }
        ACCESS  read-write
        STATUS  mandatory
        DESCRIPTION
            "This parameter specifies the TPG remote printing protocol  for this port."
        ::= { tpgEntry 9 }


    tpgLpdModeRFC OBJECT-TYPE
        SYNTAX  INTEGER { disabled(0), enabled(1) }
        ACCESS  read-write
        STATUS  mandatory
        DESCRIPTION
            "This parameter specifies how to handle missing lenght information for the LPD printing backend.
             If enabled (default) lenght 0 is commited, otherwise we use a pseudo length bigger than any job
             like Microsoft/Windows."
        ::= { tpgEntry 10 }

    tpgRemoteUrl OBJECT-TYPE
        SYNTAX  DisplayString (SIZE (1..64))
        ACCESS  read-write
        STATUS  mandatory
        DESCRIPTION
            "This parameter specifies the TPG remote URL name for IPP printing."
        ::= { tpgEntry 11 }

    tpgRemoteIPPs OBJECT-TYPE
        SYNTAX  INTEGER { disabled(0), enabled(1) }
        ACCESS  read-write
        STATUS  mandatory
        DESCRIPTION
            "This parameter specifies if IPP uses SSL connections."
        ::= { tpgEntry 12 }

    tpgRemoteStStr  OBJECT-TYPE
        SYNTAX  DisplayString (SIZE (1..64))
        ACCESS  read-only
        STATUS  mandatory
        DESCRIPTION
            "This parameter specifies the TPG remote printer status."
        ::= { tpgEntry 13 }
    
    -- todo end
    
    -- the sehLrs group
    
    -- This group specifies the parameters of SEH LRS.
        
    lrsAesKey OBJECT-TYPE
        SYNTAX  DisplayString (SIZE (1..256))
        ACCESS  read-write
        STATUS  mandatory
        DESCRIPTION
            "This parameter defines the AES decryption key"
        ::= { sehLrs 1 }
        
    lrsAesType OBJECT-TYPE
        SYNTAX  INTEGER { aes16(16), aes24(24), aes32(32) }
        ACCESS  read-write
        STATUS  mandatory
        DESCRIPTION
            "This parameter defines the AES type of the key"
        ::= { sehLrs 2 }
        
    lrsIsppPort OBJECT-TYPE
        SYNTAX  INTEGER
        ACCESS  read-write
        STATUS  mandatory
        DESCRIPTION
            "This parameter defines the number of the ISPP port"
        ::= { sehLrs 3 }
        
    lrsUseInstallationKey OBJECT-TYPE
        SYNTAX  INTEGER { disabled(0), enabled(1) }
        ACCESS  read-write
        STATUS  mandatory
        DESCRIPTION
            "This parameter enables/disables the use of the installation key "
        ::= { sehLrs 4 }
        
    lrsAllowKeyChange OBJECT-TYPE
        SYNTAX  INTEGER { disabled(0), enabled(1) }
        ACCESS  read-write
        STATUS  mandatory
        DESCRIPTION
            "This parameter enables/disables the automatic adoption
            of the AES decryption key from the host"
        ::= { sehLrs 5 }
        
    lrsPrtPort OBJECT-TYPE
        SYNTAX  INTEGER
        ACCESS  read-write
        STATUS  mandatory
        DESCRIPTION
            "This parameter defines the logical printer which is used to address the printer"
        ::= { sehLrs 6 }
    

    -- the sehProtection group
    
    -- This group specifies several protection and filter parameters used by e.g myUTN.

    protection OBJECT-TYPE
        SYNTAX  INTEGER { disabled(0), enabled(1) }
        ACCESS  read-write
        STATUS  mandatory
        DESCRIPTION
            "This parameter enables the protection filter rules at all."
        ::= { sehProtection 1 }
    
    protectionTest OBJECT-TYPE
        SYNTAX  INTEGER { disabled(0), enabled(1) }
        ACCESS  read-write
        STATUS  mandatory
        DESCRIPTION
            "This parameter enables the protection filter rules test mode.
             If protection is on, it will be switched off with next restart.
             To enable filter rules permanently, this parameter is to switch off."
        ::= { sehProtection 2 }

    protectionLevel OBJECT-TYPE
        SYNTAX  INTEGER { 
        protectall(1),
        protecttcp(2),
        protectutn(3)
        }
       ACCESS  read-write
        STATUS mandatory
        DESCRIPTION
           "This parameter determines the manner of
            of our filter rules below. 
            protectutn will only protect the tcp/utn port,
            protecttcp will protect all tcp ports,
            protectall will protect all ip ports."
        ::= { sehProtection 3 }
        
    ipFilterNumber OBJECT-TYPE
        SYNTAX  INTEGER
        ACCESS  read-only
        STATUS  mandatory
        DESCRIPTION
            "Number of entries in the  Ip filter table."
        ::= { sehProtection 10 }
    
    IpFilterEntryType ::= SEQUENCE {
    ipFilterIndex   INTEGER,
    ipFilterOnOff   INTEGER,
    ipFilterAddr    DisplayString
    }

    ipFilterTable OBJECT-TYPE
        SYNTAX  SEQUENCE OF IpFilterEntryType
        ACCESS  not-accessible
        STATUS  mandatory
        DESCRIPTION
            "This object specifies a table containing IP filter descriptions."
        ::= { sehProtection 11 }

    ipFilterEntry OBJECT-TYPE
        SYNTAX  IpFilterEntryType
        ACCESS  not-accessible
        STATUS  mandatory
        DESCRIPTION
            "Entry of Ip filter table."
        INDEX   { ipFilterIndex }
        ::= { ipFilterTable 1 }
    
    ipFilterIndex OBJECT-TYPE
        SYNTAX  INTEGER (0..256)
        ACCESS  not-accessible
        STATUS  mandatory
        DESCRIPTION
            "This object contains the index of the table being a
            unique value for each IP filter rule."
        ::= { ipFilterEntry 1 }
    
    ipFilterOnOff OBJECT-TYPE
        SYNTAX  INTEGER { off(0), on(1) }
        ACCESS  read-write
        STATUS  mandatory
        DESCRIPTION
            "This parameter specifies wether the rule is active or not."
        ::= { ipFilterEntry 2 }
 
    ipFilterAddr OBJECT-TYPE
        SYNTAX  DisplayString (SIZE (1..64))
        ACCESS  read-write
        STATUS  mandatory
        DESCRIPTION
            "This parameter specifies the Ip address for the filter rule."
        ::= { ipFilterEntry 3 }

    macFilterNumber OBJECT-TYPE
        SYNTAX  INTEGER
        ACCESS  read-only
        STATUS  mandatory
        DESCRIPTION
            "Number of entries in the  Ip filter table."
        ::= { sehProtection 12 }
    
    macFilterTable OBJECT-TYPE
        SYNTAX  SEQUENCE OF MacFilterEntry
        ACCESS  not-accessible
        STATUS  mandatory
        DESCRIPTION
            "This object specifies a table containing IP filter descriptions."
        ::= { sehProtection 13 }

    macFilterEntry OBJECT-TYPE
        SYNTAX  MacFilterEntry
        ACCESS  not-accessible
        STATUS  mandatory
        DESCRIPTION
            "Entry of Ip filter table."
        INDEX   { macFilterIndex }
        ::= { macFilterTable 1 }
    
    MacFilterEntry ::= SEQUENCE {
    macFilterIndex   INTEGER,
    macFilterOnOff   INTEGER,
    macFilterAddr    PhysAddress
    }

    macFilterIndex OBJECT-TYPE
        SYNTAX  INTEGER (0..256)
        ACCESS  not-accessible
        STATUS  mandatory
        DESCRIPTION
            "This object contains the index of the table being a
            unique value for each IP filter rule."
        ::= { macFilterEntry 1 }
    
    macFilterOnOff OBJECT-TYPE
        SYNTAX  INTEGER { off(0), on(1) }
        ACCESS  read-write
        STATUS  mandatory
        DESCRIPTION
            "This parameter specifies wether the rule is active or not."
        ::= { macFilterEntry 2 }
 
    macFilterAddr OBJECT-TYPE
        SYNTAX  PhysAddress (SIZE (6))
        ACCESS  read-write
        STATUS  mandatory
        DESCRIPTION
            "This parameter specifies the Ip address for the filter rule."
        ::= { macFilterEntry 3 }

   cipherStrength OBJECT-TYPE
        SYNTAX  INTEGER { low(1), medium(2), high(3), default(4) }
        ACCESS  read-write
        STATUS  mandatory
        DESCRIPTION
            "This object specifies a central switch for the strenght of used ciphersuites."
        ::= { sehProtection 20 }

   rsaBits OBJECT-TYPE
        SYNTAX  INTEGER { low(512), middle(768), default(1024), high(2048) }
        ACCESS  read-write
        STATUS  mandatory
        DESCRIPTION
            "This object specifies the RSA key bit lenght. Higher values results in more secure but slower connections."
        ::= { sehProtection 21 }

    -- the sehUser group
    
    -- This group specifies SEH user definition used by e.g myUTN.

     usrAnyName OBJECT-TYPE
        SYNTAX  DisplayString (SIZE (1..64))
        ACCESS  read-write
        STATUS  mandatory
        DESCRIPTION
            "This parameter specifies the any users name."
        ::= { sehUser 1 }

     usrAnyPwd OBJECT-TYPE
        SYNTAX  DisplayString (SIZE (1..64))
        ACCESS  read-write
        STATUS  mandatory
        DESCRIPTION
            "This parameter specifies the any users password."
        ::= { sehUser 2 }

     usrAnyAcc OBJECT-TYPE
        SYNTAX  INTEGER { noAccess(1), readOnly(2), readWrite(3) }
        ACCESS  read-write
        STATUS  mandatory
        DESCRIPTION
            "This parameter specifies the any users access rights."
        ::= { sehUser 3 }
    
     usrAnyHash OBJECT-TYPE
        SYNTAX  INTEGER { md5(1), sha1(2) }
        ACCESS  read-write
        STATUS  mandatory
        DESCRIPTION
            "This parameter specifies the password Hash of user any."
        ::= { sehUser 4 }
    
     usrAnyCypher OBJECT-TYPE
        SYNTAX  INTEGER { none(1), aes(2), des(3)}
        ACCESS  read-write
        STATUS  mandatory
        DESCRIPTION
            "This parameter specifies the encryption cypher of user any."
        ::= { sehUser 5 }

     usrAdminName OBJECT-TYPE
        SYNTAX  DisplayString (SIZE (1..64))
        ACCESS  read-write
        STATUS  mandatory
        DESCRIPTION
            "This parameter specifies the administrators name."
        ::= { sehUser 11 }

     usrAdminPwd OBJECT-TYPE
        SYNTAX  DisplayString (SIZE (1..64))
        ACCESS  read-write
        STATUS  mandatory
        DESCRIPTION
            "This parameter specifies the administrators password."
        ::= { sehUser 12 }

     usrAdminAcc OBJECT-TYPE
        SYNTAX  INTEGER { noAccess(1), readOnly(2), readWrite(3) }
        ACCESS  read-write
        STATUS  mandatory
        DESCRIPTION
            "This parameter specifies the administrators access rights."
        ::= { sehUser 13 }

     usrAdminHash OBJECT-TYPE
        SYNTAX  INTEGER { md5(1), sha1(2) }
        ACCESS  read-write
        STATUS  mandatory
        DESCRIPTION
            "This parameter specifies the password Hash of user any."
        ::= { sehUser 14 }
    
     usrAdminCypher OBJECT-TYPE
        SYNTAX  INTEGER { none(1), aes(2), des(3)}
        ACCESS  read-write
        STATUS  mandatory
        DESCRIPTION
            "This parameter specifies the encryption cypher of user any."
        ::= { sehUser 15 }

    -- the sehIPsec group
    
    -- This group specifies IPsec parameters used by e.g Print Server.

    ipsecIPsec OBJECT-TYPE
        SYNTAX  INTEGER { disabled(0), enabled(1) }
        ACCESS  read-write
        STATUS  mandatory
        DESCRIPTION
            "This parameter enables or disables IPsec."
        ::= { sehIPsec 1 }

    ipsecConfig OBJECT-TYPE
        SYNTAX  INTEGER { rules(0), files(1) }
        ACCESS  read-write
        STATUS  mandatory
        DESCRIPTION
            "This parameter specifies the configurations for IPsec, which uses
            configured Rules or configuration files."
        ::= { sehIPsec 2 }

    ipsecDefAction OBJECT-TYPE
        SYNTAX  INTEGER { allow(0), drop(1) }
        ACCESS  read-write
        STATUS  mandatory
        DESCRIPTION
            "This parameter specifies the action for IPsec default configured 
            rules."
        ::= { sehIPsec 3 }

    ipsecRulesNumber OBJECT-TYPE
        SYNTAX  INTEGER
        ACCESS  read-only
        STATUS  mandatory
        DESCRIPTION
            "This parameter specifies the number of available IPsec rules."
        ::= { sehIPsec 4 }
    
    ipsecRulesTable OBJECT-TYPE
        SYNTAX  SEQUENCE OF IPsecRulesEntry
        ACCESS  not-accessible
        STATUS  mandatory
        DESCRIPTION
            "This object specifies a table containing a list of IPsec rules
            entries. The number of entries is given by the value of 
            ipsecRulesNumber."
        ::= { sehIPsec 5 }

    ipsecAddrTmplNumber OBJECT-TYPE
        SYNTAX  INTEGER
        ACCESS  read-only
        STATUS  mandatory
        DESCRIPTION
            "This parameter specifies the number of available IPsec address
            templates."
        ::= { sehIPsec 6 }

    ipsecAddrTmplTable OBJECT-TYPE
        SYNTAX  SEQUENCE OF IPsecAddrTmplEntry
        ACCESS  not-accessible
        STATUS  mandatory
        DESCRIPTION
            "This object specifies a table containing a list of IPsec address
            templates entries. The number of entries is given by the value of 
            ipsecAddrTmplNumber."
        ::= { sehIPsec 7 }

    ipsecServTmplNumber OBJECT-TYPE
        SYNTAX  INTEGER
        ACCESS  read-only
        STATUS  mandatory
        DESCRIPTION
            "This parameter specifies the number of available IPsec service
            templates."
        ::= { sehIPsec 8 }

    ipsecServTmplTable OBJECT-TYPE
        SYNTAX  SEQUENCE OF IPsecServTmplEntry
        ACCESS  not-accessible
        STATUS  mandatory
        DESCRIPTION
            "This object specifies a table containing a list of IPsec service
            templates entries. The number of entries is given by the value of 
            ipsecServTmplNumber."
        ::= { sehIPsec 9 }

    ipsecSATmplNumber OBJECT-TYPE
        SYNTAX  INTEGER
        ACCESS  read-only
        STATUS  mandatory
        DESCRIPTION
            "This parameter specifies the number of available IPsec SA 
            (Security association) templates."
        ::= { sehIPsec 10 }

    ipsecSATmplTable OBJECT-TYPE
        SYNTAX  SEQUENCE OF IPsecSATmplEntry
        ACCESS  not-accessible
        STATUS  mandatory
        DESCRIPTION
            "This object specifies a table containing a list of IPsec SA 
            templates entries. The number of entries is given by the value of 
            ipsecSATmplNumber."
        ::= { sehIPsec 11 }

    ipsecIKETmplNumber OBJECT-TYPE
        SYNTAX  INTEGER
        ACCESS  read-only
        STATUS  mandatory
        DESCRIPTION
            "This parameter specifies the number of available IPsec IKE 
            (IPsec key exchange) templates."
        ::= { sehIPsec 12 }

    ipsecIKETmplTable OBJECT-TYPE
        SYNTAX  SEQUENCE OF IPsecIKETmplEntry
        ACCESS  not-accessible
        STATUS  mandatory
        DESCRIPTION
            "This object specifies a table containing a list of IPsec IKE 
            templates entries. The number of entries is given by the value of 
            ipsecIKETmplNumber."
        ::= { sehIPsec 13 }

    ipsecDHCP OBJECT-TYPE
        SYNTAX  INTEGER { disabled(0), enabled(1) }
        ACCESS  read-write
        STATUS  mandatory
        DESCRIPTION
            "This parameter allows or doesn't allow the broadcast DHCPv4/BootP
            for the services selected to bypass the IPsec policies."
        ::= { sehIPsec 14 }

    ipsecNetbios OBJECT-TYPE
        SYNTAX  INTEGER { disabled(0), enabled(1) }
        ACCESS  read-write
        STATUS  mandatory
        DESCRIPTION
            "This parameter allows or doesn't allow the broadcast Netbios
            for the services selected to bypass the IPsec policies."
        ::= { sehIPsec 15 }

    ipsecBonjour OBJECT-TYPE
        SYNTAX  INTEGER { disabled(0), enabled(1) }
        ACCESS  read-write
        STATUS  mandatory
        DESCRIPTION
            "This parameter allows or doesn't allow the multicast Bonjour
            for the services selected to bypass the IPsec policies."
        ::= { sehIPsec 16 }

    ipsecSLP OBJECT-TYPE
        SYNTAX  INTEGER { disabled(0), enabled(1) }
        ACCESS  read-write
        STATUS  mandatory
        DESCRIPTION
            "This parameter allows or doesn't allow the multicast SLP
            for the services selected to bypass the IPsec policies."
        ::= { sehIPsec 17 }

    ipsecFTP OBJECT-TYPE
        SYNTAX  INTEGER { disabled(0), enabled(1) }
        ACCESS  read-write
        STATUS  mandatory
        DESCRIPTION
            "This parameter allows or doesn't allow IPsec for the ftp protocol."
        ::= { sehIPsec 18 }

    ipsecTest OBJECT-TYPE
        SYNTAX  INTEGER { disabled(0), enabled(1) }
        ACCESS  read-write
        STATUS  mandatory
        DESCRIPTION
            "This parameter enables the IPsec test mode."
        ::= { sehIPsec 19 }

    ipsecRulesEntry OBJECT-TYPE
        SYNTAX  IPsecRulesEntry
        ACCESS  not-accessible
        STATUS  mandatory
        DESCRIPTION
            "Parameters regarding to configured rules."
        INDEX   { ipsecRulesIndex }
        ::= { ipsecRulesTable 1 }
    
    IPsecRulesEntry ::= SEQUENCE {
    ipsecRulesIndex      INTEGER,
    ipsecRulesEnabled    INTEGER,
    ipsecRulesIaddr      INTEGER,
    ipsecRulesIserv      INTEGER,
    ipsecRulesIPsec      INTEGER,
    ipsecRulesAction     INTEGER
    }

    ipsecRulesIndex OBJECT-TYPE
        SYNTAX  INTEGER (0..256)
        ACCESS  read-only
        STATUS  mandatory
        DESCRIPTION
            "This object contains the index of the table being a
            unique value for each IPsec rule. Its value ranges
            between 1 and the value of ipsecRulesNumber."
        ::= { ipsecRulesEntry 1 }
            
    ipsecRulesEnabled OBJECT-TYPE
        SYNTAX  INTEGER { disabled(0), enabled(1) }
        ACCESS  read-write
        STATUS  mandatory
        DESCRIPTION
            "This parameter enables or disables the IPsec rules."
        ::= { ipsecRulesEntry 2 }

    ipsecRulesIaddr OBJECT-TYPE
        SYNTAX  INTEGER { 
        addrtmpl1(1), 
        addrtmpl2(2), 
        addrtmpl3(3),
        addrtmpl4(4),
        addrtmpl5(5),
        addrtmpl6(6),
        addrtmpl7(7),
        addrtmpl8(8) }
        ACCESS  read-write
        STATUS  mandatory
        DESCRIPTION
            "This parameter specifies the address template number
            of the IPsec rules."
        ::= { ipsecRulesEntry 3 }

    ipsecRulesIserv OBJECT-TYPE
        SYNTAX  INTEGER {
        servtmpl1(1),
        servtmpl2(2),
        servtmpl3(3),
        servtmpl4(4) }
        ACCESS  read-write
        STATUS  mandatory
        DESCRIPTION
            "This parameter specifies the service template number
            of the IPsec rules."
        ::= { ipsecRulesEntry 4 }

    ipsecRulesIPsec OBJECT-TYPE
        SYNTAX  INTEGER {
        ipsectmpl1(1),
        ipsectmpl2(2),
        ipsectmpl3(3),
        ipsectmpl4(4) }
        ACCESS  read-write
        STATUS  mandatory
        DESCRIPTION
            "This parameter specifies the IPsec template number
            of the IPsec rules."
        ::= { ipsecRulesEntry 5 }

    ipsecRulesAction OBJECT-TYPE
        SYNTAX  INTEGER { allow(0), drop(1), requie(2) }
        ACCESS  read-write
        STATUS  mandatory
        DESCRIPTION
            "This parameter specifies the action of the IPsec rules."
        ::= { ipsecRulesEntry 6 }

    ipsecAddrTmplEntry OBJECT-TYPE
        SYNTAX  IPsecAddrTmplEntry
        ACCESS  not-accessible
        STATUS  mandatory
        DESCRIPTION
            "Parameters regarding to IPsec address Templates."
        INDEX   { ipsecAddrTmplIndex }
        ::= { ipsecAddrTmplTable 1 }
    
    IPsecAddrTmplEntry ::= SEQUENCE {
    ipsecAddrTmplIndex      INTEGER,
    ipsecAddrTmplName       DisplayString,
    ipsecAddrTmplRemoteIPv4 DisplayString,
    ipsecAddrTmplLocalIPv6  DisplayString,
    ipsecAddrTmplRemoteIPv6 DisplayString
    }

    ipsecAddrTmplIndex OBJECT-TYPE
        SYNTAX  INTEGER (0..256)
        ACCESS  read-only
        STATUS  mandatory
        DESCRIPTION
            "This object contains the index of the table being a
            unique value for each IPsec address templtes. Its value 
            ranges between 1 and the value of ipsecAddrTmplNumber."
        ::= { ipsecAddrTmplEntry 1 }
            
    ipsecAddrTmplName OBJECT-TYPE
        SYNTAX  DisplayString (SIZE (1..16))
        ACCESS  read-write
        STATUS  mandatory
        DESCRIPTION
            "IPsec address templates name."
        ::= { ipsecAddrTmplEntry 2 }

    ipsecAddrTmplRemoteIPv4 OBJECT-TYPE
        SYNTAX  DisplayString (SIZE (1..18))
        ACCESS  read-write
        STATUS  mandatory
        DESCRIPTION
            "IPsec address templates remote ip address (IPv4)."
        ::= { ipsecAddrTmplEntry 3 }

    ipsecAddrTmplLocalIPv6 OBJECT-TYPE
        SYNTAX  DisplayString (SIZE (1..44))
        ACCESS  read-write
        STATUS  mandatory
        DESCRIPTION
            "IPsec address templates local ip address (IPv6)."
        ::= { ipsecAddrTmplEntry 4 }

    ipsecAddrTmplRemoteIPv6  OBJECT-TYPE
        SYNTAX  DisplayString (SIZE (1..44))
        ACCESS  read-write
        STATUS  mandatory
        DESCRIPTION
            "IPsec address templates remote ip address (IPv6)."
        ::= { ipsecAddrTmplEntry 5 }

    ipsecServTmplEntry OBJECT-TYPE
        SYNTAX  IPsecServTmplEntry
        ACCESS  not-accessible
        STATUS  mandatory
        DESCRIPTION
            "Parameters regarding to IPsec service Templates."
        INDEX   { ipsecServTmplIndex }
        ::= { ipsecServTmplTable 1 }
    
    IPsecServTmplEntry ::= SEQUENCE {
    ipsecServTmplIndex      INTEGER,
    ipsecServTmplName       DisplayString,
    ipsecServTmplServ       DisplayString
    }

    ipsecServTmplIndex OBJECT-TYPE
        SYNTAX  INTEGER (0..256)
        ACCESS  read-only
        STATUS  mandatory
        DESCRIPTION
            "This object contains the index of the table being a
            unique value for each IPsec service templtes. Its value 
            ranges between 1 and the value of ipsecServTmplNumber."
        ::= { ipsecServTmplEntry 1 }
         
    ipsecServTmplName OBJECT-TYPE
        SYNTAX  DisplayString (SIZE (1..16))
        ACCESS  read-write
        STATUS  mandatory
        DESCRIPTION
            "IPsec services templates name."
        ::= { ipsecServTmplEntry 2 }

    ipsecServTmplServ OBJECT-TYPE
        SYNTAX  DisplayString (SIZE (1..128))
        ACCESS  read-write
        STATUS  mandatory
        DESCRIPTION
            "IPsec services - multi-choice of
            ALL
            FTP
            IPP
            LPR
            ICMP
            SNMP
            Socketprinting
            ThinPrint
            HTTP
            SNTP"
        ::= { ipsecServTmplEntry 3 }

    ipsecSATmplEntry OBJECT-TYPE
        SYNTAX  IPsecSATmplEntry
        ACCESS  not-accessible
        STATUS  mandatory
        DESCRIPTION
            "Parameters regarding to IPsec Templates SA."
        INDEX   { ipsecSATmplIndex }
        ::= { ipsecSATmplTable 1 }
    
    IPsecSATmplEntry ::= SEQUENCE {
    ipsecSATmplIndex      INTEGER,
    ipsecSATmplName       DisplayString,
    ipsecSATmplCert       INTEGER,
    ipsecSATmplVeri       INTEGER,
    ipsecSATmplPSK        DisplayString,
    ipsecSATmplIKE        INTEGER
    }

    ipsecSATmplIndex OBJECT-TYPE
        SYNTAX  INTEGER (0..256)
        ACCESS  read-only
        STATUS  mandatory
        DESCRIPTION
            "This object contains the index of the table being a
            unique value for each IPsec SA templtes. Its value 
            ranges between 1 and the value of ipsecSATmplNumber."
        ::= { ipsecSATmplEntry 1 }

    ipsecSATmplName OBJECT-TYPE
        SYNTAX  DisplayString (SIZE (1..16))
        ACCESS  read-write
        STATUS  mandatory
        DESCRIPTION
            "IPsec SA templates name."
        ::= { ipsecSATmplEntry 2 }

    ipsecSATmplCert OBJECT-TYPE
        SYNTAX  INTEGER { psk(0), certificate(1) }
        ACCESS  read-write
        STATUS  mandatory
        DESCRIPTION
            "This parameter specifies the certification type of the IPsec 
            SA template."
        ::= { ipsecSATmplEntry 3 }

    ipsecSATmplVeri OBJECT-TYPE
        SYNTAX  INTEGER { disabled(0), enabled(1) }
        ACCESS  read-write
        STATUS  mandatory
        DESCRIPTION
            "This parameter enables or disables the certification verify 
            of the IPsec SA template."
        ::= { ipsecSATmplEntry 4 }

    ipsecSATmplPSK OBJECT-TYPE
        SYNTAX  DisplayString (SIZE (1..16))
        ACCESS  read-write
        STATUS  mandatory
        DESCRIPTION
            "This parameter specifies the Pre-Shared Key of the IPsec 
            SA template.."
        ::= { ipsecSATmplEntry 5 }

    ipsecSATmplIKE OBJECT-TYPE
        SYNTAX  INTEGER {
        iketmpl1(1),
        iketmpl2(2),
        iketmpl3(3),
        iketmpl4(4) }
        ACCESS  read-write
        STATUS  mandatory
        DESCRIPTION
            "This parameter specifies the IKE template number
            of the SA template."
        ::= { ipsecSATmplEntry 6 }

    ipsecIKETmplEntry OBJECT-TYPE
        SYNTAX  IPsecIKETmplEntry
        ACCESS  not-accessible
        STATUS  mandatory
        DESCRIPTION
            "Parameters regarding to IPsec IKE templates."
        INDEX   { ipsecIKETmplIndex }
        ::= { ipsecIKETmplTable 1 }
    
    IPsecIKETmplEntry ::= SEQUENCE {
    ipsecIKETmplIndex      INTEGER,
    ipsecIKETmplName       DisplayString,
    ipsecIKETmplModes      DisplayString,
    ipsecIKETmplDhGroup    INTEGER,
    ipsecIKETmplEncV1      INTEGER,
    ipsecIKETmplAuthV1     INTEGER,
    ipsecIKETmplLtV1       DisplayString,
    ipsecIKETmplEncMode    INTEGER,
    ipsecIKETmplPfsGroup   INTEGER,
    ipsecIKETmplEncV2      DisplayString,
    ipsecIKETmplAuthV2     DisplayString,
    ipsecIKETmplAH         INTEGER,
    ipsecIKETmplLtV2       DisplayString,
    ipsecIKETmplLtKb       DisplayString
    }

    ipsecIKETmplIndex OBJECT-TYPE
        SYNTAX  INTEGER (0..256)
        ACCESS  read-only
        STATUS  mandatory
        DESCRIPTION
            "This object contains the index of the table being a
            unique value for each IKE templtes. Its value ranges 
            between 1 and the value of ipsecIKETmplNumber."
        ::= { ipsecIKETmplEntry 1 }
            
    ipsecIKETmplName OBJECT-TYPE
        SYNTAX  DisplayString (SIZE (1..16))
        ACCESS  read-write
        STATUS  mandatory
        DESCRIPTION
            "IKE templates name."
        ::= { ipsecIKETmplEntry 2 }

    ipsecIKETmplModes OBJECT-TYPE
        SYNTAX  DisplayString (SIZE (1..128))
        ACCESS  read-write
        STATUS  mandatory
        DESCRIPTION
            "IKE templates neogotiation modes - multi-choice of
            MAIN and AGGRESSIVE."
        ::= { ipsecIKETmplEntry 3 }

    ipsecIKETmplDhGroup OBJECT-TYPE
        SYNTAX  INTEGER {
        modp768(1),
        modp1024(2),
        modp1536(3),
        modp2048(4),
        modp3072(5),
        modp4096(6),
        modp6144(7),
        modp8192(8) }
        ACCESS  read-write
        STATUS  mandatory
        DESCRIPTION
            "This parameter specifies the Diffie-Hellman group of the 
            Phase 1 for the IKE template ."
        ::= { ipsecIKETmplEntry 4 }

    ipsecIKETmplEncV1 OBJECT-TYPE
        SYNTAX  INTEGER {
        des(0),
        tripledes(1),
        aes(2),
        cast128(3) }
        ACCESS  read-write
        STATUS  mandatory
        DESCRIPTION
            "This parameter specifies the encryption algorithm of the 
            Phase 1 for the IKE template."
        ::= { ipsecIKETmplEntry 5 }

    ipsecIKETmplAuthV1 OBJECT-TYPE
        SYNTAX  INTEGER {
        md5(0),
        sha1(1),
        sha256(2),
        sha384(3),
        sha512(4) }
        ACCESS  read-write
        STATUS  mandatory
        DESCRIPTION
            "This parameter specifies the Hash algorithm of the 
            Phase 1 for the IKE template."
        ::= { ipsecIKETmplEntry 6 }

    ipsecIKETmplLtV1 OBJECT-TYPE
        SYNTAX  DisplayString (SIZE (1..10))
        ACCESS  read-write
        STATUS  mandatory
        DESCRIPTION
            "This parameter specifies the lifetime of the 
            Phase 1 for the IKE template."
        ::= { ipsecIKETmplEntry 7 }

    ipsecIKETmplEncMode OBJECT-TYPE
        SYNTAX  INTEGER { transport(0) }
        ACCESS  read-write
        STATUS  mandatory
        DESCRIPTION
            "This parameter specifies the encapsulation type of the 
            Phase 2 for the IKE template."
        ::= { ipsecIKETmplEntry 8 }

    ipsecIKETmplPfsGroup OBJECT-TYPE
        SYNTAX  INTEGER {
        nopfs(0),
        modp768(1),
        modp1024(2),
        modp1536(3),
        modp2048(4),
        modp3072(5),
        modp4096(6),
        modp6144(7),
        modp8192(8) }
        ACCESS  read-write
        STATUS  mandatory
        DESCRIPTION
            "This parameter specifies the Diffie-Hellman group of the 
            Phase 2 for the IKE template."
        ::= { ipsecIKETmplEntry 9 }

    ipsecIKETmplEncV2 OBJECT-TYPE
        SYNTAX  DisplayString (SIZE (1..128))
        ACCESS  read-write
        STATUS  mandatory
        DESCRIPTION
            "This parameter specifies the encryption algorithms of the 
            Phase 2 for the IKE template. - multi-choice of
            3des 
            des
            aes 
            cast-128
            des64
            des32
            rc5
            rc4
            idea
            3idea
            or none."
        ::= { ipsecIKETmplEntry 10 }

    ipsecIKETmplAuthV2 OBJECT-TYPE
        SYNTAX  DisplayString (SIZE (1..128))
        ACCESS  read-write
        STATUS  mandatory
        DESCRIPTION
            "This parameter specifies the Authentication algorithms of the 
            Phase 2 for the IKE template. - multi-choice of
            md5
            sha1
            sha256
            sha384
            sha512
            des
            3des
            des64
            des32
            none."
        ::= { ipsecIKETmplEntry 11 }

    ipsecIKETmplAH  OBJECT-TYPE
        SYNTAX  INTEGER { disabled(0), enabled(1) }
        ACCESS  read-write
        STATUS  mandatory
        DESCRIPTION
            "This parameter specifies to use the AH protocol	 
            of the IPsec SA template or not."
        ::= { ipsecIKETmplEntry 12 }

    ipsecIKETmplLtV2 OBJECT-TYPE
        SYNTAX  DisplayString (SIZE (1..10))
        ACCESS  read-write
        STATUS  mandatory
        DESCRIPTION
            "This parameter specifies the lifetime of the 
            Phase 2 for the IKE template."
        ::= { ipsecIKETmplEntry 13 }

    ipsecIKETmplLtKb OBJECT-TYPE
        SYNTAX  DisplayString (SIZE (1..10))
        ACCESS  read-write
        STATUS  mandatory
        DESCRIPTION
            "This parameter specifies the lifetime (kbyte) of the 
            Phase 2 for the IKE template."
        ::= { ipsecIKETmplEntry 14 }

    -- the sehUtn group
    
    -- This group specifies SEH USB port specific parameters for myUTN.


    utnPortNumber OBJECT-TYPE
        SYNTAX  INTEGER
        ACCESS  read-only
        STATUS  mandatory
        DESCRIPTION
            "Number of entries in the  UTN port table."
        ::= { sehUtn 1 }
    
    utnPortTable OBJECT-TYPE
        SYNTAX  SEQUENCE OF UtnPortEntry
        ACCESS  not-accessible
        STATUS  mandatory
        DESCRIPTION
            "This object specifies a table containing UTN port descriptions."
        ::= { sehUtn 2 }

    utnPortEntry OBJECT-TYPE
        SYNTAX  UtnPortEntry
        ACCESS  not-accessible
        STATUS  mandatory
        DESCRIPTION
            "Entry of UTN port table."
        INDEX   { utnPortIndex }
        ::= { utnPortTable 1 }
    
    UtnPortEntry ::= SEQUENCE {
        utnPortIndex     INTEGER,
        utnPortSecure    INTEGER,
        utnPortPoSwitch  INTEGER,
        utnPortPoOffDura INTEGER,
        utnPortAccCtrl   INTEGER,
        utnPortKeyVal    DisplayString,
        utnPortProdId    DisplayString,
        utnPortVendId    DisplayString,
        utnPortIp4Vlan   INTEGER,
        utnPortTag       DisplayString,
        utnPortComp      INTEGER,
        utnPortUsbManu   DisplayString,
        utnPortUsbProd   DisplayString,
        utnPortUsbVendId DisplayString,
        utnPortUsbProdId DisplayString,
        utnPortUsbSer    DisplayString,
        utnPortUsbOwn    DisplayString,
        utnPortSlot      INTEGER }

    utnPortIndex OBJECT-TYPE
        SYNTAX  INTEGER (0..256)
        ACCESS  not-accessible
        STATUS  mandatory
        DESCRIPTION
            "This object contains the index of the table being a
            unique value for each UTN port entry."
        ::= { utnPortEntry 1 }
    
    utnPortSecure OBJECT-TYPE
        SYNTAX  INTEGER { disabled(0), enabled(1) }
        ACCESS  read-write
        STATUS  mandatory
        DESCRIPTION
            "This parameter enables/disables the myUTN USB encryption."
        ::= { utnPortEntry 2 }

    utnPortPoSwitch OBJECT-TYPE
        SYNTAX  INTEGER { disabled(0), enabled(1) }
        ACCESS  read-write
        STATUS  mandatory
        DESCRIPTION
            "This parameter enables/disables the myUTN USB power cycle switch."
        ::= { utnPortEntry 3 }

    utnPortPoOffDura OBJECT-TYPE
        SYNTAX  INTEGER (0..100)
        ACCESS  read-write
        STATUS  mandatory
        DESCRIPTION
            "This parameter specifies the UTN USB port power off duration in 1/10 seconds."
        ::= { utnPortEntry 4 }

    utnPortAccCtrl OBJECT-TYPE
        SYNTAX  INTEGER {
        none(1),
        key(2),
        ids(3),
        keyids(4) }
        ACCESS  read-write
        STATUS  mandatory
        DESCRIPTION
            "This parameter specifies the UTN USB port power off duration in 1/100 seconds."
        ::= { utnPortEntry 5 }

    utnPortKeyVal OBJECT-TYPE
        SYNTAX  DisplayString (SIZE (0..64))
        ACCESS  read-write
        STATUS  mandatory
        DESCRIPTION
            "This parameter specifies the UTN USB port access key."
        ::= { utnPortEntry 6 }

    utnPortProdId OBJECT-TYPE
        SYNTAX  DisplayString (SIZE (0..7))
        ACCESS  read-write
        STATUS  mandatory
        DESCRIPTION
            "This parameter specifies the UTN USB port product id for access control."
        ::= { utnPortEntry 7 }

    utnPortVendId OBJECT-TYPE
        SYNTAX  DisplayString (SIZE (0..7))
        ACCESS  read-write
        STATUS  mandatory
        DESCRIPTION
            "This parameter specifies the UTN USB port vendor id for access control."
        ::= { utnPortEntry 8 }

    utnPortIp4Vlan OBJECT-TYPE
        SYNTAX  INTEGER (0..21)
        ACCESS  read-write
        STATUS  mandatory
        DESCRIPTION
            "This parameter specifies the UTN USB port to VLan binding.
             '0' means any VLan is aloud; a value higher than the physical 
             USB port count means no VLan is aloud."
        ::= { utnPortEntry 9 }

    utnPortTag OBJECT-TYPE
        SYNTAX  DisplayString (SIZE (0..32))
        ACCESS  read-write
        STATUS  mandatory
        DESCRIPTION
            "This parameter specifies the UTN USB port short description string."
        ::= { utnPortEntry 10 }

    utnPortComp OBJECT-TYPE
        SYNTAX  INTEGER { disabled(0), enabled(1) }
        ACCESS  read-write
        STATUS  mandatory
        DESCRIPTION
            "This parameter enables the UTN data compression for this port."
        ::= { utnPortEntry 11 }

    utnPortUsbManu OBJECT-TYPE
        SYNTAX  DisplayString (SIZE (0..64))
        ACCESS  read-only
        STATUS  mandatory
        DESCRIPTION
            "This parameter specifies the UTN USB connected device manufacturer string"
        ::= { utnPortEntry 21 }

    utnPortUsbProd OBJECT-TYPE
        SYNTAX  DisplayString (SIZE (0..64))
        ACCESS  read-only
        STATUS  mandatory
        DESCRIPTION
            "This parameter specifies the UTN USB connected device product string"
        ::= { utnPortEntry 22 }

    utnPortUsbVendId OBJECT-TYPE
        SYNTAX  DisplayString (SIZE (0..7))
        ACCESS  read-only
        STATUS  mandatory
        DESCRIPTION
            "This parameter specifies the UTN USB connected device vendor id"
        ::= { utnPortEntry 23 }

    utnPortUsbProdId OBJECT-TYPE
        SYNTAX  DisplayString (SIZE (0..7))
        ACCESS  read-only
        STATUS  mandatory
        DESCRIPTION
            "This parameter specifies the UTN USB connected device product id"
        ::= { utnPortEntry 24 }

    utnPortUsbSer OBJECT-TYPE
        SYNTAX  DisplayString (SIZE (0..64))
        ACCESS  read-only
        STATUS  mandatory
        DESCRIPTION
            "This parameter specifies the UTN USB connected device serial string"
        ::= { utnPortEntry 25 }

    utnPortUsbOwn OBJECT-TYPE
        SYNTAX  DisplayString (SIZE (0..64))
        ACCESS  read-only
        STATUS  mandatory
        DESCRIPTION
            "This parameter specifies the UTN USB device connection status"
        ::= { utnPortEntry 26 }

    utnPortSlot OBJECT-TYPE
        SYNTAX  INTEGER (0..20)
        ACCESS  read-write
        STATUS  mandatory
        DESCRIPTION
            "This parameter specifies the UTN slot number the USB is attached to."
        ::= { utnPortEntry 27 }

    utnDispDef OBJECT-TYPE
        SYNTAX  DisplayString (SIZE (0..2))
        ACCESS  read-write
        STATUS  mandatory
        DESCRIPTION
            "Default 2 chars for the myUTN-800 dispay"
        ::= { sehUtn 11 }

    utnDispErVals OBJECT-TYPE
        SYNTAX  DisplayString (SIZE (0..64))
        ACCESS  read-only
        STATUS  mandatory
        DESCRIPTION
            "Current myUTN-800 dispay error value(s)"
        ::= { sehUtn 12 }

    utnBeepPwr OBJECT-TYPE
        SYNTAX  INTEGER {off(0),on(1)}
        ACCESS  read-write
        STATUS  mandatory
        DESCRIPTION
            "myTUN-800 buzzer mode, beep if only one supply works"
        ::= { sehUtn 13 }
    
    utnBeepSDc OBJECT-TYPE
        SYNTAX  INTEGER {off(0),on(1)}
        ACCESS  read-write
        STATUS  mandatory
        DESCRIPTION
            "myTUN-800 buzzer mode, beep if SDCard doesn't work"
        ::= { sehUtn 14 }

    utnHid OBJECT-TYPE
        SYNTAX  INTEGER {off(0),on(1)}
        ACCESS  read-write
        STATUS  mandatory
        DESCRIPTION
            "myTUN accept (on) or discard (off) HID devices"
        ::= { sehUtn 15 }


    -- the seh Utn/INU relay group

    utnRelayOn OBJECT-TYPE
        SYNTAX  INTEGER {off(0),on(1)}
        ACCESS  read-write
        STATUS  mandatory
        DESCRIPTION
            "switch the relay on or off if not event driven"
        ::= { sehUtn 16 }

    utnRelayFix OBJECT-TYPE
        SYNTAX  INTEGER {off(0),on(1)}
        ACCESS  read-write
        STATUS  mandatory
        DESCRIPTION
            "switch if the relay state is fixed or event dependend"
        ::= { sehUtn 17 }

    utnRelayCtrl OBJECT-TYPE
        SYNTAX  INTEGER {fix(0),event(1),state(2)}
        ACCESS  read-write
        STATUS  mandatory
        DESCRIPTION
            "replaces utnRelayFix, set wether the relay is fix or driven by event or status changes"
        ::= { sehUtn 40 }

    utnRelayEves OBJECT-TYPE
        SYNTAX  BITS {
            relayUnused0(0),
            relayEveStart(1),
            relayEveLinkDown(2),  
            relayEveLinkUp(3),  
            relayEvePwd1On(5),                              
            relayEvePwd2On(6),  
            relayEvePwd1Off(7), 
            relayEvePwd2Off(8), 
            relayEveSDIn(9),    
            relayEveSDOut(10),   
            relayEveSDErr(11),   
            relayEveU1Con(13),   
            relayEveU1Dis(14),   
            relayEveU1Act(15),   
            relayEveU1Dea(16),   
            relayEveU2Con(17),   
            relayEveU2Dis(18),   
            relayEveU2Act(19),   
            relayEveU2Dea(20) 
            }
        ACCESS  read-only
        STATUS  mandatory
        DESCRIPTION
            "bitfield represents the relay related occured events"
        ::= { sehUtn 18 }

    utnRelayRestart OBJECT-TYPE
        SYNTAX  INTEGER {off(0),warm(1)}
        ACCESS  read-write
        STATUS  mandatory
        DESCRIPTION
            "set event trigger for the relay to restart of device"
        ::= { sehUtn 21 }

    utnRelay1Pwr OBJECT-TYPE
        SYNTAX  INTEGER {off(0),pwroff(1),pwron(2)}
        ACCESS  read-write
        STATUS  mandatory
        DESCRIPTION
            "set event trigger for the relay to the first power supply"
        ::= { sehUtn 22 }

    utnRelay2Pwr OBJECT-TYPE
        SYNTAX  INTEGER {off(0),pwroff(1),pwron(2)}
        ACCESS  read-write
        STATUS  mandatory
        DESCRIPTION
            "set event trigger for the relay to the second power supply"
        ::= { sehUtn 23 }

    utnRelayNet OBJECT-TYPE
        SYNTAX  INTEGER {off(0),netoff(1),neton(2)}
        ACCESS  read-write
        STATUS  mandatory
        DESCRIPTION
            "set event trigger for the relay to the network link state"
        ::= { sehUtn 24 }

    utnRelaySDCard OBJECT-TYPE
        SYNTAX  INTEGER {off(0),sdin(1), sdout(2), sderr(3)}
        ACCESS  read-write
        STATUS  mandatory
        DESCRIPTION
            "set event trigger for the relay to the SDCard   state"
        ::= { sehUtn 25 }

    utnRelayUsbCon OBJECT-TYPE
        SYNTAX  INTEGER {off(0), any(1), port1(2), port2(3)}
        ACCESS  read-write
        STATUS  mandatory
        DESCRIPTION
            "set event trigger for the relay to the USB connect event"
        ::= { sehUtn 26 }

    utnRelayUsbDisco OBJECT-TYPE
        SYNTAX  INTEGER {off(0), any(1), port1(2), port2(3)}
        ACCESS  read-write
        STATUS  mandatory
        DESCRIPTION
            "set event trigger for the relay to the USB disconnect event"
        ::= { sehUtn 27 }

    utnRelayUsbActivate OBJECT-TYPE
        SYNTAX  INTEGER {off(0), any(1), port1(2), port2(3)}
        ACCESS  read-write
        STATUS  mandatory
        DESCRIPTION
            "set event trigger for the relay to the USB activate event"
        ::= { sehUtn 28 }

    utnRelayUsbDeActivate OBJECT-TYPE
        SYNTAX  INTEGER {off(0), any(1), port1(2), port2(3)}
        ACCESS  read-write
        STATUS  mandatory
        DESCRIPTION
            "set event trigger for the relay to the USB deactivate event"
        ::= { sehUtn 29 }

    utnRelayStateNet OBJECT-TYPE
        SYNTAX  INTEGER {off(0),netoff(1),neton(2)}
        ACCESS  read-write
        STATUS  mandatory
        DESCRIPTION
            "set state trigger for the relay to the network link state"
        ::= { sehUtn 44 }

    utnRelayStateUsbCon OBJECT-TYPE
        SYNTAX  INTEGER {off(0), any(1), port1(2), port2(3)}
        ACCESS  read-write
        STATUS  mandatory
        DESCRIPTION
            "set state trigger for the relay to the USB connect event"
        ::= { sehUtn 46 }


    utnRelayStateUsbDisco OBJECT-TYPE
        SYNTAX  INTEGER {off(0), any(1), port1(2), port2(3)}
        ACCESS  read-write
        STATUS  mandatory
        DESCRIPTION
            "set state trigger for the relay to the USB disconnect event"
        ::= { sehUtn 47 }

    
    utnRelayStateUsbActivate OBJECT-TYPE
        SYNTAX  INTEGER {off(0), any(1), port1(2), port2(3)}
        ACCESS  read-write
        STATUS  mandatory
        DESCRIPTION
            "switch how the relay state dependends on the USB activate event"
        ::= { sehUtn 48 }


    utnRelayStateUsbDeActivate OBJECT-TYPE
        SYNTAX  INTEGER {off(0), any(1), port1(2), port2(3)}
        ACCESS  read-write
        STATUS  mandatory
        DESCRIPTION
            "switch how the relay state dependends on the USB deactivate event"
        ::= { sehUtn 49 }

    -- the sehUtnEvent group
    
    -- This group specifies SEH UTN specific events used e.g by traps.

    utnEventType OBJECT-TYPE
        SYNTAX  INTEGER {
        misc(1),
        error(2),
        usbAattached(3), 
        usbDetached(4),
        connect(5), 
        disconnect(6),
        cardreader(7),
        usbConnect(8),
        usbDisconnect(9),
        printjob(10),
        powersupply(11),
        sdcardPlugIn(12),
        sdcardPlugOut(13),
        sdcardMissing(14),
        sdcardUnusable(15),
        sdcardRdOnly(16),
        link(17),
        deviceHeat(18),
        usbPowerConsumption(19)}
        ACCESS  not-accessible
        STATUS  mandatory
        DESCRIPTION
            "This is the type of a utn event"
        ::= { sehUtnEvent 1 }

    utnEventPort OBJECT-TYPE
        SYNTAX  INTEGER
        ACCESS  not-accessible
        STATUS  mandatory
        DESCRIPTION
            "This is the event related port number starting by 1."
        ::= { sehUtnEvent 2 }

    utnEventMsg OBJECT-TYPE
        SYNTAX  DisplayString (SIZE (0..64))
        ACCESS  not-accessible
        STATUS  mandatory
        DESCRIPTION
            "This is a readable event message."
        ::= { sehUtnEvent 3 }

    utnEventManu OBJECT-TYPE
        SYNTAX  DisplayString (SIZE (0..64))
        ACCESS  not-accessible
        STATUS  mandatory
        DESCRIPTION
            "This is usb manufacturer string for a recently  occurred event."
        ::= { sehUtnEvent 4 }

    utnEventManuId OBJECT-TYPE
        SYNTAX  INTEGER
        ACCESS  not-accessible
        STATUS  mandatory
        DESCRIPTION
            "This is the event related manufacturer id"
        ::= { sehUtnEvent 5 }

    utnEventProd OBJECT-TYPE
        SYNTAX  DisplayString (SIZE (0..64))
        ACCESS  not-accessible
        STATUS  mandatory
        DESCRIPTION
            "This is usb product string for a recently  occurred event."
        ::= { sehUtnEvent 6 }

    utnEventProdId OBJECT-TYPE
        SYNTAX  INTEGER
        ACCESS  not-accessible
        STATUS  mandatory
        DESCRIPTION
            "This is the event related product id"
        ::= { sehUtnEvent 7 }

    utnEventSerial OBJECT-TYPE
        SYNTAX  DisplayString (SIZE (0..64))
        ACCESS  not-accessible
        STATUS  mandatory
        DESCRIPTION
            "This is usb serial string for a recently  occurred event."
        ::= { sehUtnEvent 8 }

    tniEventCard OBJECT-TYPE
        SYNTAX  DisplayString (SIZE (0..512))
        ACCESS  not-accessible
        STATUS  mandatory
        DESCRIPTION
            "This is latest seen nfc card data."
        ::= { sehUtnEvent 9 }


    -- the sehSND group
    
    -- This group specifies SEH SND user specific parameters for mySND.

    sndUserNumber OBJECT-TYPE
        SYNTAX  INTEGER
        ACCESS  read-only
        STATUS  mandatory
        DESCRIPTION
            "Number of entries in the  SND user table."
        ::= { sehSndUser 1 }
    
    sndUserTable OBJECT-TYPE
        SYNTAX  SEQUENCE OF SndUserEntry
        ACCESS  not-accessible
        STATUS  mandatory
        DESCRIPTION
            "This object specifies a table containing SND user descriptions."
        ::= { sehSndUser 2 }

    sndUserEntry OBJECT-TYPE
        SYNTAX  SndUserEntry
        ACCESS  not-accessible
        STATUS  mandatory
        DESCRIPTION
            "Entry of SND user table."
        INDEX   { sndUserIndex }
        ::= { sndUserTable 1 }
    
    SndUserEntry ::= SEQUENCE {
        sndUserIndex     INTEGER,
        sndUserActive    INTEGER,
        sndUserName      DisplayString,
        sndUserPwd       DisplayString,
        sndUserEmail     DisplayString,
        sndUserFFilter   INTEGER,
        sndUserRAdm      INTEGER,
        sndUserRDLoad    INTEGER,
        sndUserRSend     INTEGER,
        sndUserRTogg     INTEGER,
        sndUserRWrt      INTEGER }

    sndUserIndex OBJECT-TYPE
        SYNTAX  INTEGER (0..256)
        ACCESS  not-accessible
        STATUS  mandatory
        DESCRIPTION
            "This object contains the index of the table being a
            unique value for each SND user entry."
        ::= { sndUserEntry 1 }

    sndUserActive OBJECT-TYPE
        SYNTAX  INTEGER { inactive(0), active(1) }
        ACCESS  read-write
        STATUS  mandatory
        DESCRIPTION
            "This parameter enables/disables this mySND user account."
        ::= { sndUserEntry 2 }

    sndUserName OBJECT-TYPE
        SYNTAX  DisplayString (SIZE (0..32))
        ACCESS  read-write
        STATUS  mandatory
        DESCRIPTION
            "This is the SND login user name."
        ::= { sndUserEntry 3 }

    sndUserPwd OBJECT-TYPE
        SYNTAX  DisplayString (SIZE (0..32))
        ACCESS  read-write
        STATUS  mandatory
        DESCRIPTION
            "This is the SND login user password."
        ::= { sndUserEntry 4 }

    sndUserEmail OBJECT-TYPE
        SYNTAX  DisplayString (SIZE (0..32))
        ACCESS  read-write
        STATUS  mandatory
        DESCRIPTION
            "This is the SND user email address."
        ::= { sndUserEntry 5 }

    sndUserFFilter OBJECT-TYPE
        SYNTAX  INTEGER (0..5)
        ACCESS  read-write
        STATUS  mandatory
        DESCRIPTION
            "This is the SND user related file filter referenced by his index."
        ::= { sndUserEntry 6 }

    sndUserRAdm OBJECT-TYPE
        SYNTAX  INTEGER { off(0), on(1) }
        ACCESS  read-write
        STATUS  mandatory
        DESCRIPTION
            "This parameter enables the user to administrate the device."
        ::= { sndUserEntry 7 }

    sndUserRDLoad OBJECT-TYPE
        SYNTAX  INTEGER { off(0), on(1) }
        ACCESS  read-write
        STATUS  mandatory
        DESCRIPTION
            "This parameter switches the user right to download files from the device."
        ::= { sndUserEntry 8 }

    sndUserRSend OBJECT-TYPE
        SYNTAX  INTEGER { off(0), on(1) }
        ACCESS  read-write
        STATUS  mandatory
        DESCRIPTION
            "This parameter switches the user right to send files by email from this device."
        ::= { sndUserEntry 9 }

    sndUserRTogg OBJECT-TYPE
        SYNTAX  INTEGER { off(0), on(1) }
        ACCESS  read-write
        STATUS  mandatory
        DESCRIPTION
            "This parameter switches the user right to toggle files archive flags ."
        ::= { sndUserEntry 10 }

    sndUserRWrt OBJECT-TYPE
        SYNTAX  INTEGER { off(0), on(1) }
        ACCESS  read-write
        STATUS  mandatory
        DESCRIPTION
            "This parameter gives the user write access to the connected media."
        ::= { sndUserEntry 11 }

    -- This group specifies SEH SND file send specific parameters for mySND.

    sndSendMaxFiles OBJECT-TYPE
        SYNTAX  INTEGER (0..100)
        ACCESS  read-write
        STATUS  mandatory
        DESCRIPTION
            "This is a max number of files attached with outgoing emails."
        ::= { sehSndSender 1 }
    
    sndSendMaxKb OBJECT-TYPE
        SYNTAX  INTEGER (100..10000)
        ACCESS  read-write
        STATUS  mandatory
        DESCRIPTION
            "This is a size limit in kb for outgoing emails."
        ::= { sehSndSender 2 }

    sndSenderPDMedia OBJECT-TYPE
        SYNTAX  INTEGER { off(0), on(1) }
        ACCESS  read-write
        STATUS  mandatory
        DESCRIPTION
            "This parameter switches the auto send functionality for the PenDrive media."
        ::= { sehSndSender 3 }

    sndSenderPDDir OBJECT-TYPE
        SYNTAX  DisplayString (SIZE (0..32))
        ACCESS  read-write
        STATUS  mandatory
        DESCRIPTION
            "This is the SND autosend PenDrive directory."
        ::= { sehSndSender 4 }

    sndSenderPDExt OBJECT-TYPE
        SYNTAX  DisplayString (SIZE (0..32))
        ACCESS  read-write
        STATUS  mandatory
        DESCRIPTION
            "This is the SND autosend PenDrive file extension filter."
        ::= { sehSndSender 5 }

    sndSenderPDaBit OBJECT-TYPE
    --    SYNTAX  INTEGER {none(0),archBit(1),delete(2)} 
        SYNTAX  INTEGER {none(0),archBit(1)} 
        ACCESS  read-write
        STATUS  mandatory
        DESCRIPTION
            "This parameter defines the action for e file after sucessfully sending it."
        ::= { sehSndSender 6 }
    
    sndSenderPDRcpNum OBJECT-TYPE
        SYNTAX  INTEGER
        ACCESS  read-only
        STATUS  mandatory
        DESCRIPTION
            "Number of email recipients for PenDrive auto send."
        ::= { sehSndSender 7 }
    
   sndSenderPDRcpTable OBJECT-TYPE
        SYNTAX  SEQUENCE OF SndSenderPDRcpEntry
        ACCESS  not-accessible
        STATUS  mandatory
        DESCRIPTION
            "This object specifies the table of SND PenDrive email recipients."
        ::= { sehSndSender 8 }

    sndSenderPDRcpEntry OBJECT-TYPE
        SYNTAX  SndSenderPDRcpEntry
        ACCESS  not-accessible
        STATUS  mandatory
        DESCRIPTION
            "Entry of SND user table."
        INDEX   { sndPDRcpIndex }
        ::= { sndSenderPDRcpTable 1 }
    
    SndSenderPDRcpEntry ::= SEQUENCE {
        sndPDRcpIndex INTEGER,
        sndPDRcpEmail DisplayString }

    sndPDRcpIndex OBJECT-TYPE
        SYNTAX  INTEGER (0..256)
        ACCESS  not-accessible
        STATUS  mandatory
        DESCRIPTION
            "This object contains the index of the table being a
            unique value for each SND PenDrive recipient entry."
        ::= { sndSenderPDRcpEntry 1 }

    sndPDRcpEmail OBJECT-TYPE
        SYNTAX  DisplayString (SIZE (0..32))
        ACCESS  read-write
        STATUS  mandatory
        DESCRIPTION
            "This is the SND PendDrive recipients email address."
        ::= { sndSenderPDRcpEntry 2 }

    sndSenderSDActive OBJECT-TYPE
        SYNTAX  INTEGER {inactive(0),active(1)} 
        ACCESS  read-write
        STATUS  mandatory
        DESCRIPTION
            "This parameter switches the following SDRcp email off/on."
        ::= { sehSndSender 20 }
    
    sndSenderSDRcp OBJECT-TYPE
        SYNTAX  DisplayString (SIZE (0..32))
        ACCESS  read-write
        STATUS  mandatory
        DESCRIPTION
            "This is the SND SDCard recipient email address for any card IDs."
        ::= { sehSndSender 21 }

    sndSenderSDNum OBJECT-TYPE
        SYNTAX  INTEGER
        ACCESS  read-only
        STATUS  mandatory
        DESCRIPTION
            "Number of SndSender table entries."
        ::= { sehSndSender 30 }
    
   sndSenderSDTable OBJECT-TYPE
        SYNTAX  SEQUENCE OF SndSenderSDEntry
        ACCESS  not-accessible
        STATUS  mandatory
        DESCRIPTION
            "This object specifies the table of SND SDCard specific parameters."
        ::= { sehSndSender 31 }

    sndSenderSDEntry OBJECT-TYPE
        SYNTAX  SndSenderSDEntry
        ACCESS  not-accessible
        STATUS  mandatory
        DESCRIPTION
            "Entry of SND SDCard table."
        INDEX   { sndSDIndex }
        ::= { sndSenderSDTable 1 }
    
    SndSenderSDEntry ::= SEQUENCE {
        sndSDIndex    INTEGER,
        sndSDMedia    INTEGER,
        sndSDDir      DisplayString,
        sndSDExt      DisplayString,
        sndSDaBit     INTEGER }

    sndSDIndex OBJECT-TYPE
        SYNTAX  INTEGER (0..256)
        ACCESS  not-accessible
        STATUS  mandatory
        DESCRIPTION
            "This object contains the index of the table being a
            unique value for each SND SDCard entry."
        ::= { sndSenderSDEntry 1 }

    sndSDMedia OBJECT-TYPE
        SYNTAX  INTEGER { off(0), on(1) }
        ACCESS  read-write
        STATUS  mandatory
        DESCRIPTION
            "This parameter switches the auto send functionality for the SDCard media."
        ::= { sndSenderSDEntry 2 }

    sndSDDir OBJECT-TYPE
        SYNTAX  DisplayString (SIZE (0..64))
        ACCESS  read-write
        STATUS  mandatory
        DESCRIPTION
            "This is the SND PendDrive recipients email address."
        ::= { sndSenderSDEntry 3 }

    sndSDExt OBJECT-TYPE
        SYNTAX  DisplayString (SIZE (0..32))
        ACCESS  read-write
        STATUS  mandatory
        DESCRIPTION
            "This is the SND autosend SDCard file extension filter."
        ::= { sndSenderSDEntry 4 }

    sndSDaBit OBJECT-TYPE
    --    SYNTAX  INTEGER {none(0),archBit(1),delete(2)} 
        SYNTAX  INTEGER {none(0),archBit(1)} 
        ACCESS  read-write
        STATUS  mandatory
        DESCRIPTION
            "This parameter defines the action for file on a SDCard after sucessfully sending it."
        ::= { sndSenderSDEntry 5 }

    -- This group specifies SEH SND file filter for mySND.

    sndFFilterNum OBJECT-TYPE
        SYNTAX  INTEGER
        ACCESS  read-only
        STATUS  mandatory
        DESCRIPTION
            "Number of email recipients for PenDrive auto send."
        ::= { sehSndFFilter 1 }
    
   sndFFilterTable OBJECT-TYPE
        SYNTAX  SEQUENCE OF SndFFilterEntry
        ACCESS  not-accessible
        STATUS  mandatory
        DESCRIPTION
            "This object specifies the table of SND PenDrive email recipients."
        ::= { sehSndFFilter 2 }

    sndFFilterEntry OBJECT-TYPE
        SYNTAX  SndFFilterEntry
        ACCESS  not-accessible
        STATUS  mandatory
        DESCRIPTION
            "Entry of SND user table."
        INDEX   { sndFFilterIndex }
        ::= { sndFFilterTable 1 }
    
    SndFFilterEntry ::= SEQUENCE {
        sndFFilterIndex INTEGER,
        sndFFilterName  DisplayString,
        sndFFilter      DisplayString }

    sndFFilterIndex OBJECT-TYPE
        SYNTAX  INTEGER (0..256)
        ACCESS  not-accessible
        STATUS  mandatory
        DESCRIPTION
            "This object contains the index of the table being a
            unique value for each SND PenDrive recipient entry."
        ::= { sndFFilterEntry 1 }

    sndFFilterName OBJECT-TYPE
        SYNTAX  DisplayString (SIZE (0..32))
        ACCESS  read-write
        STATUS  mandatory
        DESCRIPTION
            "This is the SND file filter name."
        ::= { sndFFilterEntry 2 }

    sndFFilter OBJECT-TYPE
        SYNTAX  DisplayString (SIZE (0..64))
        ACCESS  read-write
        STATUS  mandatory
        DESCRIPTION
            "This is the SND file filter, a comma separated list of allowed extensions."
        ::= { sndFFilterEntry 3 }


    -- This group specifies SEH SND SDCard parameters for mySND.

    sndSDCardNum OBJECT-TYPE
        SYNTAX  INTEGER
        ACCESS  read-only
        STATUS  mandatory
        DESCRIPTION
            "Number of SDCard parameter sets."
        ::= { sehSndSDCard 1 }
    
   sndSDCardTable OBJECT-TYPE
        SYNTAX  SEQUENCE OF SndSDCardEntry
        ACCESS  not-accessible
        STATUS  mandatory
        DESCRIPTION
            "This object specifies the table of SND SDCard parameters."
        ::= { sehSndSDCard 2 }

    sndSDCardEntry OBJECT-TYPE
        SYNTAX  SndSDCardEntry
        ACCESS  not-accessible
        STATUS  mandatory
        DESCRIPTION
            "Entry of SND SCard table."
        INDEX   { sndSDCardIndex }
        ::= { sndSDCardTable 1 }
    
    SndSDCardEntry ::= SEQUENCE {
        sndSDCardIndex INTEGER,
        sndSDCardCid   DisplayString,
        sndSDCardName  DisplayString,
        sndSDCardUList DisplayString,
        sndSDCardARcp  DisplayString }

    sndSDCardIndex OBJECT-TYPE
        SYNTAX  INTEGER (0..256)
        ACCESS  not-accessible
        STATUS  mandatory
        DESCRIPTION
            "This object contains the index of the table being a
            unique value for each SDCard entry."
        ::= { sndSDCardEntry 1 }

    sndSDCardCid OBJECT-TYPE
        SYNTAX  DisplayString (SIZE (0..33))
        ACCESS  read-only
        STATUS  mandatory
        DESCRIPTION
            "This is the SND stored SDCard CID as 32byte hex string plus zero C-terminator."
        ::= { sndSDCardEntry 2 }

    sndSDCardName OBJECT-TYPE
        SYNTAX  DisplayString (SIZE (0..32))
        ACCESS  read-write
        STATUS  mandatory
        DESCRIPTION
            "This is the SND SDCard name."
        ::= { sndSDCardEntry 3 }

    sndSDCardUList OBJECT-TYPE
        SYNTAX  DisplayString (SIZE (0..16))
        ACCESS  read-write
        STATUS  mandatory
        DESCRIPTION
            "This is the SDCrad user list, a comma separated list of user indices."
        ::= { sndSDCardEntry 4 }

    sndSDCardARcp OBJECT-TYPE
        SYNTAX  DisplayString (SIZE (0..32))
        ACCESS  read-write
        STATUS  mandatory
        DESCRIPTION
            "This is the SND SDCard auto send recipients email address."
        ::= { sndSDCardEntry 5 }

    sndPDPort OBJECT-TYPE
        SYNTAX  INTEGER { off(0), on(1) }
        ACCESS  read-write
        STATUS  mandatory
        DESCRIPTION
            "This parameter switches SND USB PenDrive port off or on"
        ::= { sehSnd 10 }

    -- the sehtpr group
    
    -- This group specifies the Personal Printing Services parameters of SEH TPR.
        
    pps OBJECT-TYPE
        SYNTAX  INTEGER { off(0), on(1) }
        ACCESS  read-write
        STATUS  mandatory
        DESCRIPTION
            "This parameter switches PPS off or on."
        ::= { sehPPS 1 }
  

    ppsPIN OBJECT-TYPE
        SYNTAX  DisplayString (SIZE (0..32))
        ACCESS  read-write
        STATUS  mandatory
        DESCRIPTION
            "This is the PPS User-PIN."
        ::= { sehPPS 2 }

    ppsPrtId OBJECT-TYPE
        SYNTAX  DisplayString (SIZE (0..64))
        ACCESS  read-write
        STATUS  mandatory
        DESCRIPTION
            "This is the Personal Printing printer ID."
        ::= { sehPPS 3 }

    ppsDelete OBJECT-TYPE
        SYNTAX  INTEGER { none(0), server(1), tpr(2) }
        ACCESS  read-write
        STATUS  mandatory
        DESCRIPTION
            "This parameter selects who has finally to delete a print job."
        ::= { sehPPS 4 }

    ppsDelelteDelay OBJECT-TYPE
         SYNTAX  INTEGER (0..60)
         ACCESS  read-write
         STATUS  mandatory
         DESCRIPTION
            "This is the delay in seconds for the tpr to sends the delete job command after completition."
         ::= { sehPPS 5 }

    ppsSingle OBJECT-TYPE
        SYNTAX  INTEGER { off(0), on(1) }
        ACCESS  read-write
        STATUS  mandatory
        DESCRIPTION
            "This parameter switches the feature one job per card on or off."
        ::= { sehPPS 6 }
  
    ppsBeep OBJECT-TYPE
        SYNTAX  INTEGER { off(0), on(1) }
        ACCESS  read-write
        STATUS  mandatory
        DESCRIPTION
            "This parameter switches TPR beeper on or off."
        ::= { sehPPS 7 }

    ppsUSRForm OBJECT-TYPE
        SYNTAX  INTEGER { raw(0), formatted(1) }
        ACCESS  read-write
        STATUS  mandatory
        DESCRIPTION
            "This parameter decides which type of USR hex value format is used."
        ::= { sehPPS 8 }

    ppsPWD OBJECT-TYPE
        SYNTAX  DisplayString (SIZE (0..32))
        ACCESS  read-write
        STATUS  mandatory
        DESCRIPTION
            "This is the PPS user password."
        ::= { sehPPS 9 }

    ppsPort OBJECT-TYPE
        SYNTAX  INTEGER (0..65535)
        ACCESS  read-write
        STATUS  mandatory
        DESCRIPTION
            "This parameter specifies the local PPS port."
        ::= { sehPPS 10 }

    ppsSSL OBJECT-TYPE
        SYNTAX  INTEGER { off(0), on(1) }
        ACCESS  read-write
        STATUS  mandatory
        DESCRIPTION
            "This parameter switches SSL for the PPS server TCP connection on or off."
        ::= { sehPPS 11 }

    ppsVerify OBJECT-TYPE
        SYNTAX  INTEGER { off(0), on(1) }
        ACCESS  read-write
        STATUS  mandatory
        DESCRIPTION
            "This parameter switches the ssl verification of the PPS server on or off."
        ::= { sehPPS 12 }

     ppsServer OBJECT-TYPE
        SYNTAX  DisplayString (SIZE (0..64))
        ACCESS  read-write
        STATUS  mandatory
        DESCRIPTION
            "This is the main PPS server name."
        ::= { sehPPS 20 }
 
     ppsServerAlt OBJECT-TYPE
        SYNTAX  DisplayString (SIZE (0..64))
        ACCESS  read-write
        STATUS  mandatory
        DESCRIPTION
            "This is the alternativ PPS server name."
        ::= { sehPPS 21 }
 
    -- This group specifies the new design of mmore than one PPS servers.

     ppsNumber OBJECT-TYPE
        SYNTAX  INTEGER
        ACCESS  read-only
        STATUS  mandatory
        DESCRIPTION
            "This parameter specifies the number of available PPS server gateway entries"
        ::= { sehPPS 30 }
    
     ppsTable OBJECT-TYPE
        SYNTAX  SEQUENCE OF PPSEntry
        ACCESS  not-accessible
        STATUS  mandatory
        DESCRIPTION
            "This object specifies a table containing a list of ThinPrint gateway
            entries. The number of entries is given by the value of tpgNumber."
        ::= { sehPPS 31 }

     ppsEntry OBJECT-TYPE
        SYNTAX  PPSEntry
        ACCESS  not-accessible
        STATUS  mandatory
        DESCRIPTION
            "Parameters regarding to PPS server entry."
        INDEX   { pps-Index }
        ::= { ppsTable 1 }
    
    PPSEntry ::= SEQUENCE {
    pps-Index        INTEGER,
    pps-On           INTEGER,
    pps-Server       DisplayString,
    pps-PIN          DisplayString,
    pps-PWD          DisplayString,
    pps-Port         INTEGER,
    pps-SSL          INTEGER,
    pps-Verify       INTEGER,
    pps-PrtId        DisplayString,
    pps-Delete       INTEGER,
    pps-DelelteDelay INTEGER
    }
    
    pps-Index OBJECT-TYPE
        SYNTAX  INTEGER (0..256)
        ACCESS  read-only
        STATUS  mandatory
        DESCRIPTION
            "This object contains the index of the table being a
            unique value for each PPS server. Its value
            ranges between 1 and the value of ppsNumber."
        ::= { ppsEntry 1 }

    pps-On OBJECT-TYPE
        SYNTAX  INTEGER { off(0), on(1) }
        ACCESS  read-write
        STATUS  mandatory
        DESCRIPTION
            "This parameter switches this PPS server configuration on or off." 
        ::= { ppsEntry 2 }

    pps-Server OBJECT-TYPE
        SYNTAX  DisplayString (SIZE (0..64))
        ACCESS  read-write
        STATUS  mandatory
        DESCRIPTION
            "This is the name of this PPS server."
        ::= { ppsEntry 3 }
 
    pps-PIN OBJECT-TYPE
        SYNTAX  DisplayString (SIZE (0..32))
        ACCESS  read-write
        STATUS  mandatory
        DESCRIPTION
            "This is the PPS User-PIN of this PPS server."
        ::= { ppsEntry 4 }

    pps-PWD OBJECT-TYPE
        SYNTAX  DisplayString (SIZE (0..32))
        ACCESS  read-write
        STATUS  mandatory
        DESCRIPTION
            "This is the PPS user password of this PPS server."
        ::= { ppsEntry 5 }

    pps-Port OBJECT-TYPE
        SYNTAX  INTEGER (0..65535)
        ACCESS  read-write
        STATUS  mandatory
        DESCRIPTION
            "This parameter specifies the local 
             PPS port of this PPS server."
        ::= { ppsEntry 6 }

    pps-SSL OBJECT-TYPE
        SYNTAX  INTEGER { off(0), on(1) }
        ACCESS  read-write
        STATUS  mandatory
        DESCRIPTION
            "This parameter switches SSL for this PPS server 
             TCP connection on or off."
        ::= { ppsEntry 7 }

    pps-Verify OBJECT-TYPE
        SYNTAX  INTEGER { off(0), on(1) }
        ACCESS  read-write
        STATUS  mandatory
        DESCRIPTION
            "This parameter switches the ssl verification of this 
             PPS server on or off."
        ::= { ppsEntry 8 }

    pps-PrtId OBJECT-TYPE
        SYNTAX  DisplayString (SIZE (0..64))
        ACCESS  read-write
        STATUS  mandatory
        DESCRIPTION
            "This is the Personal Printing printer ID of this PPS server."
        ::= { ppsEntry 9 }

    pps-Delete OBJECT-TYPE
        SYNTAX  INTEGER { none(0), server(1), tpr(2) }
        ACCESS  read-write
        STATUS  mandatory
        DESCRIPTION
            "This parameter selects who has finally to 
             delete the print job on this PPS server."
        ::= { ppsEntry 10 }

    pps-DelelteDelay OBJECT-TYPE
         SYNTAX  INTEGER (0..60)
         ACCESS  read-write
         STATUS  mandatory
         DESCRIPTION
            "This is the delay in seconds for the tpr to sends the 
             delete job command after completition."
        ::= { ppsEntry 11 }

    -- the sehtse group
    
    -- This group specifies the EPSON TSE device parameters of SEH TSE-Server.
        
    tseNumber OBJECT-TYPE
       SYNTAX  INTEGER
       ACCESS  read-only
       STATUS  mandatory
       DESCRIPTION
           "This parameter specifies the number of available TSE device entries"
       ::= { sehTSE 1 }
    
    tseTable OBJECT-TYPE
       SYNTAX  SEQUENCE OF TSEEntry
       ACCESS  not-accessible
       STATUS  mandatory
       DESCRIPTION
           "This object specifies a table containing a list of TSE device entries.
           The number of entries is given by the value of tseNumber."
       ::= { sehTSE 2 }

    tseEntry OBJECT-TYPE
       SYNTAX  TSEEntry
       ACCESS  not-accessible
       STATUS  mandatory
       DESCRIPTION
           "Parameters regarding to TSE device entry."
       INDEX   { tse-Index }
       ::= { tseTable 1 }
    
    TSEEntry ::= SEQUENCE {
        tse-Index        INTEGER
        }
    
    tse-Index OBJECT-TYPE
        SYNTAX  INTEGER (0..256)
        ACCESS  read-only
        STATUS  mandatory
        DESCRIPTION
            "This object contains the index of the table being a
            unique value for each TSE device. Its value
            ranges between 1 and the value of tseNumber."
        ::= { tseEntry 1 }

    -- Enterprise-specific traps for SEH
    -- Traps are defined using the conventions in RFC 1215.
    
    prtFault TRAP-TYPE
        ENTERPRISE  seh
        VARIABLES   { pprtError }
        DESCRIPTION
            "The printer error state has changed."
        ::=  1
       
   END
