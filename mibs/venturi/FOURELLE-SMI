-- --------------------------------------------------------------------------
-- FOURELLE-SMI.txt:  Venturi Wireless Structure of Management information
--
-- 16 July 2001
--
-- Copyright 2003 by Venturi Wireless
-- All rights reserved.
-- --------------------------------------------------------------------------

FOURELLE-SMI DEFINITIONS ::= BEGIN

IMPORTS
    MODULE-IDENTITY, 
    OBJECT-TYPE,
    enterprises
        FROM SNMPv2-SMI;

fourelle MODULE-IDENTITY
    LAST-UPDATED    "200107160000Z"
    ORGANIZATION    "Venturi Wireless"
    CONTACT-INFO
       "Contact:  Customer Support

        Postal:   Venturi Wireless
                  555 N. Mathilda Ave., Suite 100
                  Sunnyvale, California, USA 94086

        Phone:    408-215-5100
        FAX:      408-215-5105

        Web:      www.venturiwireless.com
        
        E-mail:   VenturiCustomerOps@venturiwireless.com"

    DESCRIPTION
        "The root MIB module for Venturi Wireless

          Copyright 2003 Venturi Wireless
          All rights reserved.

          This MIB module specifies the overall structure
          of Venturi Wireless SNMP accessible management information."

    REVISION    "200107160000Z"
        DESCRIPTION
            "1.0 - Initial document."

    REVISION    "200303270000Z"
        DESCRIPTION
            "2.0 - Company name change."

    ::= { enterprises 3382 }
END
