APRISAXE-MIB-4RF DEFINITIONS ::= BEGIN

--
-- File: $Id: 4RF-APRISAXE-MIB.txt,v 1.148.2.1 2007/09/17 01:31:14 di Exp $
--
-- Copyright: 2004  4RF COMMUNICATIONS LTD
--
-- Description:
--  MIB for AprisaXE project.
--
-- Versions:
--
-- Release 3
-- Added support for 4-wire cards and configurable cross-connections
--
-- Notes:
--  None
--


IMPORTS

    -- Standard imports
    MODULE-IDENTITY, OBJECT-TYPE, OBJECT-IDENTITY, NOTIFICATION-TYPE,
    Integer32, Unsigned32, Counter32, IpAddress
        FROM SNMPv2-SMI
    TEXTUAL-CONVENTION, DisplayString
        FROM SNMPv2-TC
    MODULE-COMPLIANCE, OBJECT-GROUP, NOTIFICATION-GROUP
        FROM SNMPv2-CONF

    -- 4RF Specific imports
    fourRFAprisaXE
        FROM PRODUCTS-MIB-4RF
    FourRFAlarmStatus, FourRFAlarmSeverity, FourRFAlarmEnabled, FourRFAlarmPresent,
    FourRFImageVersion, FourRFHardwareVersion, FourRFSerialNumber, FourRFChannelWidth,
    FourRFRSSI, FourRFModulationType, FourRFErrorCounter, FourRFFanStatus, 
    FourRFTemperature, FourRFFrequency, FourRFTxPower, FourRFRfBand, FourRFSNR,
    FourRFClockSource, FourRFNetworkClockSelect, FourRFLoopback,
    FourRFNetworkClockStatus, FourRFMHSBStatus, FourRFMHSBCommand, FourRFProcessResultType
        FROM COMMON-TC-4RF
    AprisaXESlotNumber, AprisaXECardType, AprisaXEAlarmSource, AprisaXEPortNumber,
    AprisaXEAlarmMapping, AprisaXEAdcVoltage,AprisaXEDbValue, AprisaXEIQData, 
    AprisaXEAlarmType, AprisaXEChannelControlType, AprisaXETdmPortType, 
    AprisaXEHardwareVersion, AprisaXEDataStatus, 
    AprisaXEQuadJetTrafficType, AprisaXEAlarmPolarity, AprisaXEAlarmOutput,
    AprisaXEQuadJetLineEncoding, AprisaXE4WRxGain, AprisaXE4WTxGain,
    AprisaXE4WInputLevel, AprisaXE4WOutputLevel,
    AprisaXEFXOInputLevel, AprisaXEFXOOutputLevel,
    AprisaXEFXSInputLevel, AprisaXEFXSOutputLevel, AprisaXEFXSPathMute,
    AprisaXESignalState, AprisaXETdmBus,AprisaXEPcmLaw,AprisaXEFXOCountry,
    AprisaXEAdpcmCompression,AprisaXEFXSPMLevel,
    AprisaXEInterfaceCnxnType,AprisaXEConnectionID, 
    AprisaXEPcmMode,AprisaXESerialEquipmentMode,
    AprisaXEQuadJetConnectionType, AprisaXEHssSerialMode, AprisaXE2WireSignalState,
    AprisaXEEthernetPortNumber, AprisaXEEthernetGroup,
    AprisaXEEthernetFrameRate, AprisaXEEthernetPortPriority,
    AprisaXEEthernetGrouping, AprisaXEEthernetPrioQueueScheduling, AprisaXEEthernetPrioQueueMapping,
    AprisaXEDefaultAction, AprisaXEQuadJetLoopbacks, AprisaXEQuadJetWaveFormShapers,
    AprisaXECCActivationStatus, AprisaXEQuadJetMultiframeEnable,
    AprisaXEPSCActiveRadio, AprisaXEPSCActiveTx
        FROM APRISAXE-TC-4RF
    fourRFModules 
        FROM MIB-4RF;


-- Module Identification
fourRFAprisaXEModule MODULE-IDENTITY
    LAST-UPDATED "200704300000Z"
    ORGANIZATION "www.4rf.com"
    CONTACT-INFO    
         "postal:   4RF Communications Ltd
                    26 Glover Street
                    Ngauranga
                    PO Box 13-506
                    Wellington 6032
                    New Zealand
                    
          phone:    +64 4 499 6000
          email:    support@4rf.com"
    DESCRIPTION "MIB for the AprisaXE project"

	-- Revision history
    -- (in reverse chronological order)

    REVISION    "200704300000Z"
    DESCRIPTION "Second draft"

    REVISION    "200412090304Z"
    DESCRIPTION "First draft"
    ::= { fourRFModules 5 }

    
aprisaXEConfig OBJECT-IDENTITY
    STATUS      current
    DESCRIPTION "The root of the OID sub-tree for the AprisaXE product configuration."
    ::= { fourRFAprisaXE 1 } 
    
aprisaXEGroups OBJECT-IDENTITY
    STATUS      current
    DESCRIPTION "The root of the OID sub-tree for the AprisaXE object groups."
    ::= { aprisaXEConfig 1 } 
        
aprisaXEObjects OBJECT-IDENTITY
    STATUS      current
    DESCRIPTION "The root of the OID sub-tree for the AprisaXE product objects."
    ::= { aprisaXEConfig 2 }  
    
aprisaXEEvents OBJECT-IDENTITY
    STATUS      current
    DESCRIPTION "The root of the OID sub-tree for the AprisaXE product events."
    ::= { aprisaXEConfig 3 } 

aprisaXEEventsV2 OBJECT-IDENTITY
    STATUS      current
    DESCRIPTION "The AprisaXE product events, ensures SNMPv1 compatibility."
    ::= { aprisaXEEvents 0 } 

aprisaXETestObjects OBJECT-IDENTITY
    STATUS      current
    DESCRIPTION "The root of the OID sub-tree for the AprisaXE test objects."
    ::= { aprisaXEConfig 4 } 

    

-- ***************************************************************************
-- Terminal Settings
--
-- This object group provides access to basic terminal information such as the
-- Rx and Tx frequencies. This is a product specific enhancement to the common
-- terminalGroup defined in the COMMON-4RF MIB.
-- ***************************************************************************

aprisaXETerminal OBJECT IDENTIFIER ::= { aprisaXEObjects 1 }

aprisaXETerminalRfChannelWidth OBJECT-TYPE
    SYNTAX      FourRFChannelWidth
    MAX-ACCESS  read-write
    STATUS      current
    DESCRIPTION "The terminal RF channel width, the options are:
                 20kHz, 25kHz, 50kHz, 75kHz, 100kHz, 125kHz, 150kHz, 200kHz, 250kHz,
                 400kHz, 500kHz, 800kHz,
                 1MHz, 1.25MHz,
                 1.75MHz, 2MHz,
                 3.5MHz, 7MHz"
    ::= { aprisaXETerminal 4 }

aprisaXETerminalRSSI OBJECT-TYPE
    SYNTAX      FourRFRSSI
    MAX-ACCESS  read-only
    STATUS      current
    DESCRIPTION "The terminal RSSI in dBm."
    ::= { aprisaXETerminal 5 }   

aprisaXETerminalModulationState OBJECT-TYPE
    SYNTAX      FourRFModulationType
    MAX-ACCESS  read-write
    STATUS      current
    DESCRIPTION "The terminal modulation state."
    ::= { aprisaXETerminal 6 }   

aprisaXETerminalClockReference OBJECT-TYPE
    SYNTAX      INTEGER { automatic (0),
                          manual    (1)
                }
    MAX-ACCESS  read-write
    STATUS      current
    DESCRIPTION "The terminal clock reference configuration:
                   automatic -
                   manual    - "
    ::= { aprisaXETerminal 7 }
    
aprisaXETerminalClockSource OBJECT-TYPE
    SYNTAX      FourRFClockSource
    MAX-ACCESS  read-write
    STATUS      current
    DESCRIPTION "The terminal clock source configuration:
                   network  - clocking is recovered from the synchronous network
                              to which the terminal is connected.
                   link     - clocking is recovered from the remote end of the link.
                   internal - the clock is generated internally.
                 The clock reference must be in manual mode for this to take effect."
    ::= { aprisaXETerminal 8 }

aprisaXETerminalAlarmStatus OBJECT-TYPE
    SYNTAX      FourRFAlarmStatus
    MAX-ACCESS  read-only
    STATUS      current
    DESCRIPTION "The terminal alarm status, this reflects the overall status of the
                 terminal. This will match the colour of the front panel control LED.
                 The states used are noAlarm, minorAlarm and majorAlarm."
    ::= { aprisaXETerminal 9 }
    
aprisaXETerminalRxAlarmStatus OBJECT-TYPE
    SYNTAX      FourRFAlarmStatus
    MAX-ACCESS  read-only
    STATUS      current
    DESCRIPTION "The terminal alarm status, this reflects the overall RX status of the
                 terminal. This will match the colour of the front panel RX LED.
                 The states used are noAlarm, minorAlarm and majorAlarm."
    ::= { aprisaXETerminal 10 }
    
aprisaXETerminalTxAlarmStatus OBJECT-TYPE
    SYNTAX      FourRFAlarmStatus
    MAX-ACCESS  read-only
    STATUS      current
    DESCRIPTION "The terminal alarm status, this reflects the overall TX status of the
                 terminal. This will match the colour of the front panel TX LED.
                 The states used are noAlarm, minorAlarm and majorAlarm."
    ::= { aprisaXETerminal 11 }
    
aprisaXETerminalBandwidth OBJECT-TYPE
    SYNTAX      Unsigned32
    MAX-ACCESS  read-only
    STATUS      current
    DESCRIPTION "This returns the total bandwidth available over the link in kbps."
    ::= { aprisaXETerminal 12 }

aprisaXEMotherboardSerialNumber  OBJECT-TYPE
    SYNTAX      FourRFSerialNumber
    MAX-ACCESS  read-only
    STATUS      current
    DESCRIPTION "The unique serial number for the motherboard."
    ::= { aprisaXETerminal 13 }
  
aprisaXETerminalAllocatedBandwidth OBJECT-TYPE
    SYNTAX      Unsigned32
    MAX-ACCESS  read-only
    STATUS      current
    DESCRIPTION "This returns the total bandwidth allocated over the link in kbps."
    ::= { aprisaXETerminal 14 }
   
aprisaXETerminalLoopbackBandwidth OBJECT-TYPE
    SYNTAX      Unsigned32
    MAX-ACCESS  read-only
    STATUS      current
    DESCRIPTION "This returns the total loopback bandwidth allocated in kbps."
    ::= { aprisaXETerminal 15 }

aprisaXETerminalNetworkClockPrimaryStatus OBJECT-TYPE
    SYNTAX      FourRFNetworkClockStatus
    MAX-ACCESS  read-only
    STATUS      current
    DESCRIPTION "This returns the status of the network clock primary source."
    ::= { aprisaXETerminal 16 }
 
aprisaXETerminalNetworkClockSecondaryStatus OBJECT-TYPE
    SYNTAX      FourRFNetworkClockStatus
    MAX-ACCESS  read-only
    STATUS      current
    DESCRIPTION "This returns the status of the network clock secondary source."
    ::= { aprisaXETerminal 17 }

aprisaXETerminalNetworkClockCommand OBJECT-TYPE        
    SYNTAX      INTEGER { none                  (0),
                          makePrimaryActive     (1), 
                          makeSecondaryActive   (2)
                }
    MAX-ACCESS  read-write
    STATUS      current
    DESCRIPTION "Forces a change in the active network clock."
    ::= { aprisaXETerminal 18}    
    
aprisaXETerminalStartupComplete OBJECT-TYPE        
    SYNTAX      INTEGER { notComplete     (0),
                          startupComplete (1)
                }
    MAX-ACCESS  read-only
    STATUS      current
    DESCRIPTION "Indicates whether the terminal startup sequence is complete."
    ::= { aprisaXETerminal 19 }    
        
aprisaXETerminalImageAlarmClear OBJECT-TYPE        
    SYNTAX      INTEGER { noCommand                    (0),
                          clearAlternateImageAlarm     (1), 
                          clearDefaultImageAlarm       (2)
                }
    MAX-ACCESS  read-write
    STATUS      current
    DESCRIPTION "Indicates whether the terminal startup sequence is complete."
    ::= { aprisaXETerminal 20 }    
    
aprisaXETerminalMuxStatus OBJECT-TYPE
    SYNTAX      INTEGER { none        (0),
                          muxOnly     (1)
                }
    MAX-ACCESS  read-only
    STATUS      obsolete
    DESCRIPTION "This indicates if the terminal is operating in Mux mode."
    ::= { aprisaXETerminal 21 }

aprisaXETerminalBootloaderDataVersion OBJECT-TYPE
    SYNTAX      Unsigned32
    MAX-ACCESS  read-only
    STATUS      current
    DESCRIPTION "This indicates the data version of the shared data field in the bootloader."
    ::= { aprisaXETerminal 22 }
        
aprisaXETerminalUploadFailAlarmClear OBJECT-TYPE        
    SYNTAX      INTEGER { noCommand            (0),
                          clearUploadFailAlarm (1) 
                }
    MAX-ACCESS  read-write
    STATUS      current
    DESCRIPTION "Used to clear a current Upload Failure Alarm."
    ::= { aprisaXETerminal 23 }    
    
aprisaXETerminalEquipmentType OBJECT-TYPE
    SYNTAX      INTEGER { axeUnknown     (0),
                          axeRadio       (1),
                          axeMux         (2),
                          axeProtSwitch  (3),
                          axeProtRadio   (4)
                }
    MAX-ACCESS  read-only
    STATUS      current
    DESCRIPTION "This indicates what type of equipment the terminal is."
    ::= { aprisaXETerminal 24 }    
    

aprisaXETerminalGroup OBJECT-GROUP
    OBJECTS     { aprisaXETerminalRfChannelWidth,
                  aprisaXETerminalRSSI,
                  aprisaXETerminalModulationState,
                  aprisaXETerminalClockReference,
                  aprisaXETerminalClockSource,
                  aprisaXETerminalAlarmStatus,
                  aprisaXETerminalRxAlarmStatus,
                  aprisaXETerminalTxAlarmStatus,
                  aprisaXETerminalBandwidth,
                  aprisaXEMotherboardSerialNumber,
                  aprisaXETerminalAllocatedBandwidth,
                  aprisaXETerminalLoopbackBandwidth,
                  aprisaXETerminalNetworkClockPrimaryStatus,
                  aprisaXETerminalNetworkClockSecondaryStatus,
                  aprisaXETerminalNetworkClockCommand,
                  aprisaXETerminalStartupComplete,
                  aprisaXETerminalImageAlarmClear,
                  aprisaXETerminalMuxStatus,
                  aprisaXETerminalBootloaderDataVersion,
                  aprisaXETerminalUploadFailAlarmClear,
                  aprisaXETerminalEquipmentType
    }
    STATUS      current
    DESCRIPTION "The AprisaXE terminal settings group."
    ::= { aprisaXEGroups 1 } 

-- ***************************************************************************
-- End Terminal Settings
-- ***************************************************************************



-- ***************************************************************************
-- Terminal performance information
--
-- This section provides basic performance statistics for the terminal.
-- ***************************************************************************

aprisaXEPerformance OBJECT IDENTIFIER ::= { aprisaXEObjects 6 }

aprisaXECorrectableErrorCount OBJECT-TYPE
    SYNTAX      FourRFErrorCounter
    MAX-ACCESS  read-only
    STATUS      current
    DESCRIPTION "The terminal correctable error count."
    ::= { aprisaXEPerformance 1 }

aprisaXEUncorrectableErrorCount OBJECT-TYPE
    SYNTAX      FourRFErrorCounter
    MAX-ACCESS  read-only
    STATUS      current
    DESCRIPTION "The terminal uncorrectable error count."
    ::= { aprisaXEPerformance 2 } 
    
aprisaXEModemSNR OBJECT-TYPE
    SYNTAX      FourRFSNR
    MAX-ACCESS  read-only
    STATUS      current
    DESCRIPTION "The modem signal to noise ratio."
    ::= { aprisaXEPerformance 3 } 
    
aprisaXETxPacketCount OBJECT-TYPE
    SYNTAX      Counter32
    MAX-ACCESS  read-only
    STATUS      current
    DESCRIPTION "The terminal transmitted ethernet packet count (to link)."
    ::= { aprisaXEPerformance 4 } 

aprisaXERxPacketCount OBJECT-TYPE
    SYNTAX      Counter32
    MAX-ACCESS  read-only
    STATUS      current
    DESCRIPTION "The terminal received ethernet packet count (from link)."
    ::= { aprisaXEPerformance 5 } 
    
aprisaXERxPacketErrorCount OBJECT-TYPE
    SYNTAX      Counter32
    MAX-ACCESS  read-only
    STATUS      current
    DESCRIPTION "The terminal received ethernet packet error count (from link)."
    ::= { aprisaXEPerformance 6 } 
    
aprisaXEErrorCounterCommand OBJECT-TYPE
    SYNTAX      INTEGER { countersRunning   (0),
                          resetCounters     (1), 
                          freezeCounters    (2),
                          unfreezeCounters  (3)
                }
    MAX-ACCESS  read-write
    STATUS      current
    DESCRIPTION "Forces reset, freeze or unfreeze the error counters."
    ::= { aprisaXEPerformance 7 }    

aprisaXEErrorFreeSeconds OBJECT-TYPE
    SYNTAX      Counter32
    MAX-ACCESS  read-only
    STATUS      current
    DESCRIPTION "The number of Error Free Seconds for the terminal."
    ::= { aprisaXEPerformance 8 } 

aprisaXEErroredSeconds OBJECT-TYPE
    SYNTAX      Counter32
    MAX-ACCESS  read-only
    STATUS      current
    DESCRIPTION "The number of Errored Seconds for the terminal."
    ::= { aprisaXEPerformance 9 } 

aprisaXEBERExponent OBJECT-TYPE
    SYNTAX      DisplayString ( SIZE (0..64) )
    MAX-ACCESS  read-only
    STATUS      current
    DESCRIPTION "The exponent of the Bit Error Rate for the terminal."
    ::= { aprisaXEPerformance 10 } 

aprisaXEPscSysUncorrectableErrorCount OBJECT-TYPE
    SYNTAX      DisplayString ( SIZE (0..64) )
    MAX-ACCESS  read-only
    STATUS      current
    DESCRIPTION "The terminal uncorrectable error count."
    ::= { aprisaXEPerformance 11 } 

aprisaXEPscSysErrorFreeSeconds OBJECT-TYPE
    SYNTAX      Counter32
    MAX-ACCESS  read-only
    STATUS      current
    DESCRIPTION "The number of Error Free Seconds for the terminal."
    ::= { aprisaXEPerformance 12 } 

aprisaXEPscSysErroredSeconds OBJECT-TYPE
    SYNTAX      Counter32
    MAX-ACCESS  read-only
    STATUS      current
    DESCRIPTION "The number of Errored Seconds for the terminal."
    ::= { aprisaXEPerformance 13 } 

aprisaXEPscSysBERExponent OBJECT-TYPE
    SYNTAX      DisplayString( SIZE(0..64) )
    MAX-ACCESS  read-only
    STATUS      current
    DESCRIPTION "The exponent of the Bit Error Rate for the terminal."
    ::= { aprisaXEPerformance 14 } 

aprisaXEPscRadioAUncorrectableErrorCount OBJECT-TYPE
    SYNTAX      FourRFErrorCounter
    MAX-ACCESS  read-only
    STATUS      current
    DESCRIPTION "The terminal uncorrectable error count."
    ::= { aprisaXEPerformance 15 } 

aprisaXEPscRadioAErrorFreeSeconds OBJECT-TYPE
    SYNTAX      Counter32
    MAX-ACCESS  read-only
    STATUS      current
    DESCRIPTION "The number of Error Free Seconds for the terminal."
    ::= { aprisaXEPerformance 16 } 

aprisaXEPscRadioAErroredSeconds OBJECT-TYPE
    SYNTAX      Counter32
    MAX-ACCESS  read-only
    STATUS      current
    DESCRIPTION "The number of Errored Seconds for the terminal."
    ::= { aprisaXEPerformance 17 } 

aprisaXEPscRadioABERExponent OBJECT-TYPE
    SYNTAX      DisplayString( SIZE(0..64) )
    MAX-ACCESS  read-only
    STATUS      current
    DESCRIPTION "The exponent of the Bit Error Rate for the terminal."
    ::= { aprisaXEPerformance 18 } 

aprisaXEPscRadioBUncorrectableErrorCount OBJECT-TYPE
    SYNTAX      FourRFErrorCounter
    MAX-ACCESS  read-only
    STATUS      current
    DESCRIPTION "The terminal uncorrectable error count."
    ::= { aprisaXEPerformance 19 } 

aprisaXEPscRadioBErrorFreeSeconds OBJECT-TYPE
    SYNTAX      Counter32
    MAX-ACCESS  read-only
    STATUS      current
    DESCRIPTION "The number of Error Free Seconds for the terminal."
    ::= { aprisaXEPerformance 20 } 

aprisaXEPscRadioBErroredSeconds OBJECT-TYPE
    SYNTAX      Counter32
    MAX-ACCESS  read-only
    STATUS      current
    DESCRIPTION "The number of Errored Seconds for the terminal."
    ::= { aprisaXEPerformance 21 } 

aprisaXEPscRadioBBERExponent OBJECT-TYPE
    SYNTAX      DisplayString( SIZE(0..64) )
    MAX-ACCESS  read-only
    STATUS      current
    DESCRIPTION "The exponent of the Bit Error Rate for the terminal."
    ::= { aprisaXEPerformance 22 } 

aprisaXEPerformanceGroup OBJECT-GROUP
    OBJECTS     { aprisaXECorrectableErrorCount, 
                  aprisaXEUncorrectableErrorCount, 
                  aprisaXEModemSNR,
                  aprisaXETxPacketCount,
                  aprisaXERxPacketCount,
                  aprisaXERxPacketErrorCount,
                  aprisaXEErrorCounterCommand,
                  aprisaXEErrorFreeSeconds,
                  aprisaXEErroredSeconds,
                  aprisaXEBERExponent,
                  aprisaXEPscSysUncorrectableErrorCount,
                  aprisaXEPscSysErrorFreeSeconds,
                  aprisaXEPscSysErroredSeconds,
                  aprisaXEPscSysBERExponent,
                  aprisaXEPscRadioAUncorrectableErrorCount,
                  aprisaXEPscRadioAErrorFreeSeconds,
                  aprisaXEPscRadioAErroredSeconds,
                  aprisaXEPscRadioABERExponent,
                  aprisaXEPscRadioBUncorrectableErrorCount,
                  aprisaXEPscRadioBErrorFreeSeconds,
                  aprisaXEPscRadioBErroredSeconds,
                  aprisaXEPscRadioBBERExponent
    }
    STATUS      current
    DESCRIPTION "The AprisaXE terminal performance group."
    ::= { aprisaXEGroups 6 } 

-- ***************************************************************************
-- End Performance
-- ***************************************************************************



-- ***************************************************************************
-- External Alarms
--
-- This section specifies the MIB attributes for handling external alarm
-- inputs and outputs. For AprisaXE there are two external alarm inputs
-- and four external alarm outputs. Two of the external alarm outputs will 
-- be used to reflect the alarm state of the remote terminal, one for major
-- and one for minor alarms.
--
-- The alarms can be enabled and disabled and the severity associated with
-- the inputs can be set. The polarity indicating an alarm can also be set.
-- ***************************************************************************

aprisaXEExternalAlarms OBJECT IDENTIFIER ::= { aprisaXEObjects 11 }

-- The first external alarm input
aprisaXEExternalAlarm1 OBJECT IDENTIFIER ::= { aprisaXEExternalAlarms 1 }

aprisaXEExternalAlarm1Status OBJECT-TYPE
    SYNTAX      FourRFAlarmStatus
    MAX-ACCESS  read-only
    STATUS      current
    DESCRIPTION "The status of the first external alarm input."
    ::= { aprisaXEExternalAlarm1 1 }

aprisaXEExternalAlarm1Severity OBJECT-TYPE
    SYNTAX      FourRFAlarmSeverity
    MAX-ACCESS  read-write
    STATUS      current
    DESCRIPTION "The severity of the first external alarm input."
    ::= { aprisaXEExternalAlarm1 2 }

aprisaXEExternalAlarm1Enabled OBJECT-TYPE
    SYNTAX      FourRFAlarmEnabled
    MAX-ACCESS  read-write
    STATUS      current
    DESCRIPTION "Indicates whether the first external alarm input is enabled.
                 If not changes to the input will be ignored. By default the
                 alarm is enabled."
    ::= { aprisaXEExternalAlarm1 3 }

aprisaXEExternalAlarm1Mapping OBJECT-TYPE
    SYNTAX      AprisaXEAlarmMapping 
    MAX-ACCESS  read-write
    STATUS      current
    DESCRIPTION "This defines how the first external alarm input is mapped to
                 the remote alarms."
    ::= { aprisaXEExternalAlarm1 4 }

aprisaXEExternalAlarm1Description OBJECT-TYPE
    SYNTAX      DisplayString ( SIZE (0..64) )
    MAX-ACCESS  read-write
    STATUS      current
    DESCRIPTION "A description (user defined) for the external alarm."
    ::= { aprisaXEExternalAlarm1 5 }
    
aprisaXEExternalAlarm1Group OBJECT-GROUP
    OBJECTS     { aprisaXEExternalAlarm1Status, 
                  aprisaXEExternalAlarm1Severity, 
                  aprisaXEExternalAlarm1Enabled,
                  aprisaXEExternalAlarm1Mapping,
                  aprisaXEExternalAlarm1Description
    }
    STATUS      current
    DESCRIPTION "The AprisaXE  first external alarm input group."
    ::= { aprisaXEGroups 11 } 
    
    
-- The second external alarm input
aprisaXEExternalAlarm2 OBJECT IDENTIFIER ::= { aprisaXEExternalAlarms 2 }

aprisaXEExternalAlarm2Status OBJECT-TYPE
    SYNTAX      FourRFAlarmStatus
    MAX-ACCESS  read-only
    STATUS      current
    DESCRIPTION "The status of the second external alarm input."
    ::= { aprisaXEExternalAlarm2 1 }

aprisaXEExternalAlarm2Severity OBJECT-TYPE
    SYNTAX      FourRFAlarmSeverity
    MAX-ACCESS  read-write
    STATUS      current
    DESCRIPTION "The severity of the second external alarm input."
    ::= { aprisaXEExternalAlarm2 2 }

aprisaXEExternalAlarm2Enabled OBJECT-TYPE
    SYNTAX      FourRFAlarmEnabled
    MAX-ACCESS  read-write
    STATUS      current
    DESCRIPTION "Indicates whether the second external alarm input is enabled.
                 If not changes to the input will be ignored. By default the
                 alarm is enabled."
    ::= { aprisaXEExternalAlarm2 3 }

aprisaXEExternalAlarm2Mapping OBJECT-TYPE
    SYNTAX      AprisaXEAlarmMapping 
    MAX-ACCESS  read-write
    STATUS      current
    DESCRIPTION "This defines how the second external alarm input is mapped to
                 the remote alarms."
    ::= { aprisaXEExternalAlarm2 4 }

aprisaXEExternalAlarm2Description OBJECT-TYPE
    SYNTAX      DisplayString ( SIZE (0..64) )
    MAX-ACCESS  read-write
    STATUS      current
    DESCRIPTION "A description (user defined) for the external alarm."
    ::= { aprisaXEExternalAlarm2 5 }
    
aprisaXEExternalAlarm2Group OBJECT-GROUP
    OBJECTS     { aprisaXEExternalAlarm2Status, 
                  aprisaXEExternalAlarm2Severity, 
                  aprisaXEExternalAlarm2Enabled,
                  aprisaXEExternalAlarm2Mapping,
                  aprisaXEExternalAlarm2Description
    }
    STATUS      current
    DESCRIPTION "The AprisaXE second external alarm input group."
    ::= { aprisaXEGroups 16 } 

    
-- General configuration

aprisaXEExternalAlarmPolarity OBJECT-TYPE
    SYNTAX      AprisaXEAlarmPolarity
    MAX-ACCESS  read-write
    STATUS      current
    DESCRIPTION "Indicates the polarity used to indicate the presence of an
                 alarm at an external alarm input."
    ::= { aprisaXEExternalAlarms 3 }
    
aprisaXEExternalAlarmOutputPolarity OBJECT-TYPE
    SYNTAX      INTEGER { polarityClosed (0),
                          polarityOpen   (1)
                }
    MAX-ACCESS  read-write
    STATUS      current
    DESCRIPTION "Indicates the polarity used to indicate the presence of an
                 alarm at an external alarm output, this may be different from
                 the input polarity."
    ::= { aprisaXEExternalAlarms 4 }

aprisaXEExternalAlarmsGroup OBJECT-GROUP
    OBJECTS     { aprisaXEExternalAlarmPolarity,
                  aprisaXEExternalAlarmOutputPolarity
    }
    STATUS      current
    DESCRIPTION "The AprisaXE general external alarm details group."
    ::= { aprisaXEGroups 17 } 
   

-- The first external alarm output
aprisaXEExternalAlarmOutputOne OBJECT IDENTIFIER ::= { aprisaXEExternalAlarms 5 }

aprisaXEExternalAlarmOutputOneStatus OBJECT-TYPE
    SYNTAX      FourRFAlarmStatus
    MAX-ACCESS  read-only
    STATUS      current
    DESCRIPTION "The status of the first external alarm output."
    ::= { aprisaXEExternalAlarmOutputOne 1 }

aprisaXEExternalAlarmOutputOneMapping OBJECT-TYPE
    SYNTAX      AprisaXEAlarmMapping 
    MAX-ACCESS  read-write
    STATUS      current
    DESCRIPTION "This defines how the first external alarm output is mapped to
                 the alarms."
    ::= { aprisaXEExternalAlarmOutputOne 2 }
    
aprisaXEExternalAlarmOutputOneGroup OBJECT-GROUP
    OBJECTS     { aprisaXEExternalAlarmOutputOneStatus,
                  aprisaXEExternalAlarmOutputOneMapping
    }
    STATUS      current
    DESCRIPTION "The AprisaXE first external alarm output group."
    ::= { aprisaXEGroups 12 }
    
-- The second external alarm output
aprisaXEExternalAlarmOutputTwo OBJECT IDENTIFIER ::= { aprisaXEExternalAlarms 6 }

aprisaXEExternalAlarmOutputTwoStatus OBJECT-TYPE
    SYNTAX      FourRFAlarmStatus
    MAX-ACCESS  read-only
    STATUS      current
    DESCRIPTION "The status of the second external alarm output."
    ::= { aprisaXEExternalAlarmOutputTwo 1 }

aprisaXEExternalAlarmOutputTwoMapping OBJECT-TYPE
    SYNTAX      AprisaXEAlarmMapping 
    MAX-ACCESS  read-write
    STATUS      current
    DESCRIPTION "This defines how the second external alarm output is mapped to
                 the alarms."
    ::= { aprisaXEExternalAlarmOutputTwo 2 }
    
aprisaXEExternalAlarmOutputTwoGroup OBJECT-GROUP
    OBJECTS     { aprisaXEExternalAlarmOutputTwoStatus,
                  aprisaXEExternalAlarmOutputTwoMapping
    }
    STATUS      current
    DESCRIPTION "The AprisaXE second external alarm output group."
    ::= { aprisaXEGroups 13 }
    
-- The third external alarm output
aprisaXEExternalAlarmOutputThree OBJECT IDENTIFIER ::= { aprisaXEExternalAlarms 7 }

aprisaXEExternalAlarmOutputThreeStatus OBJECT-TYPE
    SYNTAX      FourRFAlarmStatus
    MAX-ACCESS  read-only
    STATUS      current
    DESCRIPTION "The status of the third external alarm output."
    ::= { aprisaXEExternalAlarmOutputThree 1 }

aprisaXEExternalAlarmOutputThreeMapping OBJECT-TYPE
    SYNTAX      AprisaXEAlarmMapping 
    MAX-ACCESS  read-write
    STATUS      current
    DESCRIPTION "This defines how the third external alarm output is mapped to
                 the alarms."
    ::= { aprisaXEExternalAlarmOutputThree 2 }
    
aprisaXEExternalAlarmOutputThreeGroup OBJECT-GROUP
    OBJECTS     { aprisaXEExternalAlarmOutputThreeStatus,
                  aprisaXEExternalAlarmOutputThreeMapping
    }
    STATUS      current
    DESCRIPTION "The AprisaXE third external alarm output group."
    ::= { aprisaXEGroups 14 }
    
-- The fourth external alarm output
aprisaXEExternalAlarmOutputFour OBJECT IDENTIFIER ::= { aprisaXEExternalAlarms 8 }

aprisaXEExternalAlarmOutputFourStatus OBJECT-TYPE
    SYNTAX      FourRFAlarmStatus
    MAX-ACCESS  read-only
    STATUS      current
    DESCRIPTION "The status of the fourth external alarm output."
    ::= { aprisaXEExternalAlarmOutputFour 1 }

aprisaXEExternalAlarmOutputFourMapping OBJECT-TYPE
    SYNTAX      AprisaXEAlarmMapping 
    MAX-ACCESS  read-write
    STATUS      current
    DESCRIPTION "This defines how the fourth external alarm output is mapped to
                 the alarms."
    ::= { aprisaXEExternalAlarmOutputFour 2 }
    
aprisaXEExternalAlarmOutputFourGroup OBJECT-GROUP
    OBJECTS     { aprisaXEExternalAlarmOutputFourStatus,
                  aprisaXEExternalAlarmOutputFourMapping
    }
    STATUS      current
    DESCRIPTION "The AprisaXE fourth external alarm output group."
    ::= { aprisaXEGroups 15 }
     
-- ***************************************************************************
-- End External Alarms
-- ***************************************************************************



-- ***************************************************************************
-- Remote Alarms
--
-- This section specifies the MIB attributes for handling alarms from the 
-- remote terminal. The remote terminal can report a major or minor alarm
-- or both. The MIB will provide access to the status of both the major and
-- minor alarms. The remote alarms can be mapped to the external alarm outputs.
-- ***************************************************************************

aprisaXERemoteAlarms OBJECT IDENTIFIER ::= { aprisaXEObjects 16 }

aprisaXEMajorRemoteAlarmStatus OBJECT-TYPE
    SYNTAX      FourRFAlarmStatus
    MAX-ACCESS  read-only
    STATUS      obsolete
    DESCRIPTION "The status of the remote major alarm."
    ::= { aprisaXERemoteAlarms 1 }
    
aprisaXEMajorRemoteAlarmOutput OBJECT-TYPE
    SYNTAX      AprisaXEAlarmOutput 
    MAX-ACCESS  read-write
    STATUS      obsolete
    DESCRIPTION "This defines how the remote major alarm is mapped to the
                 external alarm outputs."
    ::= { aprisaXERemoteAlarms 2 }

aprisaXEMinorRemoteAlarmStatus OBJECT-TYPE
    SYNTAX      FourRFAlarmStatus
    MAX-ACCESS  read-only
    STATUS      obsolete
    DESCRIPTION "The status of the remote minor alarm."
    ::= { aprisaXERemoteAlarms 10 }

aprisaXEMinorRemoteAlarmOutput OBJECT-TYPE
    SYNTAX      AprisaXEAlarmOutput 
    MAX-ACCESS  read-write
    STATUS      obsolete
    DESCRIPTION "This defines how the remote minor alarm is mapped to the
                 external alarm outputs."
    ::= { aprisaXERemoteAlarms 11 }

aprisaXERemoteAlarmGroup OBJECT-GROUP
    OBJECTS     { aprisaXEMajorRemoteAlarmStatus,
                  aprisaXEMajorRemoteAlarmOutput,
                  aprisaXEMinorRemoteAlarmStatus,
                  aprisaXEMinorRemoteAlarmOutput
    }
    STATUS      obsolete
    DESCRIPTION "The AprisaXE remote alarm status group.
                 This group has been replaced by the now mappable external
                 alarm output OIDs aprisaXEExternalAlarmOutputXXXGroup."
    ::= { aprisaXEGroups 21 } 



-- ***************************************************************************
-- MHSB Mode
--
-- This section specifies the MIB attributes for handling MHSB Mode
-- ***************************************************************************

aprisaXEMHSB OBJECT IDENTIFIER ::= {aprisaXEObjects 19 }

aprisaXEMHSBStatus OBJECT-TYPE
    SYNTAX      FourRFMHSBStatus 
    MAX-ACCESS  read-only
    STATUS      current
    DESCRIPTION "The state of an MHSB configured terminal."
    ::= {aprisaXEMHSB 1}
    
aprisaXEMHSBEnable OBJECT-TYPE
    SYNTAX      INTEGER { disabled (0),
                          enabled  (1)
                }
    MAX-ACCESS  read-write
    STATUS      current
    DESCRIPTION "Set the terminal into Monitored Hot Standby Mode."
    ::= { aprisaXEMHSB 2}
    
aprisaXEMHSBCommand OBJECT-TYPE
    SYNTAX      FourRFMHSBCommand
    MAX-ACCESS  read-write
    STATUS      current
    DESCRIPTION "Commands to apply while in MHSB mode."
    ::= { aprisaXEMHSB 3}
   
aprisaXEMHSBTerminalSelect OBJECT-TYPE
    SYNTAX      INTEGER { none      (0),
                          terminalA (1),
                          terminalB (2)
                }
    MAX-ACCESS  read-write
    STATUS      current
    DESCRIPTION "Configure terminal as terminal A or terminal B of an MHSB pair."
    ::= {aprisaXEMHSB 4}
   
aprisaXEMHSBSwitchoverStatus OBJECT-TYPE
    SYNTAX      FourRFAlarmStatus
    MAX-ACCESS  read-only
    STATUS      current
    DESCRIPTION "Status of the alarm reflecting if a switchover has occurred."
    ::= {aprisaXEMHSB 5}

aprisaXEMHSBGroup OBJECT-GROUP
    OBJECTS     { aprisaXEMHSBStatus,
                  aprisaXEMHSBEnable,
                  aprisaXEMHSBCommand,
                  aprisaXEMHSBTerminalSelect,
                  aprisaXEMHSBSwitchoverStatus
    }
    STATUS      current
    DESCRIPTION "The aprisaXE MHSB group."
    ::=  { aprisaXEGroups 23}


            
-- ***************************************************************************
-- Fan Status
--
-- This section specifies the MIB attributes for handling the fan status.
-- ***************************************************************************

aprisaXEFans OBJECT IDENTIFIER ::= { aprisaXEObjects 21 }

aprisaXEFan1Status OBJECT-TYPE
    SYNTAX      FourRFFanStatus
    MAX-ACCESS  read-only
    STATUS      current
    DESCRIPTION "The status of the fan one."
    ::= { aprisaXEFans 1 }
    
aprisaXEFan2Status OBJECT-TYPE
    SYNTAX      FourRFFanStatus 
    MAX-ACCESS  read-only
    STATUS      current
    DESCRIPTION "The status of the fan two."
    ::= { aprisaXEFans 2 }

aprisaXEFanEnable OBJECT-TYPE
    SYNTAX      INTEGER { fansDisabled (0),
                          fansEnabled  (1)
                }
    MAX-ACCESS  read-write
    STATUS      current
    DESCRIPTION "Turn the fans on or off."
    ::= { aprisaXEFans 3 }
    
aprisaXEFanGroup OBJECT-GROUP
    OBJECTS     { aprisaXEFan1Status,
                  aprisaXEFan2Status,
                  aprisaXEFanEnable
    }
    STATUS      current
    DESCRIPTION "The AprisaXE fan status group."
    ::= { aprisaXEGroups 26 } 

    

-- ***************************************************************************
-- AlarmTable
--
-- This section defines the alarm table. This is used to report all currently
-- active alarms. A maximum of 500 alarms will be stored in the table.
-- ***************************************************************************

aprisaXEAlarmTable OBJECT-TYPE
    SYNTAX      SEQUENCE OF AprisaXEAlarmEntry
    MAX-ACCESS  not-accessible
    STATUS      current
    DESCRIPTION "This table stores the currently active alarms. Up to 500
                 separate alarms will be stored in the table."
    ::= { aprisaXEObjects 26 }

AprisaXEAlarmEntry ::= SEQUENCE {
        aprisaXEAlarmIndex    INTEGER,
        aprisaXEAlarmSlot     INTEGER,
        aprisaXEAlarmSource   INTEGER,
        aprisaXEAlarmPort     INTEGER,
        aprisaXEAlarmSeverity INTEGER,
        aprisaXEAlarmType     INTEGER,
        aprisaXEAlarmTime     OCTET STRING
    }

aprisaXEAlarmEntry OBJECT-TYPE
    SYNTAX      AprisaXEAlarmEntry
    MAX-ACCESS  not-accessible
    STATUS      current
    DESCRIPTION "The table entry index specification, just the alarm index."
    INDEX       { aprisaXEAlarmIndex }
    ::= { aprisaXEAlarmTable 1 }

aprisaXEAlarmIndex OBJECT-TYPE
    SYNTAX      INTEGER ( 0..500 )
    MAX-ACCESS  read-only
    STATUS      current
    DESCRIPTION "The index into the alarm table."
    ::= { aprisaXEAlarmEntry 1 }
    
aprisaXEAlarmSlot OBJECT-TYPE
    SYNTAX      AprisaXESlotNumber
    MAX-ACCESS  read-only
    STATUS      current
    DESCRIPTION "The number of the slot generating the alarm."
    ::= { aprisaXEAlarmEntry 2 }
    
aprisaXEAlarmSource OBJECT-TYPE
    SYNTAX      AprisaXEAlarmSource
    MAX-ACCESS  read-only
    STATUS      current
    DESCRIPTION "The source of the alarm, a card type or external."
    ::= { aprisaXEAlarmEntry 3 }
    
aprisaXEAlarmPort OBJECT-TYPE
    SYNTAX      AprisaXEPortNumber
    MAX-ACCESS  read-only
    STATUS      current
    DESCRIPTION "The source port of the alarm."
    ::= { aprisaXEAlarmEntry 4 }

aprisaXEAlarmSeverity OBJECT-TYPE
    SYNTAX      FourRFAlarmSeverity
    MAX-ACCESS  read-only
    STATUS      current
    DESCRIPTION "The severity of the alarm."
    ::= { aprisaXEAlarmEntry 5 }

aprisaXEAlarmType OBJECT-TYPE
    SYNTAX      AprisaXEAlarmType
    MAX-ACCESS  read-only
    STATUS      current
    DESCRIPTION "The type of the alarm."
    ::= { aprisaXEAlarmEntry 6 }
    
aprisaXEAlarmTime OBJECT-TYPE
    SYNTAX      DisplayString
    MAX-ACCESS  read-only
    STATUS      current
    DESCRIPTION "The time that the alarm occurred."
    ::= { aprisaXEAlarmEntry 7 }

-- ***************************************************************************
-- End AlarmTable
-- ***************************************************************************



-- ***************************************************************************
-- AlarmHistoryTable
--
-- This section defines the alarm table. A maximum of 100 alarms will be stored 
-- in the table.
-- ***************************************************************************

aprisaXEAlarmHistoryTable OBJECT-TYPE
    SYNTAX      SEQUENCE OF AprisaXEAlarmHistoryEntry
    MAX-ACCESS  not-accessible
    STATUS      current
    DESCRIPTION "This table stores a history of the alarms as they become
                 active and cleared."
    ::= { aprisaXEObjects 31 }

AprisaXEAlarmHistoryEntry ::= SEQUENCE {
        aprisaXEAlarmHistoryIndex    INTEGER,
        aprisaXEAlarmHistorySlot     INTEGER,
        aprisaXEAlarmHistorySource   INTEGER,
        aprisaXEAlarmHistoryPort     INTEGER,
        aprisaXEAlarmHistorySeverity INTEGER,
        aprisaXEAlarmHistoryType     INTEGER,
        aprisaXEAlarmHistoryPresent  INTEGER,
        aprisaXEAlarmHistoryTime     OCTET STRING
    }

aprisaXEAlarmHistoryEntry OBJECT-TYPE
    SYNTAX      AprisaXEAlarmHistoryEntry
    MAX-ACCESS  not-accessible
    STATUS      current
    DESCRIPTION "The table entry index specification, just the alarm index."
    INDEX       { aprisaXEAlarmHistoryIndex }
    ::= { aprisaXEAlarmHistoryTable 1 }

aprisaXEAlarmHistoryIndex OBJECT-TYPE
    SYNTAX      INTEGER ( 0..100 )
    MAX-ACCESS  read-only
    STATUS      current
    DESCRIPTION "The index into the alarm history table."
    ::= { aprisaXEAlarmHistoryEntry 1 }
    
aprisaXEAlarmHistorySlot OBJECT-TYPE
    SYNTAX      AprisaXESlotNumber
    MAX-ACCESS  read-only
    STATUS      current
    DESCRIPTION "The number of the slot generating the alarm."
    ::= { aprisaXEAlarmHistoryEntry 2 }
    
aprisaXEAlarmHistorySource OBJECT-TYPE
    SYNTAX      AprisaXEAlarmSource
    MAX-ACCESS  read-only
    STATUS      current
    DESCRIPTION "The source of the alarm, a card type or external."
    ::= { aprisaXEAlarmHistoryEntry 3 }
    
aprisaXEAlarmHistoryPort OBJECT-TYPE
    SYNTAX      AprisaXEPortNumber
    MAX-ACCESS  read-only
    STATUS      current
    DESCRIPTION "The source port of the alarm."
    ::= { aprisaXEAlarmHistoryEntry 4 }

aprisaXEAlarmHistorySeverity OBJECT-TYPE
    SYNTAX      FourRFAlarmSeverity
    MAX-ACCESS  read-only
    STATUS      current
    DESCRIPTION "The severity of the alarm."
    ::= { aprisaXEAlarmHistoryEntry 5 }

    
aprisaXEAlarmHistoryType OBJECT-TYPE
    SYNTAX      AprisaXEAlarmType
    MAX-ACCESS  read-only
    STATUS      current
    DESCRIPTION "The type of the alarm."
    ::= { aprisaXEAlarmHistoryEntry 6 }
    
aprisaXEAlarmHistoryPresent OBJECT-TYPE
    SYNTAX      FourRFAlarmPresent
    MAX-ACCESS  read-only
    STATUS      current
    DESCRIPTION "Indicates whether the alarm is present or not."
    ::= { aprisaXEAlarmHistoryEntry 7 }
    
aprisaXEAlarmHistoryTime OBJECT-TYPE
    SYNTAX      DisplayString
    MAX-ACCESS  read-only
    STATUS      current
    DESCRIPTION "The time that the alarm state change occurred."
    ::= { aprisaXEAlarmHistoryEntry 8 }

-- ***************************************************************************
-- End AlarmHistoryTable
-- ***************************************************************************



aprisaXEAlarmControl OBJECT IDENTIFIER ::= { aprisaXEObjects 32 }

aprisaXEAlarmHistoryCommand OBJECT-TYPE
    SYNTAX      INTEGER { noCommand    (0),
                          clearHistory (1)
                }
    MAX-ACCESS  read-write
    STATUS      current
    DESCRIPTION "Allows the alarm history table to be cleared."
    ::= { aprisaXEAlarmControl 1 }
    
aprisaXEAlarmControlGroup OBJECT-GROUP
    OBJECTS     { aprisaXEAlarmHistoryCommand }
    STATUS      current
    DESCRIPTION "The AprisaXE alarm control group."
    ::= { aprisaXEGroups 32 } 


    
-- ***************************************************************************
-- Transmitter - there is only one transmitter for each AprisaXE
--
-- NB: The units for all fields need to be confirmed
--
-- ***************************************************************************

aprisaXETransmitter OBJECT IDENTIFIER ::= { aprisaXEObjects 36 }

aprisaXETransmitterStatus OBJECT-TYPE
    SYNTAX      INTEGER { transmitterOff (0),
                          transmitterOn  (1)
                }
    MAX-ACCESS  read-only
    STATUS      current
    DESCRIPTION "Indicates whether the transmitter is currently on or off."
    ::= { aprisaXETransmitter 1 }
    
aprisaXETransmitterCommand OBJECT-TYPE
    SYNTAX      INTEGER { noCommand      (0),
                          transmitterOff (1),
                          transmitterOn  (2)
                }
    MAX-ACCESS  read-write
    STATUS      current
    DESCRIPTION "Commands used to control the transmitter, currently the transmitter can 
                 be switched on and off. No other commands are defined."
    ::= { aprisaXETransmitter 2 }

aprisaXETransmitterSynthesiserStatus OBJECT-TYPE
    SYNTAX      FourRFAlarmStatus
    MAX-ACCESS  read-only
    STATUS      current
    DESCRIPTION "The status of the transmitter synthesiser."
    ::= { aprisaXETransmitter 3 }

aprisaXETransmitter5VPowerStatus OBJECT-TYPE
    SYNTAX      FourRFAlarmStatus
    MAX-ACCESS  read-only
    STATUS      current
    DESCRIPTION "The status of the transmitter 5V power supply."
    ::= { aprisaXETransmitter 4 }
    
aprisaXETransmitter11VPowerStatus OBJECT-TYPE
    SYNTAX      FourRFAlarmStatus
    MAX-ACCESS  read-only
    STATUS      current
    DESCRIPTION "The status of the transmitter 11V power supply."
    ::= { aprisaXETransmitter 5 }
    
aprisaXETransmitter28VPowerStatus OBJECT-TYPE
    SYNTAX      FourRFAlarmStatus
    MAX-ACCESS  read-only
    STATUS      current
    DESCRIPTION "The status of the transmitter 28V power supply."
    ::= { aprisaXETransmitter 6 }

aprisaXETransmitterFrequency OBJECT-TYPE
    SYNTAX      FourRFFrequency
    MAX-ACCESS  read-write
    STATUS      current
    DESCRIPTION "The terminal transmit frequency in MHz. The possible bands are:
                   330 to 400 MHz (300 MHz)
                   400 to 470 MHz (400 MHz)
                   1350 to 1550 MHz (1400 MHz)
                 The frequency value should be supplied in Hz."
    ::= { aprisaXETransmitter 7 }
    
aprisaXETransmitterPower OBJECT-TYPE
    SYNTAX      FourRFTxPower
    MAX-ACCESS  read-write
    STATUS      current
    DESCRIPTION "The TX power value, the value should be entered in dB."
    ::= { aprisaXETransmitter 8 }

aprisaXETransmitterAGC OBJECT-TYPE
    SYNTAX      AprisaXEAdcVoltage
    MAX-ACCESS  read-only
    STATUS      obsolete
    DESCRIPTION "The Automatic Gain Control value in millivolts."
    ::= { aprisaXETransmitter 9 }
    
aprisaXETransmitterForwardPower OBJECT-TYPE
    SYNTAX      AprisaXEAdcVoltage
    MAX-ACCESS  read-only
    STATUS      obsolete
    DESCRIPTION "The forward power measurement value in millivolts."
    ::= { aprisaXETransmitter 10 }
    
aprisaXETransmitterReversePower OBJECT-TYPE
    SYNTAX      AprisaXEAdcVoltage
    MAX-ACCESS  read-only
    STATUS      obsolete
    DESCRIPTION "The reverse power value in millivolts."
    ::= { aprisaXETransmitter 11 }

aprisaXETransmitterTemperature OBJECT-TYPE
    SYNTAX      FourRFTemperature
    MAX-ACCESS  read-only
    STATUS      obsolete
    DESCRIPTION "The temperature value in degrees Celcius."
    ::= { aprisaXETransmitter 12 }
    
aprisaXETransmitterVTune OBJECT-TYPE
    SYNTAX      AprisaXEAdcVoltage
    MAX-ACCESS  read-only
    STATUS      obsolete
    DESCRIPTION "The voltage output from TX synth."
    ::= { aprisaXETransmitter 13 }
    
aprisaXETransmitter28VSupply OBJECT-TYPE
    SYNTAX      AprisaXEAdcVoltage
    MAX-ACCESS  read-only
    STATUS      obsolete
    DESCRIPTION "The 28V supply rail value in millivolts."
    ::= { aprisaXETransmitter 14 }
    
aprisaXETransmitter11VSupply OBJECT-TYPE
    SYNTAX      AprisaXEAdcVoltage
    MAX-ACCESS  read-only
    STATUS      obsolete
    DESCRIPTION "The 11V supply rail value in millivolts."
    ::= { aprisaXETransmitter 15 }
    
aprisaXETransmitter5VDigitalSupply OBJECT-TYPE
    SYNTAX      AprisaXEAdcVoltage
    MAX-ACCESS  read-only
    STATUS      obsolete
    DESCRIPTION "The 5V digital supply rail value in millivolts."
    ::= { aprisaXETransmitter 16 }
    
aprisaXETransmitter7VSupply OBJECT-TYPE
    SYNTAX      AprisaXEAdcVoltage
    MAX-ACCESS  read-only
    STATUS      obsolete
    DESCRIPTION "The 7V RF supply rail value in millivolts."
    ::= { aprisaXETransmitter 17 }
    
aprisaXETransmitter9VSupply OBJECT-TYPE
    SYNTAX      AprisaXEAdcVoltage
    MAX-ACCESS  read-only
    STATUS      obsolete
    DESCRIPTION "The 9V supply synthesiser rail value in millivolts."
    ::= { aprisaXETransmitter 18 }

aprisaXETransmitterCharacterisationDataStatus OBJECT-TYPE
    SYNTAX      AprisaXEDataStatus
    MAX-ACCESS  read-only
    STATUS      current
    DESCRIPTION "The status of the transmitter characterisation data."
    ::= { aprisaXETransmitter 19 }
    
aprisaXETransmitterSerialNumber OBJECT-TYPE
    SYNTAX      FourRFSerialNumber
    MAX-ACCESS  read-only
    STATUS      current
    DESCRIPTION "The unique module serial number for the transmitter."
    ::= { aprisaXETransmitter 20 }
    
aprisaXETransmitterReturnLoss OBJECT-TYPE
    SYNTAX      AprisaXEDbValue
    MAX-ACCESS  read-only
    STATUS      current
    DESCRIPTION "The return loss for the transmitter."
    ::= { aprisaXETransmitter 21 }
    
aprisaXETransmitterMibDataStatus OBJECT-TYPE
    SYNTAX      AprisaXEDataStatus
    MAX-ACCESS  read-only
    STATUS      current
    DESCRIPTION "The status of the transmitter MIB data."
    ::= { aprisaXETransmitter 22 }

aprisaXETransmitterADCChZero OBJECT-TYPE
    SYNTAX      AprisaXEAdcVoltage
    MAX-ACCESS  read-only
    STATUS      current
    DESCRIPTION "The TX adc ch zero voltage."
    ::= { aprisaXETransmitter 23 }

aprisaXETransmitterADCChOne OBJECT-TYPE
    SYNTAX      AprisaXEAdcVoltage
    MAX-ACCESS  read-only
    STATUS      current
    DESCRIPTION "The TX adc ch one voltage."
    ::= { aprisaXETransmitter 24 }

aprisaXETransmitterADCChTwo OBJECT-TYPE
    SYNTAX      AprisaXEAdcVoltage
    MAX-ACCESS  read-only
    STATUS      current
    DESCRIPTION "The TX adc ch two voltage."
    ::= { aprisaXETransmitter 25 }

aprisaXETransmitterADCChThree OBJECT-TYPE
    SYNTAX      AprisaXEAdcVoltage
    MAX-ACCESS  read-only
    STATUS      current
    DESCRIPTION "The TX adc ch three voltage."
    ::= { aprisaXETransmitter 26 }
    
aprisaXETransmitterADCChFour OBJECT-TYPE
    SYNTAX      AprisaXEAdcVoltage
    MAX-ACCESS  read-only
    STATUS      current
    DESCRIPTION "The TX adc ch four voltage."
    ::= { aprisaXETransmitter 27 }
    
aprisaXETransmitterADCChFive OBJECT-TYPE
    SYNTAX      AprisaXEAdcVoltage
    MAX-ACCESS  read-only
    STATUS      current
    DESCRIPTION "The TX adc ch five voltage."
    ::= { aprisaXETransmitter 28 }
    
aprisaXETransmitterADCChSix OBJECT-TYPE
    SYNTAX      AprisaXEAdcVoltage
    MAX-ACCESS  read-only
    STATUS      current
    DESCRIPTION "The TX adc ch six voltage."
    ::= { aprisaXETransmitter 29 }
    
aprisaXETransmitterADCChSeven OBJECT-TYPE
    SYNTAX      AprisaXEAdcVoltage
    MAX-ACCESS  read-only
    STATUS      current
    DESCRIPTION "The TX adc ch seven voltage."
    ::= { aprisaXETransmitter 30 }
    
aprisaXETransmitterADCChEight OBJECT-TYPE
    SYNTAX      AprisaXEAdcVoltage
    MAX-ACCESS  read-only
    STATUS      current
    DESCRIPTION "The TX adc ch eight voltage."
    ::= { aprisaXETransmitter 31 }
    
aprisaXETransmitterADCChNine OBJECT-TYPE
    SYNTAX      AprisaXEAdcVoltage
    MAX-ACCESS  read-only
    STATUS      current
    DESCRIPTION "The TX adc ch nine voltage."
    ::= { aprisaXETransmitter 32 }

aprisaXETransmitterADCChTen OBJECT-TYPE
    SYNTAX      AprisaXEAdcVoltage
    MAX-ACCESS  read-only
    STATUS      current
    DESCRIPTION "The TX adc ch ten voltage."
    ::= { aprisaXETransmitter 33 }

aprisaXETransmitterADCChEleven OBJECT-TYPE
    SYNTAX      AprisaXEAdcVoltage
    MAX-ACCESS  read-only
    STATUS      current
    DESCRIPTION "The TX adc ch eleven voltage."
    ::= { aprisaXETransmitter 34 }
    
aprisaXETransmitterNeg5VPowerStatus OBJECT-TYPE
    SYNTAX      FourRFAlarmStatus
    MAX-ACCESS  read-only
    STATUS      current
    DESCRIPTION "The status of the transmitter Negative 5V power supply."
    ::= { aprisaXETransmitter 35 }
    
aprisaXETransmitterAmplifierBalanceStatus OBJECT-TYPE
    SYNTAX      FourRFAlarmStatus
    MAX-ACCESS  read-only
    STATUS      current
    DESCRIPTION "The status of the transmitter Balanced Power Amplifier."
    ::= { aprisaXETransmitter 36 }
    
aprisaXETransmitterTcxoAdjustment OBJECT-TYPE
    SYNTAX      INTEGER { txTCXOAdjustmentPosFive (0),
                          txTCXOAdjustmentPosOne  (1),
                          txTCXOAdjustmentZero    (2),
                          txTCXOAdjustmentNegOne  (3),
                          txTCXOAdjustmentNegFive (4)
                }
    MAX-ACCESS  read-write
    STATUS      current
    DESCRIPTION "The TX TCXO adjustment to be made by the customer, to 
                 tune the TCXO. This is a shift in DAC steps."
    ::= { aprisaXETransmitter 37 }

aprisaXETransmitterSynthFileVersion OBJECT-TYPE
    SYNTAX      INTEGER ( 0..999 )
    MAX-ACCESS  read-only
    STATUS      current
    DESCRIPTION "The version of the Synth File loaded from the filesystem."
    ::= { aprisaXETransmitter 38 }
        
aprisaXETransmitterOperationalDataVersion OBJECT-TYPE
    SYNTAX      DisplayString
    MAX-ACCESS  read-only
    STATUS      current
    DESCRIPTION "The version of the operational data for the transmitter."
    ::= { aprisaXETransmitter 39 }
        
aprisaXETransmitterSwCompatibility OBJECT-TYPE
    SYNTAX      INTEGER ( 0..999 )
    MAX-ACCESS  read-only
    STATUS      current
    DESCRIPTION "The transmitter software compatibility number."
    ::= { aprisaXETransmitter 40 }
                             
aprisaXETransmitterGroup OBJECT-GROUP
    OBJECTS     { aprisaXETransmitterStatus,
                  aprisaXETransmitterCommand,
                  aprisaXETransmitterSynthesiserStatus,
                  aprisaXETransmitter5VPowerStatus,
                  aprisaXETransmitter11VPowerStatus,
                  aprisaXETransmitter28VPowerStatus,
                  aprisaXETransmitterFrequency,
                  aprisaXETransmitterPower,
                  aprisaXETransmitterAGC,
                  aprisaXETransmitterForwardPower,
                  aprisaXETransmitterReversePower,
                  aprisaXETransmitterTemperature,
                  aprisaXETransmitterVTune,
                  aprisaXETransmitter28VSupply,
                  aprisaXETransmitter11VSupply,
                  aprisaXETransmitter5VDigitalSupply,
                  aprisaXETransmitter7VSupply,
                  aprisaXETransmitter9VSupply,
                  aprisaXETransmitterCharacterisationDataStatus,
                  aprisaXETransmitterSerialNumber,
                  aprisaXETransmitterReturnLoss,
                  aprisaXETransmitterMibDataStatus,
                  aprisaXETransmitterADCChZero,
                  aprisaXETransmitterADCChOne,
                  aprisaXETransmitterADCChTwo,
                  aprisaXETransmitterADCChThree,
                  aprisaXETransmitterADCChFour,
                  aprisaXETransmitterADCChFive,
                  aprisaXETransmitterADCChSix,
                  aprisaXETransmitterADCChSeven,
                  aprisaXETransmitterADCChEight,
                  aprisaXETransmitterADCChNine,
                  aprisaXETransmitterADCChTen,
                  aprisaXETransmitterADCChEleven,
                  aprisaXETransmitterNeg5VPowerStatus,
                  aprisaXETransmitterAmplifierBalanceStatus,
                  aprisaXETransmitterTcxoAdjustment,
                  aprisaXETransmitterSynthFileVersion
    }
    STATUS      current
    DESCRIPTION "The AprisaXE transmitter settings group."
    ::= { aprisaXEGroups 36 } 

-- ***************************************************************************
-- End Transmitter
-- ***************************************************************************



-- ***************************************************************************
-- Receiver - there is only one Receiver for each AprisaXE
--
-- NB: The units for all fields need to be confirmed
--
-- ***************************************************************************

aprisaXEReceiver OBJECT IDENTIFIER ::= { aprisaXEObjects 51 }

aprisaXEReceiverStatus OBJECT-TYPE
    SYNTAX      INTEGER { receiverOff (0),
                          receiverOn  (1)
                }
    MAX-ACCESS  read-only
    STATUS      current
    DESCRIPTION "Status of the receiver, currently the receiver can be On/Off
                 and the loopback can be On/Off."
    ::= { aprisaXEReceiver 1 }
                                    
aprisaXEReceiverCommand OBJECT-TYPE
    SYNTAX      INTEGER { noCommand   (0),
                          receiverOff (1),
                          receiverOn  (2)
                }
    MAX-ACCESS  read-write
    STATUS      current
    DESCRIPTION "Commands used to control the receiver, currently the receiver can 
                 be switched on and off and the loopback option switched on and off."
    ::= { aprisaXEReceiver 2 }

aprisaXEReceiverSynthesiserStatus OBJECT-TYPE
    SYNTAX      FourRFAlarmStatus
    MAX-ACCESS  read-only
    STATUS      current
    DESCRIPTION "The status of the receiver synthesiser."
    ::= { aprisaXEReceiver 3 }

aprisaXEReceiver12VPowerStatus OBJECT-TYPE
    SYNTAX      FourRFAlarmStatus
    MAX-ACCESS  read-only
    STATUS      current
    DESCRIPTION "The status of the Receiver 12V power supply."
    ::= { aprisaXEReceiver 4 }
    
aprisaXEReceiverFrequency OBJECT-TYPE
    SYNTAX      FourRFFrequency
    MAX-ACCESS  read-write
    STATUS      current
    DESCRIPTION "The terminal transmit frequency in MHz. The possible bands are:
                   330 to 400 MHz (300 MHz)
                   400 to 470 MHz (400 MHz)
                   1350 to 1550 MHz (1400 MHz)
                 The frequency value should be supplied in Hz."
    ::= { aprisaXEReceiver 5 }

aprisaXEReceiverRSSI OBJECT-TYPE
    SYNTAX      FourRFRSSI
    MAX-ACCESS  read-only
    STATUS      current
    DESCRIPTION "The characterised RSSI Voltage."
    ::= { aprisaXEReceiver 6 }
    
aprisaXEReceiverTemperature OBJECT-TYPE
    SYNTAX      FourRFTemperature
    MAX-ACCESS  read-only
    STATUS      current
    DESCRIPTION "The temperature value, this should only be accessible in 
                 engineering mode."
    ::= { aprisaXEReceiver 8 }
    
aprisaXEReceiverVTune OBJECT-TYPE
    SYNTAX      AprisaXEAdcVoltage
    MAX-ACCESS  read-only
    STATUS      obsolete
    DESCRIPTION "The voltage output from RX synth value, this should only be
                 accessible in engineering mode."
    ::= { aprisaXEReceiver 9 }
    
aprisaXEReceiver9VSupply OBJECT-TYPE
    SYNTAX      AprisaXEAdcVoltage
    MAX-ACCESS  read-only
    STATUS      obsolete
    DESCRIPTION "The 9V supply rail value, this should only be accessible in 
                 engineering mode."
    ::= { aprisaXEReceiver 10 }
    
aprisaXEReceiver5VSupply OBJECT-TYPE
    SYNTAX      AprisaXEAdcVoltage
    MAX-ACCESS  read-only
    STATUS      obsolete
    DESCRIPTION "The 5V supply rail value, this should only be accessible in 
                 engineering mode."
    ::= { aprisaXEReceiver 11 }
    
aprisaXEReceiverModemAGC OBJECT-TYPE
    SYNTAX      AprisaXEAdcVoltage
    MAX-ACCESS  read-only
    STATUS      obsolete
    DESCRIPTION "The modem AGC, this should only be accessible in
                 engineering mode."
    ::= { aprisaXEReceiver 12 }
    
aprisaXEReceiverNeg1V5Supply OBJECT-TYPE
    SYNTAX      AprisaXEAdcVoltage
    MAX-ACCESS  read-only
    STATUS      obsolete
    DESCRIPTION "The -1.5V supply rail value, this should only be accessible in
                 engineering mode."
    ::= { aprisaXEReceiver 13 }
    
aprisaXEReceiver3V3Supply OBJECT-TYPE
    SYNTAX      AprisaXEAdcVoltage
    MAX-ACCESS  read-only
    STATUS      obsolete
    DESCRIPTION "The 3.3V supply rail value, this should only be accessible in
                 engineering mode."
    ::= { aprisaXEReceiver 14 }

aprisaXEReceiverDacTest OBJECT-TYPE
    SYNTAX      AprisaXEAdcVoltage
    MAX-ACCESS  read-only
    STATUS      obsolete
    DESCRIPTION "The DacTest value, this should only be accessible in 
                 engineering mode."
    ::= { aprisaXEReceiver 15 }
    
aprisaXEReceiverCharacterisationDataStatus OBJECT-TYPE
    SYNTAX      AprisaXEDataStatus
    MAX-ACCESS  read-only
    STATUS      current
    DESCRIPTION "The status of the receiver characterisation data."
    ::= { aprisaXEReceiver 16 }
    
aprisaXEReceiverSerialNumber OBJECT-TYPE
    SYNTAX      FourRFSerialNumber
    MAX-ACCESS  read-only
    STATUS      current
    DESCRIPTION "The unique module serial number for the receiver."
    ::= { aprisaXEReceiver 17 }
 
aprisaXEReceiverRfLoopback OBJECT-TYPE
    SYNTAX      FourRFLoopback
    MAX-ACCESS  read-write
    STATUS      current
    DESCRIPTION "Enables and disabled RF loopback."
    ::= { aprisaXEReceiver 18 }
    
aprisaXEReceiverRfLoopbackTimeout OBJECT-TYPE
    SYNTAX      Unsigned32
    MAX-ACCESS  read-write
    STATUS      current
    DESCRIPTION "The number of seconds after which RF loopback should timeout."
    ::= { aprisaXEReceiver 19 }
    
aprisaXEReceiverMibDataStatus OBJECT-TYPE
    SYNTAX      AprisaXEDataStatus
    MAX-ACCESS  read-only
    STATUS      current
    DESCRIPTION "The status of the receiver MIB data."
    ::= { aprisaXEReceiver 20 }
    
aprisaXEReceiverADCChZero OBJECT-TYPE
    SYNTAX      AprisaXEAdcVoltage
    MAX-ACCESS  read-only
    STATUS      current
    DESCRIPTION "The RX adc ch zero voltage."
    ::= { aprisaXEReceiver 21 }

aprisaXEReceiverADCChOne OBJECT-TYPE
    SYNTAX      AprisaXEAdcVoltage
    MAX-ACCESS  read-only
    STATUS      current
    DESCRIPTION "The RX adc ch one voltage."
    ::= { aprisaXEReceiver 22 }

aprisaXEReceiverADCChTwo OBJECT-TYPE
    SYNTAX      AprisaXEAdcVoltage
    MAX-ACCESS  read-only
    STATUS      current
    DESCRIPTION "The RX adc ch two voltage."
    ::= { aprisaXEReceiver 23 }

aprisaXEReceiverADCChThree OBJECT-TYPE
    SYNTAX      AprisaXEAdcVoltage
    MAX-ACCESS  read-only
    STATUS      current
    DESCRIPTION "The RX adc ch three voltage."
    ::= { aprisaXEReceiver 24 }
    
aprisaXEReceiverADCChFour OBJECT-TYPE
    SYNTAX      AprisaXEAdcVoltage
    MAX-ACCESS  read-only
    STATUS      current
    DESCRIPTION "The RX adc ch four voltage."
    ::= { aprisaXEReceiver 25 }
    
aprisaXEReceiverADCChFive OBJECT-TYPE
    SYNTAX      AprisaXEAdcVoltage
    MAX-ACCESS  read-only
    STATUS      current
    DESCRIPTION "The RX adc ch five voltage."
    ::= { aprisaXEReceiver 26 }
    
aprisaXEReceiverADCChSix OBJECT-TYPE
    SYNTAX      AprisaXEAdcVoltage
    MAX-ACCESS  read-only
    STATUS      current
    DESCRIPTION "The RX adc ch six voltage."
    ::= { aprisaXEReceiver 27 }
    
aprisaXEReceiverADCChSeven OBJECT-TYPE
    SYNTAX      AprisaXEAdcVoltage
    MAX-ACCESS  read-only
    STATUS      current
    DESCRIPTION "The RX adc ch seven voltage."
    ::= { aprisaXEReceiver 28 }
    
aprisaXEReceiverADCChEight OBJECT-TYPE
    SYNTAX      AprisaXEAdcVoltage
    MAX-ACCESS  read-only
    STATUS      current
    DESCRIPTION "The RX adc ch eight voltage."
    ::= { aprisaXEReceiver 29 }
    
aprisaXEReceiverADCChNine OBJECT-TYPE
    SYNTAX      AprisaXEAdcVoltage
    MAX-ACCESS  read-only
    STATUS      current
    DESCRIPTION "The RX adc ch nine voltage."
    ::= { aprisaXEReceiver 30 }

aprisaXEReceiverADCChTen OBJECT-TYPE
    SYNTAX      AprisaXEAdcVoltage
    MAX-ACCESS  read-only
    STATUS      current
    DESCRIPTION "The RX adc ch ten voltage."
    ::= { aprisaXEReceiver 31 }
    
aprisaXEReceiverRSSIThresQPSKLowerOn OBJECT-TYPE
    SYNTAX      Integer32(-110..-40)
    MAX-ACCESS  read-write
    STATUS      current
    DESCRIPTION "The QPSK Lower ON RSSI Threshold."
    ::= { aprisaXEReceiver 32 }
    
aprisaXEReceiverRSSIThres16QAMLowerOn OBJECT-TYPE
    SYNTAX      Integer32(-110..-40)
    MAX-ACCESS  read-write
    STATUS      current
    DESCRIPTION "The 16QAM Lower ON RSSI Threshold."
    ::= { aprisaXEReceiver 33 }
    
aprisaXEReceiverRSSIThres32QAMLowerOn OBJECT-TYPE
    SYNTAX      Integer32(-110..-40)
    MAX-ACCESS  read-write
    STATUS      current
    DESCRIPTION "The 32QAM Lower ON RSSI Threshold."
    ::= { aprisaXEReceiver 34 }
    
aprisaXEReceiverRSSIThres64QAMLowerOn OBJECT-TYPE
    SYNTAX      Integer32(-110..-40)
    MAX-ACCESS  read-write
    STATUS      current
    DESCRIPTION "The 64QAM Lower ON RSSI Threshold."
    ::= { aprisaXEReceiver 35 }

aprisaXEReceiverSynthFileVersion OBJECT-TYPE
    SYNTAX      INTEGER ( 0..999 )
    MAX-ACCESS  read-only
    STATUS      current
    DESCRIPTION "The version of the Synth File loaded from the filesystem."
    ::= { aprisaXEReceiver 36 }
                             
aprisaXEReceiverOperationalDataVersion OBJECT-TYPE
    SYNTAX      DisplayString
    MAX-ACCESS  read-only
    STATUS      current
    DESCRIPTION "The version of the operational data of the receiver."
    ::= { aprisaXEReceiver 37 }
                             
aprisaXEReceiverSwCompatibility OBJECT-TYPE
    SYNTAX      INTEGER ( 0..999 )
    MAX-ACCESS  read-only
    STATUS      current
    DESCRIPTION "The receiver software compatibility number."
    ::= { aprisaXEReceiver 38 }

aprisaXETReceiverGroup OBJECT-GROUP
    OBJECTS     { aprisaXEReceiverStatus,
                  aprisaXEReceiverCommand,
                  aprisaXEReceiverSynthesiserStatus,
                  aprisaXEReceiver12VPowerStatus,
                  aprisaXEReceiverFrequency,
                  aprisaXEReceiverRSSI,
                  aprisaXEReceiverTemperature,
                  aprisaXEReceiverVTune,
                  aprisaXEReceiver9VSupply,
                  aprisaXEReceiver5VSupply,
                  aprisaXEReceiverModemAGC,
                  aprisaXEReceiverNeg1V5Supply,
                  aprisaXEReceiver3V3Supply,
                  aprisaXEReceiverDacTest,
                  aprisaXEReceiverCharacterisationDataStatus,
                  aprisaXEReceiverSerialNumber,
                  aprisaXEReceiverRfLoopback,
                  aprisaXEReceiverRfLoopbackTimeout,
                  aprisaXEReceiverMibDataStatus,
                  aprisaXEReceiverADCChZero,
                  aprisaXEReceiverADCChOne,
                  aprisaXEReceiverADCChTwo,
                  aprisaXEReceiverADCChThree,
                  aprisaXEReceiverADCChFour,
                  aprisaXEReceiverADCChFive,
                  aprisaXEReceiverADCChSix,
                  aprisaXEReceiverADCChSeven,
                  aprisaXEReceiverADCChEight,
                  aprisaXEReceiverADCChNine,
                  aprisaXEReceiverADCChTen,
                  aprisaXEReceiverRSSIThresQPSKLowerOn,
                  aprisaXEReceiverRSSIThres16QAMLowerOn,
                  aprisaXEReceiverRSSIThres32QAMLowerOn,
                  aprisaXEReceiverRSSIThres64QAMLowerOn,
                  aprisaXEReceiverSynthFileVersion
    }
    STATUS      current
    DESCRIPTION "The AprisaXE Receiver settings group."
    ::= { aprisaXEGroups 46 } 

-- ***************************************************************************
-- End Receiver
-- ***************************************************************************    



-- ***************************************************************************
-- Modem - there is only one Modem for each AprisaXE
--
-- NB: The units for all fields need to be confirmed
--
-- ***************************************************************************

aprisaXEModem OBJECT IDENTIFIER ::= { aprisaXEObjects 61 }

aprisaXEModemDemodAligmentStatus OBJECT-TYPE
    SYNTAX      FourRFAlarmStatus
    MAX-ACCESS  read-only
    STATUS      current
    DESCRIPTION "Status of the demodulator alignment."
    ::= { aprisaXEModem 1 }
    
aprisaXEModemTdmAligmentStatus OBJECT-TYPE
    SYNTAX      FourRFAlarmStatus
    MAX-ACCESS  read-only
    STATUS      current
    DESCRIPTION "Status of the TDM alignment."
    ::= { aprisaXEModem 2 }
    
aprisaXEModemRefAStatus OBJECT-TYPE
    SYNTAX      FourRFAlarmStatus
    MAX-ACCESS  read-only
    STATUS      current
    DESCRIPTION "Status of the REFa clock."
    ::= { aprisaXEModem 3 }
    
aprisaXEModemRefBStatus OBJECT-TYPE
    SYNTAX      FourRFAlarmStatus
    MAX-ACCESS  read-only
    STATUS      current
    DESCRIPTION "Status of the REFb clock."
    ::= { aprisaXEModem 4 }
    
aprisaXEModemUncorrectableBlockCount OBJECT-TYPE
    SYNTAX      FourRFErrorCounter
    MAX-ACCESS  read-only
    STATUS      current
    DESCRIPTION "Count of uncorrectable blocks since last read."
    ::= { aprisaXEModem 5 }
    
aprisaXEModemIQData OBJECT-TYPE
    SYNTAX      AprisaXEIQData
    MAX-ACCESS  read-only
    STATUS      current
    DESCRIPTION "A list of I/Q data pairs, this is a sequence of byes values
                 the first byte is an I value, the second a Q value."
    ::= { aprisaXEModem 6 }
 
aprisaXEModemSyncStatus OBJECT-TYPE
    SYNTAX      FourRFAlarmStatus
    MAX-ACCESS  read-only
    STATUS      current
    DESCRIPTION "Status of the link lock."
    ::= { aprisaXEModem 7 }
    
aprisaXEModemFreqOffsetEnable OBJECT-TYPE
    SYNTAX      INTEGER { offsetDisabled (0),
                          offsetEnabled  (1)
                }
    MAX-ACCESS  read-write
    STATUS      current
    DESCRIPTION "Turn the Modulator frequency offset of 50kHz on or off."
    ::= { aprisaXEModem 8 }
    
aprisaXEModemInterleaverEnable OBJECT-TYPE
    SYNTAX      INTEGER { interleaverEnabled  (100),
                          interleaverDisabled (101),
                          interleaverDefault  (102)
                }
    MAX-ACCESS  read-write
    STATUS      current
    DESCRIPTION "Interleaver being used on the modem. Trade off
                 between link latency and FEC performance."
        ::= { aprisaXEModem 9 }
        
aprisaXEModemQPSKCoding OBJECT-TYPE
    SYNTAX      INTEGER { grayCoded    (0),
                          nonGrayCoded (1)
                }
    MAX-ACCESS  read-write
    STATUS      current
    DESCRIPTION "Encoding and Decoding being used for QPSK. Can be either
                 Gray coded or non Gray coded."
        ::= { aprisaXEModem 10 }

aprisaXEModemConfigVersion OBJECT-TYPE
    SYNTAX      INTEGER ( 0..999 )
    MAX-ACCESS  read-only
    STATUS      current
    DESCRIPTION "Modem Configuration file version."
        ::= { aprisaXEModem 11 }

aprisaXEModemGroup OBJECT-GROUP
    OBJECTS     { aprisaXEModemDemodAligmentStatus,
                  aprisaXEModemTdmAligmentStatus,
                  aprisaXEModemRefAStatus,
                  aprisaXEModemRefBStatus,
                  aprisaXEModemUncorrectableBlockCount,
                  aprisaXEModemIQData,
                  aprisaXEModemSyncStatus,
                  aprisaXEModemFreqOffsetEnable,
                  aprisaXEModemInterleaverEnable,
                  aprisaXEModemQPSKCoding,
                  aprisaXEModemConfigVersion
    }
    STATUS      current
    DESCRIPTION "The AprisaXE Modem settings group."
    ::= { aprisaXEGroups 53 }        

-- ***************************************************************************
-- End Modem
-- ***************************************************************************    


    
-- ***************************************************************************
-- BoardTable - Table for storing basic per slot details.
-- ***************************************************************************

aprisaXEBoardTable OBJECT-TYPE
    SYNTAX      SEQUENCE OF AprisaXEBoardEntry
    MAX-ACCESS  not-accessible
    STATUS      current
    DESCRIPTION "This table stores the basic information for the plugin slots."
    ::= { aprisaXEObjects 66 }

aprisaXEBoardEntry OBJECT-TYPE
    SYNTAX      AprisaXEBoardEntry
    MAX-ACCESS  not-accessible
    STATUS      current
    DESCRIPTION "Slot Information."
    INDEX       { aprisaXEBoardSlot }
    ::= { aprisaXEBoardTable 1 }

-- Each table entry consists of the type of the card in the slot, 
-- the hardware and firmware version numbers and the hardware software
-- compatibility number.

AprisaXEBoardEntry ::= SEQUENCE {
        aprisaXEBoardSlot            INTEGER,
        aprisaXEBoardType            INTEGER,
        aprisaXEExpectedBoardType    INTEGER,
        aprisaXEBoardHardwareVersion INTEGER,
        aprisaXEBoardFirmwareVersion INTEGER,
        aprisaXEBoardHSCNumber       INTEGER,
        aprisaXEBoardSerialNumber    OCTET STRING
    }
    
aprisaXEBoardSlot OBJECT-TYPE
    SYNTAX      AprisaXESlotNumber
    MAX-ACCESS  read-only
    STATUS      current
    DESCRIPTION "The slot number in which the board resides, the physical slots are
                 numbered from zero to ten and mapped to one to eleven in the MIB.
                 The motherboard is therefore in physical slot 0 but MIB slot 1."
    ::= { aprisaXEBoardEntry 1 }

aprisaXEBoardType OBJECT-TYPE
    SYNTAX      AprisaXECardType
    MAX-ACCESS  read-only
    STATUS      current
    DESCRIPTION "The type of the board in the slot. The types are as follows:
                 - none : there is no card in the slot
                 - modem : this card will be fitted in physical slot 0
                 - transmitter : the transmitter card, this will be in physical slot 9
                 - receiver : the receiver card, this will be in physical slot 10
                 - quadJET : e1/t1 4 port card"
    ::= { aprisaXEBoardEntry 2 }

aprisaXEExpectedBoardType OBJECT-TYPE
    SYNTAX      AprisaXECardType
    MAX-ACCESS  read-write
    STATUS      current
    DESCRIPTION "The type of the board expected in the slot. The types are as follows:
                 - none : there is no card in the slot
                 - modem : this card will be fitted in physical slot 0
                 - transmitter : the transmitter card, this will be in physical slot 9
                 - receiver : the receiver card, this will be in physical slot 10
                 - quadJET : e1/t1 4 port card"
    ::= { aprisaXEBoardEntry 3 }

aprisaXEBoardHardwareVersion OBJECT-TYPE
    SYNTAX      AprisaXEHardwareVersion
    MAX-ACCESS  read-only
    STATUS      current
    DESCRIPTION "Field indicating the hardware version for the board in the slot."
    ::= { aprisaXEBoardEntry 4 }
    
aprisaXEBoardFirmwareVersion OBJECT-TYPE
    SYNTAX      AprisaXEHardwareVersion
    MAX-ACCESS  read-only
    STATUS      current
    DESCRIPTION "Field indicating the firmware version for the board in the slot."
    ::= { aprisaXEBoardEntry 5 }

aprisaXEBoardHSCNumber OBJECT-TYPE
    SYNTAX      AprisaXEHardwareVersion
    MAX-ACCESS  read-only
    STATUS      current
    DESCRIPTION "Field indicating the hardware software configuration number
                 for the board in the slot."
    ::= { aprisaXEBoardEntry 6 }
    
aprisaXEBoardSerialNumber OBJECT-TYPE
    SYNTAX      FourRFSerialNumber
    MAX-ACCESS  read-only
    STATUS      current
    DESCRIPTION "Field indicating the module serial number for the card in the slot."
    ::= { aprisaXEBoardEntry 7 }

-- ***************************************************************************
-- End BoardTable
-- ***************************************************************************



-- *************************************************************************** 
-- Alarms - notifications should be defined for each alarm.
--
-- Each alarm has at least three components:
--     Its current status noAlarm or alarmPresent indicating whether the alarm 
--     is present or not. 
--
--     The alarm severity indicating whether the alarm is major or minor (or
--     anything else we want) 
--
--     A flag indicating whether the alarm is enabled 
--     (all alarms are enabled by default)
--
-- Currently all objects are read-only and would be configured from the
-- MIB configuration at startup it is possible to allow the user to change
-- the severity and to enable and disable alarms if this is considered useful.
--
-- ***************************************************************************

aprisaXELinkAlarms OBJECT IDENTIFIER ::= { aprisaXEObjects 86 }

-- ***************************************************************************
-- The Transmitter Alarms
-- ***************************************************************************

aprisaXETransmitterAlarms OBJECT IDENTIFIER ::= { aprisaXELinkAlarms 1 }


--
-- Forward Power High Alarm
--
-- This is a minor alarm
--

aprisaXEForwardPowerHiAlarm OBJECT IDENTIFIER ::= { aprisaXETransmitterAlarms 1 }

aprisaXEForwardPowerHiAlarmStatus OBJECT-TYPE
    SYNTAX      FourRFAlarmStatus
    MAX-ACCESS  read-only
    STATUS      obsolete
    DESCRIPTION "The status of the forward power too high alarm."
    ::= { aprisaXEForwardPowerHiAlarm 1 }

aprisaXEForwardPowerHiAlarmSeverity OBJECT-TYPE
    SYNTAX      FourRFAlarmSeverity
    MAX-ACCESS  read-only
    STATUS      obsolete
    DESCRIPTION "The severity of the forward power too high alarm."
    ::= { aprisaXEForwardPowerHiAlarm 2 }

aprisaXEForwardPowerHiAlarmEnabled OBJECT-TYPE
    SYNTAX      FourRFAlarmEnabled
    MAX-ACCESS  read-only
    STATUS      obsolete
    DESCRIPTION "Indicates whether the forward power too high alarm is enabled."
    ::= { aprisaXEForwardPowerHiAlarm 3 }
    
aprisaXEForwardPowerHiAlarmThreshold OBJECT-TYPE
    SYNTAX      Integer32
    MAX-ACCESS  read-only
    STATUS      obsolete
    DESCRIPTION "Indicates the level at which the forward power too high 
                 alarm will be set."
    ::= { aprisaXEForwardPowerHiAlarm 4 }
    
aprisaXEForwardPowerHiAlarmClearThreshold OBJECT-TYPE
    SYNTAX      Integer32
    MAX-ACCESS  read-only
    STATUS      obsolete
    DESCRIPTION "Indicates the level at which the forward power alarm 
                 will be cleared."
    ::= { aprisaXEForwardPowerHiAlarm 5 }

aprisaXEForwardPowerHiAlarmsGroup OBJECT-GROUP
    OBJECTS     { aprisaXEForwardPowerHiAlarmStatus, 
                  aprisaXEForwardPowerHiAlarmSeverity, 
                  aprisaXEForwardPowerHiAlarmEnabled,
                  aprisaXEForwardPowerHiAlarmThreshold,
                  aprisaXEForwardPowerHiAlarmClearThreshold
    }
    STATUS      obsolete
    DESCRIPTION "The AprisaXE forward power too high alarm group."
    ::= { aprisaXEGroups 56 } 


--
-- Forward Power Low Alarm
--
-- This is a minor alarm
--

aprisaXEForwardPowerLoAlarm OBJECT IDENTIFIER ::= { aprisaXETransmitterAlarms 2 }

aprisaXEForwardPowerLoAlarmStatus OBJECT-TYPE
    SYNTAX      FourRFAlarmStatus
    MAX-ACCESS  read-only
    STATUS      obsolete
    DESCRIPTION "The status of the forward power too low alarm."
    ::= { aprisaXEForwardPowerLoAlarm 1 }

aprisaXEForwardPowerLoAlarmSeverity OBJECT-TYPE
    SYNTAX      FourRFAlarmSeverity
    MAX-ACCESS  read-only
    STATUS      obsolete
    DESCRIPTION "The severity of the forward power too low alarm."
    ::= { aprisaXEForwardPowerLoAlarm 2 }

aprisaXEForwardPowerLoAlarmEnabled OBJECT-TYPE
    SYNTAX      FourRFAlarmEnabled
    MAX-ACCESS  read-only
    STATUS      obsolete
    DESCRIPTION "Indicates whether the forward power too low alarm is enabled."
    ::= { aprisaXEForwardPowerLoAlarm 3 }
    
aprisaXEForwardPowerLoAlarmThreshold OBJECT-TYPE
    SYNTAX      Integer32
    MAX-ACCESS  read-only
    STATUS      obsolete
    DESCRIPTION "Indicates the level at which the forward power too low alarm 
                 will be set."
    ::= { aprisaXEForwardPowerLoAlarm 4 }
    
aprisaXEForwardPowerLoAlarmClearThreshold OBJECT-TYPE
    SYNTAX      Integer32
    MAX-ACCESS  read-only
    STATUS      obsolete
    DESCRIPTION "Indicates the level at which the forward power too low alarm 
                 will be cleared."
    ::= { aprisaXEForwardPowerLoAlarm 5 }

aprisaXEForwardPowerLoAlarmsGroup OBJECT-GROUP
    OBJECTS     { aprisaXEForwardPowerLoAlarmStatus, 
                  aprisaXEForwardPowerLoAlarmSeverity, 
                  aprisaXEForwardPowerLoAlarmEnabled,
                  aprisaXEForwardPowerLoAlarmThreshold,
                  aprisaXEForwardPowerLoAlarmClearThreshold
    }
    STATUS      obsolete
    DESCRIPTION "The AprisaXE forward power low alarm group."
    ::= { aprisaXEGroups 61 } 
    
   
--
-- Reverse Power Too High Alarm
--

aprisaXEReversePowerHiAlarm OBJECT IDENTIFIER ::= { aprisaXETransmitterAlarms 3 }

aprisaXEReversePowerHiAlarmStatus OBJECT-TYPE
    SYNTAX      FourRFAlarmStatus
    MAX-ACCESS  read-only
    STATUS      obsolete
    DESCRIPTION "The status of the reverse power out of limits alarm."
    ::= { aprisaXEReversePowerHiAlarm 1 }

aprisaXEReversePowerHiAlarmSeverity OBJECT-TYPE
    SYNTAX      FourRFAlarmSeverity
    MAX-ACCESS  read-only
    STATUS      obsolete
    DESCRIPTION "The severity of the reverse power out of limits alarm."
    ::= { aprisaXEReversePowerHiAlarm 2 }

aprisaXEReversePowerHiAlarmEnabled OBJECT-TYPE
    SYNTAX      FourRFAlarmEnabled
    MAX-ACCESS  read-only
    STATUS      obsolete
    DESCRIPTION "Indicates whether the reverse power out of limits alarm is enabled."
    ::= { aprisaXEReversePowerHiAlarm 3 }

aprisaXEReversePowerHiAlarmThreshold OBJECT-TYPE
    SYNTAX      Integer32
    MAX-ACCESS  read-only
    STATUS      obsolete
    DESCRIPTION "Indicates the level at which the reverse power alarm will be set."
    ::= { aprisaXEReversePowerHiAlarm 4 }
    
aprisaXEReversePowerHiAlarmClearThreshold OBJECT-TYPE
    SYNTAX      Integer32
    MAX-ACCESS  read-only
    STATUS      obsolete
    DESCRIPTION "Indicates the level at which the reverse power alarm will be cleared."
    ::= { aprisaXEReversePowerHiAlarm 5 }
    
aprisaXEReversePowerHiAlarmsGroup OBJECT-GROUP
    OBJECTS     { aprisaXEReversePowerHiAlarmStatus, 
                  aprisaXEReversePowerHiAlarmSeverity, 
                  aprisaXEReversePowerHiAlarmEnabled,
                  aprisaXEReversePowerHiAlarmThreshold,
                  aprisaXEReversePowerHiAlarmClearThreshold
    }
    STATUS      obsolete
    DESCRIPTION "The AprisaXE reverse power too high alarm group."
    ::= { aprisaXEGroups 66 } 
    
    
--
-- Reverse Power Too Low Alarm
--

aprisaXEReversePowerLoAlarm OBJECT IDENTIFIER ::= { aprisaXETransmitterAlarms 4 }

aprisaXEReversePowerLoAlarmStatus OBJECT-TYPE
    SYNTAX      FourRFAlarmStatus
    MAX-ACCESS  read-only
    STATUS      obsolete
    DESCRIPTION "The status of the reverse power out of limits alarm."
    ::= { aprisaXEReversePowerLoAlarm 1 }

aprisaXEReversePowerLoAlarmSeverity OBJECT-TYPE
    SYNTAX      FourRFAlarmSeverity
    MAX-ACCESS  read-only
    STATUS      obsolete
    DESCRIPTION "The severity of the reverse power out of limits alarm."
    ::= { aprisaXEReversePowerLoAlarm 2 }

aprisaXEReversePowerLoAlarmEnabled OBJECT-TYPE
    SYNTAX      FourRFAlarmEnabled
    MAX-ACCESS  read-only
    STATUS      obsolete
    DESCRIPTION "Indicates whether the reverse power out of limits alarm is enabled."
    ::= { aprisaXEReversePowerLoAlarm 3 }

aprisaXEReversePowerLoAlarmThreshold OBJECT-TYPE
    SYNTAX      Integer32
    MAX-ACCESS  read-only
    STATUS      obsolete
    DESCRIPTION "Indicates the level at which the reverse power alarm will be set."
    ::= { aprisaXEReversePowerLoAlarm 4 }
    
aprisaXEReversePowerLoAlarmClearThreshold OBJECT-TYPE
    SYNTAX      Integer32
    MAX-ACCESS  read-only
    STATUS      obsolete
    DESCRIPTION "Indicates the level at which the reverse power alarm will be cleared."
    ::= { aprisaXEReversePowerLoAlarm 5 }
    
aprisaXEReversePowerLoAlarmsGroup OBJECT-GROUP
    OBJECTS     { aprisaXEReversePowerLoAlarmStatus, 
                  aprisaXEReversePowerLoAlarmSeverity, 
                  aprisaXEReversePowerLoAlarmEnabled,
                  aprisaXEReversePowerLoAlarmThreshold,
                  aprisaXEReversePowerLoAlarmClearThreshold
    }
    STATUS      obsolete
    DESCRIPTION "The AprisaXE reverse power too low alarm group."
    ::= { aprisaXEGroups 71 }
    
    
--
-- Transmitter PA Temperature Alarm
--
-- This alarm is raised when the transmitter temperature exceeds a defined 
-- threshold. This is a major alarm as the transmitter will be switched off
-- when this alarm is present.
--
    
aprisaXETxPaTempAlarm OBJECT IDENTIFIER ::= { aprisaXETransmitterAlarms 5 }

aprisaXETxPaTempAlarmStatus OBJECT-TYPE
    SYNTAX      FourRFAlarmStatus
    MAX-ACCESS  read-only
    STATUS      obsolete
    DESCRIPTION "The status of the transmitter temperature too high alarm."
    ::= { aprisaXETxPaTempAlarm 1 }

aprisaXETxPaTempAlarmSeverity OBJECT-TYPE
    SYNTAX      FourRFAlarmSeverity
    MAX-ACCESS  read-only
    STATUS      obsolete
    DESCRIPTION "The severity of the transmitter temperature too high alarm."
    ::= { aprisaXETxPaTempAlarm 2 }

aprisaXETxPaTempAlarmEnabled OBJECT-TYPE
    SYNTAX      FourRFAlarmEnabled
    MAX-ACCESS  read-only
    STATUS      obsolete
    DESCRIPTION "Indicates whether the transmitter temperature too high alarm is enabled."
    ::= { aprisaXETxPaTempAlarm 3 }
    
aprisaXETxPaTempAlarmThreshold OBJECT-TYPE
    SYNTAX      Integer32
    MAX-ACCESS  read-only
    STATUS      obsolete
    DESCRIPTION "Indicates the level at which the transmitter temperature too high 
                 alarm will be set."
    ::= { aprisaXETxPaTempAlarm 4 }
    
aprisaXETxPaTempAlarmClearThreshold OBJECT-TYPE
    SYNTAX      Integer32
    MAX-ACCESS  read-only
    STATUS      obsolete
    DESCRIPTION "Indicates the level at which the transmitter temperature too high 
                 will be cleared."
    ::= { aprisaXETxPaTempAlarm 5 }

aprisaXETxPaTempAlarmsGroup OBJECT-GROUP
    OBJECTS     { aprisaXETxPaTempAlarmStatus, 
                  aprisaXETxPaTempAlarmSeverity, 
                  aprisaXETxPaTempAlarmEnabled,
                  aprisaXETxPaTempAlarmThreshold,
                  aprisaXETxPaTempAlarmClearThreshold
    }
    STATUS      obsolete
    DESCRIPTION "The AprisaXE transmitter temperature too high alarm group."
    ::= { aprisaXEGroups 76 } 
    
    
aprisaXETxPaTempWarnAlarm OBJECT IDENTIFIER ::= { aprisaXETransmitterAlarms 6 }

aprisaXETxPaTempWarnAlarmStatus OBJECT-TYPE
    SYNTAX      FourRFAlarmStatus
    MAX-ACCESS  read-only
    STATUS      obsolete
    DESCRIPTION "The status of the transmitter temperature warning alarm."
    ::= { aprisaXETxPaTempWarnAlarm 1 }

aprisaXETxPaTempWarnAlarmSeverity OBJECT-TYPE
    SYNTAX      FourRFAlarmSeverity
    MAX-ACCESS  read-only
    STATUS      obsolete
    DESCRIPTION "The severity of the transmitter temperature warning alarm."
    ::= { aprisaXETxPaTempWarnAlarm 2 }

aprisaXETxPaTempWarnAlarmEnabled OBJECT-TYPE
    SYNTAX      FourRFAlarmEnabled
    MAX-ACCESS  read-only
    STATUS      obsolete
    DESCRIPTION "Indicates whether the transmitter temperature warning alarm is enabled."
    ::= { aprisaXETxPaTempWarnAlarm 3 }
    
aprisaXETxPaTempWarnAlarmThreshold OBJECT-TYPE
    SYNTAX      Integer32
    MAX-ACCESS  read-only
    STATUS      obsolete
    DESCRIPTION "Indicates the level at which the transmitter temperature warning 
                 alarm will be set."
    ::= { aprisaXETxPaTempWarnAlarm 4 }
    
aprisaXETxPaTempWarnAlarmClearThreshold OBJECT-TYPE
    SYNTAX      Integer32
    MAX-ACCESS  read-only
    STATUS      obsolete
    DESCRIPTION "Indicates the level at which the transmitter temperature warning 
                 will be cleared."
    ::= { aprisaXETxPaTempWarnAlarm 5 }

aprisaXETxPaTempWarnAlarmsGroup OBJECT-GROUP
    OBJECTS     { aprisaXETxPaTempWarnAlarmStatus, 
                  aprisaXETxPaTempWarnAlarmSeverity, 
                  aprisaXETxPaTempWarnAlarmEnabled,
                  aprisaXETxPaTempWarnAlarmThreshold,
                  aprisaXETxPaTempWarnAlarmClearThreshold
    }
    STATUS      obsolete
    DESCRIPTION "The AprisaXE transmitter temperature warning alarm group."
    ::= { aprisaXEGroups 81 } 
    

aprisaXETxAgcHiAlarm OBJECT IDENTIFIER ::= { aprisaXETransmitterAlarms 7 }

aprisaXETxAgcHiAlarmStatus OBJECT-TYPE
    SYNTAX      FourRFAlarmStatus
    MAX-ACCESS  read-only
    STATUS      obsolete
    DESCRIPTION "The status of the transmitter AGC too high alarm."
    ::= { aprisaXETxAgcHiAlarm 1 }

aprisaXETxAgcHiAlarmSeverity OBJECT-TYPE
    SYNTAX      FourRFAlarmSeverity
    MAX-ACCESS  read-only
    STATUS      obsolete
    DESCRIPTION "The severity of the transmitter AGC too high alarm."
    ::= { aprisaXETxAgcHiAlarm 2 }

aprisaXETxAgcHiAlarmEnabled OBJECT-TYPE
    SYNTAX      FourRFAlarmEnabled
    MAX-ACCESS  read-only
    STATUS      obsolete
    DESCRIPTION "Indicates whether the transmitter AGC too high alarm is enabled."
    ::= { aprisaXETxAgcHiAlarm 3 }
    
aprisaXETxAgcHiAlarmThreshold OBJECT-TYPE
    SYNTAX      Integer32
    MAX-ACCESS  read-only
    STATUS      obsolete
    DESCRIPTION "Indicates the level at which the transmitter AGC too high 
                 alarm will be set."
    ::= { aprisaXETxAgcHiAlarm 4 }
    
aprisaXETxAgcHiAlarmClearThreshold OBJECT-TYPE
    SYNTAX      Integer32
    MAX-ACCESS  read-only
    STATUS      obsolete
    DESCRIPTION "Indicates the level at which the transmitter AGC too high 
                 will be cleared."
    ::= { aprisaXETxAgcHiAlarm 5 }

aprisaXETxAgcHiAlarmsGroup OBJECT-GROUP
    OBJECTS     { aprisaXETxAgcHiAlarmStatus, 
                  aprisaXETxAgcHiAlarmSeverity, 
                  aprisaXETxAgcHiAlarmEnabled,
                  aprisaXETxAgcHiAlarmThreshold,
                  aprisaXETxAgcHiAlarmClearThreshold
    }
    STATUS      obsolete
    DESCRIPTION "The AprisaXE transmitter AGC too high alarm group."
    ::= { aprisaXEGroups 86 } 
    
    
aprisaXETxAgcLoAlarm OBJECT IDENTIFIER ::= { aprisaXETransmitterAlarms 8 }

aprisaXETxAgcLoAlarmStatus OBJECT-TYPE
    SYNTAX      FourRFAlarmStatus
    MAX-ACCESS  read-only
    STATUS      obsolete
    DESCRIPTION "The status of the transmitter AGC too low alarm."
    ::= { aprisaXETxAgcLoAlarm 1 }

aprisaXETxAgcLoAlarmSeverity OBJECT-TYPE
    SYNTAX      FourRFAlarmSeverity
    MAX-ACCESS  read-only
    STATUS      obsolete
    DESCRIPTION "The severity of the transmitter AGC too low alarm."
    ::= { aprisaXETxAgcLoAlarm 2 }

aprisaXETxAgcLoAlarmEnabled OBJECT-TYPE
    SYNTAX      FourRFAlarmEnabled
    MAX-ACCESS  read-only
    STATUS      obsolete
    DESCRIPTION "Indicates whether the transmitter AGC too low alarm is enabled."
    ::= { aprisaXETxAgcLoAlarm 3 }
    
aprisaXETxAgcLoAlarmThreshold OBJECT-TYPE
    SYNTAX      Integer32
    MAX-ACCESS  read-only
    STATUS      obsolete
    DESCRIPTION "Indicates the level at which the transmitter AGC too low 
                 alarm will be set."
    ::= { aprisaXETxAgcLoAlarm 4 }
    
aprisaXETxAgcLoAlarmClearThreshold OBJECT-TYPE
    SYNTAX      Integer32
    MAX-ACCESS  read-only
    STATUS      obsolete
    DESCRIPTION "Indicates the level at which the transmitter AGC too low 
                 will be cleared."
    ::= { aprisaXETxAgcLoAlarm 5 }

aprisaXETxAgcLoAlarmsGroup OBJECT-GROUP
    OBJECTS     { aprisaXETxAgcLoAlarmStatus, 
                  aprisaXETxAgcLoAlarmSeverity, 
                  aprisaXETxAgcLoAlarmEnabled,
                  aprisaXETxAgcLoAlarmThreshold,
                  aprisaXETxAgcLoAlarmClearThreshold
    }
    STATUS      obsolete
    DESCRIPTION "The AprisaXE transmitter AGC too low alarm group."
    ::= { aprisaXEGroups 91 } 


aprisaXETxVtuneHiAlarm OBJECT IDENTIFIER ::= { aprisaXETransmitterAlarms 9 }

aprisaXETxVtuneHiAlarmStatus OBJECT-TYPE
    SYNTAX      FourRFAlarmStatus
    MAX-ACCESS  read-only
    STATUS      obsolete
    DESCRIPTION "The status of the transmitter VTUNE too high alarm."
    ::= { aprisaXETxVtuneHiAlarm 1 }

aprisaXETxVtuneHiAlarmSeverity OBJECT-TYPE
    SYNTAX      FourRFAlarmSeverity
    MAX-ACCESS  read-only
    STATUS      obsolete
    DESCRIPTION "The severity of the transmitter VTUNE too high alarm."
    ::= { aprisaXETxVtuneHiAlarm 2 }

aprisaXETxVtuneHiAlarmEnabled OBJECT-TYPE
    SYNTAX      FourRFAlarmEnabled
    MAX-ACCESS  read-only
    STATUS      obsolete
    DESCRIPTION "Indicates whether the transmitter VTUNE too high alarm is enabled."
    ::= { aprisaXETxVtuneHiAlarm 3 }
    
aprisaXETxVtuneHiAlarmThreshold OBJECT-TYPE
    SYNTAX      Integer32
    MAX-ACCESS  read-only
    STATUS      obsolete
    DESCRIPTION "Indicates the level at which the transmitter VTUNE too high 
                 alarm will be set."
    ::= { aprisaXETxVtuneHiAlarm 4 }
    
aprisaXETxVtuneHiAlarmClearThreshold OBJECT-TYPE
    SYNTAX      Integer32
    MAX-ACCESS  read-only
    STATUS      obsolete
    DESCRIPTION "Indicates the level at which the transmitter VTUNE too high 
                 will be cleared."
    ::= { aprisaXETxVtuneHiAlarm 5 }

aprisaXETxVtuneHiAlarmsGroup OBJECT-GROUP
    OBJECTS     { aprisaXETxVtuneHiAlarmStatus, 
                  aprisaXETxVtuneHiAlarmSeverity, 
                  aprisaXETxVtuneHiAlarmEnabled,
                  aprisaXETxVtuneHiAlarmThreshold,
                  aprisaXETxVtuneHiAlarmClearThreshold
    }
    STATUS      obsolete
    DESCRIPTION "The AprisaXE transmitter VTUNE too high alarm group."
    ::= { aprisaXEGroups 96 } 


aprisaXETxVtuneLoAlarm OBJECT IDENTIFIER ::= { aprisaXETransmitterAlarms 10 }

aprisaXETxVtuneLoAlarmStatus OBJECT-TYPE
    SYNTAX      FourRFAlarmStatus
    MAX-ACCESS  read-only
    STATUS      obsolete
    DESCRIPTION "The status of the transmitter VTUNE too low alarm."
    ::= { aprisaXETxVtuneLoAlarm 1 }

aprisaXETxVtuneLoAlarmSeverity OBJECT-TYPE
    SYNTAX      FourRFAlarmSeverity
    MAX-ACCESS  read-only
    STATUS      obsolete
    DESCRIPTION "The severity of the transmitter VTUNE too low alarm."
    ::= { aprisaXETxVtuneLoAlarm 2 }

aprisaXETxVtuneLoAlarmEnabled OBJECT-TYPE
    SYNTAX      FourRFAlarmEnabled
    MAX-ACCESS  read-only
    STATUS      obsolete
    DESCRIPTION "Indicates whether the transmitter VTUNE too low alarm is enabled."
    ::= { aprisaXETxVtuneLoAlarm 3 }
    
aprisaXETxVtuneLoAlarmThreshold OBJECT-TYPE
    SYNTAX      Integer32
    MAX-ACCESS  read-only
    STATUS      obsolete
    DESCRIPTION "Indicates the level at which the transmitter VTUNE too low 
                 alarm will be set."
    ::= { aprisaXETxVtuneLoAlarm 4 }
    
aprisaXETxVtuneLoAlarmClearThreshold OBJECT-TYPE
    SYNTAX      Integer32
    MAX-ACCESS  read-only
    STATUS      obsolete
    DESCRIPTION "Indicates the level at which the transmitter VTUNE too low 
                 will be cleared."
    ::= { aprisaXETxVtuneLoAlarm 5 }

aprisaXETxVtuneLoAlarmsGroup OBJECT-GROUP
    OBJECTS     { aprisaXETxVtuneLoAlarmStatus, 
                  aprisaXETxVtuneLoAlarmSeverity, 
                  aprisaXETxVtuneLoAlarmEnabled,
                  aprisaXETxVtuneLoAlarmThreshold,
                  aprisaXETxVtuneLoAlarmClearThreshold
    }
    STATUS      obsolete
    DESCRIPTION "The AprisaXE transmitter VTUNE too low alarm group."
    ::= { aprisaXEGroups 101 } 
    
    
aprisaXETx5VDigHiAlarm OBJECT IDENTIFIER ::= { aprisaXETransmitterAlarms 11 }

aprisaXETx5VDigHiAlarmStatus OBJECT-TYPE
    SYNTAX      FourRFAlarmStatus
    MAX-ACCESS  read-only
    STATUS      obsolete
    DESCRIPTION "The status of the transmitter 5V digital voltage too high alarm."
    ::= { aprisaXETx5VDigHiAlarm 1 }

aprisaXETx5VDigHiAlarmSeverity OBJECT-TYPE
    SYNTAX      FourRFAlarmSeverity
    MAX-ACCESS  read-only
    STATUS      obsolete
    DESCRIPTION "The severity of the transmitter 5V digital voltage too high alarm."
    ::= { aprisaXETx5VDigHiAlarm 2 }

aprisaXETx5VDigHiAlarmEnabled OBJECT-TYPE
    SYNTAX      FourRFAlarmEnabled
    MAX-ACCESS  read-only
    STATUS      obsolete
    DESCRIPTION "Indicates whether the transmitter 5V digital voltage too high alarm is enabled."
    ::= { aprisaXETx5VDigHiAlarm 3 }
    
aprisaXETx5VDigHiAlarmThreshold OBJECT-TYPE
    SYNTAX      Integer32
    MAX-ACCESS  read-only
    STATUS      obsolete
    DESCRIPTION "Indicates the level at which the transmitter 5V digital voltage too high 
                 alarm will be set."
    ::= { aprisaXETx5VDigHiAlarm 4 }
    
aprisaXETx5VDigHiAlarmClearThreshold OBJECT-TYPE
    SYNTAX      Integer32
    MAX-ACCESS  read-only
    STATUS      obsolete
    DESCRIPTION "Indicates the level at which the transmitter 5V digital voltage too high 
                 will be cleared."
    ::= { aprisaXETx5VDigHiAlarm 5 }

aprisaXETx5VDigHiAlarmsGroup OBJECT-GROUP
    OBJECTS     { aprisaXETx5VDigHiAlarmStatus, 
                  aprisaXETx5VDigHiAlarmSeverity, 
                  aprisaXETx5VDigHiAlarmEnabled,
                  aprisaXETx5VDigHiAlarmThreshold,
                  aprisaXETx5VDigHiAlarmClearThreshold
    }
    STATUS      obsolete
    DESCRIPTION "The AprisaXE transmitter 5V digital voltage too high alarm group."
    ::= { aprisaXEGroups 106 } 
    

aprisaXETx5VDigLoAlarm OBJECT IDENTIFIER ::= { aprisaXETransmitterAlarms 12 }

aprisaXETx5VDigLoAlarmStatus OBJECT-TYPE
    SYNTAX      FourRFAlarmStatus
    MAX-ACCESS  read-only
    STATUS      obsolete
    DESCRIPTION "The status of the transmitter 5V digital voltage too low alarm."
    ::= { aprisaXETx5VDigLoAlarm 1 }

aprisaXETx5VDigLoAlarmSeverity OBJECT-TYPE
    SYNTAX      FourRFAlarmSeverity
    MAX-ACCESS  read-only
    STATUS      obsolete
    DESCRIPTION "The severity of the transmitter 5V digital voltage too low alarm."
    ::= { aprisaXETx5VDigLoAlarm 2 }

aprisaXETx5VDigLoAlarmEnabled OBJECT-TYPE
    SYNTAX      FourRFAlarmEnabled
    MAX-ACCESS  read-only
    STATUS      obsolete
    DESCRIPTION "Indicates whether the transmitter 5V digital voltage too low alarm is enabled."
    ::= { aprisaXETx5VDigLoAlarm 3 }
    
aprisaXETx5VDigLoAlarmThreshold OBJECT-TYPE
    SYNTAX      Integer32
    MAX-ACCESS  read-only
    STATUS      obsolete
    DESCRIPTION "Indicates the level at which the transmitter 5V digital voltage too low 
                 alarm will be set."
    ::= { aprisaXETx5VDigLoAlarm 4 }
    
aprisaXETx5VDigLoAlarmClearThreshold OBJECT-TYPE
    SYNTAX      Integer32
    MAX-ACCESS  read-only
    STATUS      obsolete
    DESCRIPTION "Indicates the level at which the transmitter 5V digital voltage too low 
                 will be cleared."
    ::= { aprisaXETx5VDigLoAlarm 5 }

aprisaXETx5VDigLoAlarmsGroup OBJECT-GROUP
    OBJECTS     { aprisaXETx5VDigLoAlarmStatus, 
                  aprisaXETx5VDigLoAlarmSeverity, 
                  aprisaXETx5VDigLoAlarmEnabled,
                  aprisaXETx5VDigLoAlarmThreshold,
                  aprisaXETx5VDigLoAlarmClearThreshold
    }
    STATUS      obsolete
    DESCRIPTION "The AprisaXE transmitter 5V digital voltage too low alarm group."
    ::= { aprisaXEGroups 111 } 
    
    
aprisaXETx7VRfHiAlarm OBJECT IDENTIFIER ::= { aprisaXETransmitterAlarms 13 }

aprisaXETx7VRfHiAlarmStatus OBJECT-TYPE
    SYNTAX      FourRFAlarmStatus
    MAX-ACCESS  read-only
    STATUS      obsolete
    DESCRIPTION "The status of the transmitter 7V RF voltage too high alarm."
    ::= { aprisaXETx7VRfHiAlarm 1 }

aprisaXETx7VRfHiAlarmSeverity OBJECT-TYPE
    SYNTAX      FourRFAlarmSeverity
    MAX-ACCESS  read-only
    STATUS      obsolete
    DESCRIPTION "The severity of the transmitter 7V RF voltage too high alarm."
    ::= { aprisaXETx7VRfHiAlarm 2 }

aprisaXETx7VRfHiAlarmEnabled OBJECT-TYPE
    SYNTAX      FourRFAlarmEnabled
    MAX-ACCESS  read-only
    STATUS      obsolete
    DESCRIPTION "Indicates whether the transmitter 7V RF voltage too high alarm is enabled."
    ::= { aprisaXETx7VRfHiAlarm 3 }
    
aprisaXETx7VRfHiAlarmThreshold OBJECT-TYPE
    SYNTAX      Integer32
    MAX-ACCESS  read-only
    STATUS      obsolete
    DESCRIPTION "Indicates the level at which the transmitter 7V RF voltage too high 
                 alarm will be set."
    ::= { aprisaXETx7VRfHiAlarm 4 }
    
aprisaXETx7VRfHiAlarmClearThreshold OBJECT-TYPE
    SYNTAX      Integer32
    MAX-ACCESS  read-only
    STATUS      obsolete
    DESCRIPTION "Indicates the level at which the transmitter 7V RF voltage too high 
                 will be cleared."
    ::= { aprisaXETx7VRfHiAlarm 5 }

aprisaXETx7VRfHiAlarmsGroup OBJECT-GROUP
    OBJECTS     { aprisaXETx7VRfHiAlarmStatus, 
                  aprisaXETx7VRfHiAlarmSeverity, 
                  aprisaXETx7VRfHiAlarmEnabled,
                  aprisaXETx7VRfHiAlarmThreshold,
                  aprisaXETx7VRfHiAlarmClearThreshold
    }
    STATUS      obsolete
    DESCRIPTION "The AprisaXE transmitter 7V RF voltage too high alarm group."
    ::= { aprisaXEGroups 116 } 
    
    
aprisaXETx7VRfLoAlarm OBJECT IDENTIFIER ::= { aprisaXETransmitterAlarms 14 }

aprisaXETx7VRfLoAlarmStatus OBJECT-TYPE
    SYNTAX      FourRFAlarmStatus
    MAX-ACCESS  read-only
    STATUS      obsolete
    DESCRIPTION "The status of the transmitter 7V RF voltage too low alarm."
    ::= { aprisaXETx7VRfLoAlarm 1 }

aprisaXETx7VRfLoAlarmSeverity OBJECT-TYPE
    SYNTAX      FourRFAlarmSeverity
    MAX-ACCESS  read-only
    STATUS      obsolete
    DESCRIPTION "The severity of the transmitter 7V RF voltage too low alarm."
    ::= { aprisaXETx7VRfLoAlarm 2 }

aprisaXETx7VRfLoAlarmEnabled OBJECT-TYPE
    SYNTAX      FourRFAlarmEnabled
    MAX-ACCESS  read-only
    STATUS      obsolete
    DESCRIPTION "Indicates whether the transmitter 7V RF voltage too low alarm is enabled."
    ::= { aprisaXETx7VRfLoAlarm 3 }
    
aprisaXETx7VRfLoAlarmThreshold OBJECT-TYPE
    SYNTAX      Integer32
    MAX-ACCESS  read-only
    STATUS      obsolete
    DESCRIPTION "Indicates the level at which the transmitter 7V RF voltage too low 
                 alarm will be set."
    ::= { aprisaXETx7VRfLoAlarm 4 }
    
aprisaXETx7VRfLoAlarmClearThreshold OBJECT-TYPE
    SYNTAX      Integer32
    MAX-ACCESS  read-only
    STATUS      obsolete
    DESCRIPTION "Indicates the level at which the transmitter 7V RF voltage too low 
                 will be cleared."
    ::= { aprisaXETx7VRfLoAlarm 5 }

aprisaXETx7VRfLoAlarmsGroup OBJECT-GROUP
    OBJECTS     { aprisaXETx7VRfLoAlarmStatus, 
                  aprisaXETx7VRfLoAlarmSeverity, 
                  aprisaXETx7VRfLoAlarmEnabled,
                  aprisaXETx7VRfLoAlarmThreshold,
                  aprisaXETx7VRfLoAlarmClearThreshold
    }
    STATUS      obsolete
    DESCRIPTION "The AprisaXE transmitter 7V RF voltage too low alarm group."
    ::= { aprisaXEGroups 121 } 
  

aprisaXETx9VHiAlarm OBJECT IDENTIFIER ::= { aprisaXETransmitterAlarms 15 }

aprisaXETx9VHiAlarmStatus OBJECT-TYPE
    SYNTAX      FourRFAlarmStatus
    MAX-ACCESS  read-only
    STATUS      obsolete
    DESCRIPTION "The status of the transmitter 9V voltage too high alarm."
    ::= { aprisaXETx9VHiAlarm 1 }

aprisaXETx9VHiAlarmSeverity OBJECT-TYPE
    SYNTAX      FourRFAlarmSeverity
    MAX-ACCESS  read-only
    STATUS      obsolete
    DESCRIPTION "The severity of the transmitter 9V voltage too high alarm."
    ::= { aprisaXETx9VHiAlarm 2 }

aprisaXETx9VHiAlarmEnabled OBJECT-TYPE
    SYNTAX      FourRFAlarmEnabled
    MAX-ACCESS  read-only
    STATUS      obsolete
    DESCRIPTION "Indicates whether the transmitter 9V voltage too high alarm is enabled."
    ::= { aprisaXETx9VHiAlarm 3 }
    
aprisaXETx9VHiAlarmThreshold OBJECT-TYPE
    SYNTAX      Integer32
    MAX-ACCESS  read-only
    STATUS      obsolete
    DESCRIPTION "Indicates the level at which the transmitter 9V voltage too high 
                 alarm will be set."
    ::= { aprisaXETx9VHiAlarm 4 }
    
aprisaXETx9VHiAlarmClearThreshold OBJECT-TYPE
    SYNTAX      Integer32
    MAX-ACCESS  read-only
    STATUS      obsolete
    DESCRIPTION "Indicates the level at which the transmitter 9V voltage too high 
                 will be cleared."
    ::= { aprisaXETx9VHiAlarm 5 }

aprisaXETx9VHiAlarmsGroup OBJECT-GROUP
    OBJECTS     { aprisaXETx9VHiAlarmStatus, 
                  aprisaXETx9VHiAlarmSeverity, 
                  aprisaXETx9VHiAlarmEnabled,
                  aprisaXETx9VHiAlarmThreshold,
                  aprisaXETx9VHiAlarmClearThreshold
    }
    STATUS      obsolete
    DESCRIPTION "The AprisaXE transmitter 9V voltage too high alarm group."
    ::= { aprisaXEGroups 126 } 
    
    
aprisaXETx9VLoAlarm OBJECT IDENTIFIER ::= { aprisaXETransmitterAlarms 16 }

aprisaXETx9VLoAlarmStatus OBJECT-TYPE
    SYNTAX      FourRFAlarmStatus
    MAX-ACCESS  read-only
    STATUS      obsolete
    DESCRIPTION "The status of the transmitter 9V voltage too low alarm."
    ::= { aprisaXETx9VLoAlarm 1 }

aprisaXETx9VLoAlarmSeverity OBJECT-TYPE
    SYNTAX      FourRFAlarmSeverity
    MAX-ACCESS  read-only
    STATUS      obsolete
    DESCRIPTION "The severity of the transmitter 9V voltage too low alarm."
    ::= { aprisaXETx9VLoAlarm 2 }

aprisaXETx9VLoAlarmEnabled OBJECT-TYPE
    SYNTAX      FourRFAlarmEnabled
    MAX-ACCESS  read-only
    STATUS      obsolete
    DESCRIPTION "Indicates whether the transmitter 9V voltage too low alarm is enabled."
    ::= { aprisaXETx9VLoAlarm 3 }
    
aprisaXETx9VLoAlarmThreshold OBJECT-TYPE
    SYNTAX      Integer32
    MAX-ACCESS  read-only
    STATUS      obsolete
    DESCRIPTION "Indicates the level at which the transmitter 9V voltage too low 
                 alarm will be set."
    ::= { aprisaXETx9VLoAlarm 4 }
    
aprisaXETx9VLoAlarmClearThreshold OBJECT-TYPE
    SYNTAX      Integer32
    MAX-ACCESS  read-only
    STATUS      obsolete
    DESCRIPTION "Indicates the level at which the transmitter 9V voltage too low 
                 will be cleared."
    ::= { aprisaXETx9VLoAlarm 5 }

aprisaXETx9VLoAlarmsGroup OBJECT-GROUP
    OBJECTS     { aprisaXETx9VLoAlarmStatus, 
                  aprisaXETx9VLoAlarmSeverity, 
                  aprisaXETx9VLoAlarmEnabled,
                  aprisaXETx9VLoAlarmThreshold,
                  aprisaXETx9VLoAlarmClearThreshold
    }
    STATUS      obsolete
    DESCRIPTION "The AprisaXE transmitter 9V voltage too low alarm group."
    ::= { aprisaXEGroups 131 } 


aprisaXETx11VHiAlarm OBJECT IDENTIFIER ::= { aprisaXETransmitterAlarms 17 }

aprisaXETx11VHiAlarmStatus OBJECT-TYPE
    SYNTAX      FourRFAlarmStatus
    MAX-ACCESS  read-only
    STATUS      obsolete
    DESCRIPTION "The status of the transmitter 11V voltage too high alarm."
    ::= { aprisaXETx11VHiAlarm 1 }

aprisaXETx11VHiAlarmSeverity OBJECT-TYPE
    SYNTAX      FourRFAlarmSeverity
    MAX-ACCESS  read-only
    STATUS      obsolete
    DESCRIPTION "The severity of the transmitter 11V voltage too high alarm."
    ::= { aprisaXETx11VHiAlarm 2 }

aprisaXETx11VHiAlarmEnabled OBJECT-TYPE
    SYNTAX      FourRFAlarmEnabled
    MAX-ACCESS  read-only
    STATUS      obsolete
    DESCRIPTION "Indicates whether the transmitter 11V voltage too high alarm is enabled."
    ::= { aprisaXETx11VHiAlarm 3 }
    
aprisaXETx11VHiAlarmThreshold OBJECT-TYPE
    SYNTAX      Integer32
    MAX-ACCESS  read-only
    STATUS      obsolete
    DESCRIPTION "Indicates the level at which the transmitter 11V voltage too high 
                 alarm will be set."
    ::= { aprisaXETx11VHiAlarm 4 }
    
aprisaXETx11VHiAlarmClearThreshold OBJECT-TYPE
    SYNTAX      Integer32
    MAX-ACCESS  read-only
    STATUS      obsolete
    DESCRIPTION "Indicates the level at which the transmitter 11V voltage too high 
                 will be cleared."
    ::= { aprisaXETx11VHiAlarm 5 }

aprisaXETx11VHiAlarmsGroup OBJECT-GROUP
    OBJECTS     { aprisaXETx11VHiAlarmStatus, 
                  aprisaXETx11VHiAlarmSeverity, 
                  aprisaXETx11VHiAlarmEnabled,
                  aprisaXETx11VHiAlarmThreshold,
                  aprisaXETx11VHiAlarmClearThreshold
    }
    STATUS      obsolete
    DESCRIPTION "The AprisaXE transmitter 11V voltage too high alarm group."
    ::= { aprisaXEGroups 136 } 


aprisaXETx11VLoAlarm OBJECT IDENTIFIER ::= { aprisaXETransmitterAlarms 18 }

aprisaXETx11VLoAlarmStatus OBJECT-TYPE
    SYNTAX      FourRFAlarmStatus
    MAX-ACCESS  read-only
    STATUS      obsolete
    DESCRIPTION "The status of the transmitter 11V voltage too low alarm."
    ::= { aprisaXETx11VLoAlarm 1 }

aprisaXETx11VLoAlarmSeverity OBJECT-TYPE
    SYNTAX      FourRFAlarmSeverity
    MAX-ACCESS  read-only
    STATUS      obsolete
    DESCRIPTION "The severity of the transmitter 11V voltage too low alarm."
    ::= { aprisaXETx11VLoAlarm 2 }

aprisaXETx11VLoAlarmEnabled OBJECT-TYPE
    SYNTAX      FourRFAlarmEnabled
    MAX-ACCESS  read-only
    STATUS      obsolete
    DESCRIPTION "Indicates whether the transmitter 11V voltage too low alarm is enabled."
    ::= { aprisaXETx11VLoAlarm 3 }
    
aprisaXETx11VLoAlarmThreshold OBJECT-TYPE
    SYNTAX      Integer32
    MAX-ACCESS  read-only
    STATUS      obsolete
    DESCRIPTION "Indicates the level at which the transmitter 11V voltage too low 
                 alarm will be set."
    ::= { aprisaXETx11VLoAlarm 4 }
    
aprisaXETx11VLoAlarmClearThreshold OBJECT-TYPE
    SYNTAX      Integer32
    MAX-ACCESS  read-only
    STATUS      obsolete
    DESCRIPTION "Indicates the level at which the transmitter 11V voltage too low 
                 will be cleared."
    ::= { aprisaXETx11VLoAlarm 5 }

aprisaXETx11VLoAlarmsGroup OBJECT-GROUP
    OBJECTS     { aprisaXETx11VLoAlarmStatus, 
                  aprisaXETx11VLoAlarmSeverity, 
                  aprisaXETx11VLoAlarmEnabled,
                  aprisaXETx11VLoAlarmThreshold,
                  aprisaXETx11VLoAlarmClearThreshold
    }
    STATUS      obsolete
    DESCRIPTION "The AprisaXE transmitter 11V voltage too low alarm group."
    ::= { aprisaXEGroups 141 } 
    
    
aprisaXETx28VHiAlarm OBJECT IDENTIFIER ::= { aprisaXETransmitterAlarms 19 }

aprisaXETx28VHiAlarmStatus OBJECT-TYPE
    SYNTAX      FourRFAlarmStatus
    MAX-ACCESS  read-only
    STATUS      obsolete
    DESCRIPTION "The status of the transmitter 28V voltage too high alarm."
    ::= { aprisaXETx28VHiAlarm 1 }

aprisaXETx28VHiAlarmSeverity OBJECT-TYPE
    SYNTAX      FourRFAlarmSeverity
    MAX-ACCESS  read-only
    STATUS      obsolete
    DESCRIPTION "The severity of the transmitter 28V voltage too high alarm."
    ::= { aprisaXETx28VHiAlarm 2 }

aprisaXETx28VHiAlarmEnabled OBJECT-TYPE
    SYNTAX      FourRFAlarmEnabled
    MAX-ACCESS  read-only
    STATUS      obsolete
    DESCRIPTION "Indicates whether the transmitter 28V voltage too high alarm is enabled."
    ::= { aprisaXETx28VHiAlarm 3 }
    
aprisaXETx28VHiAlarmThreshold OBJECT-TYPE
    SYNTAX      Integer32
    MAX-ACCESS  read-only
    STATUS      obsolete
    DESCRIPTION "Indicates the level at which the transmitter 28V voltage too high 
                 alarm will be set."
    ::= { aprisaXETx28VHiAlarm 4 }
    
aprisaXETx28VHiAlarmClearThreshold OBJECT-TYPE
    SYNTAX      Integer32
    MAX-ACCESS  read-only
    STATUS      obsolete
    DESCRIPTION "Indicates the level at which the transmitter 28V voltage too high 
                 will be cleared."
    ::= { aprisaXETx28VHiAlarm 5 }

aprisaXETx28VHiAlarmsGroup OBJECT-GROUP
    OBJECTS     { aprisaXETx28VHiAlarmStatus, 
                  aprisaXETx28VHiAlarmSeverity, 
                  aprisaXETx28VHiAlarmEnabled,
                  aprisaXETx28VHiAlarmThreshold,
                  aprisaXETx28VHiAlarmClearThreshold
    }
    STATUS      obsolete
    DESCRIPTION "The AprisaXE transmitter 28V voltage too high alarm group."
    ::= { aprisaXEGroups 146 } 
    
    
aprisaXETx28VLoAlarm OBJECT IDENTIFIER ::= { aprisaXETransmitterAlarms 20 }

aprisaXETx28VLoAlarmStatus OBJECT-TYPE
    SYNTAX      FourRFAlarmStatus
    MAX-ACCESS  read-only
    STATUS      obsolete
    DESCRIPTION "The status of the transmitter 28V voltage too low alarm."
    ::= { aprisaXETx28VLoAlarm 1 }

aprisaXETx28VLoAlarmSeverity OBJECT-TYPE
    SYNTAX      FourRFAlarmSeverity
    MAX-ACCESS  read-only
    STATUS      obsolete
    DESCRIPTION "The severity of the transmitter 28V voltage too low alarm."
    ::= { aprisaXETx28VLoAlarm 2 }

aprisaXETx28VLoAlarmEnabled OBJECT-TYPE
    SYNTAX      FourRFAlarmEnabled
    MAX-ACCESS  read-only
    STATUS      obsolete
    DESCRIPTION "Indicates whether the transmitter 28V voltage too low alarm is enabled."
    ::= { aprisaXETx28VLoAlarm 3 }
    
aprisaXETx28VLoAlarmThreshold OBJECT-TYPE
    SYNTAX      Integer32
    MAX-ACCESS  read-only
    STATUS      obsolete
    DESCRIPTION "Indicates the level at which the transmitter 28V voltage too low 
                 alarm will be set."
    ::= { aprisaXETx28VLoAlarm 4 }
    
aprisaXETx28VLoAlarmClearThreshold OBJECT-TYPE
    SYNTAX      Integer32
    MAX-ACCESS  read-only
    STATUS      obsolete
    DESCRIPTION "Indicates the level at which the transmitter 28V voltage too low 
                 will be cleared."
    ::= { aprisaXETx28VLoAlarm 5 }

aprisaXETx28VLoAlarmsGroup OBJECT-GROUP
    OBJECTS     { aprisaXETx28VLoAlarmStatus, 
                  aprisaXETx28VLoAlarmSeverity, 
                  aprisaXETx28VLoAlarmEnabled,
                  aprisaXETx28VLoAlarmThreshold,
                  aprisaXETx28VLoAlarmClearThreshold
    }
    STATUS      obsolete
    DESCRIPTION "The AprisaXE transmitter 28V voltage too low alarm group."
    ::= { aprisaXEGroups 151 } 
    
    
--
-- Transmitter synthesiser out of lock alarm
--
    
aprisaXETxSynthOutOfLockAlarm OBJECT IDENTIFIER ::= { aprisaXETransmitterAlarms 21 }

aprisaXETxSynthOutOfLockAlarmStatus OBJECT-TYPE
    SYNTAX      FourRFAlarmStatus
    MAX-ACCESS  read-only
    STATUS      current
    DESCRIPTION "The status of the TX synth out of lock alarm."
    ::= { aprisaXETxSynthOutOfLockAlarm 1 }

aprisaXETxSynthOutOfLockAlarmSeverity OBJECT-TYPE
    SYNTAX      FourRFAlarmSeverity
    MAX-ACCESS  read-only
    STATUS      current
    DESCRIPTION "The severity of the TX synth out of lock alarm."
    ::= { aprisaXETxSynthOutOfLockAlarm 2 }

aprisaXETxSynthOutOfLockAlarmEnabled OBJECT-TYPE
    SYNTAX      FourRFAlarmEnabled
    MAX-ACCESS  read-only
    STATUS      current
    DESCRIPTION "Indicates whether the TX synth out of lock alarm is enabled."
    ::= { aprisaXETxSynthOutOfLockAlarm 3 }

aprisaXETxSynthOutOfLockAlarmsGroup OBJECT-GROUP
    OBJECTS     { aprisaXETxSynthOutOfLockAlarmStatus, 
                  aprisaXETxSynthOutOfLockAlarmSeverity, 
                  aprisaXETxSynthOutOfLockAlarmEnabled
    }
    STATUS      current
    DESCRIPTION "The AprisaXE TX Synth out of lock alarm group."
    ::= { aprisaXEGroups 153 } 


--
-- Return Loss Too High Alarm
--
-- The threshold values vary according to the currently selected modulation.
--

aprisaXEReturnLossHiAlarm OBJECT IDENTIFIER ::= { aprisaXETransmitterAlarms 22 }

aprisaXEReturnLossHiAlarmStatus OBJECT-TYPE
    SYNTAX      FourRFAlarmStatus
    MAX-ACCESS  read-only
    STATUS      current
    DESCRIPTION "The status of the return loss out of limits alarm."
    ::= { aprisaXEReturnLossHiAlarm 1 }

aprisaXEReturnLossHiAlarmSeverity OBJECT-TYPE
    SYNTAX      FourRFAlarmSeverity
    MAX-ACCESS  read-only
    STATUS      current
    DESCRIPTION "The severity of the return loss out of limits alarm."
    ::= { aprisaXEReturnLossHiAlarm 2 }

aprisaXEReturnLossHiAlarmEnabled OBJECT-TYPE
    SYNTAX      FourRFAlarmEnabled
    MAX-ACCESS  read-only
    STATUS      current
    DESCRIPTION "Indicates whether the return loss out of limits alarm is enabled."
    ::= { aprisaXEReturnLossHiAlarm 3 }

aprisaXEReturnLossHiAlarmThreshold OBJECT-TYPE
    SYNTAX      Integer32
    MAX-ACCESS  read-write
    STATUS      current
    DESCRIPTION "Indicates the level at which the return loss alarm will be set."
    ::= { aprisaXEReturnLossHiAlarm 4 }
    
aprisaXEReturnLossHiAlarmClearThreshold OBJECT-TYPE
    SYNTAX      Integer32
    MAX-ACCESS  read-write
    STATUS      current
    DESCRIPTION "Indicates the level at which the return loss alarm will be cleared."
    ::= { aprisaXEReturnLossHiAlarm 5 }
    
aprisaXEReturnLossHiAlarmsGroup OBJECT-GROUP
    OBJECTS     { aprisaXEReturnLossHiAlarmStatus, 
                  aprisaXEReturnLossHiAlarmSeverity, 
                  aprisaXEReturnLossHiAlarmEnabled,
                  aprisaXEReturnLossHiAlarmThreshold,
                  aprisaXEReturnLossHiAlarmClearThreshold
    }
    STATUS      current
    DESCRIPTION "The AprisaXE reverse power too high alarm group."
    ::= { aprisaXEGroups 152 } 
 
-- ***************************************************************************
-- End of Transmitter alarms
-- ***************************************************************************    



-- ***************************************************************************
-- The Receiver alarms
-- ***************************************************************************    

aprisaXEReceiverAlarms OBJECT IDENTIFIER ::= { aprisaXELinkAlarms 6 }


-- Rx Synthesizer out of lock 

aprisaXERxSynthOutOfLockAlarm OBJECT IDENTIFIER ::= { aprisaXEReceiverAlarms 1 }

aprisaXERxSynthOutOfLockAlarmStatus OBJECT-TYPE
    SYNTAX      FourRFAlarmStatus
    MAX-ACCESS  read-only
    STATUS      current
    DESCRIPTION "The status of the Synth out of lock alarm."
    ::= { aprisaXERxSynthOutOfLockAlarm 1 }

aprisaXERxSynthOutOfLockAlarmSeverity OBJECT-TYPE
    SYNTAX      FourRFAlarmSeverity
    MAX-ACCESS  read-only
    STATUS      current
    DESCRIPTION "The severity of the Synth out of lock alarm."
    ::= { aprisaXERxSynthOutOfLockAlarm 2 }

aprisaXERxSynthOutOfLockAlarmEnabled OBJECT-TYPE
    SYNTAX      FourRFAlarmEnabled
    MAX-ACCESS  read-only
    STATUS      current
    DESCRIPTION "Indicates whether the Synth out of lock alarm is enabled."
    ::= { aprisaXERxSynthOutOfLockAlarm 3 }

aprisaXERxSynthOutOfLockAlarmsGroup OBJECT-GROUP
    OBJECTS     { aprisaXERxSynthOutOfLockAlarmStatus, 
                  aprisaXERxSynthOutOfLockAlarmSeverity, 
                  aprisaXERxSynthOutOfLockAlarmEnabled
    }
    STATUS      current
    DESCRIPTION "The AprisaXE Synth out of lock alarm group."
    ::= { aprisaXEGroups 161 } 


--
-- 12 V alarm 
--
aprisaXERx12VAlarm OBJECT IDENTIFIER ::= { aprisaXEReceiverAlarms 3 }

aprisaXERx12VAlarmStatus OBJECT-TYPE
    SYNTAX      FourRFAlarmStatus
    MAX-ACCESS  read-only
    STATUS      current
    DESCRIPTION "The status of the 12V supply alarm."
    ::= { aprisaXERx12VAlarm 1 }

aprisaXERx12VAlarmSeverity OBJECT-TYPE
    SYNTAX      FourRFAlarmSeverity
    MAX-ACCESS  read-only
    STATUS      current
    DESCRIPTION "The severity of the 12V supply aprisaXERxVtuneLoAlarmalarm."
    ::= { aprisaXERx12VAlarm 2 }

aprisaXERx12VAlarmEnabled OBJECT-TYPE
    SYNTAX      FourRFAlarmEnabled
    MAX-ACCESS  read-only
    STATUS      current
    DESCRIPTION "Indicates whether the 12V supply alarm is enabled."
    ::= { aprisaXERx12VAlarm 3 }
    
aprisaXERx12VAlarmsGroup OBJECT-GROUP
    OBJECTS     { aprisaXERx12VAlarmStatus, 
                  aprisaXERx12VAlarmSeverity, 
                  aprisaXERx12VAlarmEnabled
    }
    STATUS      current
    DESCRIPTION "The AprisaXE 12V supply alarm group."
    ::= { aprisaXEGroups 166 } 


--
-- 3.3V high alarm
--

aprisaXERx3V3HiAlarm OBJECT IDENTIFIER ::= { aprisaXEReceiverAlarms 4 }

aprisaXERx3V3HiAlarmStatus OBJECT-TYPE
    SYNTAX      FourRFAlarmStatus
    MAX-ACCESS  read-only
    STATUS      obsolete
    DESCRIPTION "The status of the 3.3V supply high alarm."
    ::= { aprisaXERx3V3HiAlarm 1 }

aprisaXERx3V3HiAlarmSeverity OBJECT-TYPE
    SYNTAX      FourRFAlarmSeverity
    MAX-ACCESS  read-only
    STATUS      obsolete
    DESCRIPTION "The severity of the 3.3V supply high alarm."
    ::= { aprisaXERx3V3HiAlarm 2 }

aprisaXERx3V3HiAlarmEnabled OBJECT-TYPE
    SYNTAX      FourRFAlarmEnabled
    MAX-ACCESS  read-only
    STATUS      obsolete
    DESCRIPTION "Indicates whether the 3.3V supply high alarm is enabled."
    ::= { aprisaXERx3V3HiAlarm 3 }
    
aprisaXERx3V3HiAlarmThreshold OBJECT-TYPE
    SYNTAX      Integer32
    MAX-ACCESS  read-only
    STATUS      obsolete
    DESCRIPTION "Indicates the level at which the 3.3V supply high 
                 alarm will be set."
    ::= { aprisaXERx3V3HiAlarm 4 }
    
aprisaXERx3V3HiAlarmClearThreshold OBJECT-TYPE
    SYNTAX      Integer32
    MAX-ACCESS  read-only
    STATUS      obsolete
    DESCRIPTION "Indicates the level at which the 3.3V supply high 
                 will be cleared."
    ::= { aprisaXERx3V3HiAlarm 5 }

aprisaXERx3V3HiAlarmsGroup OBJECT-GROUP
    OBJECTS     { aprisaXERx3V3HiAlarmStatus, 
                  aprisaXERx3V3HiAlarmSeverity, 
                  aprisaXERx3V3HiAlarmEnabled,
                  aprisaXERx3V3HiAlarmThreshold,
                  aprisaXERx3V3HiAlarmClearThreshold
    }
    STATUS      obsolete
    DESCRIPTION "The AprisaXE 3.3V supply high alarm group."
    ::= { aprisaXEGroups 171 } 


--
--3.3V low alarm
--

aprisaXERx3V3LoAlarm OBJECT IDENTIFIER ::= { aprisaXEReceiverAlarms 5 }

aprisaXERx3V3LoAlarmStatus OBJECT-TYPE
    SYNTAX      FourRFAlarmStatus
    MAX-ACCESS  read-only
    STATUS      obsolete
    DESCRIPTION "The status of the 3.3V supply low alarm."
    ::= { aprisaXERx3V3LoAlarm 1 }

aprisaXERx3V3LoAlarmSeverity OBJECT-TYPE
    SYNTAX      FourRFAlarmSeverity
    MAX-ACCESS  read-only
    STATUS      obsolete
    DESCRIPTION "The severity of the 3.3V supply low alarm."
    ::= { aprisaXERx3V3LoAlarm 2 }

aprisaXERx3V3LoAlarmEnabled OBJECT-TYPE
    SYNTAX      FourRFAlarmEnabled
    MAX-ACCESS  read-only
    STATUS      obsolete
    DESCRIPTION "Indicates whether the 3.3V supply low alarm is enabled."
    ::= { aprisaXERx3V3LoAlarm 3 }
    
aprisaXERx3V3LoAlarmThreshold OBJECT-TYPE
    SYNTAX      Integer32
    MAX-ACCESS  read-only
    STATUS      obsolete
    DESCRIPTION "Indicates the level at which the 3.3V supply low 
                 alarm will be set."
    ::= { aprisaXERx3V3LoAlarm 4 }
    
aprisaXERx3V3LoAlarmClearThreshold OBJECT-TYPE
    SYNTAX      Integer32
    MAX-ACCESS  read-only
    STATUS      obsolete
    DESCRIPTION "Indicates the level at which the 3.3V supply low 
                 will be cleared."
    ::= { aprisaXERx3V3LoAlarm 5 }

aprisaXERx3V3LoAlarmsGroup OBJECT-GROUP
    OBJECTS     { aprisaXERx3V3LoAlarmStatus, 
                  aprisaXERx3V3LoAlarmSeverity, 
                  aprisaXERx3V3LoAlarmEnabled,
                  aprisaXERx3V3LoAlarmThreshold,
                  aprisaXERx3V3LoAlarmClearThreshold
    }
    STATUS      obsolete
    DESCRIPTION "The AprisaXE 3.3V supply low alarm group."
    ::= { aprisaXEGroups 176 } 


--
-- 5V high alarm
--

aprisaXERx5VHiAlarm OBJECT IDENTIFIER ::= { aprisaXEReceiverAlarms 6 }

aprisaXERx5VHiAlarmStatus OBJECT-TYPE
    SYNTAX      FourRFAlarmStatus
    MAX-ACCESS  read-only
    STATUS      obsolete
    DESCRIPTION "The status of the 5V supply High alarm."
    ::= { aprisaXERx5VHiAlarm 1 }

aprisaXERx5VHiAlarmSeverity OBJECT-TYPE
    SYNTAX      FourRFAlarmSeverity
    MAX-ACCESS  read-only
    STATUS      obsolete
    DESCRIPTION "The severity of the 5V supply High alarm."
    ::= { aprisaXERx5VHiAlarm 2 }

aprisaXERx5VHiAlarmEnabled OBJECT-TYPE
    SYNTAX      FourRFAlarmEnabled
    MAX-ACCESS  read-only
    STATUS      obsolete
    DESCRIPTION "Indicates whether the 5V supply High alarm is enabled."
    ::= { aprisaXERx5VHiAlarm 3 }
    
aprisaXERx5VHiAlarmThreshold OBJECT-TYPE
    SYNTAX      Integer32
    MAX-ACCESS  read-only
    STATUS      obsolete
    DESCRIPTION "Indicates the level at which the 5V supply High 
                 alarm will be set."
    ::= { aprisaXERx5VHiAlarm 4 }
    
aprisaXERx5VHiAlarmClearThreshold OBJECT-TYPE
    SYNTAX      Integer32
    MAX-ACCESS  read-only
    STATUS      obsolete
    DESCRIPTION "Indicates the level at which the 5V supply High 
                 will be cleared."
    ::= { aprisaXERx5VHiAlarm 5 }

aprisaXERx5VHiAlarmsGroup OBJECT-GROUP
    OBJECTS     { aprisaXERx5VHiAlarmStatus, 
                  aprisaXERx5VHiAlarmSeverity, 
                  aprisaXERx5VHiAlarmEnabled,
                  aprisaXERx5VHiAlarmThreshold,
                  aprisaXERx5VHiAlarmClearThreshold
    }
    STATUS      obsolete
    DESCRIPTION "The AprisaXE 5V supply High alarm group."
    ::= { aprisaXEGroups 181 } 


--
--5V low alarm
--

aprisaXERx5VLoAlarm OBJECT IDENTIFIER ::= { aprisaXEReceiverAlarms 7 }

aprisaXERx5VLoAlarmStatus OBJECT-TYPE
    SYNTAX      FourRFAlarmStatus
    MAX-ACCESS  read-only
    STATUS      obsolete
    DESCRIPTION "The status of the 5V supply low alarm."
    ::= { aprisaXERx5VLoAlarm 1 }

aprisaXERx5VLoAlarmSeverity OBJECT-TYPE
    SYNTAX      FourRFAlarmSeverity
    MAX-ACCESS  read-only
    STATUS      obsolete
    DESCRIPTION "The severity of the 5V supply low alarm."
    ::= { aprisaXERx5VLoAlarm 2 }

aprisaXERx5VLoAlarmEnabled OBJECT-TYPE
    SYNTAX      FourRFAlarmEnabled
    MAX-ACCESS  read-only
    STATUS      obsolete
    DESCRIPTION "Indicates whether the 5V supply low alarm is enabled."
    ::= { aprisaXERx5VLoAlarm 3 }
    
aprisaXERx5VLoAlarmThreshold OBJECT-TYPE
    SYNTAX      Integer32
    MAX-ACCESS  read-only
    STATUS      obsolete
    DESCRIPTION "Indicates the level at which the 5V supply low 
                 alarm will be set."
    ::= { aprisaXERx5VLoAlarm 4 }
    
aprisaXERx5VLoAlarmClearThreshold OBJECT-TYPE
    SYNTAX      Integer32
    MAX-ACCESS  read-only
    STATUS      obsolete
    DESCRIPTION "Indicates the level at which the 5V supply low 
                 will be cleared."
    ::= { aprisaXERx5VLoAlarm 5 }

aprisaXERx5VLoAlarmsGroup OBJECT-GROUP
    OBJECTS     { aprisaXERx5VLoAlarmStatus, 
                  aprisaXERx5VLoAlarmSeverity, 
                  aprisaXERx5VLoAlarmEnabled,
                  aprisaXERx5VLoAlarmThreshold,
                  aprisaXERx5VLoAlarmClearThreshold
    }
    STATUS      obsolete
    DESCRIPTION "The AprisaXE 5V supply low alarm group."
    ::= { aprisaXEGroups 186 } 


--
-- 9V high alarm
--

aprisaXERx9VHiAlarm OBJECT IDENTIFIER ::= { aprisaXEReceiverAlarms 8 }

aprisaXERx9VHiAlarmStatus OBJECT-TYPE
    SYNTAX      FourRFAlarmStatus
    MAX-ACCESS  read-only
    STATUS      obsolete
    DESCRIPTION "The status of the 9V supply High alarm."
    ::= { aprisaXERx9VHiAlarm 1 }

aprisaXERx9VHiAlarmSeverity OBJECT-TYPE
    SYNTAX      FourRFAlarmSeverity
    MAX-ACCESS  read-only
    STATUS      obsolete
    DESCRIPTION "The severity of the 9V supply High alarm."
    ::= { aprisaXERx9VHiAlarm 2 }

aprisaXERx9VHiAlarmEnabled OBJECT-TYPE
    SYNTAX      FourRFAlarmEnabled
    MAX-ACCESS  read-only
    STATUS      obsolete
    DESCRIPTION "Indicates whether the 9V supply High alarm is enabled."
    ::= { aprisaXERx9VHiAlarm 3 }
    
aprisaXERx9VHiAlarmThreshold OBJECT-TYPE
    SYNTAX      Integer32
    MAX-ACCESS  read-only
    STATUS      obsolete
    DESCRIPTION "Indicates the level at which the 9V supply High 
                 alarm will be set."
    ::= { aprisaXERx9VHiAlarm 4 }
    
aprisaXERx9VHiAlarmClearThreshold OBJECT-TYPE
    SYNTAX      Integer32
    MAX-ACCESS  read-only
    STATUS      obsolete
    DESCRIPTION "Indicates the level at which the 9V supply High 
                 will be cleared."
    ::= { aprisaXERx9VHiAlarm 5 }

aprisaXERx9VHiAlarmsGroup OBJECT-GROUP
    OBJECTS     { aprisaXERx9VHiAlarmStatus, 
                  aprisaXERx9VHiAlarmSeverity, 
                  aprisaXERx9VHiAlarmEnabled,
                  aprisaXERx9VHiAlarmThreshold,
                  aprisaXERx9VHiAlarmClearThreshold
    }
    STATUS      obsolete
    DESCRIPTION "The AprisaXE 9V supply High alarm group."
    ::= { aprisaXEGroups 191 } 


--
-- 9V low alarm
-- 
   
aprisaXERx9VLoAlarm OBJECT IDENTIFIER ::= { aprisaXEReceiverAlarms 9 }

aprisaXERx9VLoAlarmStatus OBJECT-TYPE
    SYNTAX      FourRFAlarmStatus
    MAX-ACCESS  read-only
    STATUS      obsolete
    DESCRIPTION "The status of the 9V supply low alarm."
    ::= { aprisaXERx9VLoAlarm 1 }

aprisaXERx9VLoAlarmSeverity OBJECT-TYPE
    SYNTAX      FourRFAlarmSeverity
    MAX-ACCESS  read-only
    STATUS      obsolete
    DESCRIPTION "The severity of the 9V supply low alarm."
    ::= { aprisaXERx9VLoAlarm 2 }

aprisaXERx9VLoAlarmEnabled OBJECT-TYPE
    SYNTAX      FourRFAlarmEnabled
    MAX-ACCESS  read-only
    STATUS      obsolete
    DESCRIPTION "Indicates whether the 9V supply low alarm is enabled."
    ::= { aprisaXERx9VLoAlarm 3 }
    
aprisaXERx9VLoAlarmThreshold OBJECT-TYPE
    SYNTAX      Integer32
    MAX-ACCESS  read-only
    STATUS      obsolete
    DESCRIPTION "Indicates the level at which the 9V supply low 
                 alarm will be set."
    ::= { aprisaXERx9VLoAlarm 4 }
    
aprisaXERx9VLoAlarmClearThreshold OBJECT-TYPE
    SYNTAX      Integer32
    MAX-ACCESS  read-only
    STATUS      obsolete
    DESCRIPTION "Indicates the level at which the 9V supply low 
                 will be cleared."
    ::= { aprisaXERx9VLoAlarm 5 }

aprisaXERx9VLoAlarmsGroup OBJECT-GROUP
    OBJECTS     { aprisaXERx9VLoAlarmStatus, 
                  aprisaXERx9VLoAlarmSeverity, 
                  aprisaXERx9VLoAlarmEnabled,
                  aprisaXERx9VLoAlarmThreshold,
                  aprisaXERx9VLoAlarmClearThreshold
    }
    STATUS      obsolete
    DESCRIPTION "The AprisaXE 9V supply low alarm group."
    ::= { aprisaXEGroups 196 } 


--
-- Neg 1V5 high alarm
--    

aprisaXERxNeg1V5HiAlarm OBJECT IDENTIFIER ::= { aprisaXEReceiverAlarms 10 }

aprisaXERxNeg1V5HiAlarmStatus OBJECT-TYPE
    SYNTAX      FourRFAlarmStatus
    MAX-ACCESS  read-only
    STATUS      obsolete
    DESCRIPTION "The status of the Neg 1.5V supply High alarm."
    ::= { aprisaXERxNeg1V5HiAlarm 1 }

aprisaXERxNeg1V5HiAlarmSeverity OBJECT-TYPE
    SYNTAX      FourRFAlarmSeverity
    MAX-ACCESS  read-only
    STATUS      obsolete
    DESCRIPTION "The severity of the Neg 1.5V supply High alarm."
    ::= { aprisaXERxNeg1V5HiAlarm 2 }

aprisaXERxNeg1V5HiAlarmEnabled OBJECT-TYPE
    SYNTAX      FourRFAlarmEnabled
    MAX-ACCESS  read-only
    STATUS      obsolete
    DESCRIPTION "Indicates whether the Neg 1.5V supply High alarm is enabled."
    ::= { aprisaXERxNeg1V5HiAlarm 3 }
    
aprisaXERxNeg1V5HiAlarmThreshold OBJECT-TYPE
    SYNTAX      Integer32
    MAX-ACCESS  read-only
    STATUS      obsolete
    DESCRIPTION "Indicates the level at which the Neg 1.5V supply High 
                 alarm will be set."
    ::= { aprisaXERxNeg1V5HiAlarm 4 }
    
aprisaXERxNeg1V5HiAlarmClearThreshold OBJECT-TYPE
    SYNTAX      Integer32
    MAX-ACCESS  read-only
    STATUS      obsolete
    DESCRIPTION "Indicates the level at which the Neg 1.5V supply High 
                 will be cleared."
    ::= { aprisaXERxNeg1V5HiAlarm 5 }

aprisaXERxNeg1V5HiAlarmsGroup OBJECT-GROUP
    OBJECTS     { aprisaXERxNeg1V5HiAlarmStatus, 
                  aprisaXERxNeg1V5HiAlarmSeverity, 
                  aprisaXERxNeg1V5HiAlarmEnabled,
                  aprisaXERxNeg1V5HiAlarmThreshold,
                  aprisaXERxNeg1V5HiAlarmClearThreshold
    }
    STATUS      obsolete
    DESCRIPTION "The AprisaXE Neg 1.5V supply High alarm group."
    ::= { aprisaXEGroups 201 } 


--
-- Neg 1V5 low alarm
--

aprisaXERxNeg1V5LoAlarm OBJECT IDENTIFIER ::= { aprisaXEReceiverAlarms 11 }

aprisaXERxNeg1V5LoAlarmStatus OBJECT-TYPE
    SYNTAX      FourRFAlarmStatus
    MAX-ACCESS  read-only
    STATUS      obsolete
    DESCRIPTION "The status of the Neg 1.5V supply low alarm."
    ::= { aprisaXERxNeg1V5LoAlarm 1 }

aprisaXERxNeg1V5LoAlarmSeverity OBJECT-TYPE
    SYNTAX      FourRFAlarmSeverity
    MAX-ACCESS  read-only
    STATUS      obsolete
    DESCRIPTION "The severity of the Neg 1.5V supply low alarm."
    ::= { aprisaXERxNeg1V5LoAlarm 2 }

aprisaXERxNeg1V5LoAlarmEnabled OBJECT-TYPE
    SYNTAX      FourRFAlarmEnabled
    MAX-ACCESS  read-only
    STATUS      obsolete
    DESCRIPTION "Indicates whether the Neg 1.5V supply low alarm is enabled."
    ::= { aprisaXERxNeg1V5LoAlarm 3 }
    
aprisaXERxNeg1V5LoAlarmThreshold OBJECT-TYPE
    SYNTAX      Integer32
    MAX-ACCESS  read-only
    STATUS      obsolete
    DESCRIPTION "Indicates the level at which the Neg 1.5V supply low 
                 alarm will be set."
    ::= { aprisaXERxNeg1V5LoAlarm 4 }
    
aprisaXERxNeg1V5LoAlarmClearThreshold OBJECT-TYPE
    SYNTAX      Integer32
    MAX-ACCESS  read-only
    STATUS      obsolete
    DESCRIPTION "Indicates the level at which the Neg 1.5V supply low 
                 will be cleared."
    ::= { aprisaXERxNeg1V5LoAlarm 5 }

aprisaXERxNeg1V5LoAlarmsGroup OBJECT-GROUP
    OBJECTS     { aprisaXERxNeg1V5LoAlarmStatus, 
                  aprisaXERxNeg1V5LoAlarmSeverity, 
                  aprisaXERxNeg1V5LoAlarmEnabled,
                  aprisaXERxNeg1V5LoAlarmThreshold,
                  aprisaXERxNeg1V5LoAlarmClearThreshold
    }
    STATUS      obsolete
    DESCRIPTION "The AprisaXE Neg 1.5V supply low alarm group."
    ::= { aprisaXEGroups 206 } 


--
-- AGC high alarm
--

aprisaXERxAgcHiAlarm OBJECT IDENTIFIER ::= { aprisaXEReceiverAlarms 12 }

aprisaXERxAgcHiAlarmStatus OBJECT-TYPE
    SYNTAX      FourRFAlarmStatus
    MAX-ACCESS  read-only
    STATUS      obsolete
    DESCRIPTION "The status of the AGC high alarm."
    ::= { aprisaXERxAgcHiAlarm 1 }

aprisaXERxAgcHiAlarmSeverity OBJECT-TYPE
    SYNTAX      FourRFAlarmSeverity
    MAX-ACCESS  read-only
    STATUS      obsolete
    DESCRIPTION "The severity of the AGC high alarm."
    ::= { aprisaXERxAgcHiAlarm 2 }

aprisaXERxAgcHiAlarmEnabled OBJECT-TYPE
    SYNTAX      FourRFAlarmEnabled
    MAX-ACCESS  read-only
    STATUS      obsolete
    DESCRIPTION "Indicates whether the AGC high alarm is enabled."
    ::= { aprisaXERxAgcHiAlarm 3 }
    
aprisaXERxAgcHiAlarmThreshold OBJECT-TYPE
    SYNTAX      Integer32
    MAX-ACCESS  read-only
    STATUS      obsolete
    DESCRIPTION "Indicates the level at which the AGC high 
                 alarm will be set."
    ::= { aprisaXERxAgcHiAlarm 4 }
    
aprisaXERxAgcHiAlarmClearThreshold OBJECT-TYPE
    SYNTAX      Integer32
    MAX-ACCESS  read-only
    STATUS      obsolete
    DESCRIPTION "Indicates the level at which the AGC high 
                 will be cleared."
    ::= { aprisaXERxAgcHiAlarm 5 }

aprisaXERxAgcHiAlarmsGroup OBJECT-GROUP
    OBJECTS     { aprisaXERxAgcHiAlarmStatus, 
                  aprisaXERxAgcHiAlarmSeverity, 
                  aprisaXERxAgcHiAlarmEnabled,
                  aprisaXERxAgcHiAlarmThreshold,
                  aprisaXERxAgcHiAlarmClearThreshold
    }
    STATUS      obsolete
    DESCRIPTION "The AprisaXE AGC high alarm group."
    ::= { aprisaXEGroups 211 } 


--
--AGC low alarm
--

aprisaXERxAgcLoAlarm OBJECT IDENTIFIER ::= { aprisaXEReceiverAlarms 13 }

aprisaXERxAgcLoAlarmStatus OBJECT-TYPE
    SYNTAX      FourRFAlarmStatus
    MAX-ACCESS  read-only
    STATUS      obsolete
    DESCRIPTION "The status of the AGC low alarm."
    ::= { aprisaXERxAgcLoAlarm 1 }

aprisaXERxAgcLoAlarmSeverity OBJECT-TYPE
    SYNTAX      FourRFAlarmSeverity
    MAX-ACCESS  read-only
    STATUS      obsolete
    DESCRIPTION "The severity of the AGC low alarm."
    ::= { aprisaXERxAgcLoAlarm 2 }

aprisaXERxAgcLoAlarmEnabled OBJECT-TYPE
    SYNTAX      FourRFAlarmEnabled
    MAX-ACCESS  read-only
    STATUS      obsolete
    DESCRIPTION "Indicates whether the AGC low alarm is enabled."
    ::= { aprisaXERxAgcLoAlarm 3 }
    
aprisaXERxAgcLoAlarmThreshold OBJECT-TYPE
    SYNTAX      Integer32
    MAX-ACCESS  read-only
    STATUS      obsolete
    DESCRIPTION "Indicates the level at which the AGC low 
                 alarm will be set."
    ::= { aprisaXERxAgcLoAlarm 4 }
    
aprisaXERxAgcLoAlarmClearThreshold OBJECT-TYPE
    SYNTAX      Integer32
    MAX-ACCESS  read-only
    STATUS      obsolete
    DESCRIPTION "Indicates the level at which the AGC low 
                 will be cleared."
    ::= { aprisaXERxAgcLoAlarm 5 }

aprisaXERxAgcLoAlarmsGroup OBJECT-GROUP
    OBJECTS     { aprisaXERxAgcLoAlarmStatus, 
                  aprisaXERxAgcLoAlarmSeverity, 
                  aprisaXERxAgcLoAlarmEnabled,
                  aprisaXERxAgcLoAlarmThreshold,
                  aprisaXERxAgcLoAlarmClearThreshold
    }
    STATUS      obsolete
    DESCRIPTION "The AprisaXE AGC low alarm group."
    ::= { aprisaXEGroups 216 } 


-- 
-- RSSI High alarm
--

aprisaXERxRssiHiAlarm OBJECT IDENTIFIER ::= { aprisaXEReceiverAlarms 14 }

aprisaXERxRssiHiAlarmStatus OBJECT-TYPE
    SYNTAX      FourRFAlarmStatus
    MAX-ACCESS  read-only
    STATUS      current
    DESCRIPTION "The status of the RSSI High alarm."
    ::= { aprisaXERxRssiHiAlarm 1 }

aprisaXERxRssiHiAlarmSeverity OBJECT-TYPE
    SYNTAX      FourRFAlarmSeverity
    MAX-ACCESS  read-only
    STATUS      current
    DESCRIPTION "The severity of the RSSI High alarm."
    ::= { aprisaXERxRssiHiAlarm 2 }

aprisaXERxRssiHiAlarmEnabled OBJECT-TYPE
    SYNTAX      FourRFAlarmEnabled
    MAX-ACCESS  read-only
    STATUS      current
    DESCRIPTION "Indicates whether the RSSI High alarm is enabled."
    ::= { aprisaXERxRssiHiAlarm 3 }
    
aprisaXERxRssiHiAlarmThreshold OBJECT-TYPE
    SYNTAX      Integer32
    MAX-ACCESS  read-only
    STATUS      current
    DESCRIPTION "Indicates the level at which the RSSI High 
                 alarm will be set."
    ::= { aprisaXERxRssiHiAlarm 4 }
    
aprisaXERxRssiHiAlarmClearThreshold OBJECT-TYPE
    SYNTAX      Integer32
    MAX-ACCESS  read-only
    STATUS      current
    DESCRIPTION "Indicates the level at which the RSSI High 
                 will be cleared."
    ::= { aprisaXERxRssiHiAlarm 5 }

aprisaXERxRssiHiAlarmsGroup OBJECT-GROUP
    OBJECTS     { aprisaXERxRssiHiAlarmStatus, 
                  aprisaXERxRssiHiAlarmSeverity, 
                  aprisaXERxRssiHiAlarmEnabled,
                  aprisaXERxRssiHiAlarmThreshold,
                  aprisaXERxRssiHiAlarmClearThreshold
    }
    STATUS      current
    DESCRIPTION "The AprisaXE RSSI High alarm group."
    ::= { aprisaXEGroups 221 }


--
-- RSSI low alarms
--

aprisaXERxRssiLoAlarm OBJECT IDENTIFIER ::= { aprisaXEReceiverAlarms 15 }

aprisaXERxRssiLoAlarmStatus OBJECT-TYPE
    SYNTAX      FourRFAlarmStatus
    MAX-ACCESS  read-only
    STATUS      current
    DESCRIPTION "The status of the RSSI low alarm."
    ::= { aprisaXERxRssiLoAlarm 1 }

aprisaXERxRssiLoAlarmSeverity OBJECT-TYPE
    SYNTAX      FourRFAlarmSeverity
    MAX-ACCESS  read-only
    STATUS      current
    DESCRIPTION "The severity of the RSSI low alarm."
    ::= { aprisaXERxRssiLoAlarm 2 }

aprisaXERxRssiLoAlarmEnabled OBJECT-TYPE
    SYNTAX      FourRFAlarmEnabled
    MAX-ACCESS  read-only
    STATUS      current
    DESCRIPTION "Indicates whether the RSSI low alarm is enabled."
    ::= { aprisaXERxRssiLoAlarm 3 }
    
aprisaXERxRssiLoAlarmThreshold OBJECT-TYPE
    SYNTAX      Integer32
    MAX-ACCESS  read-only
    STATUS      current
    DESCRIPTION "Indicates the level at which the RSSI low 
                 alarm will be set."
    ::= { aprisaXERxRssiLoAlarm 4 }
    
aprisaXERxRssiLoAlarmClearThreshold OBJECT-TYPE
    SYNTAX      Integer32
    MAX-ACCESS  read-only
    STATUS      current
    DESCRIPTION "Indicates the level at which the RSSI low 
                 will be cleared."
    ::= { aprisaXERxRssiLoAlarm 5 }

aprisaXERxRssiLoAlarmsGroup OBJECT-GROUP
    OBJECTS     { aprisaXERxRssiLoAlarmStatus, 
                  aprisaXERxRssiLoAlarmSeverity, 
                  aprisaXERxRssiLoAlarmEnabled,
                  aprisaXERxRssiLoAlarmThreshold,
                  aprisaXERxRssiLoAlarmClearThreshold
    }
    STATUS      current
    DESCRIPTION "The AprisaXE RSSI low alarm group."
    ::= { aprisaXEGroups 226 } 


--
-- VTune High Alarm
--

aprisaXERxVtuneHiAlarm OBJECT IDENTIFIER ::= { aprisaXEReceiverAlarms 16 }

aprisaXERxVtuneHiAlarmStatus OBJECT-TYPE
    SYNTAX      FourRFAlarmStatus
    MAX-ACCESS  read-only
    STATUS      obsolete
    DESCRIPTION "The status of the Vtune High alarm."
    ::= { aprisaXERxVtuneHiAlarm 1 }

aprisaXERxVtuneHiAlarmSeverity OBJECT-TYPE
    SYNTAX      FourRFAlarmSeverity
    MAX-ACCESS  read-only
    STATUS      obsolete
    DESCRIPTION "The severity of the Vtune High alarm."
    ::= { aprisaXERxVtuneHiAlarm 2 }

aprisaXERxVtuneHiAlarmEnabled OBJECT-TYPE
    SYNTAX      FourRFAlarmEnabled
    MAX-ACCESS  read-only
    STATUS      obsolete
    DESCRIPTION "Indicates whether the Vtune High alarm is enabled."
    ::= { aprisaXERxVtuneHiAlarm 3 }
    
aprisaXERxVtuneHiAlarmThreshold OBJECT-TYPE
    SYNTAX      Integer32
    MAX-ACCESS  read-only
    STATUS      obsolete
    DESCRIPTION "Indicates the level at which the Vtune High 
                 alarm will be set."
    ::= { aprisaXERxVtuneHiAlarm 4 }
    
aprisaXERxVtuneHiAlarmClearThreshold OBJECT-TYPE
    SYNTAX      Integer32
    MAX-ACCESS  read-only
    STATUS      obsolete
    DESCRIPTION "Indicates the level at which the Vtune High 
                 will be cleared."
    ::= { aprisaXERxVtuneHiAlarm 5 }

aprisaXERxVtuneHiAlarmsGroup OBJECT-GROUP
    OBJECTS     { aprisaXERxVtuneHiAlarmStatus, 
                  aprisaXERxVtuneHiAlarmSeverity, 
                  aprisaXERxVtuneHiAlarmEnabled,
                  aprisaXERxVtuneHiAlarmThreshold,
                  aprisaXERxVtuneHiAlarmClearThreshold
    }
    STATUS      obsolete
    DESCRIPTION "The AprisaXE Vtune High alarm group."
    ::= { aprisaXEGroups 231 }


--
--Vtune low alarm
--
     
aprisaXERxVtuneLoAlarm OBJECT IDENTIFIER ::= { aprisaXEReceiverAlarms 17 }

aprisaXERxVtuneLoAlarmStatus OBJECT-TYPE
    SYNTAX      FourRFAlarmStatus
    MAX-ACCESS  read-only
    STATUS      obsolete
    DESCRIPTION "The status of the Vtune low alarm."
    ::= { aprisaXERxVtuneLoAlarm 1 }

aprisaXERxVtuneLoAlarmSeverity OBJECT-TYPE
    SYNTAX      FourRFAlarmSeverity
    MAX-ACCESS  read-only
    STATUS      obsolete
    DESCRIPTION "The severity of the Vtune low alarm."
    ::= { aprisaXERxVtuneLoAlarm 2 }

aprisaXERxVtuneLoAlarmEnabled OBJECT-TYPE
    SYNTAX      FourRFAlarmEnabled
    MAX-ACCESS  read-only
    STATUS      obsolete
    DESCRIPTION "Indicates whether the Vtune low alarm is enabled."
    ::= { aprisaXERxVtuneLoAlarm 3 }
    
aprisaXERxVtuneLoAlarmThreshold OBJECT-TYPE
    SYNTAX      Integer32
    MAX-ACCESS  read-only
    STATUS      obsolete
    DESCRIPTION "Indicates the level at which the Vtune low 
                 alarm will be set."
    ::= { aprisaXERxVtuneLoAlarm 4 }
    
aprisaXERxVtuneLoAlarmClearThreshold OBJECT-TYPE
    SYNTAX      Integer32
    MAX-ACCESS  read-only
    STATUS      obsolete
    DESCRIPTION "Indicates the level at which the Vtune low 
                 will be cleared."
    ::= { aprisaXERxVtuneLoAlarm 5 }

aprisaXERxVtuneLoAlarmsGroup OBJECT-GROUP
    OBJECTS     { aprisaXERxVtuneLoAlarmStatus, 
                  aprisaXERxVtuneLoAlarmSeverity, 
                  aprisaXERxVtuneLoAlarmEnabled,
                  aprisaXERxVtuneLoAlarmThreshold,
                  aprisaXERxVtuneLoAlarmClearThreshold
    }
    STATUS      obsolete
    DESCRIPTION "The AprisaXE Vtune low alarm group."
    ::= { aprisaXEGroups 236 } 


--
-- EE Alarm
--

aprisaXERxEEAlarm OBJECT IDENTIFIER ::= { aprisaXEReceiverAlarms 18 }

aprisaXERxEEAlarmStatus OBJECT-TYPE
    SYNTAX      FourRFAlarmStatus
    MAX-ACCESS  read-only
    STATUS      current
    DESCRIPTION "The status of the EEPROM alarm."
    ::= { aprisaXERxEEAlarm 1 }

aprisaXERxEEAlarmSeverity OBJECT-TYPE
    SYNTAX      FourRFAlarmSeverity
    MAX-ACCESS  read-only
    STATUS      current
    DESCRIPTION "The severity of the EEPROM alarm."
    ::= { aprisaXERxEEAlarm 2 }

aprisaXERxEEAlarmEnabled OBJECT-TYPE
    SYNTAX      FourRFAlarmEnabled
    MAX-ACCESS  read-only
    STATUS      current
    DESCRIPTION "Indicates whether the EEPROM alarm is enabled."
    ::= { aprisaXERxEEAlarm 3 }
    
aprisaXERxEEAlarmsGroup OBJECT-GROUP
    OBJECTS     { aprisaXERxEEAlarmStatus, 
                  aprisaXERxEEAlarmSeverity, 
                  aprisaXERxEEAlarmEnabled
    }
    STATUS      current
    DESCRIPTION "The AprisaXE EEPROM alarm group."
    ::= { aprisaXEGroups 241 } 

-- ***************************************************************************
-- End of Receiver alarms
-- ***************************************************************************    



-- ***************************************************************************
-- The Generic Transmitter Alarms
-- ***************************************************************************

aprisaXETxADCChZeroHiAlarm OBJECT IDENTIFIER ::= { aprisaXETransmitterAlarms 23 }

aprisaXETxADCChZeroHiAlarmName OBJECT-TYPE
    SYNTAX      DisplayString
    MAX-ACCESS  read-only
    STATUS      current
    DESCRIPTION "The name of the transmitter ADC Ch Zero voltage too high alarm."
    ::= { aprisaXETxADCChZeroHiAlarm 1 }

aprisaXETxADCChZeroHiAlarmStatus OBJECT-TYPE
    SYNTAX      FourRFAlarmStatus
    MAX-ACCESS  read-only
    STATUS      current
    DESCRIPTION "The status of the transmitter ADC Ch Zero voltage too high alarm."
    ::= { aprisaXETxADCChZeroHiAlarm 2 }

aprisaXETxADCChZeroHiAlarmSeverity OBJECT-TYPE
    SYNTAX      FourRFAlarmSeverity
    MAX-ACCESS  read-only
    STATUS      current
    DESCRIPTION "The severity of the transmitter ADC Ch Zero voltage too high alarm."
    ::= { aprisaXETxADCChZeroHiAlarm 3 }

aprisaXETxADCChZeroHiAlarmEnabled OBJECT-TYPE
    SYNTAX      FourRFAlarmEnabled
    MAX-ACCESS  read-only
    STATUS      current
    DESCRIPTION "Indicates whether the transmitter ADC Ch Zero voltage too high alarm is enabled."
    ::= { aprisaXETxADCChZeroHiAlarm 4 }
    
aprisaXETxADCChZeroHiAlarmThreshold OBJECT-TYPE
    SYNTAX      Integer32
    MAX-ACCESS  read-only
    STATUS      current
    DESCRIPTION "Indicates the level at which the transmitter ADC Ch Zero voltage too high 
                 alarm will be set."
    ::= { aprisaXETxADCChZeroHiAlarm 5 }
    
aprisaXETxADCChZeroHiAlarmClearThreshold OBJECT-TYPE
    SYNTAX      Integer32
    MAX-ACCESS  read-only
    STATUS      current
    DESCRIPTION "Indicates the level at which the transmitter ADC Ch Zero voltage too high 
                 will be cleared."
    ::= { aprisaXETxADCChZeroHiAlarm 6 }

aprisaXETxADCChZeroHiAlarmsGroup OBJECT-GROUP
    OBJECTS     { aprisaXETxADCChZeroHiAlarmName,
                  aprisaXETxADCChZeroHiAlarmStatus,
                  aprisaXETxADCChZeroHiAlarmSeverity, 
                  aprisaXETxADCChZeroHiAlarmEnabled,
                  aprisaXETxADCChZeroHiAlarmThreshold,
                  aprisaXETxADCChZeroHiAlarmClearThreshold
    }
    STATUS      current
    DESCRIPTION "The aprisaXETx transmitter ADC Ch Zero voltage too high alarm group."
    ::= { aprisaXEGroups 250 } 


aprisaXETxADCChZeroLoAlarm OBJECT IDENTIFIER ::= { aprisaXETransmitterAlarms 24 }

aprisaXETxADCChZeroLoAlarmName OBJECT-TYPE
    SYNTAX      DisplayString
    MAX-ACCESS  read-only
    STATUS      current
    DESCRIPTION "The name of the transmitter ADC Ch Zero voltage too low alarm."
    ::= { aprisaXETxADCChZeroLoAlarm 1 }

aprisaXETxADCChZeroLoAlarmStatus OBJECT-TYPE
    SYNTAX      FourRFAlarmStatus
    MAX-ACCESS  read-only
    STATUS      current
    DESCRIPTION "The status of the transmitter ADC Ch Zero voltage too low alarm."
    ::= { aprisaXETxADCChZeroLoAlarm 2 }

aprisaXETxADCChZeroLoAlarmSeverity OBJECT-TYPE
    SYNTAX      FourRFAlarmSeverity
    MAX-ACCESS  read-only
    STATUS      current
    DESCRIPTION "The severity of the transmitter ADC Ch Zero voltage too low alarm."
    ::= { aprisaXETxADCChZeroLoAlarm 3 }

aprisaXETxADCChZeroLoAlarmEnabled OBJECT-TYPE
    SYNTAX      FourRFAlarmEnabled
    MAX-ACCESS  read-only
    STATUS      current
    DESCRIPTION "Indicates whether the transmitter ADC Ch Zero voltage too low alarm is enabled."
    ::= { aprisaXETxADCChZeroLoAlarm 4 }
    
aprisaXETxADCChZeroLoAlarmThreshold OBJECT-TYPE
    SYNTAX      Integer32
    MAX-ACCESS  read-only
    STATUS      current
    DESCRIPTION "Indicates the level at wLoch the transmitter ADC Ch Zero voltage too low 
                 alarm will be set."
    ::= { aprisaXETxADCChZeroLoAlarm 5 }
    
aprisaXETxADCChZeroLoAlarmClearThreshold OBJECT-TYPE
    SYNTAX      Integer32
    MAX-ACCESS  read-only
    STATUS      current
    DESCRIPTION "Indicates the level at wLoch the transmitter ADC Ch Zero voltage too low 
                 will be cleared."
    ::= { aprisaXETxADCChZeroLoAlarm 6 }

aprisaXETxADCChZeroLoAlarmsGroup OBJECT-GROUP
    OBJECTS     { aprisaXETxADCChZeroLoAlarmName,
                  aprisaXETxADCChZeroLoAlarmStatus,
                  aprisaXETxADCChZeroLoAlarmSeverity, 
                  aprisaXETxADCChZeroLoAlarmEnabled,
                  aprisaXETxADCChZeroLoAlarmThreshold,
                  aprisaXETxADCChZeroLoAlarmClearThreshold
    }
    STATUS      current
    DESCRIPTION "The aprisaXETx transmitter ADC Ch Zero voltage too High alarm group."
    ::= { aprisaXEGroups 251 }


aprisaXETxADCChOneHiAlarm OBJECT IDENTIFIER ::= { aprisaXETransmitterAlarms 25 }

aprisaXETxADCChOneHiAlarmName OBJECT-TYPE
    SYNTAX      DisplayString
    MAX-ACCESS  read-only
    STATUS      current
    DESCRIPTION "The name of the transmitter ADC Ch One voltage too high alarm."
    ::= { aprisaXETxADCChOneHiAlarm 1 }

aprisaXETxADCChOneHiAlarmStatus OBJECT-TYPE
    SYNTAX      FourRFAlarmStatus
    MAX-ACCESS  read-only
    STATUS      current
    DESCRIPTION "The status of the transmitter ADC Ch One voltage too high alarm."
    ::= { aprisaXETxADCChOneHiAlarm 2 }

aprisaXETxADCChOneHiAlarmSeverity OBJECT-TYPE
    SYNTAX      FourRFAlarmSeverity
    MAX-ACCESS  read-only
    STATUS      current
    DESCRIPTION "The severity of the transmitter ADC Ch One voltage too high alarm."
    ::= { aprisaXETxADCChOneHiAlarm 3 }

aprisaXETxADCChOneHiAlarmEnabled OBJECT-TYPE
    SYNTAX      FourRFAlarmEnabled
    MAX-ACCESS  read-only
    STATUS      current
    DESCRIPTION "Indicates whether the transmitter ADC Ch One voltage too high alarm is enabled."
    ::= { aprisaXETxADCChOneHiAlarm 4 }
    
aprisaXETxADCChOneHiAlarmThreshold OBJECT-TYPE
    SYNTAX      Integer32
    MAX-ACCESS  read-only
    STATUS      current
    DESCRIPTION "Indicates the level at which the transmitter ADC Ch One voltage too high 
                 alarm will be set."
    ::= { aprisaXETxADCChOneHiAlarm 5 }
    
aprisaXETxADCChOneHiAlarmClearThreshold OBJECT-TYPE
    SYNTAX      Integer32
    MAX-ACCESS  read-only
    STATUS      current
    DESCRIPTION "Indicates the level at which the transmitter ADC Ch One voltage too high 
                 will be cleared."
    ::= { aprisaXETxADCChOneHiAlarm 6 }

aprisaXETxADCChOneHiAlarmsGroup OBJECT-GROUP
    OBJECTS     { aprisaXETxADCChOneHiAlarmName,
                  aprisaXETxADCChOneHiAlarmStatus,
                  aprisaXETxADCChOneHiAlarmSeverity, 
                  aprisaXETxADCChOneHiAlarmEnabled,
                  aprisaXETxADCChOneHiAlarmThreshold,
                  aprisaXETxADCChOneHiAlarmClearThreshold
    }
    STATUS      current
    DESCRIPTION "The aprisaXETx transmitter ADC Ch One voltage too high alarm group."
    ::= { aprisaXEGroups 252 } 


aprisaXETxADCChOneLoAlarm OBJECT IDENTIFIER ::= { aprisaXETransmitterAlarms 26 }

aprisaXETxADCChOneLoAlarmName OBJECT-TYPE
    SYNTAX      DisplayString
    MAX-ACCESS  read-only
    STATUS      current
    DESCRIPTION "The name of the transmitter ADC Ch One voltage too low alarm."
    ::= { aprisaXETxADCChOneLoAlarm 1 }

aprisaXETxADCChOneLoAlarmStatus OBJECT-TYPE
    SYNTAX      FourRFAlarmStatus
    MAX-ACCESS  read-only
    STATUS      current
    DESCRIPTION "The status of the transmitter ADC Ch One voltage too low alarm."
    ::= { aprisaXETxADCChOneLoAlarm 2 }

aprisaXETxADCChOneLoAlarmSeverity OBJECT-TYPE
    SYNTAX      FourRFAlarmSeverity
    MAX-ACCESS  read-only
    STATUS      current
    DESCRIPTION "The severity of the transmitter ADC Ch One voltage too low alarm."
    ::= { aprisaXETxADCChOneLoAlarm 3 }

aprisaXETxADCChOneLoAlarmEnabled OBJECT-TYPE
    SYNTAX      FourRFAlarmEnabled
    MAX-ACCESS  read-only
    STATUS      current
    DESCRIPTION "Indicates whether the transmitter ADC Ch One voltage too low alarm is enabled."
    ::= { aprisaXETxADCChOneLoAlarm 4 }
    
aprisaXETxADCChOneLoAlarmThreshold OBJECT-TYPE
    SYNTAX      Integer32
    MAX-ACCESS  read-only
    STATUS      current
    DESCRIPTION "Indicates the level at wLoch the transmitter ADC Ch One voltage too low 
                 alarm will be set."
    ::= { aprisaXETxADCChOneLoAlarm 5 }
    
aprisaXETxADCChOneLoAlarmClearThreshold OBJECT-TYPE
    SYNTAX      Integer32
    MAX-ACCESS  read-only
    STATUS      current
    DESCRIPTION "Indicates the level at wLoch the transmitter ADC Ch One voltage too low 
                 will be cleared."
    ::= { aprisaXETxADCChOneLoAlarm 6 }

aprisaXETxADCChOneLoAlarmsGroup OBJECT-GROUP
    OBJECTS     { aprisaXETxADCChOneLoAlarmName,
                  aprisaXETxADCChOneLoAlarmStatus,
                  aprisaXETxADCChOneLoAlarmSeverity, 
                  aprisaXETxADCChOneLoAlarmEnabled,
                  aprisaXETxADCChOneLoAlarmThreshold,
                  aprisaXETxADCChOneLoAlarmClearThreshold
    }
    STATUS      current
    DESCRIPTION "The aprisaXETx transmitter ADC Ch One voltage too High alarm group."
    ::= { aprisaXEGroups 253 }


aprisaXETxADCChTwoHiAlarm OBJECT IDENTIFIER ::= { aprisaXETransmitterAlarms 27 }

aprisaXETxADCChTwoHiAlarmName OBJECT-TYPE
    SYNTAX      DisplayString
    MAX-ACCESS  read-only
    STATUS      current
    DESCRIPTION "The name of the transmitter ADC Ch Two voltage too high alarm."
    ::= { aprisaXETxADCChTwoHiAlarm 1 }

aprisaXETxADCChTwoHiAlarmStatus OBJECT-TYPE
    SYNTAX      FourRFAlarmStatus
    MAX-ACCESS  read-only
    STATUS      current
    DESCRIPTION "The status of the transmitter ADC Ch Two voltage too high alarm."
    ::= { aprisaXETxADCChTwoHiAlarm 2 }

aprisaXETxADCChTwoHiAlarmSeverity OBJECT-TYPE
    SYNTAX      FourRFAlarmSeverity
    MAX-ACCESS  read-only
    STATUS      current
    DESCRIPTION "The severity of the transmitter ADC Ch Two voltage too high alarm."
    ::= { aprisaXETxADCChTwoHiAlarm 3 }

aprisaXETxADCChTwoHiAlarmEnabled OBJECT-TYPE
    SYNTAX      FourRFAlarmEnabled
    MAX-ACCESS  read-only
    STATUS      current
    DESCRIPTION "Indicates whether the transmitter ADC Ch Two voltage too high alarm is enabled."
    ::= { aprisaXETxADCChTwoHiAlarm 4 }
    
aprisaXETxADCChTwoHiAlarmThreshold OBJECT-TYPE
    SYNTAX      Integer32
    MAX-ACCESS  read-only
    STATUS      current
    DESCRIPTION "Indicates the level at which the transmitter ADC Ch Two voltage too high 
                 alarm will be set."
    ::= { aprisaXETxADCChTwoHiAlarm 5 }
    
aprisaXETxADCChTwoHiAlarmClearThreshold OBJECT-TYPE
    SYNTAX      Integer32
    MAX-ACCESS  read-only
    STATUS      current
    DESCRIPTION "Indicates the level at which the transmitter ADC Ch Two voltage too high 
                 will be cleared."
    ::= { aprisaXETxADCChTwoHiAlarm 6 }

aprisaXETxADCChTwoHiAlarmsGroup OBJECT-GROUP
    OBJECTS     { aprisaXETxADCChTwoHiAlarmName,
                  aprisaXETxADCChTwoHiAlarmStatus,
                  aprisaXETxADCChTwoHiAlarmSeverity, 
                  aprisaXETxADCChTwoHiAlarmEnabled,
                  aprisaXETxADCChTwoHiAlarmThreshold,
                  aprisaXETxADCChTwoHiAlarmClearThreshold
    }
    STATUS      current
    DESCRIPTION "The aprisaXETx transmitter ADC Ch Two voltage too high alarm group."
    ::= { aprisaXEGroups 254 } 


aprisaXETxADCChTwoLoAlarm OBJECT IDENTIFIER ::= { aprisaXETransmitterAlarms 28 }

aprisaXETxADCChTwoLoAlarmName OBJECT-TYPE
    SYNTAX      DisplayString
    MAX-ACCESS  read-only
    STATUS      current
    DESCRIPTION "The name of the transmitter ADC Ch Two voltage too low alarm."
    ::= { aprisaXETxADCChTwoLoAlarm 1 }

aprisaXETxADCChTwoLoAlarmStatus OBJECT-TYPE
    SYNTAX      FourRFAlarmStatus
    MAX-ACCESS  read-only
    STATUS      current
    DESCRIPTION "The status of the transmitter ADC Ch Two voltage too low alarm."
    ::= { aprisaXETxADCChTwoLoAlarm 2 }

aprisaXETxADCChTwoLoAlarmSeverity OBJECT-TYPE
    SYNTAX      FourRFAlarmSeverity
    MAX-ACCESS  read-only
    STATUS      current
    DESCRIPTION "The severity of the transmitter ADC Ch Two voltage too low alarm."
    ::= { aprisaXETxADCChTwoLoAlarm 3 }

aprisaXETxADCChTwoLoAlarmEnabled OBJECT-TYPE
    SYNTAX      FourRFAlarmEnabled
    MAX-ACCESS  read-only
    STATUS      current
    DESCRIPTION "Indicates whether the transmitter ADC Ch Two voltage too low alarm is enabled."
    ::= { aprisaXETxADCChTwoLoAlarm 4 }
    
aprisaXETxADCChTwoLoAlarmThreshold OBJECT-TYPE
    SYNTAX      Integer32
    MAX-ACCESS  read-only
    STATUS      current
    DESCRIPTION "Indicates the level at wLoch the transmitter ADC Ch Two voltage too low 
                 alarm will be set."
    ::= { aprisaXETxADCChTwoLoAlarm 5 }
    
aprisaXETxADCChTwoLoAlarmClearThreshold OBJECT-TYPE
    SYNTAX      Integer32
    MAX-ACCESS  read-only
    STATUS      current
    DESCRIPTION "Indicates the level at wLoch the transmitter ADC Ch Two voltage too low 
                 will be cleared."
    ::= { aprisaXETxADCChTwoLoAlarm 6 }

aprisaXETxADCChTwoLoAlarmsGroup OBJECT-GROUP
    OBJECTS     { aprisaXETxADCChTwoLoAlarmName,
                  aprisaXETxADCChTwoLoAlarmStatus,
                  aprisaXETxADCChTwoLoAlarmSeverity, 
                  aprisaXETxADCChTwoLoAlarmEnabled,
                  aprisaXETxADCChTwoLoAlarmThreshold,
                  aprisaXETxADCChTwoLoAlarmClearThreshold
    }
    STATUS      current
    DESCRIPTION "The aprisaXETx transmitter ADC Ch Two voltage too High alarm group."
    ::= { aprisaXEGroups 255 }


aprisaXETxADCChThreeHiAlarm OBJECT IDENTIFIER ::= { aprisaXETransmitterAlarms 29 }

aprisaXETxADCChThreeHiAlarmName OBJECT-TYPE
    SYNTAX      DisplayString
    MAX-ACCESS  read-only
    STATUS      current
    DESCRIPTION "The name of the transmitter ADC Ch Three voltage too high alarm."
    ::= { aprisaXETxADCChThreeHiAlarm 1 }

aprisaXETxADCChThreeHiAlarmStatus OBJECT-TYPE
    SYNTAX      FourRFAlarmStatus
    MAX-ACCESS  read-only
    STATUS      current
    DESCRIPTION "The status of the transmitter ADC Ch Three voltage too high alarm."
    ::= { aprisaXETxADCChThreeHiAlarm 2 }

aprisaXETxADCChThreeHiAlarmSeverity OBJECT-TYPE
    SYNTAX      FourRFAlarmSeverity
    MAX-ACCESS  read-only
    STATUS      current
    DESCRIPTION "The severity of the transmitter ADC Ch Three voltage too high alarm."
    ::= { aprisaXETxADCChThreeHiAlarm 3 }

aprisaXETxADCChThreeHiAlarmEnabled OBJECT-TYPE
    SYNTAX      FourRFAlarmEnabled
    MAX-ACCESS  read-only
    STATUS      current
    DESCRIPTION "Indicates whether the transmitter ADC Ch Three voltage too high alarm is enabled."
    ::= { aprisaXETxADCChThreeHiAlarm 4 }
    
aprisaXETxADCChThreeHiAlarmThreshold OBJECT-TYPE
    SYNTAX      Integer32
    MAX-ACCESS  read-only
    STATUS      current
    DESCRIPTION "Indicates the level at which the transmitter ADC Ch Three voltage too high 
                 alarm will be set."
    ::= { aprisaXETxADCChThreeHiAlarm 5 }
    
aprisaXETxADCChThreeHiAlarmClearThreshold OBJECT-TYPE
    SYNTAX      Integer32
    MAX-ACCESS  read-only
    STATUS      current
    DESCRIPTION "Indicates the level at which the transmitter ADC Ch Three voltage too high 
                 will be cleared."
    ::= { aprisaXETxADCChThreeHiAlarm 6 }

aprisaXETxADCChThreeHiAlarmsGroup OBJECT-GROUP
    OBJECTS     { aprisaXETxADCChThreeHiAlarmName,
                  aprisaXETxADCChThreeHiAlarmStatus,
                  aprisaXETxADCChThreeHiAlarmSeverity, 
                  aprisaXETxADCChThreeHiAlarmEnabled,
                  aprisaXETxADCChThreeHiAlarmThreshold,
                  aprisaXETxADCChThreeHiAlarmClearThreshold
    }
    STATUS      current
    DESCRIPTION "The aprisaXETx transmitter ADC Ch Three voltage too high alarm group."
    ::= { aprisaXEGroups 256 } 


aprisaXETxADCChThreeLoAlarm OBJECT IDENTIFIER ::= { aprisaXETransmitterAlarms 30 }

aprisaXETxADCChThreeLoAlarmName OBJECT-TYPE
    SYNTAX      DisplayString
    MAX-ACCESS  read-only
    STATUS      current
    DESCRIPTION "The name of the transmitter ADC Ch Three voltage too low alarm."
    ::= { aprisaXETxADCChThreeLoAlarm 1 }

aprisaXETxADCChThreeLoAlarmStatus OBJECT-TYPE
    SYNTAX      FourRFAlarmStatus
    MAX-ACCESS  read-only
    STATUS      current
    DESCRIPTION "The status of the transmitter ADC Ch Three voltage too low alarm."
    ::= { aprisaXETxADCChThreeLoAlarm 2 }

aprisaXETxADCChThreeLoAlarmSeverity OBJECT-TYPE
    SYNTAX      FourRFAlarmSeverity
    MAX-ACCESS  read-only
    STATUS      current
    DESCRIPTION "The severity of the transmitter ADC Ch Three voltage too low alarm."
    ::= { aprisaXETxADCChThreeLoAlarm 3 }

aprisaXETxADCChThreeLoAlarmEnabled OBJECT-TYPE
    SYNTAX      FourRFAlarmEnabled
    MAX-ACCESS  read-only
    STATUS      current
    DESCRIPTION "Indicates whether the transmitter ADC Ch Three voltage too low alarm is enabled."
    ::= { aprisaXETxADCChThreeLoAlarm 4 }
    
aprisaXETxADCChThreeLoAlarmThreshold OBJECT-TYPE
    SYNTAX      Integer32
    MAX-ACCESS  read-only
    STATUS      current
    DESCRIPTION "Indicates the level at wLoch the transmitter ADC Ch Three voltage too low 
                 alarm will be set."
    ::= { aprisaXETxADCChThreeLoAlarm 5 }
    
aprisaXETxADCChThreeLoAlarmClearThreshold OBJECT-TYPE
    SYNTAX      Integer32
    MAX-ACCESS  read-only
    STATUS      current
    DESCRIPTION "Indicates the level at wLoch the transmitter ADC Ch Three voltage too low 
                 will be cleared."
    ::= { aprisaXETxADCChThreeLoAlarm 6 }

aprisaXETxADCChThreeLoAlarmsGroup OBJECT-GROUP
    OBJECTS     { aprisaXETxADCChThreeLoAlarmName,
                  aprisaXETxADCChThreeLoAlarmStatus,
                  aprisaXETxADCChThreeLoAlarmSeverity, 
                  aprisaXETxADCChThreeLoAlarmEnabled,
                  aprisaXETxADCChThreeLoAlarmThreshold,
                  aprisaXETxADCChThreeLoAlarmClearThreshold
    }
    STATUS      current
    DESCRIPTION "The aprisaXETx transmitter ADC Ch Three voltage too High alarm group."
    ::= { aprisaXEGroups 257 }


aprisaXETxADCChFourHiAlarm OBJECT IDENTIFIER ::= { aprisaXETransmitterAlarms 31 }

aprisaXETxADCChFourHiAlarmName OBJECT-TYPE
    SYNTAX      DisplayString
    MAX-ACCESS  read-only
    STATUS      current
    DESCRIPTION "The name of the transmitter ADC Ch Four voltage too high alarm."
    ::= { aprisaXETxADCChFourHiAlarm 1 }

aprisaXETxADCChFourHiAlarmStatus OBJECT-TYPE
    SYNTAX      FourRFAlarmStatus
    MAX-ACCESS  read-only
    STATUS      current
    DESCRIPTION "The status of the transmitter ADC Ch Four voltage too high alarm."
    ::= { aprisaXETxADCChFourHiAlarm 2 }

aprisaXETxADCChFourHiAlarmSeverity OBJECT-TYPE
    SYNTAX      FourRFAlarmSeverity
    MAX-ACCESS  read-only
    STATUS      current
    DESCRIPTION "The severity of the transmitter ADC Ch Four voltage too high alarm."
    ::= { aprisaXETxADCChFourHiAlarm 3 }

aprisaXETxADCChFourHiAlarmEnabled OBJECT-TYPE
    SYNTAX      FourRFAlarmEnabled
    MAX-ACCESS  read-only
    STATUS      current
    DESCRIPTION "Indicates whether the transmitter ADC Ch Four voltage too high alarm is enabled."
    ::= { aprisaXETxADCChFourHiAlarm 4 }
    
aprisaXETxADCChFourHiAlarmThreshold OBJECT-TYPE
    SYNTAX      Integer32
    MAX-ACCESS  read-only
    STATUS      current
    DESCRIPTION "Indicates the level at which the transmitter ADC Ch Four voltage too high 
                 alarm will be set."
    ::= { aprisaXETxADCChFourHiAlarm 5 }
    
aprisaXETxADCChFourHiAlarmClearThreshold OBJECT-TYPE
    SYNTAX      Integer32
    MAX-ACCESS  read-only
    STATUS      current
    DESCRIPTION "Indicates the level at which the transmitter ADC Ch Four voltage too high 
                 will be cleared."
    ::= { aprisaXETxADCChFourHiAlarm 6 }

aprisaXETxADCChFourHiAlarmsGroup OBJECT-GROUP
    OBJECTS     { aprisaXETxADCChFourHiAlarmName,
                  aprisaXETxADCChFourHiAlarmStatus,
                  aprisaXETxADCChFourHiAlarmSeverity, 
                  aprisaXETxADCChFourHiAlarmEnabled,
                  aprisaXETxADCChFourHiAlarmThreshold,
                  aprisaXETxADCChFourHiAlarmClearThreshold
    }
    STATUS      current
    DESCRIPTION "The aprisaXETx transmitter ADC Ch Four voltage too high alarm group."
    ::= { aprisaXEGroups 258 } 


aprisaXETxADCChFourLoAlarm OBJECT IDENTIFIER ::= { aprisaXETransmitterAlarms 32 }

aprisaXETxADCChFourLoAlarmName OBJECT-TYPE
    SYNTAX      DisplayString
    MAX-ACCESS  read-only
    STATUS      current
    DESCRIPTION "The name of the transmitter ADC Ch Four voltage too low alarm."
    ::= { aprisaXETxADCChFourLoAlarm 1 }

aprisaXETxADCChFourLoAlarmStatus OBJECT-TYPE
    SYNTAX      FourRFAlarmStatus
    MAX-ACCESS  read-only
    STATUS      current
    DESCRIPTION "The status of the transmitter ADC Ch Four voltage too low alarm."
    ::= { aprisaXETxADCChFourLoAlarm 2 }

aprisaXETxADCChFourLoAlarmSeverity OBJECT-TYPE
    SYNTAX      FourRFAlarmSeverity
    MAX-ACCESS  read-only
    STATUS      current
    DESCRIPTION "The severity of the transmitter ADC Ch Four voltage too low alarm."
    ::= { aprisaXETxADCChFourLoAlarm 3 }

aprisaXETxADCChFourLoAlarmEnabled OBJECT-TYPE
    SYNTAX      FourRFAlarmEnabled
    MAX-ACCESS  read-only
    STATUS      current
    DESCRIPTION "Indicates whether the transmitter ADC Ch Four voltage too low alarm is enabled."
    ::= { aprisaXETxADCChFourLoAlarm 4 }
    
aprisaXETxADCChFourLoAlarmThreshold OBJECT-TYPE
    SYNTAX      Integer32
    MAX-ACCESS  read-only
    STATUS      current
    DESCRIPTION "Indicates the level at wLoch the transmitter ADC Ch Four voltage too low 
                 alarm will be set."
    ::= { aprisaXETxADCChFourLoAlarm 5 }
    
aprisaXETxADCChFourLoAlarmClearThreshold OBJECT-TYPE
    SYNTAX      Integer32
    MAX-ACCESS  read-only
    STATUS      current
    DESCRIPTION "Indicates the level at wLoch the transmitter ADC Ch Four voltage too low 
                 will be cleared."
    ::= { aprisaXETxADCChFourLoAlarm 6 }

aprisaXETxADCChFourLoAlarmsGroup OBJECT-GROUP
    OBJECTS     { aprisaXETxADCChFourLoAlarmName,
                  aprisaXETxADCChFourLoAlarmStatus,
                  aprisaXETxADCChFourLoAlarmSeverity, 
                  aprisaXETxADCChFourLoAlarmEnabled,
                  aprisaXETxADCChFourLoAlarmThreshold,
                  aprisaXETxADCChFourLoAlarmClearThreshold
    }
    STATUS      current
    DESCRIPTION "The aprisaXETx transmitter ADC Ch Four voltage too High alarm group."
    ::= { aprisaXEGroups 259 }


aprisaXETxADCChFiveHiAlarm OBJECT IDENTIFIER ::= { aprisaXETransmitterAlarms 33 }

aprisaXETxADCChFiveHiAlarmName OBJECT-TYPE
    SYNTAX      DisplayString
    MAX-ACCESS  read-only
    STATUS      current
    DESCRIPTION "The name of the transmitter ADC Ch Five voltage too high alarm."
    ::= { aprisaXETxADCChFiveHiAlarm 1 }

aprisaXETxADCChFiveHiAlarmStatus OBJECT-TYPE
    SYNTAX      FourRFAlarmStatus
    MAX-ACCESS  read-only
    STATUS      current
    DESCRIPTION "The status of the transmitter ADC Ch Five voltage too high alarm."
    ::= { aprisaXETxADCChFiveHiAlarm 2 }

aprisaXETxADCChFiveHiAlarmSeverity OBJECT-TYPE
    SYNTAX      FourRFAlarmSeverity
    MAX-ACCESS  read-only
    STATUS      current
    DESCRIPTION "The severity of the transmitter ADC Ch Five voltage too high alarm."
    ::= { aprisaXETxADCChFiveHiAlarm 3 }

aprisaXETxADCChFiveHiAlarmEnabled OBJECT-TYPE
    SYNTAX      FourRFAlarmEnabled
    MAX-ACCESS  read-only
    STATUS      current
    DESCRIPTION "Indicates whether the transmitter ADC Ch Five voltage too high alarm is enabled."
    ::= { aprisaXETxADCChFiveHiAlarm 4 }
    
aprisaXETxADCChFiveHiAlarmThreshold OBJECT-TYPE
    SYNTAX      Integer32
    MAX-ACCESS  read-only
    STATUS      current
    DESCRIPTION "Indicates the level at which the transmitter ADC Ch Five voltage too high 
                 alarm will be set."
    ::= { aprisaXETxADCChFiveHiAlarm 5 }
    
aprisaXETxADCChFiveHiAlarmClearThreshold OBJECT-TYPE
    SYNTAX      Integer32
    MAX-ACCESS  read-only
    STATUS      current
    DESCRIPTION "Indicates the level at which the transmitter ADC Ch Five voltage too high 
                 will be cleared."
    ::= { aprisaXETxADCChFiveHiAlarm 6 }

aprisaXETxADCChFiveHiAlarmsGroup OBJECT-GROUP
    OBJECTS     { aprisaXETxADCChFiveHiAlarmName,
                  aprisaXETxADCChFiveHiAlarmStatus,
                  aprisaXETxADCChFiveHiAlarmSeverity, 
                  aprisaXETxADCChFiveHiAlarmEnabled,
                  aprisaXETxADCChFiveHiAlarmThreshold,
                  aprisaXETxADCChFiveHiAlarmClearThreshold
    }
    STATUS      current
    DESCRIPTION "The aprisaXETx transmitter ADC Ch Five voltage too high alarm group."
    ::= { aprisaXEGroups 260 } 


aprisaXETxADCChFiveLoAlarm OBJECT IDENTIFIER ::= { aprisaXETransmitterAlarms 34 }

aprisaXETxADCChFiveLoAlarmName OBJECT-TYPE
    SYNTAX      DisplayString
    MAX-ACCESS  read-only
    STATUS      current
    DESCRIPTION "The name of the transmitter ADC Ch Five voltage too low alarm."
    ::= { aprisaXETxADCChFiveLoAlarm 1 }

aprisaXETxADCChFiveLoAlarmStatus OBJECT-TYPE
    SYNTAX      FourRFAlarmStatus
    MAX-ACCESS  read-only
    STATUS      current
    DESCRIPTION "The status of the transmitter ADC Ch Five voltage too low alarm."
    ::= { aprisaXETxADCChFiveLoAlarm 2 }

aprisaXETxADCChFiveLoAlarmSeverity OBJECT-TYPE
    SYNTAX      FourRFAlarmSeverity
    MAX-ACCESS  read-only
    STATUS      current
    DESCRIPTION "The severity of the transmitter ADC Ch Five voltage too low alarm."
    ::= { aprisaXETxADCChFiveLoAlarm 3 }

aprisaXETxADCChFiveLoAlarmEnabled OBJECT-TYPE
    SYNTAX      FourRFAlarmEnabled
    MAX-ACCESS  read-only
    STATUS      current
    DESCRIPTION "Indicates whether the transmitter ADC Ch Five voltage too low alarm is enabled."
    ::= { aprisaXETxADCChFiveLoAlarm 4 }
    
aprisaXETxADCChFiveLoAlarmThreshold OBJECT-TYPE
    SYNTAX      Integer32
    MAX-ACCESS  read-only
    STATUS      current
    DESCRIPTION "Indicates the level at wLoch the transmitter ADC Ch Five voltage too low 
                 alarm will be set."
    ::= { aprisaXETxADCChFiveLoAlarm 5 }
    
aprisaXETxADCChFiveLoAlarmClearThreshold OBJECT-TYPE
    SYNTAX      Integer32
    MAX-ACCESS  read-only
    STATUS      current
    DESCRIPTION "Indicates the level at wLoch the transmitter ADC Ch Five voltage too low 
                 will be cleared."
    ::= { aprisaXETxADCChFiveLoAlarm 6 }

aprisaXETxADCChFiveLoAlarmsGroup OBJECT-GROUP
    OBJECTS     { aprisaXETxADCChFiveLoAlarmName,
                  aprisaXETxADCChFiveLoAlarmStatus,
                  aprisaXETxADCChFiveLoAlarmSeverity, 
                  aprisaXETxADCChFiveLoAlarmEnabled,
                  aprisaXETxADCChFiveLoAlarmThreshold,
                  aprisaXETxADCChFiveLoAlarmClearThreshold
    }
    STATUS      current
    DESCRIPTION "The aprisaXETx transmitter ADC Ch Five voltage too High alarm group."
    ::= { aprisaXEGroups 261 }


aprisaXETxADCChSixHiAlarm OBJECT IDENTIFIER ::= { aprisaXETransmitterAlarms 35 }

aprisaXETxADCChSixHiAlarmName OBJECT-TYPE
    SYNTAX      DisplayString
    MAX-ACCESS  read-only
    STATUS      current
    DESCRIPTION "The name of the transmitter ADC Ch Six voltage too high alarm."
    ::= { aprisaXETxADCChSixHiAlarm 1 }

aprisaXETxADCChSixHiAlarmStatus OBJECT-TYPE
    SYNTAX      FourRFAlarmStatus
    MAX-ACCESS  read-only
    STATUS      current
    DESCRIPTION "The status of the transmitter ADC Ch Six voltage too high alarm."
    ::= { aprisaXETxADCChSixHiAlarm 2 }

aprisaXETxADCChSixHiAlarmSeverity OBJECT-TYPE
    SYNTAX      FourRFAlarmSeverity
    MAX-ACCESS  read-only
    STATUS      current
    DESCRIPTION "The severity of the transmitter ADC Ch Six voltage too high alarm."
    ::= { aprisaXETxADCChSixHiAlarm 3 }

aprisaXETxADCChSixHiAlarmEnabled OBJECT-TYPE
    SYNTAX      FourRFAlarmEnabled
    MAX-ACCESS  read-only
    STATUS      current
    DESCRIPTION "Indicates whether the transmitter ADC Ch Six voltage too high alarm is enabled."
    ::= { aprisaXETxADCChSixHiAlarm 4 }
    
aprisaXETxADCChSixHiAlarmThreshold OBJECT-TYPE
    SYNTAX      Integer32
    MAX-ACCESS  read-only
    STATUS      current
    DESCRIPTION "Indicates the level at which the transmitter ADC Ch Six voltage too high 
                 alarm will be set."
    ::= { aprisaXETxADCChSixHiAlarm 5 }
    
aprisaXETxADCChSixHiAlarmClearThreshold OBJECT-TYPE
    SYNTAX      Integer32
    MAX-ACCESS  read-only
    STATUS      current
    DESCRIPTION "Indicates the level at which the transmitter ADC Ch Six voltage too high 
                 will be cleared."
    ::= { aprisaXETxADCChSixHiAlarm 6 }

aprisaXETxADCChSixHiAlarmsGroup OBJECT-GROUP
    OBJECTS     { aprisaXETxADCChSixHiAlarmName,
                  aprisaXETxADCChSixHiAlarmStatus,
                  aprisaXETxADCChSixHiAlarmSeverity, 
                  aprisaXETxADCChSixHiAlarmEnabled,
                  aprisaXETxADCChSixHiAlarmThreshold,
                  aprisaXETxADCChSixHiAlarmClearThreshold
    }
    STATUS      current
    DESCRIPTION "The aprisaXETx transmitter ADC Ch Six voltage too high alarm group."
    ::= { aprisaXEGroups 262 } 


aprisaXETxADCChSixLoAlarm OBJECT IDENTIFIER ::= { aprisaXETransmitterAlarms 36 }

aprisaXETxADCChSixLoAlarmName OBJECT-TYPE
    SYNTAX      DisplayString
    MAX-ACCESS  read-only
    STATUS      current
    DESCRIPTION "The name of the transmitter ADC Ch Six voltage too low alarm."
    ::= { aprisaXETxADCChSixLoAlarm 1 }

aprisaXETxADCChSixLoAlarmStatus OBJECT-TYPE
    SYNTAX      FourRFAlarmStatus
    MAX-ACCESS  read-only
    STATUS      current
    DESCRIPTION "The status of the transmitter ADC Ch Six voltage too low alarm."
    ::= { aprisaXETxADCChSixLoAlarm 2 }

aprisaXETxADCChSixLoAlarmSeverity OBJECT-TYPE
    SYNTAX      FourRFAlarmSeverity
    MAX-ACCESS  read-only
    STATUS      current
    DESCRIPTION "The severity of the transmitter ADC Ch Six voltage too low alarm."
    ::= { aprisaXETxADCChSixLoAlarm 3 }

aprisaXETxADCChSixLoAlarmEnabled OBJECT-TYPE
    SYNTAX      FourRFAlarmEnabled
    MAX-ACCESS  read-only
    STATUS      current
    DESCRIPTION "Indicates whether the transmitter ADC Ch Six voltage too low alarm is enabled."
    ::= { aprisaXETxADCChSixLoAlarm 4 }
    
aprisaXETxADCChSixLoAlarmThreshold OBJECT-TYPE
    SYNTAX      Integer32
    MAX-ACCESS  read-only
    STATUS      current
    DESCRIPTION "Indicates the level at wLoch the transmitter ADC Ch Six voltage too low 
                 alarm will be set."
    ::= { aprisaXETxADCChSixLoAlarm 5 }
    
aprisaXETxADCChSixLoAlarmClearThreshold OBJECT-TYPE
    SYNTAX      Integer32
    MAX-ACCESS  read-only
    STATUS      current
    DESCRIPTION "Indicates the level at wLoch the transmitter ADC Ch Six voltage too low 
                 will be cleared."
    ::= { aprisaXETxADCChSixLoAlarm 6 }

aprisaXETxADCChSixLoAlarmsGroup OBJECT-GROUP
    OBJECTS     { aprisaXETxADCChSixLoAlarmName,
                  aprisaXETxADCChSixLoAlarmStatus,
                  aprisaXETxADCChSixLoAlarmSeverity, 
                  aprisaXETxADCChSixLoAlarmEnabled,
                  aprisaXETxADCChSixLoAlarmThreshold,
                  aprisaXETxADCChSixLoAlarmClearThreshold
    }
    STATUS      current
    DESCRIPTION "The aprisaXETx transmitter ADC Ch Six voltage too High alarm group."
    ::= { aprisaXEGroups 263 }


aprisaXETxADCChSevenHiAlarm OBJECT IDENTIFIER ::= { aprisaXETransmitterAlarms 37 }

aprisaXETxADCChSevenHiAlarmName OBJECT-TYPE
    SYNTAX      DisplayString
    MAX-ACCESS  read-only
    STATUS      current
    DESCRIPTION "The name of the transmitter ADC Ch Seven voltage too high alarm."
    ::= { aprisaXETxADCChSevenHiAlarm 1 }

aprisaXETxADCChSevenHiAlarmStatus OBJECT-TYPE
    SYNTAX      FourRFAlarmStatus
    MAX-ACCESS  read-only
    STATUS      current
    DESCRIPTION "The status of the transmitter ADC Ch Seven voltage too high alarm."
    ::= { aprisaXETxADCChSevenHiAlarm 2 }

aprisaXETxADCChSevenHiAlarmSeverity OBJECT-TYPE
    SYNTAX      FourRFAlarmSeverity
    MAX-ACCESS  read-only
    STATUS      current
    DESCRIPTION "The severity of the transmitter ADC Ch Seven voltage too high alarm."
    ::= { aprisaXETxADCChSevenHiAlarm 3 }

aprisaXETxADCChSevenHiAlarmEnabled OBJECT-TYPE
    SYNTAX      FourRFAlarmEnabled
    MAX-ACCESS  read-only
    STATUS      current
    DESCRIPTION "Indicates whether the transmitter ADC Ch Seven voltage too high alarm is enabled."
    ::= { aprisaXETxADCChSevenHiAlarm 4 }
    
aprisaXETxADCChSevenHiAlarmThreshold OBJECT-TYPE
    SYNTAX      Integer32
    MAX-ACCESS  read-only
    STATUS      current
    DESCRIPTION "Indicates the level at which the transmitter ADC Ch Seven voltage too high 
                 alarm will be set."
    ::= { aprisaXETxADCChSevenHiAlarm 5 }
    
aprisaXETxADCChSevenHiAlarmClearThreshold OBJECT-TYPE
    SYNTAX      Integer32
    MAX-ACCESS  read-only
    STATUS      current
    DESCRIPTION "Indicates the level at which the transmitter ADC Ch Seven voltage too high 
                 will be cleared."
    ::= { aprisaXETxADCChSevenHiAlarm 6 }

aprisaXETxADCChSevenHiAlarmsGroup OBJECT-GROUP
    OBJECTS     { aprisaXETxADCChSevenHiAlarmName,
                  aprisaXETxADCChSevenHiAlarmStatus,
                  aprisaXETxADCChSevenHiAlarmSeverity, 
                  aprisaXETxADCChSevenHiAlarmEnabled,
                  aprisaXETxADCChSevenHiAlarmThreshold,
                  aprisaXETxADCChSevenHiAlarmClearThreshold
    }
    STATUS      current
    DESCRIPTION "The aprisaXETx transmitter ADC Ch Seven voltage too high alarm group."
    ::= { aprisaXEGroups 264 } 


aprisaXETxADCChSevenLoAlarm OBJECT IDENTIFIER ::= { aprisaXETransmitterAlarms 38 }

aprisaXETxADCChSevenLoAlarmName OBJECT-TYPE
    SYNTAX      DisplayString
    MAX-ACCESS  read-only
    STATUS      current
    DESCRIPTION "The name of the transmitter ADC Ch Seven voltage too low alarm."
    ::= { aprisaXETxADCChSevenLoAlarm 1 }

aprisaXETxADCChSevenLoAlarmStatus OBJECT-TYPE
    SYNTAX      FourRFAlarmStatus
    MAX-ACCESS  read-only
    STATUS      current
    DESCRIPTION "The status of the transmitter ADC Ch Seven voltage too low alarm."
    ::= { aprisaXETxADCChSevenLoAlarm 2 }

aprisaXETxADCChSevenLoAlarmSeverity OBJECT-TYPE
    SYNTAX      FourRFAlarmSeverity
    MAX-ACCESS  read-only
    STATUS      current
    DESCRIPTION "The severity of the transmitter ADC Ch Seven voltage too low alarm."
    ::= { aprisaXETxADCChSevenLoAlarm 3 }

aprisaXETxADCChSevenLoAlarmEnabled OBJECT-TYPE
    SYNTAX      FourRFAlarmEnabled
    MAX-ACCESS  read-only
    STATUS      current
    DESCRIPTION "Indicates whether the transmitter ADC Ch Seven voltage too low alarm is enabled."
    ::= { aprisaXETxADCChSevenLoAlarm 4 }
    
aprisaXETxADCChSevenLoAlarmThreshold OBJECT-TYPE
    SYNTAX      Integer32
    MAX-ACCESS  read-only
    STATUS      current
    DESCRIPTION "Indicates the level at wLoch the transmitter ADC Ch Seven voltage too low 
                 alarm will be set."
    ::= { aprisaXETxADCChSevenLoAlarm 5 }
    
aprisaXETxADCChSevenLoAlarmClearThreshold OBJECT-TYPE
    SYNTAX      Integer32
    MAX-ACCESS  read-only
    STATUS      current
    DESCRIPTION "Indicates the level at wLoch the transmitter ADC Ch Seven voltage too low 
                 will be cleared."
    ::= { aprisaXETxADCChSevenLoAlarm 6 }

aprisaXETxADCChSevenLoAlarmsGroup OBJECT-GROUP
    OBJECTS     { aprisaXETxADCChSevenLoAlarmName,
                  aprisaXETxADCChSevenLoAlarmStatus,
                  aprisaXETxADCChSevenLoAlarmSeverity, 
                  aprisaXETxADCChSevenLoAlarmEnabled,
                  aprisaXETxADCChSevenLoAlarmThreshold,
                  aprisaXETxADCChSevenLoAlarmClearThreshold
    }
    STATUS      current
    DESCRIPTION "The aprisaXETx transmitter ADC Ch Seven voltage too High alarm group."
    ::= { aprisaXEGroups 265 }


aprisaXETxADCChEightHiAlarm OBJECT IDENTIFIER ::= { aprisaXETransmitterAlarms 39 }

aprisaXETxADCChEightHiAlarmName OBJECT-TYPE
    SYNTAX      DisplayString
    MAX-ACCESS  read-only
    STATUS      current
    DESCRIPTION "The name of the transmitter ADC Ch Eight voltage too high alarm."
    ::= { aprisaXETxADCChEightHiAlarm 1 }

aprisaXETxADCChEightHiAlarmStatus OBJECT-TYPE
    SYNTAX      FourRFAlarmStatus
    MAX-ACCESS  read-only
    STATUS      current
    DESCRIPTION "The status of the transmitter ADC Ch Eight voltage too high alarm."
    ::= { aprisaXETxADCChEightHiAlarm 2 }

aprisaXETxADCChEightHiAlarmSeverity OBJECT-TYPE
    SYNTAX      FourRFAlarmSeverity
    MAX-ACCESS  read-only
    STATUS      current
    DESCRIPTION "The severity of the transmitter ADC Ch Eight voltage too high alarm."
    ::= { aprisaXETxADCChEightHiAlarm 3 }

aprisaXETxADCChEightHiAlarmEnabled OBJECT-TYPE
    SYNTAX      FourRFAlarmEnabled
    MAX-ACCESS  read-only
    STATUS      current
    DESCRIPTION "Indicates whether the transmitter ADC Ch Eight voltage too high alarm is enabled."
    ::= { aprisaXETxADCChEightHiAlarm 4 }
    
aprisaXETxADCChEightHiAlarmThreshold OBJECT-TYPE
    SYNTAX      Integer32
    MAX-ACCESS  read-only
    STATUS      current
    DESCRIPTION "Indicates the level at which the transmitter ADC Ch Eight voltage too high 
                 alarm will be set."
    ::= { aprisaXETxADCChEightHiAlarm 5 }
    
aprisaXETxADCChEightHiAlarmClearThreshold OBJECT-TYPE
    SYNTAX      Integer32
    MAX-ACCESS  read-only
    STATUS      current
    DESCRIPTION "Indicates the level at which the transmitter ADC Ch Eight voltage too high 
                 will be cleared."
    ::= { aprisaXETxADCChEightHiAlarm 6 }

aprisaXETxADCChEightHiAlarmsGroup OBJECT-GROUP
    OBJECTS     { aprisaXETxADCChEightHiAlarmName,
                  aprisaXETxADCChEightHiAlarmStatus,
                  aprisaXETxADCChEightHiAlarmSeverity, 
                  aprisaXETxADCChEightHiAlarmEnabled,
                  aprisaXETxADCChEightHiAlarmThreshold,
                  aprisaXETxADCChEightHiAlarmClearThreshold
    }
    STATUS      current
    DESCRIPTION "The aprisaXETx transmitter ADC Ch Eight voltage too high alarm group."
    ::= { aprisaXEGroups 266 } 


aprisaXETxADCChEightLoAlarm OBJECT IDENTIFIER ::= { aprisaXETransmitterAlarms 40 }

aprisaXETxADCChEightLoAlarmName OBJECT-TYPE
    SYNTAX      DisplayString
    MAX-ACCESS  read-only
    STATUS      current
    DESCRIPTION "The name of the transmitter ADC Ch Eight voltage too low alarm."
    ::= { aprisaXETxADCChEightLoAlarm 1 }

aprisaXETxADCChEightLoAlarmStatus OBJECT-TYPE
    SYNTAX      FourRFAlarmStatus
    MAX-ACCESS  read-only
    STATUS      current
    DESCRIPTION "The status of the transmitter ADC Ch Eight voltage too low alarm."
    ::= { aprisaXETxADCChEightLoAlarm 2 }

aprisaXETxADCChEightLoAlarmSeverity OBJECT-TYPE
    SYNTAX      FourRFAlarmSeverity
    MAX-ACCESS  read-only
    STATUS      current
    DESCRIPTION "The severity of the transmitter ADC Ch Eight voltage too low alarm."
    ::= { aprisaXETxADCChEightLoAlarm 3 }

aprisaXETxADCChEightLoAlarmEnabled OBJECT-TYPE
    SYNTAX      FourRFAlarmEnabled
    MAX-ACCESS  read-only
    STATUS      current
    DESCRIPTION "Indicates whether the transmitter ADC Ch Eight voltage too low alarm is enabled."
    ::= { aprisaXETxADCChEightLoAlarm 4 }
    
aprisaXETxADCChEightLoAlarmThreshold OBJECT-TYPE
    SYNTAX      Integer32
    MAX-ACCESS  read-only
    STATUS      current
    DESCRIPTION "Indicates the level at wLoch the transmitter ADC Ch Eight voltage too low 
                 alarm will be set."
    ::= { aprisaXETxADCChEightLoAlarm 5 }
    
aprisaXETxADCChEightLoAlarmClearThreshold OBJECT-TYPE
    SYNTAX      Integer32
    MAX-ACCESS  read-only
    STATUS      current
    DESCRIPTION "Indicates the level at wLoch the transmitter ADC Ch Eight voltage too low 
                 will be cleared."
    ::= { aprisaXETxADCChEightLoAlarm 6 }

aprisaXETxADCChEightLoAlarmsGroup OBJECT-GROUP
    OBJECTS     { aprisaXETxADCChEightLoAlarmName,
                  aprisaXETxADCChEightLoAlarmStatus,
                  aprisaXETxADCChEightLoAlarmSeverity, 
                  aprisaXETxADCChEightLoAlarmEnabled,
                  aprisaXETxADCChEightLoAlarmThreshold,
                  aprisaXETxADCChEightLoAlarmClearThreshold
    }
    STATUS      current
    DESCRIPTION "The aprisaXETx transmitter ADC Ch Eight voltage too High alarm group."
    ::= { aprisaXEGroups 267 }


aprisaXETxADCChNineHiAlarm OBJECT IDENTIFIER ::= { aprisaXETransmitterAlarms 41 }

aprisaXETxADCChNineHiAlarmName OBJECT-TYPE
    SYNTAX      DisplayString
    MAX-ACCESS  read-only
    STATUS      current
    DESCRIPTION "The name of the transmitter ADC Ch Nine voltage too high alarm."
    ::= { aprisaXETxADCChNineHiAlarm 1 }

aprisaXETxADCChNineHiAlarmStatus OBJECT-TYPE
    SYNTAX      FourRFAlarmStatus
    MAX-ACCESS  read-only
    STATUS      current
    DESCRIPTION "The status of the transmitter ADC Ch Nine voltage too high alarm."
    ::= { aprisaXETxADCChNineHiAlarm 2 }

aprisaXETxADCChNineHiAlarmSeverity OBJECT-TYPE
    SYNTAX      FourRFAlarmSeverity
    MAX-ACCESS  read-only
    STATUS      current
    DESCRIPTION "The severity of the transmitter ADC Ch Nine voltage too high alarm."
    ::= { aprisaXETxADCChNineHiAlarm 3 }

aprisaXETxADCChNineHiAlarmEnabled OBJECT-TYPE
    SYNTAX      FourRFAlarmEnabled
    MAX-ACCESS  read-only
    STATUS      current
    DESCRIPTION "Indicates whether the transmitter ADC Ch Nine voltage too high alarm is enabled."
    ::= { aprisaXETxADCChNineHiAlarm 4 }
    
aprisaXETxADCChNineHiAlarmThreshold OBJECT-TYPE
    SYNTAX      Integer32
    MAX-ACCESS  read-only
    STATUS      current
    DESCRIPTION "Indicates the level at which the transmitter ADC Ch Nine voltage too high 
                 alarm will be set."
    ::= { aprisaXETxADCChNineHiAlarm 5 }
    
aprisaXETxADCChNineHiAlarmClearThreshold OBJECT-TYPE
    SYNTAX      Integer32
    MAX-ACCESS  read-only
    STATUS      current
    DESCRIPTION "Indicates the level at which the transmitter ADC Ch Nine voltage too high 
                 will be cleared."
    ::= { aprisaXETxADCChNineHiAlarm 6 }

aprisaXETxADCChNineHiAlarmsGroup OBJECT-GROUP
    OBJECTS     { aprisaXETxADCChNineHiAlarmName,
                  aprisaXETxADCChNineHiAlarmStatus,
                  aprisaXETxADCChNineHiAlarmSeverity, 
                  aprisaXETxADCChNineHiAlarmEnabled,
                  aprisaXETxADCChNineHiAlarmThreshold,
                  aprisaXETxADCChNineHiAlarmClearThreshold
    }
    STATUS      current
    DESCRIPTION "The aprisaXETx transmitter ADC Ch Nine voltage too high alarm group."
    ::= { aprisaXEGroups 268 } 


aprisaXETxADCChNineLoAlarm OBJECT IDENTIFIER ::= { aprisaXETransmitterAlarms 42 }

aprisaXETxADCChNineLoAlarmName OBJECT-TYPE
    SYNTAX      DisplayString
    MAX-ACCESS  read-only
    STATUS      current
    DESCRIPTION "The name of the transmitter ADC Ch Nine voltage too low alarm."
    ::= { aprisaXETxADCChNineLoAlarm 1 }

aprisaXETxADCChNineLoAlarmStatus OBJECT-TYPE
    SYNTAX      FourRFAlarmStatus
    MAX-ACCESS  read-only
    STATUS      current
    DESCRIPTION "The status of the transmitter ADC Ch Nine voltage too low alarm."
    ::= { aprisaXETxADCChNineLoAlarm 2 }

aprisaXETxADCChNineLoAlarmSeverity OBJECT-TYPE
    SYNTAX      FourRFAlarmSeverity
    MAX-ACCESS  read-only
    STATUS      current
    DESCRIPTION "The severity of the transmitter ADC Ch Nine voltage too low alarm."
    ::= { aprisaXETxADCChNineLoAlarm 3 }

aprisaXETxADCChNineLoAlarmEnabled OBJECT-TYPE
    SYNTAX      FourRFAlarmEnabled
    MAX-ACCESS  read-only
    STATUS      current
    DESCRIPTION "Indicates whether the transmitter ADC Ch Nine voltage too low alarm is enabled."
    ::= { aprisaXETxADCChNineLoAlarm 4 }
    
aprisaXETxADCChNineLoAlarmThreshold OBJECT-TYPE
    SYNTAX      Integer32
    MAX-ACCESS  read-only
    STATUS      current
    DESCRIPTION "Indicates the level at wLoch the transmitter ADC Ch Nine voltage too low 
                 alarm will be set."
    ::= { aprisaXETxADCChNineLoAlarm 5 }
    
aprisaXETxADCChNineLoAlarmClearThreshold OBJECT-TYPE
    SYNTAX      Integer32
    MAX-ACCESS  read-only
    STATUS      current
    DESCRIPTION "Indicates the level at wLoch the transmitter ADC Ch Nine voltage too low 
                 will be cleared."
    ::= { aprisaXETxADCChNineLoAlarm 6 }

aprisaXETxADCChNineLoAlarmsGroup OBJECT-GROUP
    OBJECTS     { aprisaXETxADCChNineLoAlarmName,
                  aprisaXETxADCChNineLoAlarmStatus,
                  aprisaXETxADCChNineLoAlarmSeverity, 
                  aprisaXETxADCChNineLoAlarmEnabled,
                  aprisaXETxADCChNineLoAlarmThreshold,
                  aprisaXETxADCChNineLoAlarmClearThreshold
    }
    STATUS      current
    DESCRIPTION "The aprisaXETx transmitter ADC Ch Nine voltage too High alarm group."
    ::= { aprisaXEGroups 269 }


aprisaXETxADCChTenHiAlarm OBJECT IDENTIFIER ::= { aprisaXETransmitterAlarms 43 }

aprisaXETxADCChTenHiAlarmName OBJECT-TYPE
    SYNTAX      DisplayString
    MAX-ACCESS  read-only
    STATUS      current
    DESCRIPTION "The name of the transmitter ADC Ch Ten voltage too high alarm."
    ::= { aprisaXETxADCChTenHiAlarm 1 }

aprisaXETxADCChTenHiAlarmStatus OBJECT-TYPE
    SYNTAX      FourRFAlarmStatus
    MAX-ACCESS  read-only
    STATUS      current
    DESCRIPTION "The status of the transmitter ADC Ch Ten voltage too high alarm."
    ::= { aprisaXETxADCChTenHiAlarm 2 }

aprisaXETxADCChTenHiAlarmSeverity OBJECT-TYPE
    SYNTAX      FourRFAlarmSeverity
    MAX-ACCESS  read-only
    STATUS      current
    DESCRIPTION "The severity of the transmitter ADC Ch Ten voltage too high alarm."
    ::= { aprisaXETxADCChTenHiAlarm 3 }

aprisaXETxADCChTenHiAlarmEnabled OBJECT-TYPE
    SYNTAX      FourRFAlarmEnabled
    MAX-ACCESS  read-only
    STATUS      current
    DESCRIPTION "Indicates whether the transmitter ADC Ch Ten voltage too high alarm is enabled."
    ::= { aprisaXETxADCChTenHiAlarm 4 }
    
aprisaXETxADCChTenHiAlarmThreshold OBJECT-TYPE
    SYNTAX      Integer32
    MAX-ACCESS  read-only
    STATUS      current
    DESCRIPTION "Indicates the level at which the transmitter ADC Ch Ten voltage too high 
                 alarm will be set."
    ::= { aprisaXETxADCChTenHiAlarm 5 }
    
aprisaXETxADCChTenHiAlarmClearThreshold OBJECT-TYPE
    SYNTAX      Integer32
    MAX-ACCESS  read-only
    STATUS      current
    DESCRIPTION "Indicates the level at which the transmitter ADC Ch Ten voltage too high 
                 will be cleared."
    ::= { aprisaXETxADCChTenHiAlarm 6 }

aprisaXETxADCChTenHiAlarmsGroup OBJECT-GROUP
    OBJECTS     { aprisaXETxADCChTenHiAlarmName,
                  aprisaXETxADCChTenHiAlarmStatus,
                  aprisaXETxADCChTenHiAlarmSeverity, 
                  aprisaXETxADCChTenHiAlarmEnabled,
                  aprisaXETxADCChTenHiAlarmThreshold,
                  aprisaXETxADCChTenHiAlarmClearThreshold
    }
    STATUS      current
    DESCRIPTION "The aprisaXETx transmitter ADC Ch Ten voltage too high alarm group."
    ::= { aprisaXEGroups 270 } 


aprisaXETxADCChTenLoAlarm OBJECT IDENTIFIER ::= { aprisaXETransmitterAlarms 44 }

aprisaXETxADCChTenLoAlarmName OBJECT-TYPE
    SYNTAX      DisplayString
    MAX-ACCESS  read-only
    STATUS      current
    DESCRIPTION "The name of the transmitter ADC Ch Ten voltage too low alarm."
    ::= { aprisaXETxADCChTenLoAlarm 1 }

aprisaXETxADCChTenLoAlarmStatus OBJECT-TYPE
    SYNTAX      FourRFAlarmStatus
    MAX-ACCESS  read-only
    STATUS      current
    DESCRIPTION "The status of the transmitter ADC Ch Ten voltage too low alarm."
    ::= { aprisaXETxADCChTenLoAlarm 2 }

aprisaXETxADCChTenLoAlarmSeverity OBJECT-TYPE
    SYNTAX      FourRFAlarmSeverity
    MAX-ACCESS  read-only
    STATUS      current
    DESCRIPTION "The severity of the transmitter ADC Ch Ten voltage too low alarm."
    ::= { aprisaXETxADCChTenLoAlarm 3 }

aprisaXETxADCChTenLoAlarmEnabled OBJECT-TYPE
    SYNTAX      FourRFAlarmEnabled
    MAX-ACCESS  read-only
    STATUS      current
    DESCRIPTION "Indicates whether the transmitter ADC Ch Ten voltage too low alarm is enabled."
    ::= { aprisaXETxADCChTenLoAlarm 4 }
    
aprisaXETxADCChTenLoAlarmThreshold OBJECT-TYPE
    SYNTAX      Integer32
    MAX-ACCESS  read-only
    STATUS      current
    DESCRIPTION "Indicates the level at wLoch the transmitter ADC Ch Ten voltage too low 
                 alarm will be set."
    ::= { aprisaXETxADCChTenLoAlarm 5 }
    
aprisaXETxADCChTenLoAlarmClearThreshold OBJECT-TYPE
    SYNTAX      Integer32
    MAX-ACCESS  read-only
    STATUS      current
    DESCRIPTION "Indicates the level at wLoch the transmitter ADC Ch Ten voltage too low 
                 will be cleared."
    ::= { aprisaXETxADCChTenLoAlarm 6 }

aprisaXETxADCChTenLoAlarmsGroup OBJECT-GROUP
    OBJECTS     { aprisaXETxADCChTenLoAlarmName,
                  aprisaXETxADCChTenLoAlarmStatus,
                  aprisaXETxADCChTenLoAlarmSeverity, 
                  aprisaXETxADCChTenLoAlarmEnabled,
                  aprisaXETxADCChTenLoAlarmThreshold,
                  aprisaXETxADCChTenLoAlarmClearThreshold
    }
    STATUS      current
    DESCRIPTION "The aprisaXETx transmitter ADC Ch Ten voltage too High alarm group."
    ::= { aprisaXEGroups 271 }


aprisaXETxADCChElevenHiAlarm OBJECT IDENTIFIER ::= { aprisaXETransmitterAlarms 45 }

aprisaXETxADCChElevenHiAlarmName OBJECT-TYPE
    SYNTAX      DisplayString
    MAX-ACCESS  read-only
    STATUS      current
    DESCRIPTION "The name of the transmitter ADC Ch Eleven voltage too high alarm."
    ::= { aprisaXETxADCChElevenHiAlarm 1 }

aprisaXETxADCChElevenHiAlarmStatus OBJECT-TYPE
    SYNTAX      FourRFAlarmStatus
    MAX-ACCESS  read-only
    STATUS      current
    DESCRIPTION "The status of the transmitter ADC Ch Eleven voltage too high alarm."
    ::= { aprisaXETxADCChElevenHiAlarm 2 }

aprisaXETxADCChElevenHiAlarmSeverity OBJECT-TYPE
    SYNTAX      FourRFAlarmSeverity
    MAX-ACCESS  read-only
    STATUS      current
    DESCRIPTION "The severity of the transmitter ADC Ch Eleven voltage too high alarm."
    ::= { aprisaXETxADCChElevenHiAlarm 3 }

aprisaXETxADCChElevenHiAlarmEnabled OBJECT-TYPE
    SYNTAX      FourRFAlarmEnabled
    MAX-ACCESS  read-only
    STATUS      current
    DESCRIPTION "Indicates whether the transmitter ADC Ch Eleven voltage too high alarm is enabled."
    ::= { aprisaXETxADCChElevenHiAlarm 4 }
    
aprisaXETxADCChElevenHiAlarmThreshold OBJECT-TYPE
    SYNTAX      Integer32
    MAX-ACCESS  read-only
    STATUS      current
    DESCRIPTION "Indicates the level at which the transmitter ADC Ch Eleven voltage too high 
                 alarm will be set."
    ::= { aprisaXETxADCChElevenHiAlarm 5 }
    
aprisaXETxADCChElevenHiAlarmClearThreshold OBJECT-TYPE
    SYNTAX      Integer32
    MAX-ACCESS  read-only
    STATUS      current
    DESCRIPTION "Indicates the level at which the transmitter ADC Ch Eleven voltage too high 
                 will be cleared."
    ::= { aprisaXETxADCChElevenHiAlarm 6 }

aprisaXETxADCChElevenHiAlarmsGroup OBJECT-GROUP
    OBJECTS     { aprisaXETxADCChElevenHiAlarmName,
                  aprisaXETxADCChElevenHiAlarmStatus,
                  aprisaXETxADCChElevenHiAlarmSeverity, 
                  aprisaXETxADCChElevenHiAlarmEnabled,
                  aprisaXETxADCChElevenHiAlarmThreshold,
                  aprisaXETxADCChElevenHiAlarmClearThreshold
    }
    STATUS      current
    DESCRIPTION "The aprisaXETx transmitter ADC Ch Eleven voltage too high alarm group."
    ::= { aprisaXEGroups 272 } 


aprisaXETxADCChElevenLoAlarm OBJECT IDENTIFIER ::= { aprisaXETransmitterAlarms 46 }

aprisaXETxADCChElevenLoAlarmName OBJECT-TYPE
    SYNTAX      DisplayString
    MAX-ACCESS  read-only
    STATUS      current
    DESCRIPTION "The name of the transmitter ADC Ch Eleven voltage too low alarm."
    ::= { aprisaXETxADCChElevenLoAlarm 1 }

aprisaXETxADCChElevenLoAlarmStatus OBJECT-TYPE
    SYNTAX      FourRFAlarmStatus
    MAX-ACCESS  read-only
    STATUS      current
    DESCRIPTION "The status of the transmitter ADC Ch Eleven voltage too low alarm."
    ::= { aprisaXETxADCChElevenLoAlarm 2 }

aprisaXETxADCChElevenLoAlarmSeverity OBJECT-TYPE
    SYNTAX      FourRFAlarmSeverity
    MAX-ACCESS  read-only
    STATUS      current
    DESCRIPTION "The severity of the transmitter ADC Ch Eleven voltage too low alarm."
    ::= { aprisaXETxADCChElevenLoAlarm 3 }

aprisaXETxADCChElevenLoAlarmEnabled OBJECT-TYPE
    SYNTAX      FourRFAlarmEnabled
    MAX-ACCESS  read-only
    STATUS      current
    DESCRIPTION "Indicates whether the transmitter ADC Ch Eleven voltage too low alarm is enabled."
    ::= { aprisaXETxADCChElevenLoAlarm 4 }
    
aprisaXETxADCChElevenLoAlarmThreshold OBJECT-TYPE
    SYNTAX      Integer32
    MAX-ACCESS  read-only
    STATUS      current
    DESCRIPTION "Indicates the level at wLoch the transmitter ADC Ch Eleven voltage too low 
                 alarm will be set."
    ::= { aprisaXETxADCChElevenLoAlarm 5 }
    
aprisaXETxADCChElevenLoAlarmClearThreshold OBJECT-TYPE
    SYNTAX      Integer32
    MAX-ACCESS  read-only
    STATUS      current
    DESCRIPTION "Indicates the level at wLoch the transmitter ADC Ch Eleven voltage too low 
                 will be cleared."
    ::= { aprisaXETxADCChElevenLoAlarm 6 }

aprisaXETxADCChElevenLoAlarmsGroup OBJECT-GROUP
    OBJECTS     { aprisaXETxADCChElevenLoAlarmName,
                  aprisaXETxADCChElevenLoAlarmStatus,
                  aprisaXETxADCChElevenLoAlarmSeverity, 
                  aprisaXETxADCChElevenLoAlarmEnabled,
                  aprisaXETxADCChElevenLoAlarmThreshold,
                  aprisaXETxADCChElevenLoAlarmClearThreshold
    }
    STATUS      current
    DESCRIPTION "The aprisaXETx transmitter ADC Ch Eleven voltage too High alarm group."
    ::= { aprisaXEGroups 273 }

-- ***************************************************************************
-- End of the Generic Transmitter alarms
-- ***************************************************************************    



-- ***************************************************************************
-- The Generic Receiver Alarms
-- ***************************************************************************

aprisaXERxADCChZeroHiAlarm OBJECT IDENTIFIER ::= { aprisaXEReceiverAlarms 19 }

aprisaXERxADCChZeroHiAlarmName OBJECT-TYPE
    SYNTAX      DisplayString
    MAX-ACCESS  read-only
    STATUS      current
    DESCRIPTION "The name of the receiver ADC Ch Zero voltage too high alarm."
    ::= { aprisaXERxADCChZeroHiAlarm 1 }

aprisaXERxADCChZeroHiAlarmStatus OBJECT-TYPE
    SYNTAX      FourRFAlarmStatus
    MAX-ACCESS  read-only
    STATUS      current
    DESCRIPTION "The status of the receiver ADC Ch Zero voltage too high alarm."
    ::= { aprisaXERxADCChZeroHiAlarm 2 }

aprisaXERxADCChZeroHiAlarmSeverity OBJECT-TYPE
    SYNTAX      FourRFAlarmSeverity
    MAX-ACCESS  read-only
    STATUS      current
    DESCRIPTION "The severity of the receiver ADC Ch Zero voltage too high alarm."
    ::= { aprisaXERxADCChZeroHiAlarm 3 }

aprisaXERxADCChZeroHiAlarmEnabled OBJECT-TYPE
    SYNTAX      FourRFAlarmEnabled
    MAX-ACCESS  read-only
    STATUS      current
    DESCRIPTION "Indicates whether the receiver ADC Ch Zero voltage too high alarm is enabled."
    ::= { aprisaXERxADCChZeroHiAlarm 4 }
    
aprisaXERxADCChZeroHiAlarmThreshold OBJECT-TYPE
    SYNTAX      Integer32
    MAX-ACCESS  read-only
    STATUS      current
    DESCRIPTION "Indicates the level at which the receiver ADC Ch Zero voltage too high 
                 alarm will be set."
    ::= { aprisaXERxADCChZeroHiAlarm 5 }
    
aprisaXERxADCChZeroHiAlarmClearThreshold OBJECT-TYPE
    SYNTAX      Integer32
    MAX-ACCESS  read-only
    STATUS      current
    DESCRIPTION "Indicates the level at which the receiver ADC Ch Zero voltage too high 
                 will be cleared."
    ::= { aprisaXERxADCChZeroHiAlarm 6 }

aprisaXERxADCChZeroHiAlarmsGroup OBJECT-GROUP
    OBJECTS     { aprisaXERxADCChZeroHiAlarmName,
                  aprisaXERxADCChZeroHiAlarmStatus,
                  aprisaXERxADCChZeroHiAlarmSeverity, 
                  aprisaXERxADCChZeroHiAlarmEnabled,
                  aprisaXERxADCChZeroHiAlarmThreshold,
                  aprisaXERxADCChZeroHiAlarmClearThreshold
    }
    STATUS      current
    DESCRIPTION "The aprisaXERx receiver ADC Ch Zero voltage too high alarm group."
    ::= { aprisaXEGroups 275 } 


aprisaXERxADCChZeroLoAlarm OBJECT IDENTIFIER ::= { aprisaXEReceiverAlarms 20 }

aprisaXERxADCChZeroLoAlarmName OBJECT-TYPE
    SYNTAX      DisplayString
    MAX-ACCESS  read-only
    STATUS      current
    DESCRIPTION "The name of the receiver ADC Ch Zero voltage too low alarm."
    ::= { aprisaXERxADCChZeroLoAlarm 1 }

aprisaXERxADCChZeroLoAlarmStatus OBJECT-TYPE
    SYNTAX      FourRFAlarmStatus
    MAX-ACCESS  read-only
    STATUS      current
    DESCRIPTION "The status of the receiver ADC Ch Zero voltage too low alarm."
    ::= { aprisaXERxADCChZeroLoAlarm 2 }

aprisaXERxADCChZeroLoAlarmSeverity OBJECT-TYPE
    SYNTAX      FourRFAlarmSeverity
    MAX-ACCESS  read-only
    STATUS      current
    DESCRIPTION "The severity of the receiver ADC Ch Zero voltage too low alarm."
    ::= { aprisaXERxADCChZeroLoAlarm 3 }

aprisaXERxADCChZeroLoAlarmEnabled OBJECT-TYPE
    SYNTAX      FourRFAlarmEnabled
    MAX-ACCESS  read-only
    STATUS      current
    DESCRIPTION "Indicates whether the receiver ADC Ch Zero voltage too low alarm is enabled."
    ::= { aprisaXERxADCChZeroLoAlarm 4 }
    
aprisaXERxADCChZeroLoAlarmThreshold OBJECT-TYPE
    SYNTAX      Integer32
    MAX-ACCESS  read-only
    STATUS      current
    DESCRIPTION "Indicates the level at wLoch the receiver ADC Ch Zero voltage too low 
                 alarm will be set."
    ::= { aprisaXERxADCChZeroLoAlarm 5 }
    
aprisaXERxADCChZeroLoAlarmClearThreshold OBJECT-TYPE
    SYNTAX      Integer32
    MAX-ACCESS  read-only
    STATUS      current
    DESCRIPTION "Indicates the level at wLoch the receiver ADC Ch Zero voltage too low 
                 will be cleared."
    ::= { aprisaXERxADCChZeroLoAlarm 6 }

aprisaXERxADCChZeroLoAlarmsGroup OBJECT-GROUP
    OBJECTS     { aprisaXERxADCChZeroLoAlarmName,
                  aprisaXERxADCChZeroLoAlarmStatus,
                  aprisaXERxADCChZeroLoAlarmSeverity, 
                  aprisaXERxADCChZeroLoAlarmEnabled,
                  aprisaXERxADCChZeroLoAlarmThreshold,
                  aprisaXERxADCChZeroLoAlarmClearThreshold
    }
    STATUS      current
    DESCRIPTION "The aprisaXERx receiver ADC Ch Zero voltage too High alarm group."
    ::= { aprisaXEGroups 276 }


aprisaXERxADCChOneHiAlarm OBJECT IDENTIFIER ::= { aprisaXEReceiverAlarms 21 }

aprisaXERxADCChOneHiAlarmName OBJECT-TYPE
    SYNTAX      DisplayString
    MAX-ACCESS  read-only
    STATUS      current
    DESCRIPTION "The name of the receiver ADC Ch One voltage too high alarm."
    ::= { aprisaXERxADCChOneHiAlarm 1 }

aprisaXERxADCChOneHiAlarmStatus OBJECT-TYPE
    SYNTAX      FourRFAlarmStatus
    MAX-ACCESS  read-only
    STATUS      current
    DESCRIPTION "The status of the receiver ADC Ch One voltage too high alarm."
    ::= { aprisaXERxADCChOneHiAlarm 2 }

aprisaXERxADCChOneHiAlarmSeverity OBJECT-TYPE
    SYNTAX      FourRFAlarmSeverity
    MAX-ACCESS  read-only
    STATUS      current
    DESCRIPTION "The severity of the receiver ADC Ch One voltage too high alarm."
    ::= { aprisaXERxADCChOneHiAlarm 3 }

aprisaXERxADCChOneHiAlarmEnabled OBJECT-TYPE
    SYNTAX      FourRFAlarmEnabled
    MAX-ACCESS  read-only
    STATUS      current
    DESCRIPTION "Indicates whether the receiver ADC Ch One voltage too high alarm is enabled."
    ::= { aprisaXERxADCChOneHiAlarm 4 }
    
aprisaXERxADCChOneHiAlarmThreshold OBJECT-TYPE
    SYNTAX      Integer32
    MAX-ACCESS  read-only
    STATUS      current
    DESCRIPTION "Indicates the level at which the receiver ADC Ch One voltage too high 
                 alarm will be set."
    ::= { aprisaXERxADCChOneHiAlarm 5 }
    
aprisaXERxADCChOneHiAlarmClearThreshold OBJECT-TYPE
    SYNTAX      Integer32
    MAX-ACCESS  read-only
    STATUS      current
    DESCRIPTION "Indicates the level at which the receiver ADC Ch One voltage too high 
                 will be cleared."
    ::= { aprisaXERxADCChOneHiAlarm 6 }

aprisaXERxADCChOneHiAlarmsGroup OBJECT-GROUP
    OBJECTS     { aprisaXERxADCChOneHiAlarmName,
                  aprisaXERxADCChOneHiAlarmStatus,
                  aprisaXERxADCChOneHiAlarmSeverity, 
                  aprisaXERxADCChOneHiAlarmEnabled,
                  aprisaXERxADCChOneHiAlarmThreshold,
                  aprisaXERxADCChOneHiAlarmClearThreshold
    }
    STATUS      current
    DESCRIPTION "The aprisaXERx receiver ADC Ch One voltage too high alarm group."
    ::= { aprisaXEGroups 277 } 


aprisaXERxADCChOneLoAlarm OBJECT IDENTIFIER ::= { aprisaXEReceiverAlarms 22 }

aprisaXERxADCChOneLoAlarmName OBJECT-TYPE
    SYNTAX      DisplayString
    MAX-ACCESS  read-only
    STATUS      current
    DESCRIPTION "The name of the receiver ADC Ch One voltage too low alarm."
    ::= { aprisaXERxADCChOneLoAlarm 1 }

aprisaXERxADCChOneLoAlarmStatus OBJECT-TYPE
    SYNTAX      FourRFAlarmStatus
    MAX-ACCESS  read-only
    STATUS      current
    DESCRIPTION "The status of the receiver ADC Ch One voltage too low alarm."
    ::= { aprisaXERxADCChOneLoAlarm 2 }

aprisaXERxADCChOneLoAlarmSeverity OBJECT-TYPE
    SYNTAX      FourRFAlarmSeverity
    MAX-ACCESS  read-only
    STATUS      current
    DESCRIPTION "The severity of the receiver ADC Ch One voltage too low alarm."
    ::= { aprisaXERxADCChOneLoAlarm 3 }

aprisaXERxADCChOneLoAlarmEnabled OBJECT-TYPE
    SYNTAX      FourRFAlarmEnabled
    MAX-ACCESS  read-only
    STATUS      current
    DESCRIPTION "Indicates whether the receiver ADC Ch One voltage too low alarm is enabled."
    ::= { aprisaXERxADCChOneLoAlarm 4 }
    
aprisaXERxADCChOneLoAlarmThreshold OBJECT-TYPE
    SYNTAX      Integer32
    MAX-ACCESS  read-only
    STATUS      current
    DESCRIPTION "Indicates the level at wLoch the receiver ADC Ch One voltage too low 
                 alarm will be set."
    ::= { aprisaXERxADCChOneLoAlarm 5 }
    
aprisaXERxADCChOneLoAlarmClearThreshold OBJECT-TYPE
    SYNTAX      Integer32
    MAX-ACCESS  read-only
    STATUS      current
    DESCRIPTION "Indicates the level at wLoch the receiver ADC Ch One voltage too low 
                 will be cleared."
    ::= { aprisaXERxADCChOneLoAlarm 6 }

aprisaXERxADCChOneLoAlarmsGroup OBJECT-GROUP
    OBJECTS     { aprisaXERxADCChOneLoAlarmName,
                  aprisaXERxADCChOneLoAlarmStatus,
                  aprisaXERxADCChOneLoAlarmSeverity, 
                  aprisaXERxADCChOneLoAlarmEnabled,
                  aprisaXERxADCChOneLoAlarmThreshold,
                  aprisaXERxADCChOneLoAlarmClearThreshold
    }
    STATUS      current
    DESCRIPTION "The aprisaXERx receiver ADC Ch One voltage too High alarm group."
    ::= { aprisaXEGroups 278 }


aprisaXERxADCChTwoHiAlarm OBJECT IDENTIFIER ::= { aprisaXEReceiverAlarms 23 }

aprisaXERxADCChTwoHiAlarmName OBJECT-TYPE
    SYNTAX      DisplayString
    MAX-ACCESS  read-only
    STATUS      current
    DESCRIPTION "The name of the receiver ADC Ch Two voltage too high alarm."
    ::= { aprisaXERxADCChTwoHiAlarm 1 }

aprisaXERxADCChTwoHiAlarmStatus OBJECT-TYPE
    SYNTAX      FourRFAlarmStatus
    MAX-ACCESS  read-only
    STATUS      current
    DESCRIPTION "The status of the receiver ADC Ch Two voltage too high alarm."
    ::= { aprisaXERxADCChTwoHiAlarm 2 }

aprisaXERxADCChTwoHiAlarmSeverity OBJECT-TYPE
    SYNTAX      FourRFAlarmSeverity
    MAX-ACCESS  read-only
    STATUS      current
    DESCRIPTION "The severity of the receiver ADC Ch Two voltage too high alarm."
    ::= { aprisaXERxADCChTwoHiAlarm 3 }

aprisaXERxADCChTwoHiAlarmEnabled OBJECT-TYPE
    SYNTAX      FourRFAlarmEnabled
    MAX-ACCESS  read-only
    STATUS      current
    DESCRIPTION "Indicates whether the receiver ADC Ch Two voltage too high alarm is enabled."
    ::= { aprisaXERxADCChTwoHiAlarm 4 }
    
aprisaXERxADCChTwoHiAlarmThreshold OBJECT-TYPE
    SYNTAX      Integer32
    MAX-ACCESS  read-only
    STATUS      current
    DESCRIPTION "Indicates the level at which the receiver ADC Ch Two voltage too high 
                 alarm will be set."
    ::= { aprisaXERxADCChTwoHiAlarm 5 }
    
aprisaXERxADCChTwoHiAlarmClearThreshold OBJECT-TYPE
    SYNTAX      Integer32
    MAX-ACCESS  read-only
    STATUS      current
    DESCRIPTION "Indicates the level at which the receiver ADC Ch Two voltage too high 
                 will be cleared."
    ::= { aprisaXERxADCChTwoHiAlarm 6 }

aprisaXERxADCChTwoHiAlarmsGroup OBJECT-GROUP
    OBJECTS     { aprisaXERxADCChTwoHiAlarmName,
                  aprisaXERxADCChTwoHiAlarmStatus,
                  aprisaXERxADCChTwoHiAlarmSeverity, 
                  aprisaXERxADCChTwoHiAlarmEnabled,
                  aprisaXERxADCChTwoHiAlarmThreshold,
                  aprisaXERxADCChTwoHiAlarmClearThreshold
    }
    STATUS      current
    DESCRIPTION "The aprisaXERx receiver ADC Ch Two voltage too high alarm group."
    ::= { aprisaXEGroups 279 } 


aprisaXERxADCChTwoLoAlarm OBJECT IDENTIFIER ::= { aprisaXEReceiverAlarms 24 }

aprisaXERxADCChTwoLoAlarmName OBJECT-TYPE
    SYNTAX      DisplayString
    MAX-ACCESS  read-only
    STATUS      current
    DESCRIPTION "The name of the receiver ADC Ch Two voltage too low alarm."
    ::= { aprisaXERxADCChTwoLoAlarm 1 }

aprisaXERxADCChTwoLoAlarmStatus OBJECT-TYPE
    SYNTAX      FourRFAlarmStatus
    MAX-ACCESS  read-only
    STATUS      current
    DESCRIPTION "The status of the receiver ADC Ch Two voltage too low alarm."
    ::= { aprisaXERxADCChTwoLoAlarm 2 }

aprisaXERxADCChTwoLoAlarmSeverity OBJECT-TYPE
    SYNTAX      FourRFAlarmSeverity
    MAX-ACCESS  read-only
    STATUS      current
    DESCRIPTION "The severity of the receiver ADC Ch Two voltage too low alarm."
    ::= { aprisaXERxADCChTwoLoAlarm 3 }

aprisaXERxADCChTwoLoAlarmEnabled OBJECT-TYPE
    SYNTAX      FourRFAlarmEnabled
    MAX-ACCESS  read-only
    STATUS      current
    DESCRIPTION "Indicates whether the receiver ADC Ch Two voltage too low alarm is enabled."
    ::= { aprisaXERxADCChTwoLoAlarm 4 }
    
aprisaXERxADCChTwoLoAlarmThreshold OBJECT-TYPE
    SYNTAX      Integer32
    MAX-ACCESS  read-only
    STATUS      current
    DESCRIPTION "Indicates the level at wLoch the receiver ADC Ch Two voltage too low 
                 alarm will be set."
    ::= { aprisaXERxADCChTwoLoAlarm 5 }
    
aprisaXERxADCChTwoLoAlarmClearThreshold OBJECT-TYPE
    SYNTAX      Integer32
    MAX-ACCESS  read-only
    STATUS      current
    DESCRIPTION "Indicates the level at wLoch the receiver ADC Ch Two voltage too low 
                 will be cleared."
    ::= { aprisaXERxADCChTwoLoAlarm 6 }

aprisaXERxADCChTwoLoAlarmsGroup OBJECT-GROUP
    OBJECTS     { aprisaXERxADCChTwoLoAlarmName,
                  aprisaXERxADCChTwoLoAlarmStatus,
                  aprisaXERxADCChTwoLoAlarmSeverity, 
                  aprisaXERxADCChTwoLoAlarmEnabled,
                  aprisaXERxADCChTwoLoAlarmThreshold,
                  aprisaXERxADCChTwoLoAlarmClearThreshold
    }
    STATUS      current
    DESCRIPTION "The aprisaXERx receiver ADC Ch Two voltage too High alarm group."
    ::= { aprisaXEGroups 280 }


aprisaXERxADCChThreeHiAlarm OBJECT IDENTIFIER ::= { aprisaXEReceiverAlarms 25 }

aprisaXERxADCChThreeHiAlarmName OBJECT-TYPE
    SYNTAX      DisplayString
    MAX-ACCESS  read-only
    STATUS      current
    DESCRIPTION "The name of the receiver ADC Ch Three voltage too high alarm."
    ::= { aprisaXERxADCChThreeHiAlarm 1 }

aprisaXERxADCChThreeHiAlarmStatus OBJECT-TYPE
    SYNTAX      FourRFAlarmStatus
    MAX-ACCESS  read-only
    STATUS      current
    DESCRIPTION "The status of the receiver ADC Ch Three voltage too high alarm."
    ::= { aprisaXERxADCChThreeHiAlarm 2 }

aprisaXERxADCChThreeHiAlarmSeverity OBJECT-TYPE
    SYNTAX      FourRFAlarmSeverity
    MAX-ACCESS  read-only
    STATUS      current
    DESCRIPTION "The severity of the receiver ADC Ch Three voltage too high alarm."
    ::= { aprisaXERxADCChThreeHiAlarm 3 }

aprisaXERxADCChThreeHiAlarmEnabled OBJECT-TYPE
    SYNTAX      FourRFAlarmEnabled
    MAX-ACCESS  read-only
    STATUS      current
    DESCRIPTION "Indicates whether the receiver ADC Ch Three voltage too high alarm is enabled."
    ::= { aprisaXERxADCChThreeHiAlarm 4 }
    
aprisaXERxADCChThreeHiAlarmThreshold OBJECT-TYPE
    SYNTAX      Integer32
    MAX-ACCESS  read-only
    STATUS      current
    DESCRIPTION "Indicates the level at which the receiver ADC Ch Three voltage too high 
                 alarm will be set."
    ::= { aprisaXERxADCChThreeHiAlarm 5 }
    
aprisaXERxADCChThreeHiAlarmClearThreshold OBJECT-TYPE
    SYNTAX      Integer32
    MAX-ACCESS  read-only
    STATUS      current
    DESCRIPTION "Indicates the level at which the receiver ADC Ch Three voltage too high 
                 will be cleared."
    ::= { aprisaXERxADCChThreeHiAlarm 6 }

aprisaXERxADCChThreeHiAlarmsGroup OBJECT-GROUP
    OBJECTS     { aprisaXERxADCChThreeHiAlarmName,
                  aprisaXERxADCChThreeHiAlarmStatus,
                  aprisaXERxADCChThreeHiAlarmSeverity, 
                  aprisaXERxADCChThreeHiAlarmEnabled,
                  aprisaXERxADCChThreeHiAlarmThreshold,
                  aprisaXERxADCChThreeHiAlarmClearThreshold
    }
    STATUS      current
    DESCRIPTION "The aprisaXERx receiver ADC Ch Three voltage too high alarm group."
    ::= { aprisaXEGroups 281 } 


aprisaXERxADCChThreeLoAlarm OBJECT IDENTIFIER ::= { aprisaXEReceiverAlarms 26 }

aprisaXERxADCChThreeLoAlarmName OBJECT-TYPE
    SYNTAX      DisplayString
    MAX-ACCESS  read-only
    STATUS      current
    DESCRIPTION "The name of the receiver ADC Ch Three voltage too low alarm."
    ::= { aprisaXERxADCChThreeLoAlarm 1 }

aprisaXERxADCChThreeLoAlarmStatus OBJECT-TYPE
    SYNTAX      FourRFAlarmStatus
    MAX-ACCESS  read-only
    STATUS      current
    DESCRIPTION "The status of the receiver ADC Ch Three voltage too low alarm."
    ::= { aprisaXERxADCChThreeLoAlarm 2 }

aprisaXERxADCChThreeLoAlarmSeverity OBJECT-TYPE
    SYNTAX      FourRFAlarmSeverity
    MAX-ACCESS  read-only
    STATUS      current
    DESCRIPTION "The severity of the receiver ADC Ch Three voltage too low alarm."
    ::= { aprisaXERxADCChThreeLoAlarm 3 }

aprisaXERxADCChThreeLoAlarmEnabled OBJECT-TYPE
    SYNTAX      FourRFAlarmEnabled
    MAX-ACCESS  read-only
    STATUS      current
    DESCRIPTION "Indicates whether the receiver ADC Ch Three voltage too low alarm is enabled."
    ::= { aprisaXERxADCChThreeLoAlarm 4 }
    
aprisaXERxADCChThreeLoAlarmThreshold OBJECT-TYPE
    SYNTAX      Integer32
    MAX-ACCESS  read-only
    STATUS      current
    DESCRIPTION "Indicates the level at wLoch the receiver ADC Ch Three voltage too low 
                 alarm will be set."
    ::= { aprisaXERxADCChThreeLoAlarm 5 }
    
aprisaXERxADCChThreeLoAlarmClearThreshold OBJECT-TYPE
    SYNTAX      Integer32
    MAX-ACCESS  read-only
    STATUS      current
    DESCRIPTION "Indicates the level at wLoch the receiver ADC Ch Three voltage too low 
                 will be cleared."
    ::= { aprisaXERxADCChThreeLoAlarm 6 }

aprisaXERxADCChThreeLoAlarmsGroup OBJECT-GROUP
    OBJECTS     { aprisaXERxADCChThreeLoAlarmName,
                  aprisaXERxADCChThreeLoAlarmStatus,
                  aprisaXERxADCChThreeLoAlarmSeverity, 
                  aprisaXERxADCChThreeLoAlarmEnabled,
                  aprisaXERxADCChThreeLoAlarmThreshold,
                  aprisaXERxADCChThreeLoAlarmClearThreshold
    }
    STATUS      current
    DESCRIPTION "The aprisaXERx receiver ADC Ch Three voltage too High alarm group."
    ::= { aprisaXEGroups 282 }


aprisaXERxADCChFourHiAlarm OBJECT IDENTIFIER ::= { aprisaXEReceiverAlarms 27 }

aprisaXERxADCChFourHiAlarmName OBJECT-TYPE
    SYNTAX      DisplayString
    MAX-ACCESS  read-only
    STATUS      current
    DESCRIPTION "The name of the receiver ADC Ch Four voltage too high alarm."
    ::= { aprisaXERxADCChFourHiAlarm 1 }

aprisaXERxADCChFourHiAlarmStatus OBJECT-TYPE
    SYNTAX      FourRFAlarmStatus
    MAX-ACCESS  read-only
    STATUS      current
    DESCRIPTION "The status of the receiver ADC Ch Four voltage too high alarm."
    ::= { aprisaXERxADCChFourHiAlarm 2 }

aprisaXERxADCChFourHiAlarmSeverity OBJECT-TYPE
    SYNTAX      FourRFAlarmSeverity
    MAX-ACCESS  read-only
    STATUS      current
    DESCRIPTION "The severity of the receiver ADC Ch Four voltage too high alarm."
    ::= { aprisaXERxADCChFourHiAlarm 3 }

aprisaXERxADCChFourHiAlarmEnabled OBJECT-TYPE
    SYNTAX      FourRFAlarmEnabled
    MAX-ACCESS  read-only
    STATUS      current
    DESCRIPTION "Indicates whether the receiver ADC Ch Four voltage too high alarm is enabled."
    ::= { aprisaXERxADCChFourHiAlarm 4 }
    
aprisaXERxADCChFourHiAlarmThreshold OBJECT-TYPE
    SYNTAX      Integer32
    MAX-ACCESS  read-only
    STATUS      current
    DESCRIPTION "Indicates the level at which the receiver ADC Ch Four voltage too high 
                 alarm will be set."
    ::= { aprisaXERxADCChFourHiAlarm 5 }
    
aprisaXERxADCChFourHiAlarmClearThreshold OBJECT-TYPE
    SYNTAX      Integer32
    MAX-ACCESS  read-only
    STATUS      current
    DESCRIPTION "Indicates the level at which the receiver ADC Ch Four voltage too high 
                 will be cleared."
    ::= { aprisaXERxADCChFourHiAlarm 6 }

aprisaXERxADCChFourHiAlarmsGroup OBJECT-GROUP
    OBJECTS     { aprisaXERxADCChFourHiAlarmName,
                  aprisaXERxADCChFourHiAlarmStatus,
                  aprisaXERxADCChFourHiAlarmSeverity, 
                  aprisaXERxADCChFourHiAlarmEnabled,
                  aprisaXERxADCChFourHiAlarmThreshold,
                  aprisaXERxADCChFourHiAlarmClearThreshold
    }
    STATUS      current
    DESCRIPTION "The aprisaXERx receiver ADC Ch Four voltage too high alarm group."
    ::= { aprisaXEGroups 283 } 


aprisaXERxADCChFourLoAlarm OBJECT IDENTIFIER ::= { aprisaXEReceiverAlarms 28 }

aprisaXERxADCChFourLoAlarmName OBJECT-TYPE
    SYNTAX      DisplayString
    MAX-ACCESS  read-only
    STATUS      current
    DESCRIPTION "The name of the receiver ADC Ch Four voltage too low alarm."
    ::= { aprisaXERxADCChFourLoAlarm 1 }

aprisaXERxADCChFourLoAlarmStatus OBJECT-TYPE
    SYNTAX      FourRFAlarmStatus
    MAX-ACCESS  read-only
    STATUS      current
    DESCRIPTION "The status of the receiver ADC Ch Four voltage too low alarm."
    ::= { aprisaXERxADCChFourLoAlarm 2 }

aprisaXERxADCChFourLoAlarmSeverity OBJECT-TYPE
    SYNTAX      FourRFAlarmSeverity
    MAX-ACCESS  read-only
    STATUS      current
    DESCRIPTION "The severity of the receiver ADC Ch Four voltage too low alarm."
    ::= { aprisaXERxADCChFourLoAlarm 3 }

aprisaXERxADCChFourLoAlarmEnabled OBJECT-TYPE
    SYNTAX      FourRFAlarmEnabled
    MAX-ACCESS  read-only
    STATUS      current
    DESCRIPTION "Indicates whether the receiver ADC Ch Four voltage too low alarm is enabled."
    ::= { aprisaXERxADCChFourLoAlarm 4 }
    
aprisaXERxADCChFourLoAlarmThreshold OBJECT-TYPE
    SYNTAX      Integer32
    MAX-ACCESS  read-only
    STATUS      current
    DESCRIPTION "Indicates the level at wLoch the receiver ADC Ch Four voltage too low 
                 alarm will be set."
    ::= { aprisaXERxADCChFourLoAlarm 5 }
    
aprisaXERxADCChFourLoAlarmClearThreshold OBJECT-TYPE
    SYNTAX      Integer32
    MAX-ACCESS  read-only
    STATUS      current
    DESCRIPTION "Indicates the level at wLoch the receiver ADC Ch Four voltage too low 
                 will be cleared."
    ::= { aprisaXERxADCChFourLoAlarm 6 }

aprisaXERxADCChFourLoAlarmsGroup OBJECT-GROUP
    OBJECTS     { aprisaXERxADCChFourLoAlarmName,
                  aprisaXERxADCChFourLoAlarmStatus,
                  aprisaXERxADCChFourLoAlarmSeverity, 
                  aprisaXERxADCChFourLoAlarmEnabled,
                  aprisaXERxADCChFourLoAlarmThreshold,
                  aprisaXERxADCChFourLoAlarmClearThreshold
    }
    STATUS      current
    DESCRIPTION "The aprisaXERx receiver ADC Ch Four voltage too High alarm group."
    ::= { aprisaXEGroups 284 }


aprisaXERxADCChFiveHiAlarm OBJECT IDENTIFIER ::= { aprisaXEReceiverAlarms 29 }

aprisaXERxADCChFiveHiAlarmName OBJECT-TYPE
    SYNTAX      DisplayString
    MAX-ACCESS  read-only
    STATUS      current
    DESCRIPTION "The name of the receiver ADC Ch Five voltage too high alarm."
    ::= { aprisaXERxADCChFiveHiAlarm 1 }

aprisaXERxADCChFiveHiAlarmStatus OBJECT-TYPE
    SYNTAX      FourRFAlarmStatus
    MAX-ACCESS  read-only
    STATUS      current
    DESCRIPTION "The status of the receiver ADC Ch Five voltage too high alarm."
    ::= { aprisaXERxADCChFiveHiAlarm 2 }

aprisaXERxADCChFiveHiAlarmSeverity OBJECT-TYPE
    SYNTAX      FourRFAlarmSeverity
    MAX-ACCESS  read-only
    STATUS      current
    DESCRIPTION "The severity of the receiver ADC Ch Five voltage too high alarm."
    ::= { aprisaXERxADCChFiveHiAlarm 3 }

aprisaXERxADCChFiveHiAlarmEnabled OBJECT-TYPE
    SYNTAX      FourRFAlarmEnabled
    MAX-ACCESS  read-only
    STATUS      current
    DESCRIPTION "Indicates whether the receiver ADC Ch Five voltage too high alarm is enabled."
    ::= { aprisaXERxADCChFiveHiAlarm 4 }
    
aprisaXERxADCChFiveHiAlarmThreshold OBJECT-TYPE
    SYNTAX      Integer32
    MAX-ACCESS  read-only
    STATUS      current
    DESCRIPTION "Indicates the level at which the receiver ADC Ch Five voltage too high 
                 alarm will be set."
    ::= { aprisaXERxADCChFiveHiAlarm 5 }
    
aprisaXERxADCChFiveHiAlarmClearThreshold OBJECT-TYPE
    SYNTAX      Integer32
    MAX-ACCESS  read-only
    STATUS      current
    DESCRIPTION "Indicates the level at which the receiver ADC Ch Five voltage too high 
                 will be cleared."
    ::= { aprisaXERxADCChFiveHiAlarm 6 }

aprisaXERxADCChFiveHiAlarmsGroup OBJECT-GROUP
    OBJECTS     { aprisaXERxADCChFiveHiAlarmName,
                  aprisaXERxADCChFiveHiAlarmStatus,
                  aprisaXERxADCChFiveHiAlarmSeverity, 
                  aprisaXERxADCChFiveHiAlarmEnabled,
                  aprisaXERxADCChFiveHiAlarmThreshold,
                  aprisaXERxADCChFiveHiAlarmClearThreshold
    }
    STATUS      current
    DESCRIPTION "The aprisaXERx receiver ADC Ch Five voltage too high alarm group."
    ::= { aprisaXEGroups 285 } 


aprisaXERxADCChFiveLoAlarm OBJECT IDENTIFIER ::= { aprisaXEReceiverAlarms 30 }

aprisaXERxADCChFiveLoAlarmName OBJECT-TYPE
    SYNTAX      DisplayString
    MAX-ACCESS  read-only
    STATUS      current
    DESCRIPTION "The name of the receiver ADC Ch Five voltage too low alarm."
    ::= { aprisaXERxADCChFiveLoAlarm 1 }

aprisaXERxADCChFiveLoAlarmStatus OBJECT-TYPE
    SYNTAX      FourRFAlarmStatus
    MAX-ACCESS  read-only
    STATUS      current
    DESCRIPTION "The status of the receiver ADC Ch Five voltage too low alarm."
    ::= { aprisaXERxADCChFiveLoAlarm 2 }

aprisaXERxADCChFiveLoAlarmSeverity OBJECT-TYPE
    SYNTAX      FourRFAlarmSeverity
    MAX-ACCESS  read-only
    STATUS      current
    DESCRIPTION "The severity of the receiver ADC Ch Five voltage too low alarm."
    ::= { aprisaXERxADCChFiveLoAlarm 3 }

aprisaXERxADCChFiveLoAlarmEnabled OBJECT-TYPE
    SYNTAX      FourRFAlarmEnabled
    MAX-ACCESS  read-only
    STATUS      current
    DESCRIPTION "Indicates whether the receiver ADC Ch Five voltage too low alarm is enabled."
    ::= { aprisaXERxADCChFiveLoAlarm 4 }
    
aprisaXERxADCChFiveLoAlarmThreshold OBJECT-TYPE
    SYNTAX      Integer32
    MAX-ACCESS  read-only
    STATUS      current
    DESCRIPTION "Indicates the level at wLoch the receiver ADC Ch Five voltage too low 
                 alarm will be set."
    ::= { aprisaXERxADCChFiveLoAlarm 5 }
    
aprisaXERxADCChFiveLoAlarmClearThreshold OBJECT-TYPE
    SYNTAX      Integer32
    MAX-ACCESS  read-only
    STATUS      current
    DESCRIPTION "Indicates the level at wLoch the receiver ADC Ch Five voltage too low 
                 will be cleared."
    ::= { aprisaXERxADCChFiveLoAlarm 6 }

aprisaXERxADCChFiveLoAlarmsGroup OBJECT-GROUP
    OBJECTS     { aprisaXERxADCChFiveLoAlarmName,
                  aprisaXERxADCChFiveLoAlarmStatus,
                  aprisaXERxADCChFiveLoAlarmSeverity, 
                  aprisaXERxADCChFiveLoAlarmEnabled,
                  aprisaXERxADCChFiveLoAlarmThreshold,
                  aprisaXERxADCChFiveLoAlarmClearThreshold
    }
    STATUS      current
    DESCRIPTION "The aprisaXERx receiver ADC Ch Five voltage too High alarm group."
    ::= { aprisaXEGroups 286 }


aprisaXERxADCChSixHiAlarm OBJECT IDENTIFIER ::= { aprisaXEReceiverAlarms 31 }

aprisaXERxADCChSixHiAlarmName OBJECT-TYPE
    SYNTAX      DisplayString
    MAX-ACCESS  read-only
    STATUS      current
    DESCRIPTION "The name of the receiver ADC Ch Six voltage too high alarm."
    ::= { aprisaXERxADCChSixHiAlarm 1 }

aprisaXERxADCChSixHiAlarmStatus OBJECT-TYPE
    SYNTAX      FourRFAlarmStatus
    MAX-ACCESS  read-only
    STATUS      current
    DESCRIPTION "The status of the receiver ADC Ch Six voltage too high alarm."
    ::= { aprisaXERxADCChSixHiAlarm 2 }

aprisaXERxADCChSixHiAlarmSeverity OBJECT-TYPE
    SYNTAX      FourRFAlarmSeverity
    MAX-ACCESS  read-only
    STATUS      current
    DESCRIPTION "The severity of the receiver ADC Ch Six voltage too high alarm."
    ::= { aprisaXERxADCChSixHiAlarm 3 }

aprisaXERxADCChSixHiAlarmEnabled OBJECT-TYPE
    SYNTAX      FourRFAlarmEnabled
    MAX-ACCESS  read-only
    STATUS      current
    DESCRIPTION "Indicates whether the receiver ADC Ch Six voltage too high alarm is enabled."
    ::= { aprisaXERxADCChSixHiAlarm 4 }
    
aprisaXERxADCChSixHiAlarmThreshold OBJECT-TYPE
    SYNTAX      Integer32
    MAX-ACCESS  read-only
    STATUS      current
    DESCRIPTION "Indicates the level at which the receiver ADC Ch Six voltage too high 
                 alarm will be set."
    ::= { aprisaXERxADCChSixHiAlarm 5 }
    
aprisaXERxADCChSixHiAlarmClearThreshold OBJECT-TYPE
    SYNTAX      Integer32
    MAX-ACCESS  read-only
    STATUS      current
    DESCRIPTION "Indicates the level at which the receiver ADC Ch Six voltage too high 
                 will be cleared."
    ::= { aprisaXERxADCChSixHiAlarm 6 }

aprisaXERxADCChSixHiAlarmsGroup OBJECT-GROUP
    OBJECTS     { aprisaXERxADCChSixHiAlarmName,
                  aprisaXERxADCChSixHiAlarmStatus,
                  aprisaXERxADCChSixHiAlarmSeverity, 
                  aprisaXERxADCChSixHiAlarmEnabled,
                  aprisaXERxADCChSixHiAlarmThreshold,
                  aprisaXERxADCChSixHiAlarmClearThreshold
    }
    STATUS      current
    DESCRIPTION "The aprisaXERx receiver ADC Ch Six voltage too high alarm group."
    ::= { aprisaXEGroups 287 } 


aprisaXERxADCChSixLoAlarm OBJECT IDENTIFIER ::= { aprisaXEReceiverAlarms 32 }

aprisaXERxADCChSixLoAlarmName OBJECT-TYPE
    SYNTAX      DisplayString
    MAX-ACCESS  read-only
    STATUS      current
    DESCRIPTION "The name of the receiver ADC Ch Six voltage too low alarm."
    ::= { aprisaXERxADCChSixLoAlarm 1 }

aprisaXERxADCChSixLoAlarmStatus OBJECT-TYPE
    SYNTAX      FourRFAlarmStatus
    MAX-ACCESS  read-only
    STATUS      current
    DESCRIPTION "The status of the receiver ADC Ch Six voltage too low alarm."
    ::= { aprisaXERxADCChSixLoAlarm 2 }

aprisaXERxADCChSixLoAlarmSeverity OBJECT-TYPE
    SYNTAX      FourRFAlarmSeverity
    MAX-ACCESS  read-only
    STATUS      current
    DESCRIPTION "The severity of the receiver ADC Ch Six voltage too low alarm."
    ::= { aprisaXERxADCChSixLoAlarm 3 }

aprisaXERxADCChSixLoAlarmEnabled OBJECT-TYPE
    SYNTAX      FourRFAlarmEnabled
    MAX-ACCESS  read-only
    STATUS      current
    DESCRIPTION "Indicates whether the receiver ADC Ch Six voltage too low alarm is enabled."
    ::= { aprisaXERxADCChSixLoAlarm 4 }
    
aprisaXERxADCChSixLoAlarmThreshold OBJECT-TYPE
    SYNTAX      Integer32
    MAX-ACCESS  read-only
    STATUS      current
    DESCRIPTION "Indicates the level at wLoch the receiver ADC Ch Six voltage too low 
                 alarm will be set."
    ::= { aprisaXERxADCChSixLoAlarm 5 }
    
aprisaXERxADCChSixLoAlarmClearThreshold OBJECT-TYPE
    SYNTAX      Integer32
    MAX-ACCESS  read-only
    STATUS      current
    DESCRIPTION "Indicates the level at wLoch the receiver ADC Ch Six voltage too low 
                 will be cleared."
    ::= { aprisaXERxADCChSixLoAlarm 6 }

aprisaXERxADCChSixLoAlarmsGroup OBJECT-GROUP
    OBJECTS     { aprisaXERxADCChSixLoAlarmName,
                  aprisaXERxADCChSixLoAlarmStatus,
                  aprisaXERxADCChSixLoAlarmSeverity, 
                  aprisaXERxADCChSixLoAlarmEnabled,
                  aprisaXERxADCChSixLoAlarmThreshold,
                  aprisaXERxADCChSixLoAlarmClearThreshold
    }
    STATUS      current
    DESCRIPTION "The aprisaXERx receiver ADC Ch Six voltage too High alarm group."
    ::= { aprisaXEGroups 288 }


aprisaXERxADCChSevenHiAlarm OBJECT IDENTIFIER ::= { aprisaXEReceiverAlarms 33 }

aprisaXERxADCChSevenHiAlarmName OBJECT-TYPE
    SYNTAX      DisplayString
    MAX-ACCESS  read-only
    STATUS      current
    DESCRIPTION "The name of the receiver ADC Ch Seven voltage too high alarm."
    ::= { aprisaXERxADCChSevenHiAlarm 1 }

aprisaXERxADCChSevenHiAlarmStatus OBJECT-TYPE
    SYNTAX      FourRFAlarmStatus
    MAX-ACCESS  read-only
    STATUS      current
    DESCRIPTION "The status of the receiver ADC Ch Seven voltage too high alarm."
    ::= { aprisaXERxADCChSevenHiAlarm 2 }

aprisaXERxADCChSevenHiAlarmSeverity OBJECT-TYPE
    SYNTAX      FourRFAlarmSeverity
    MAX-ACCESS  read-only
    STATUS      current
    DESCRIPTION "The severity of the receiver ADC Ch Seven voltage too high alarm."
    ::= { aprisaXERxADCChSevenHiAlarm 3 }

aprisaXERxADCChSevenHiAlarmEnabled OBJECT-TYPE
    SYNTAX      FourRFAlarmEnabled
    MAX-ACCESS  read-only
    STATUS      current
    DESCRIPTION "Indicates whether the receiver ADC Ch Seven voltage too high alarm is enabled."
    ::= { aprisaXERxADCChSevenHiAlarm 4 }
    
aprisaXERxADCChSevenHiAlarmThreshold OBJECT-TYPE
    SYNTAX      Integer32
    MAX-ACCESS  read-only
    STATUS      current
    DESCRIPTION "Indicates the level at which the receiver ADC Ch Seven voltage too high 
                 alarm will be set."
    ::= { aprisaXERxADCChSevenHiAlarm 5 }
    
aprisaXERxADCChSevenHiAlarmClearThreshold OBJECT-TYPE
    SYNTAX      Integer32
    MAX-ACCESS  read-only
    STATUS      current
    DESCRIPTION "Indicates the level at which the receiver ADC Ch Seven voltage too high 
                 will be cleared."
    ::= { aprisaXERxADCChSevenHiAlarm 6 }

aprisaXERxADCChSevenHiAlarmsGroup OBJECT-GROUP
    OBJECTS     { aprisaXERxADCChSevenHiAlarmName,
                  aprisaXERxADCChSevenHiAlarmStatus,
                  aprisaXERxADCChSevenHiAlarmSeverity, 
                  aprisaXERxADCChSevenHiAlarmEnabled,
                  aprisaXERxADCChSevenHiAlarmThreshold,
                  aprisaXERxADCChSevenHiAlarmClearThreshold
    }
    STATUS      current
    DESCRIPTION "The aprisaXERx receiver ADC Ch Seven voltage too high alarm group."
    ::= { aprisaXEGroups 289 } 


aprisaXERxADCChSevenLoAlarm OBJECT IDENTIFIER ::= { aprisaXEReceiverAlarms 34 }

aprisaXERxADCChSevenLoAlarmName OBJECT-TYPE
    SYNTAX      DisplayString
    MAX-ACCESS  read-only
    STATUS      current
    DESCRIPTION "The name of the receiver ADC Ch Seven voltage too low alarm."
    ::= { aprisaXERxADCChSevenLoAlarm 1 }

aprisaXERxADCChSevenLoAlarmStatus OBJECT-TYPE
    SYNTAX      FourRFAlarmStatus
    MAX-ACCESS  read-only
    STATUS      current
    DESCRIPTION "The status of the receiver ADC Ch Seven voltage too low alarm."
    ::= { aprisaXERxADCChSevenLoAlarm 2 }

aprisaXERxADCChSevenLoAlarmSeverity OBJECT-TYPE
    SYNTAX      FourRFAlarmSeverity
    MAX-ACCESS  read-only
    STATUS      current
    DESCRIPTION "The severity of the receiver ADC Ch Seven voltage too low alarm."
    ::= { aprisaXERxADCChSevenLoAlarm 3 }

aprisaXERxADCChSevenLoAlarmEnabled OBJECT-TYPE
    SYNTAX      FourRFAlarmEnabled
    MAX-ACCESS  read-only
    STATUS      current
    DESCRIPTION "Indicates whether the receiver ADC Ch Seven voltage too low alarm is enabled."
    ::= { aprisaXERxADCChSevenLoAlarm 4 }
    
aprisaXERxADCChSevenLoAlarmThreshold OBJECT-TYPE
    SYNTAX      Integer32
    MAX-ACCESS  read-only
    STATUS      current
    DESCRIPTION "Indicates the level at wLoch the receiver ADC Ch Seven voltage too low 
                 alarm will be set."
    ::= { aprisaXERxADCChSevenLoAlarm 5 }
    
aprisaXERxADCChSevenLoAlarmClearThreshold OBJECT-TYPE
    SYNTAX      Integer32
    MAX-ACCESS  read-only
    STATUS      current
    DESCRIPTION "Indicates the level at wLoch the receiver ADC Ch Seven voltage too low 
                 will be cleared."
    ::= { aprisaXERxADCChSevenLoAlarm 6 }

aprisaXERxADCChSevenLoAlarmsGroup OBJECT-GROUP
    OBJECTS     { aprisaXERxADCChSevenLoAlarmName,
                  aprisaXERxADCChSevenLoAlarmStatus,
                  aprisaXERxADCChSevenLoAlarmSeverity, 
                  aprisaXERxADCChSevenLoAlarmEnabled,
                  aprisaXERxADCChSevenLoAlarmThreshold,
                  aprisaXERxADCChSevenLoAlarmClearThreshold
    }
    STATUS      current
    DESCRIPTION "The aprisaXERx receiver ADC Ch Seven voltage too High alarm group."
    ::= { aprisaXEGroups 290 }


aprisaXERxADCChEightHiAlarm OBJECT IDENTIFIER ::= { aprisaXEReceiverAlarms 35 }

aprisaXERxADCChEightHiAlarmName OBJECT-TYPE
    SYNTAX      DisplayString
    MAX-ACCESS  read-only
    STATUS      current
    DESCRIPTION "The name of the receiver ADC Ch Eight voltage too high alarm."
    ::= { aprisaXERxADCChEightHiAlarm 1 }

aprisaXERxADCChEightHiAlarmStatus OBJECT-TYPE
    SYNTAX      FourRFAlarmStatus
    MAX-ACCESS  read-only
    STATUS      current
    DESCRIPTION "The status of the receiver ADC Ch Eight voltage too high alarm."
    ::= { aprisaXERxADCChEightHiAlarm 2 }

aprisaXERxADCChEightHiAlarmSeverity OBJECT-TYPE
    SYNTAX      FourRFAlarmSeverity
    MAX-ACCESS  read-only
    STATUS      current
    DESCRIPTION "The severity of the receiver ADC Ch Eight voltage too high alarm."
    ::= { aprisaXERxADCChEightHiAlarm 3 }

aprisaXERxADCChEightHiAlarmEnabled OBJECT-TYPE
    SYNTAX      FourRFAlarmEnabled
    MAX-ACCESS  read-only
    STATUS      current
    DESCRIPTION "Indicates whether the receiver ADC Ch Eight voltage too high alarm is enabled."
    ::= { aprisaXERxADCChEightHiAlarm 4 }
    
aprisaXERxADCChEightHiAlarmThreshold OBJECT-TYPE
    SYNTAX      Integer32
    MAX-ACCESS  read-only
    STATUS      current
    DESCRIPTION "Indicates the level at which the receiver ADC Ch Eight voltage too high 
                 alarm will be set."
    ::= { aprisaXERxADCChEightHiAlarm 5 }
    
aprisaXERxADCChEightHiAlarmClearThreshold OBJECT-TYPE
    SYNTAX      Integer32
    MAX-ACCESS  read-only
    STATUS      current
    DESCRIPTION "Indicates the level at which the receiver ADC Ch Eight voltage too high 
                 will be cleared."
    ::= { aprisaXERxADCChEightHiAlarm 6 }

aprisaXERxADCChEightHiAlarmsGroup OBJECT-GROUP
    OBJECTS     { aprisaXERxADCChEightHiAlarmName,
                  aprisaXERxADCChEightHiAlarmStatus,
                  aprisaXERxADCChEightHiAlarmSeverity, 
                  aprisaXERxADCChEightHiAlarmEnabled,
                  aprisaXERxADCChEightHiAlarmThreshold,
                  aprisaXERxADCChEightHiAlarmClearThreshold
    }
    STATUS      current
    DESCRIPTION "The aprisaXERx receiver ADC Ch Eight voltage too high alarm group."
    ::= { aprisaXEGroups 291 } 


aprisaXERxADCChEightLoAlarm OBJECT IDENTIFIER ::= { aprisaXEReceiverAlarms 36 }

aprisaXERxADCChEightLoAlarmName OBJECT-TYPE
    SYNTAX      DisplayString
    MAX-ACCESS  read-only
    STATUS      current
    DESCRIPTION "The name of the receiver ADC Ch Eight voltage too low alarm."
    ::= { aprisaXERxADCChEightLoAlarm 1 }

aprisaXERxADCChEightLoAlarmStatus OBJECT-TYPE
    SYNTAX      FourRFAlarmStatus
    MAX-ACCESS  read-only
    STATUS      current
    DESCRIPTION "The status of the receiver ADC Ch Eight voltage too low alarm."
    ::= { aprisaXERxADCChEightLoAlarm 2 }

aprisaXERxADCChEightLoAlarmSeverity OBJECT-TYPE
    SYNTAX      FourRFAlarmSeverity
    MAX-ACCESS  read-only
    STATUS      current
    DESCRIPTION "The severity of the receiver ADC Ch Eight voltage too low alarm."
    ::= { aprisaXERxADCChEightLoAlarm 3 }

aprisaXERxADCChEightLoAlarmEnabled OBJECT-TYPE
    SYNTAX      FourRFAlarmEnabled
    MAX-ACCESS  read-only
    STATUS      current
    DESCRIPTION "Indicates whether the receiver ADC Ch Eight voltage too low alarm is enabled."
    ::= { aprisaXERxADCChEightLoAlarm 4 }
    
aprisaXERxADCChEightLoAlarmThreshold OBJECT-TYPE
    SYNTAX      Integer32
    MAX-ACCESS  read-only
    STATUS      current
    DESCRIPTION "Indicates the level at wLoch the receiver ADC Ch Eight voltage too low 
                 alarm will be set."
    ::= { aprisaXERxADCChEightLoAlarm 5 }
    
aprisaXERxADCChEightLoAlarmClearThreshold OBJECT-TYPE
    SYNTAX      Integer32
    MAX-ACCESS  read-only
    STATUS      current
    DESCRIPTION "Indicates the level at wLoch the receiver ADC Ch Eight voltage too low 
                 will be cleared."
    ::= { aprisaXERxADCChEightLoAlarm 6 }

aprisaXERxADCChEightLoAlarmsGroup OBJECT-GROUP
    OBJECTS     { aprisaXERxADCChEightLoAlarmName,
                  aprisaXERxADCChEightLoAlarmStatus,
                  aprisaXERxADCChEightLoAlarmSeverity, 
                  aprisaXERxADCChEightLoAlarmEnabled,
                  aprisaXERxADCChEightLoAlarmThreshold,
                  aprisaXERxADCChEightLoAlarmClearThreshold
    }
    STATUS      current
    DESCRIPTION "The aprisaXERx receiver ADC Ch Eight voltage too High alarm group."
    ::= { aprisaXEGroups 292 }


aprisaXERxADCChNineHiAlarm OBJECT IDENTIFIER ::= { aprisaXEReceiverAlarms 37 }

aprisaXERxADCChNineHiAlarmName OBJECT-TYPE
    SYNTAX      DisplayString
    MAX-ACCESS  read-only
    STATUS      current
    DESCRIPTION "The name of the receiver ADC Ch Nine voltage too high alarm."
    ::= { aprisaXERxADCChNineHiAlarm 1 }

aprisaXERxADCChNineHiAlarmStatus OBJECT-TYPE
    SYNTAX      FourRFAlarmStatus
    MAX-ACCESS  read-only
    STATUS      current
    DESCRIPTION "The status of the receiver ADC Ch Nine voltage too high alarm."
    ::= { aprisaXERxADCChNineHiAlarm 2 }

aprisaXERxADCChNineHiAlarmSeverity OBJECT-TYPE
    SYNTAX      FourRFAlarmSeverity
    MAX-ACCESS  read-only
    STATUS      current
    DESCRIPTION "The severity of the receiver ADC Ch Nine voltage too high alarm."
    ::= { aprisaXERxADCChNineHiAlarm 3 }

aprisaXERxADCChNineHiAlarmEnabled OBJECT-TYPE
    SYNTAX      FourRFAlarmEnabled
    MAX-ACCESS  read-only
    STATUS      current
    DESCRIPTION "Indicates whether the receiver ADC Ch Nine voltage too high alarm is enabled."
    ::= { aprisaXERxADCChNineHiAlarm 4 }
    
aprisaXERxADCChNineHiAlarmThreshold OBJECT-TYPE
    SYNTAX      Integer32
    MAX-ACCESS  read-only
    STATUS      current
    DESCRIPTION "Indicates the level at which the receiver ADC Ch Nine voltage too high 
                 alarm will be set."
    ::= { aprisaXERxADCChNineHiAlarm 5 }
    
aprisaXERxADCChNineHiAlarmClearThreshold OBJECT-TYPE
    SYNTAX      Integer32
    MAX-ACCESS  read-only
    STATUS      current
    DESCRIPTION "Indicates the level at which the receiver ADC Ch Nine voltage too high 
                 will be cleared."
    ::= { aprisaXERxADCChNineHiAlarm 6 }

aprisaXERxADCChNineHiAlarmsGroup OBJECT-GROUP
    OBJECTS     { aprisaXERxADCChNineHiAlarmName,
                  aprisaXERxADCChNineHiAlarmStatus,
                  aprisaXERxADCChNineHiAlarmSeverity, 
                  aprisaXERxADCChNineHiAlarmEnabled,
                  aprisaXERxADCChNineHiAlarmThreshold,
                  aprisaXERxADCChNineHiAlarmClearThreshold
    }
    STATUS      current
    DESCRIPTION "The aprisaXERx receiver ADC Ch Nine voltage too high alarm group."
    ::= { aprisaXEGroups 293 } 


aprisaXERxADCChNineLoAlarm OBJECT IDENTIFIER ::= { aprisaXEReceiverAlarms 38 }

aprisaXERxADCChNineLoAlarmName OBJECT-TYPE
    SYNTAX      DisplayString
    MAX-ACCESS  read-only
    STATUS      current
    DESCRIPTION "The name of the receiver ADC Ch Nine voltage too low alarm."
    ::= { aprisaXERxADCChNineLoAlarm 1 }

aprisaXERxADCChNineLoAlarmStatus OBJECT-TYPE
    SYNTAX      FourRFAlarmStatus
    MAX-ACCESS  read-only
    STATUS      current
    DESCRIPTION "The status of the receiver ADC Ch Nine voltage too low alarm."
    ::= { aprisaXERxADCChNineLoAlarm 2 }

aprisaXERxADCChNineLoAlarmSeverity OBJECT-TYPE
    SYNTAX      FourRFAlarmSeverity
    MAX-ACCESS  read-only
    STATUS      current
    DESCRIPTION "The severity of the receiver ADC Ch Nine voltage too low alarm."
    ::= { aprisaXERxADCChNineLoAlarm 3 }

aprisaXERxADCChNineLoAlarmEnabled OBJECT-TYPE
    SYNTAX      FourRFAlarmEnabled
    MAX-ACCESS  read-only
    STATUS      current
    DESCRIPTION "Indicates whether the receiver ADC Ch Nine voltage too low alarm is enabled."
    ::= { aprisaXERxADCChNineLoAlarm 4 }
    
aprisaXERxADCChNineLoAlarmThreshold OBJECT-TYPE
    SYNTAX      Integer32
    MAX-ACCESS  read-only
    STATUS      current
    DESCRIPTION "Indicates the level at wLoch the receiver ADC Ch Nine voltage too low 
                 alarm will be set."
    ::= { aprisaXERxADCChNineLoAlarm 5 }
    
aprisaXERxADCChNineLoAlarmClearThreshold OBJECT-TYPE
    SYNTAX      Integer32
    MAX-ACCESS  read-only
    STATUS      current
    DESCRIPTION "Indicates the level at wLoch the receiver ADC Ch Nine voltage too low 
                 will be cleared."
    ::= { aprisaXERxADCChNineLoAlarm 6 }

aprisaXERxADCChNineLoAlarmsGroup OBJECT-GROUP
    OBJECTS     { aprisaXERxADCChNineLoAlarmName,
                  aprisaXERxADCChNineLoAlarmStatus,
                  aprisaXERxADCChNineLoAlarmSeverity, 
                  aprisaXERxADCChNineLoAlarmEnabled,
                  aprisaXERxADCChNineLoAlarmThreshold,
                  aprisaXERxADCChNineLoAlarmClearThreshold
    }
    STATUS      current
    DESCRIPTION "The aprisaXERx receiver ADC Ch Nine voltage too High alarm group."
    ::= { aprisaXEGroups 294 }


aprisaXERxADCChTenHiAlarm OBJECT IDENTIFIER ::= { aprisaXEReceiverAlarms 39 }

aprisaXERxADCChTenHiAlarmName OBJECT-TYPE
    SYNTAX      DisplayString
    MAX-ACCESS  read-only
    STATUS      current
    DESCRIPTION "The name of the receiver ADC Ch Ten voltage too high alarm."
    ::= { aprisaXERxADCChTenHiAlarm 1 }

aprisaXERxADCChTenHiAlarmStatus OBJECT-TYPE
    SYNTAX      FourRFAlarmStatus
    MAX-ACCESS  read-only
    STATUS      current
    DESCRIPTION "The status of the receiver ADC Ch Ten voltage too high alarm."
    ::= { aprisaXERxADCChTenHiAlarm 2 }

aprisaXERxADCChTenHiAlarmSeverity OBJECT-TYPE
    SYNTAX      FourRFAlarmSeverity
    MAX-ACCESS  read-only
    STATUS      current
    DESCRIPTION "The severity of the receiver ADC Ch Ten voltage too high alarm."
    ::= { aprisaXERxADCChTenHiAlarm 3 }

aprisaXERxADCChTenHiAlarmEnabled OBJECT-TYPE
    SYNTAX      FourRFAlarmEnabled
    MAX-ACCESS  read-only
    STATUS      current
    DESCRIPTION "Indicates whether the receiver ADC Ch Ten voltage too high alarm is enabled."
    ::= { aprisaXERxADCChTenHiAlarm 4 }
    
aprisaXERxADCChTenHiAlarmThreshold OBJECT-TYPE
    SYNTAX      Integer32
    MAX-ACCESS  read-only
    STATUS      current
    DESCRIPTION "Indicates the level at which the receiver ADC Ch Ten voltage too high 
                 alarm will be set."
    ::= { aprisaXERxADCChTenHiAlarm 5 }
    
aprisaXERxADCChTenHiAlarmClearThreshold OBJECT-TYPE
    SYNTAX      Integer32
    MAX-ACCESS  read-only
    STATUS      current
    DESCRIPTION "Indicates the level at which the receiver ADC Ch Ten voltage too high 
                 will be cleared."
    ::= { aprisaXERxADCChTenHiAlarm 6 }

aprisaXERxADCChTenHiAlarmsGroup OBJECT-GROUP
    OBJECTS     { aprisaXERxADCChTenHiAlarmName,
                  aprisaXERxADCChTenHiAlarmStatus,
                  aprisaXERxADCChTenHiAlarmSeverity, 
                  aprisaXERxADCChTenHiAlarmEnabled,
                  aprisaXERxADCChTenHiAlarmThreshold,
                  aprisaXERxADCChTenHiAlarmClearThreshold
    }
    STATUS      current
    DESCRIPTION "The aprisaXERx receiver ADC Ch Ten voltage too high alarm group."
    ::= { aprisaXEGroups 295 } 


aprisaXERxADCChTenLoAlarm OBJECT IDENTIFIER ::= { aprisaXEReceiverAlarms 40 }

aprisaXERxADCChTenLoAlarmName OBJECT-TYPE
    SYNTAX      DisplayString
    MAX-ACCESS  read-only
    STATUS      current
    DESCRIPTION "The name of the receiver ADC Ch Ten voltage too low alarm."
    ::= { aprisaXERxADCChTenLoAlarm 1 }

aprisaXERxADCChTenLoAlarmStatus OBJECT-TYPE
    SYNTAX      FourRFAlarmStatus
    MAX-ACCESS  read-only
    STATUS      current
    DESCRIPTION "The status of the receiver ADC Ch Ten voltage too low alarm."
    ::= { aprisaXERxADCChTenLoAlarm 2 }

aprisaXERxADCChTenLoAlarmSeverity OBJECT-TYPE
    SYNTAX      FourRFAlarmSeverity
    MAX-ACCESS  read-only
    STATUS      current
    DESCRIPTION "The severity of the receiver ADC Ch Ten voltage too low alarm."
    ::= { aprisaXERxADCChTenLoAlarm 3 }

aprisaXERxADCChTenLoAlarmEnabled OBJECT-TYPE
    SYNTAX      FourRFAlarmEnabled
    MAX-ACCESS  read-only
    STATUS      current
    DESCRIPTION "Indicates whether the receiver ADC Ch Ten voltage too low alarm is enabled."
    ::= { aprisaXERxADCChTenLoAlarm 4 }
    
aprisaXERxADCChTenLoAlarmThreshold OBJECT-TYPE
    SYNTAX      Integer32
    MAX-ACCESS  read-only
    STATUS      current
    DESCRIPTION "Indicates the level at wLoch the receiver ADC Ch Ten voltage too low 
                 alarm will be set."
    ::= { aprisaXERxADCChTenLoAlarm 5 }
    
aprisaXERxADCChTenLoAlarmClearThreshold OBJECT-TYPE
    SYNTAX      Integer32
    MAX-ACCESS  read-only
    STATUS      current
    DESCRIPTION "Indicates the level at wLoch the receiver ADC Ch Ten voltage too low 
                 will be cleared."
    ::= { aprisaXERxADCChTenLoAlarm 6 }

aprisaXERxADCChTenLoAlarmsGroup OBJECT-GROUP
    OBJECTS     { aprisaXERxADCChTenLoAlarmName,
                  aprisaXERxADCChTenLoAlarmStatus,
                  aprisaXERxADCChTenLoAlarmSeverity, 
                  aprisaXERxADCChTenLoAlarmEnabled,
                  aprisaXERxADCChTenLoAlarmThreshold,
                  aprisaXERxADCChTenLoAlarmClearThreshold
    }
    STATUS      current
    DESCRIPTION "The aprisaXERx receiver ADC Ch Ten voltage too High alarm group."
    ::= { aprisaXEGroups 296 }

-- ***************************************************************************
-- End of the Generic Receiver alarms
-- ***************************************************************************    



-- ***************************************************************************
-- Modem alarms
-- ***************************************************************************    

aprisaXEModemAlarms OBJECT IDENTIFIER ::= { aprisaXELinkAlarms 10 }

aprisaXEModemSyncAlarm OBJECT IDENTIFIER ::= { aprisaXEModemAlarms 1 }

aprisaXEModemSyncAlarmStatus OBJECT-TYPE
    SYNTAX      FourRFAlarmStatus
    MAX-ACCESS  read-only
    STATUS      current
    DESCRIPTION "The status of the loss of modem sync alarm."
    ::= { aprisaXEModemSyncAlarm 1 }

aprisaXEModemSyncAlarmSeverity OBJECT-TYPE
    SYNTAX      FourRFAlarmSeverity
    MAX-ACCESS  read-only
    STATUS      current
    DESCRIPTION "The severity of the loss of modem sync alarm."
    ::= { aprisaXEModemSyncAlarm 2 }

aprisaXEModemSyncAlarmEnabled OBJECT-TYPE
    SYNTAX      FourRFAlarmEnabled
    MAX-ACCESS  read-only
    STATUS      current
    DESCRIPTION "Indicates whether the loss of modem sync alarm is enabled."
    ::= { aprisaXEModemSyncAlarm 3 }

-- ***************************************************************************
-- End of Modem alarms
-- ***************************************************************************    



-- ***************************************************************************
-- Quad E1 Alarms
-- ***************************************************************************    

aprisaXEQuadJetBoardTable OBJECT-TYPE
    SYNTAX      SEQUENCE OF AprisaXEQuadJetBoardEntry
    MAX-ACCESS  not-accessible
    STATUS      current
    DESCRIPTION "Table of Quad E1 card specific configuration details."
    ::= { aprisaXEObjects 87 }

aprisaXEQuadJetBoardEntry OBJECT-TYPE
    SYNTAX      AprisaXEQuadJetBoardEntry
    MAX-ACCESS  not-accessible
    STATUS      current
    DESCRIPTION "Quad E1 configuration details."
    INDEX       { aprisaXEQuadJetBoardTableIndex }
    ::= { aprisaXEQuadJetBoardTable 1 }
        
AprisaXEQuadJetBoardEntry ::= SEQUENCE {
        aprisaXEQuadJetBoardTableIndex INTEGER
    }

aprisaXEQuadJetBoardTableIndex OBJECT-TYPE
    SYNTAX      AprisaXESlotNumber
    MAX-ACCESS  read-only
    STATUS      current
    DESCRIPTION "Quad E1 board indexed by slot."
    ::= { aprisaXEQuadJetBoardEntry 1 }

aprisaXEQuadJetPortTable OBJECT-TYPE
    SYNTAX      SEQUENCE OF AprisaXEQuadJetPortEntry
    MAX-ACCESS  not-accessible
    STATUS      current
    DESCRIPTION "Table based on slot and port of QuadJet cards alarms."
    ::= { aprisaXEObjects 88 }

aprisaXEQuadJetPortEntry OBJECT-TYPE
    SYNTAX      AprisaXEQuadJetPortEntry
    MAX-ACCESS  not-accessible
    STATUS      current
    DESCRIPTION "Quad E1 port alarms."
    INDEX       { aprisaXEQuadJetPortTableSlot,
                  aprisaXEQuadJetPortTablePort
    }
    ::= { aprisaXEQuadJetPortTable 1 }

AprisaXEQuadJetPortEntry ::= SEQUENCE {
        aprisaXEQuadJetPortTableSlot           INTEGER,
        aprisaXEQuadJetPortTablePort           INTEGER,
        aprisaXEQuadJetLOFAlarmStatus          INTEGER,
        aprisaXEQuadJetLOFAlarmSeverity        INTEGER,
        aprisaXEQuadJetLOFAlarmEnabled         INTEGER,
        aprisaXEQuadJetAISAlarmStatus          INTEGER,
        aprisaXEQuadJetAISAlarmSeverity        INTEGER,
        aprisaXEQuadJetAISAlarmEnabled         INTEGER,
        aprisaXEQuadJetRAIAlarmStatus          INTEGER,
        aprisaXEQuadJetRAIAlarmSeverity        INTEGER,
        aprisaXEQuadJetRAIAlarmEnabled         INTEGER,
        aprisaXEQuadJetRMAIAlarmStatus         INTEGER,
        aprisaXEQuadJetRMAIAlarmSeverity       INTEGER,
        aprisaXEQuadJetRMAIAlarmEnabled        INTEGER,
        aprisaXEQuadJetTS16AISAlarmStatus      INTEGER,
        aprisaXEQuadJetTS16AISAlarmSeverity    INTEGER,
        aprisaXEQuadJetTS16AISAlarmEnabled     INTEGER,
        aprisaXEQuadJetTS16LOSAlarmStatus      INTEGER,
        aprisaXEQuadJetTS16LOSAlarmSeverity    INTEGER,
        aprisaXEQuadJetTS16LOSAlarmEnabled     INTEGER,
        aprisaXEQuadJetLOSAlarmStatus          INTEGER,
        aprisaXEQuadJetLOSAlarmSeverity        INTEGER,
        aprisaXEQuadJetLOSAlarmEnabled         INTEGER,
        aprisaXEQuadJetCRC4AlarmStatus         INTEGER,
        aprisaXEQuadJetCRC4AlarmSeverity       INTEGER,
        aprisaXEQuadJetCRC4AlarmEnabled        INTEGER,
        aprisaXEQuadJetCRC4AlarmThreshold      Integer32,
        aprisaXEQuadJetCRC4AlarmClearThreshold Integer32
    }

aprisaXEQuadJetPortTableSlot OBJECT-TYPE
    SYNTAX      AprisaXESlotNumber
    MAX-ACCESS  read-only
    STATUS      current
    DESCRIPTION "Port table index based on slot number."
    ::= { aprisaXEQuadJetPortEntry 1 }

aprisaXEQuadJetPortTablePort OBJECT-TYPE
    SYNTAX      AprisaXEPortNumber
    MAX-ACCESS  read-only
    STATUS      current
    DESCRIPTION "Port table index based on port number."
    ::= { aprisaXEQuadJetPortEntry 2 }
        
aprisaXEQuadJetLOFAlarmStatus OBJECT-TYPE
    SYNTAX      FourRFAlarmStatus
    MAX-ACCESS  read-only
    STATUS      current
    DESCRIPTION "Red alarm status."
    ::= { aprisaXEQuadJetPortEntry 3 }

aprisaXEQuadJetLOFAlarmSeverity OBJECT-TYPE
    SYNTAX      FourRFAlarmSeverity
    MAX-ACCESS  read-only
    STATUS      current
    DESCRIPTION "Red alarm severity."
    ::= { aprisaXEQuadJetPortEntry 4 }

aprisaXEQuadJetLOFAlarmEnabled OBJECT-TYPE
    SYNTAX      FourRFAlarmEnabled
    MAX-ACCESS  read-only
    STATUS      current
    DESCRIPTION "Red alarm enabled or disabled."
    ::= { aprisaXEQuadJetPortEntry 5 }

aprisaXEQuadJetAISAlarmStatus OBJECT-TYPE
    SYNTAX      FourRFAlarmStatus
    MAX-ACCESS  read-only
    STATUS      current
    DESCRIPTION "AIS alarm status."
    ::= { aprisaXEQuadJetPortEntry 6 }

aprisaXEQuadJetAISAlarmSeverity OBJECT-TYPE
    SYNTAX      FourRFAlarmSeverity
    MAX-ACCESS  read-only
    STATUS      current
    DESCRIPTION "AIS alarm severity."
    ::= { aprisaXEQuadJetPortEntry 7 }

aprisaXEQuadJetAISAlarmEnabled OBJECT-TYPE
    SYNTAX      FourRFAlarmEnabled
    MAX-ACCESS  read-only
    STATUS      current
    DESCRIPTION "AIS alarm enabled or disabled."
    ::= { aprisaXEQuadJetPortEntry 8 }

aprisaXEQuadJetRAIAlarmStatus OBJECT-TYPE
    SYNTAX      FourRFAlarmStatus
    MAX-ACCESS  read-only
    STATUS      current
    DESCRIPTION "RAI alarm status."
    ::= { aprisaXEQuadJetPortEntry 9 }

aprisaXEQuadJetRAIAlarmSeverity OBJECT-TYPE
    SYNTAX      FourRFAlarmSeverity
    MAX-ACCESS  read-only
    STATUS      current
    DESCRIPTION "RAI alarm severity."
    ::= { aprisaXEQuadJetPortEntry 10 }

aprisaXEQuadJetRAIAlarmEnabled OBJECT-TYPE
    SYNTAX      FourRFAlarmEnabled
    MAX-ACCESS  read-only
    STATUS      current
    DESCRIPTION "RAI alarm enabled or disabled."
    ::= { aprisaXEQuadJetPortEntry 11 }

aprisaXEQuadJetRMAIAlarmStatus OBJECT-TYPE
    SYNTAX      FourRFAlarmStatus
    MAX-ACCESS  read-only
    STATUS      current
    DESCRIPTION "RMAI alarm status."
    ::= { aprisaXEQuadJetPortEntry 12 }

aprisaXEQuadJetRMAIAlarmSeverity OBJECT-TYPE
    SYNTAX      FourRFAlarmSeverity
    MAX-ACCESS  read-only
    STATUS      current
    DESCRIPTION "RMAI alarm severity."
    ::= { aprisaXEQuadJetPortEntry 13 }

aprisaXEQuadJetRMAIAlarmEnabled OBJECT-TYPE
    SYNTAX      FourRFAlarmEnabled
    MAX-ACCESS  read-only
    STATUS      current
    DESCRIPTION "RMAI alarm enabled or disabled."
    ::= { aprisaXEQuadJetPortEntry 14 }

aprisaXEQuadJetTS16AISAlarmStatus OBJECT-TYPE
    SYNTAX      FourRFAlarmStatus
    MAX-ACCESS  read-only
    STATUS      current
    DESCRIPTION "TS16 AIS alarm status."
    ::= { aprisaXEQuadJetPortEntry 15 }

aprisaXEQuadJetTS16AISAlarmSeverity OBJECT-TYPE
    SYNTAX      FourRFAlarmSeverity
    MAX-ACCESS  read-only
    STATUS      current
    DESCRIPTION "TS16 AIS alarm severity."
    ::= { aprisaXEQuadJetPortEntry 16 }

aprisaXEQuadJetTS16AISAlarmEnabled OBJECT-TYPE
    SYNTAX      FourRFAlarmEnabled
    MAX-ACCESS  read-only
    STATUS      current
    DESCRIPTION "TS16 AIS alarm enabled or disabled."
    ::= { aprisaXEQuadJetPortEntry 17 }

aprisaXEQuadJetTS16LOSAlarmStatus OBJECT-TYPE
    SYNTAX      FourRFAlarmStatus
    MAX-ACCESS  read-only
    STATUS      current
    DESCRIPTION "TS16 LOS alarm status."
    ::= { aprisaXEQuadJetPortEntry 18 }

aprisaXEQuadJetTS16LOSAlarmSeverity OBJECT-TYPE
    SYNTAX      FourRFAlarmSeverity
    MAX-ACCESS  read-only
    STATUS      current
    DESCRIPTION "TS16 LOS alarm severity."
    ::= { aprisaXEQuadJetPortEntry 19 }

aprisaXEQuadJetTS16LOSAlarmEnabled OBJECT-TYPE
    SYNTAX      FourRFAlarmEnabled
    MAX-ACCESS  read-only
    STATUS      current
    DESCRIPTION "TS16 LOS alarm enabled or disabled."
    ::= { aprisaXEQuadJetPortEntry 20 }

aprisaXEQuadJetLOSAlarmStatus OBJECT-TYPE
    SYNTAX      FourRFAlarmStatus
    MAX-ACCESS  read-only
    STATUS      current
    DESCRIPTION "LOS alarm status."
    ::= { aprisaXEQuadJetPortEntry 21 }

aprisaXEQuadJetLOSAlarmSeverity OBJECT-TYPE
    SYNTAX      FourRFAlarmSeverity
    MAX-ACCESS  read-only
    STATUS      current
    DESCRIPTION "LOS alarm severity."
    ::= { aprisaXEQuadJetPortEntry 22 }

aprisaXEQuadJetLOSAlarmEnabled OBJECT-TYPE
    SYNTAX      FourRFAlarmEnabled
    MAX-ACCESS  read-only
    STATUS      current
    DESCRIPTION "LOS alarm enabled or disabled."
    ::= { aprisaXEQuadJetPortEntry 23 }

aprisaXEQuadJetCRC4AlarmStatus OBJECT-TYPE
    SYNTAX      FourRFAlarmStatus
    MAX-ACCESS  read-only
    STATUS      current
    DESCRIPTION "CRC4 alarm status."
    ::= { aprisaXEQuadJetPortEntry 24 }

aprisaXEQuadJetCRC4AlarmSeverity OBJECT-TYPE
    SYNTAX      FourRFAlarmSeverity
    MAX-ACCESS  read-only
    STATUS      current
    DESCRIPTION "CRC4 alarm severity."
    ::= { aprisaXEQuadJetPortEntry 25 }

aprisaXEQuadJetCRC4AlarmEnabled OBJECT-TYPE
    SYNTAX      FourRFAlarmEnabled
    MAX-ACCESS  read-only
    STATUS      current
    DESCRIPTION "CRC4 alarm enabled or disabled."
    ::= { aprisaXEQuadJetPortEntry 26 }

aprisaXEQuadJetCRC4AlarmThreshold OBJECT-TYPE
    SYNTAX      Integer32
    MAX-ACCESS  read-only
    STATUS      current
    DESCRIPTION "CRC4 Threshold value for counter to alarm at."
    ::= { aprisaXEQuadJetPortEntry 27 }

aprisaXEQuadJetCRC4AlarmClearThreshold OBJECT-TYPE
    SYNTAX      Integer32
    MAX-ACCESS  read-only
    STATUS      current
    DESCRIPTION "CRC4 Threshold at which alarm clears."
    ::= { aprisaXEQuadJetPortEntry 28 }


aprisaXEQuadJetIFConfigTable OBJECT-TYPE
    SYNTAX      SEQUENCE OF AprisaXEQuadJetIFConfigEntry
    MAX-ACCESS  not-accessible
    STATUS      current
    DESCRIPTION "Switch data table which describes the
                 allocation of user data on to the TDM busses."
    ::= { aprisaXEObjects 90 }

aprisaXEQuadJetIFConfigEntry OBJECT-TYPE
    SYNTAX      AprisaXEQuadJetIFConfigEntry
    MAX-ACCESS  not-accessible
    STATUS      current
    DESCRIPTION "Quad JET config data."
    INDEX       { aprisaXEQuadJetIFConfigSlotIndex,
                  aprisaXEQuadJetIFConfigPortIndex
    }
    ::= { aprisaXEQuadJetIFConfigTable 1 }

AprisaXEQuadJetIFConfigEntry ::= SEQUENCE {
        aprisaXEQuadJetIFConfigSlotIndex INTEGER,
        aprisaXEQuadJetIFConfigPortIndex INTEGER,
        aprisaXEQuadJetTrafficType       INTEGER,
        aprisaXEQuadJetLoopback          INTEGER,
        aprisaXEQuadJetLineEncoding      INTEGER,
        aprisaXEQuadJetPcmMode           INTEGER,
        aprisaXEQuadJetClockSource       INTEGER,
        aprisaXEQuadJetLineRadioLoopback INTEGER,
        aprisaXEQuadJetTxWaveFormShaper  INTEGER,
        aprisaXEQuadJetMultiframeEnable  INTEGER
    }

aprisaXEQuadJetIFConfigSlotIndex OBJECT-TYPE
    SYNTAX      AprisaXESlotNumber
    MAX-ACCESS  read-only
    STATUS      current
    DESCRIPTION "Index to the port table based on port number."
    ::= { aprisaXEQuadJetIFConfigEntry 1 }
    
aprisaXEQuadJetIFConfigPortIndex OBJECT-TYPE
    SYNTAX      AprisaXEPortNumber
    MAX-ACCESS  read-only
    STATUS      current
    DESCRIPTION "Index to the port table based on port number."
    ::= { aprisaXEQuadJetIFConfigEntry 2 }
           
aprisaXEQuadJetTrafficType OBJECT-TYPE
    SYNTAX      AprisaXEQuadJetTrafficType
    MAX-ACCESS  read-write
    STATUS      current
    DESCRIPTION "Controls the traffic type on a Quad JET port."
    ::= { aprisaXEQuadJetIFConfigEntry 3 }
        
aprisaXEQuadJetLoopback OBJECT-TYPE
    SYNTAX      FourRFLoopback
    MAX-ACCESS  read-write
    STATUS      obsolete
    DESCRIPTION "Controls the traffic loopback on a Quad JET port."
    ::= { aprisaXEQuadJetIFConfigEntry 4 }
        
aprisaXEQuadJetLineEncoding OBJECT-TYPE
    SYNTAX      AprisaXEQuadJetLineEncoding
    MAX-ACCESS  read-write
    STATUS      current
    DESCRIPTION "Controls the line encoding, the default is
                 HDB3 for E1, B8ZS for T1."
    ::= { aprisaXEQuadJetIFConfigEntry 5 }

aprisaXEQuadJetPcmMode OBJECT-TYPE
    SYNTAX      AprisaXEPcmMode
    MAX-ACCESS  read-write
    STATUS      current
    DESCRIPTION "Controls the PCM mode, PCM31 or PCM30C."
    ::= { aprisaXEQuadJetIFConfigEntry 6 }
        
aprisaXEQuadJetClockSource OBJECT-TYPE
    SYNTAX       FourRFNetworkClockSelect
    MAX-ACCESS   read-write
    STATUS       current
    DESCRIPTION  "Controls whether the port drives the clock soure or not."
    ::= { aprisaXEQuadJetIFConfigEntry 7 }
       
aprisaXEQuadJetLineRadioLoopback OBJECT-TYPE
    SYNTAX      AprisaXEQuadJetLoopbacks
    MAX-ACCESS  read-write
    STATUS      current
    DESCRIPTION "This indicates the E1 loopback setting on a port;
                 OFF, Line or Radio Facing."
    ::= { aprisaXEQuadJetIFConfigEntry 8 }

aprisaXEQuadJetTxWaveFormShaper OBJECT-TYPE
    SYNTAX      AprisaXEQuadJetWaveFormShapers
    MAX-ACCESS  read-write
    STATUS      current
    DESCRIPTION "This indicates the T1 Tx Waveform Shaper for a port;
                 0~133 ft, 133~266 ft, 266~399 ft, 399~533 ft, 533~655 ft."
    ::= { aprisaXEQuadJetIFConfigEntry 9 }

aprisaXEQuadJetMultiframeEnable OBJECT-TYPE
    SYNTAX      AprisaXEQuadJetMultiframeEnable
    MAX-ACCESS  read-write
    STATUS      current
    DESCRIPTION "Indicates whether support is enabled for transport of T1 SF
                 and ESF multiframe sync for a port."
    ::= { aprisaXEQuadJetIFConfigEntry 10 }


-- E1 Cross connection table, this maps cross-connection identifiers to
-- the matching E1 slot and port.

aprisaXEQuadJetIFConnectionTable OBJECT-TYPE
    SYNTAX      SEQUENCE OF AprisaXEQuadJetIFConnectionTableEntry
    MAX-ACCESS  not-accessible
    STATUS      current
    DESCRIPTION "Interface connection table which holds all the cross
                 connect information for the E1 card."
    ::= { aprisaXEObjects 91 }

aprisaXEQuadJetIFConnectionTableEntry OBJECT-TYPE
    SYNTAX      AprisaXEQuadJetIFConnectionTableEntry
    MAX-ACCESS  not-accessible
    STATUS      current
    DESCRIPTION "Quad JET cross connection data."
    INDEX       { aprisaXEQuadJetIFConnectionID,
                  aprisaXEQuadJetIFConnectionAggregateID
    }
    ::= { aprisaXEQuadJetIFConnectionTable 1 }

AprisaXEQuadJetIFConnectionTableEntry ::= SEQUENCE {
        aprisaXEQuadJetIFConnectionID           INTEGER,
        aprisaXEQuadJetIFConnectionAggregateID  INTEGER,
        aprisaXEQuadJetIFConnectionSlot         INTEGER,
        aprisaXEQuadJetIFConnectionE1Port       INTEGER,
        aprisaXEQuadJetIFConnectionType         INTEGER
    }
        
aprisaXEQuadJetIFConnectionID OBJECT-TYPE
    SYNTAX      AprisaXEConnectionID
    MAX-ACCESS  read-only
    STATUS      current
    DESCRIPTION "Backplane Connection ID."
    ::= { aprisaXEQuadJetIFConnectionTableEntry 1 }

aprisaXEQuadJetIFConnectionAggregateID OBJECT-TYPE
    SYNTAX      AprisaXEConnectionID
    MAX-ACCESS  read-only
    STATUS      current
    DESCRIPTION "Aggregate ID, 0 if an unframed connection."
    ::= { aprisaXEQuadJetIFConnectionTableEntry 2 }
        
aprisaXEQuadJetIFConnectionSlot OBJECT-TYPE
    SYNTAX      AprisaXESlotNumber
    MAX-ACCESS  read-only
    STATUS      current
    DESCRIPTION "Slot number that this card is in."
    ::= { aprisaXEQuadJetIFConnectionTableEntry 3 }

aprisaXEQuadJetIFConnectionE1Port OBJECT-TYPE
    SYNTAX      AprisaXEPortNumber
    MAX-ACCESS  read-only
    STATUS      current
    DESCRIPTION "Port number associated with this connection."
    ::= { aprisaXEQuadJetIFConnectionTableEntry 4 }
        
aprisaXEQuadJetIFConnectionType OBJECT-TYPE
    SYNTAX      AprisaXEQuadJetConnectionType
    MAX-ACCESS  read-only
    STATUS      current
    DESCRIPTION "Indicates whether the connection is for data or
                 CAS signalling."
    ::= { aprisaXEQuadJetIFConnectionTableEntry 5 }


aprisaXEQuadJetIFConnectionControl OBJECT IDENTIFIER ::= { aprisaXEObjects 93 }

aprisaXEQuadJetIFControlConnectionID OBJECT-TYPE
    SYNTAX      AprisaXEConnectionID
    MAX-ACCESS  read-write
    STATUS      current
    DESCRIPTION "Backplane Connection ID."
    ::= { aprisaXEQuadJetIFConnectionControl 1 }
        
aprisaXEQuadJetIFControlAggregateID OBJECT-TYPE
    SYNTAX      AprisaXEConnectionID
    MAX-ACCESS  read-write
    STATUS      current
    DESCRIPTION "Aggregate Connection ID."
    ::= { aprisaXEQuadJetIFConnectionControl 2 }

aprisaXEQuadJetIFConnectionControlSlot OBJECT-TYPE
    SYNTAX      AprisaXESlotNumber
    MAX-ACCESS  read-write
    STATUS      current
    DESCRIPTION "Slot number that this card is in."
    ::= { aprisaXEQuadJetIFConnectionControl 3 }

aprisaXEQuadJetIFConnectionControlE1Port OBJECT-TYPE
    SYNTAX      AprisaXEPortNumber
    MAX-ACCESS  read-write
    STATUS      current
    DESCRIPTION "Port number associated with this connection."
    ::= { aprisaXEQuadJetIFConnectionControl 4 }
 
aprisaXEQuadJetIFConnectionControlType OBJECT-TYPE
    SYNTAX      AprisaXEQuadJetConnectionType
    MAX-ACCESS  read-write
    STATUS      current
    DESCRIPTION "Indicates whether the connection is for data or
                 CAS signalling."
    ::= { aprisaXEQuadJetIFConnectionControl 5 }
        
aprisaXEQuadJetIFConnectionControlCommand OBJECT-TYPE
    SYNTAX      INTEGER { noCommand     (0),
                          addCommand    (1),
                          deleteCommand (2)
                }
    MAX-ACCESS  read-write
    STATUS      current
    DESCRIPTION "Command to send to act upon the rows in the QuedJet Interface
                 Connection table."
    ::= { aprisaXEQuadJetIFConnectionControl 6 }

-- ***************************************************************************
-- End Quad JET
-- ***************************************************************************



-- ***************************************************************************
-- Ethernet
-- ***************************************************************************    

aprisaXEEthernetConfiguration OBJECT IDENTIFIER ::= { aprisaXEObjects 95 }

aprisaXEEthernetBandwidth OBJECT-TYPE
    SYNTAX      Unsigned32
    MAX-ACCESS  read-write
    STATUS      current
    DESCRIPTION "This controls the bandwidth allocated to
                 ethernet in kbps, the minimum block is
                 8kbps, values will be rounded up to the
                 nearest 8kbps."
    ::= { aprisaXEEthernetConfiguration 1 }
        
aprisaXEEthernetManagementBandwidth OBJECT-TYPE
    SYNTAX      Unsigned32
    MAX-ACCESS  read-write
    STATUS      current
    DESCRIPTION "This controls the bandwidth available to
                 management traffic, a minimum of 8kbps is
                 required. Values will be rounded up to
                 the nearest 8kbps."
    ::= { aprisaXEEthernetConfiguration 2 }

aprisaXEEthernetCustomerConnectionID OBJECT-TYPE
    SYNTAX      AprisaXEConnectionID
    MAX-ACCESS  read-write
    STATUS      current
    DESCRIPTION "Backplane connection ID for Customer bandwidth."
    ::= { aprisaXEEthernetConfiguration 3 }

aprisaXEEthernetPBCConnectionID OBJECT-TYPE
    SYNTAX      AprisaXEConnectionID
    MAX-ACCESS  read-write
    STATUS      current
    DESCRIPTION "Backplane connection ID for Private Back Channel
                 management bandwidth."
    ::= { aprisaXEEthernetConfiguration 4 }


-- For now a simple table for basic control/status of the hub ports. Later
-- we probably want to implement the EtherLike-MIB.

aprisaXEEthernetPortTable OBJECT-TYPE
    SYNTAX      SEQUENCE OF AprisaXEEthernetPortEntry
    MAX-ACCESS  not-accessible
    STATUS      current
    DESCRIPTION "Table used to control and monitor basic ethernet
                 features on the 4-port hub."
    ::= { aprisaXEObjects 96 }

aprisaXEEthernetPortEntry OBJECT-TYPE
    SYNTAX      AprisaXEEthernetPortEntry
    MAX-ACCESS  not-accessible
    STATUS      current
    DESCRIPTION "Ethernet port status and configuration."
    INDEX       { aprisaXEEthernetPortIndex }
    ::= { aprisaXEEthernetPortTable 1 }

AprisaXEEthernetPortEntry ::= SEQUENCE {
        aprisaXEEthernetPortIndex              INTEGER,
        aprisaXEEthernetAutonegotiationStatus  INTEGER,
        aprisaXEEthernetRemoteFaultStatus      INTEGER,
        aprisaXEEthernetLinkStatus             INTEGER,
        aprisaXEEthernetJabberStatus           INTEGER,
        aprisaXEEthernetSpeed                  INTEGER,
        aprisaXEEthernetDuplexMode             INTEGER
    }

aprisaXEEthernetPortIndex OBJECT-TYPE
    SYNTAX      INTEGER ( 1..4 )
    MAX-ACCESS  read-only
    STATUS      current
    DESCRIPTION "The port index, there are four ports on the hub."
    ::= { aprisaXEEthernetPortEntry 1 }
        
aprisaXEEthernetAutonegotiationStatus OBJECT-TYPE
    SYNTAX      INTEGER { autoNegotiationNotComplete (0),
                          autoNegotiationComplete    (1)
                }
    MAX-ACCESS  read-only
    STATUS      current
    DESCRIPTION "The status of the port auto-negotiation."
    ::= { aprisaXEEthernetPortEntry 2 }
        
aprisaXEEthernetRemoteFaultStatus OBJECT-TYPE
    SYNTAX      INTEGER { remoteFaultNotDetected (0),
                          remoteFaultDetected    (1)
                }
    MAX-ACCESS  read-only
    STATUS      current
    DESCRIPTION "The status of the port remote fault detection."
    ::= { aprisaXEEthernetPortEntry 3 }
        
aprisaXEEthernetLinkStatus OBJECT-TYPE
    SYNTAX      INTEGER { down (0),
                          up   (1)
                }
    MAX-ACCESS  read-only
    STATUS      current
    DESCRIPTION "The status of the port link."
    ::= { aprisaXEEthernetPortEntry 4 }
        
aprisaXEEthernetJabberStatus OBJECT-TYPE
    SYNTAX      INTEGER { jabberNotDetected (0),
                          jabberDetected    (1)
                }
    MAX-ACCESS  read-only
    STATUS      current
    DESCRIPTION "Has jabber been detected on the port?."
    ::= { aprisaXEEthernetPortEntry 5 }
        
aprisaXEEthernetSpeed OBJECT-TYPE
    SYNTAX      INTEGER { mbps10  (0),
                          mbps100 (1)
                }
    MAX-ACCESS  read-only
    STATUS      current
    DESCRIPTION "The current port speed, 10 or 100 Mbps."
    ::= { aprisaXEEthernetPortEntry 6 }
        
aprisaXEEthernetDuplexMode OBJECT-TYPE
    SYNTAX      INTEGER { halfDuplex (0),
                          fullDuplex (1)
                }
    MAX-ACCESS  read-only
    STATUS      current
    DESCRIPTION "The current port duplex mode."
    ::= { aprisaXEEthernetPortEntry 7 }

-- ***************************************************************************
-- End Ethernet
-- ***************************************************************************



-- ***************************************************************************
-- Interface Status
-- ***************************************************************************    
--
-- A table which maintains the status of the interface cards, the amount of
-- bandwidth allocated per port and the overall alarm status.
--

aprisaXEInterfaceTable OBJECT-TYPE
    SYNTAX      SEQUENCE OF AprisaXEInterfaceTableEntry
    MAX-ACCESS  not-accessible
    STATUS      current
    DESCRIPTION "Table used to monitor the current interface status."
    ::= { aprisaXEObjects 100 }

aprisaXEInterfaceTableEntry OBJECT-TYPE
    SYNTAX      AprisaXEInterfaceTableEntry
    MAX-ACCESS  not-accessible
    STATUS      current
    DESCRIPTION "Interface bandwidth and status."
    INDEX       { aprisaXEInterfaceIndex }
    ::= { aprisaXEInterfaceTable 1 }

AprisaXEInterfaceTableEntry ::= SEQUENCE {
        aprisaXEInterfaceIndex          INTEGER,
        aprisaXEInterfaceType           INTEGER,
        aprisaXEInterfaceAlarmStatus    INTEGER,
        aprisaXEInterfacePort1Bandwidth Unsigned32,
        aprisaXEInterfacePort2Bandwidth Unsigned32,
        aprisaXEInterfacePort3Bandwidth Unsigned32,
        aprisaXEInterfacePort4Bandwidth Unsigned32
    }
        
aprisaXEInterfaceIndex OBJECT-TYPE
    SYNTAX      AprisaXESlotNumber
    MAX-ACCESS  read-only
    STATUS      current
    DESCRIPTION "The slot containing the interface card, slots 0 to
                 8 (AUX or A-H) inclusive may contain interface cards."
   ::= { aprisaXEInterfaceTableEntry 1 }
       
aprisaXEInterfaceType OBJECT-TYPE
    SYNTAX      AprisaXECardType
    MAX-ACCESS  read-only
    STATUS      current
    DESCRIPTION "Indicates the type of interface card."
    ::= { aprisaXEInterfaceTableEntry 2 }
        
aprisaXEInterfaceAlarmStatus OBJECT-TYPE
    SYNTAX      FourRFAlarmStatus
    MAX-ACCESS  read-only
    STATUS      current
    DESCRIPTION "Indicates the current alarm status for the interface."
    ::= { aprisaXEInterfaceTableEntry 3 }
        
aprisaXEInterfacePort1Bandwidth OBJECT-TYPE
    SYNTAX      Unsigned32
    MAX-ACCESS  read-only
    STATUS      current
    DESCRIPTION "Indicates the bandwidth allocated to port 1."
    ::= { aprisaXEInterfaceTableEntry 4 }

aprisaXEInterfacePort2Bandwidth OBJECT-TYPE
    SYNTAX      Unsigned32
    MAX-ACCESS  read-only
    STATUS      current
    DESCRIPTION "Indicates the bandwidth allocated to port 2."
    ::= { aprisaXEInterfaceTableEntry 5 }
        
aprisaXEInterfacePort3Bandwidth OBJECT-TYPE
    SYNTAX      Unsigned32
    MAX-ACCESS  read-only
    STATUS      current
    DESCRIPTION "Indicates the bandwidth allocated to port 3."
    ::= { aprisaXEInterfaceTableEntry 6 }
        
aprisaXEInterfacePort4Bandwidth OBJECT-TYPE
    SYNTAX      Unsigned32
    MAX-ACCESS  read-only
    STATUS      current
    DESCRIPTION "Indicates the bandwidth allocated to port 4."
    ::= { aprisaXEInterfaceTableEntry 7 }

-- ***************************************************************************
-- End Interface Status 
-- ***************************************************************************



-- ***************************************************************************
-- 4 Wire Interfaces
-- ***************************************************************************    

aprisaXE4WirePortControlTable OBJECT-TYPE
    SYNTAX      SEQUENCE OF AprisaXE4WirePortControlTableEntry
    MAX-ACCESS  not-accessible
    STATUS      current
    DESCRIPTION "Status and Control table for 4Wire."
    ::= { aprisaXEObjects 110 }

aprisaXE4WirePortControlTableEntry OBJECT-TYPE
    SYNTAX      AprisaXE4WirePortControlTableEntry
    MAX-ACCESS  not-accessible
    STATUS      current
    DESCRIPTION "Entries for 4wire table."
    INDEX       { aprisaXE4WireSlotIndex,
                  aprisaXE4WirePortIndex
    }
    ::= { aprisaXE4WirePortControlTable 1 }

AprisaXE4WirePortControlTableEntry ::= SEQUENCE {
        aprisaXE4WireConnectionID           INTEGER,
        aprisaXE4WireSlotIndex              INTEGER,
        aprisaXE4WirePortIndex              INTEGER,
        aprisaXE4WireLoopback               INTEGER,
        aprisaXE4WireAdpcmCompression       INTEGER,
        aprisaXE4WireRxGain                 INTEGER,
        aprisaXE4WireTxGain                 INTEGER,
        aprisaXE4WireEInvert                INTEGER,
        aprisaXE4WireMInvert                INTEGER,
        aprisaXE4WireSignalling             INTEGER,
        aprisaXE4WireSignallingConnectionID INTEGER,
        aprisaXE4WireInputLevel             INTEGER,
        aprisaXE4WireOutputLevel            INTEGER
    }

aprisaXE4WireConnectionID OBJECT-TYPE
    SYNTAX      AprisaXEConnectionID
    MAX-ACCESS  read-write
    STATUS      current
    DESCRIPTION "Associated cross-connect Backplane Connection ID."
    ::= { aprisaXE4WirePortControlTableEntry 1 }

aprisaXE4WireSlotIndex OBJECT-TYPE
    SYNTAX      AprisaXESlotNumber
    MAX-ACCESS  read-only
    STATUS      current
    DESCRIPTION "Slot index for 4wire Status Control table."
    ::= { aprisaXE4WirePortControlTableEntry 2 }

aprisaXE4WirePortIndex OBJECT-TYPE
    SYNTAX      AprisaXEPortNumber
    MAX-ACCESS  read-only
    STATUS      current
    DESCRIPTION "Channel index for 4 Wire Control Status table."
    ::= { aprisaXE4WirePortControlTableEntry 3 }

aprisaXE4WireLoopback OBJECT-TYPE
    SYNTAX      FourRFLoopback
    MAX-ACCESS  read-write
    STATUS      current
    DESCRIPTION "Loopback control on or off for channels."
    ::= { aprisaXE4WirePortControlTableEntry 4 }

aprisaXE4WireAdpcmCompression OBJECT-TYPE
    SYNTAX      AprisaXEAdpcmCompression
    MAX-ACCESS  read-write
    STATUS      current
    DESCRIPTION "ADPCM compression 16, 24, 32, 64 kbps or none."
    DEFVAL      { none }
    ::= { aprisaXE4WirePortControlTableEntry 5 }

aprisaXE4WireRxGain OBJECT-TYPE
    SYNTAX      AprisaXE4WRxGain
    MAX-ACCESS  read-write
    STATUS      obsolete
    DESCRIPTION "Rx gain +4 dB to -14 dB in 0.5 dB steps."
    ::= { aprisaXE4WirePortControlTableEntry 6 }

aprisaXE4WireTxGain OBJECT-TYPE
    SYNTAX      AprisaXE4WTxGain
    MAX-ACCESS  read-write
    STATUS      obsolete
    DESCRIPTION "Tx gain +14 dB to -4 dB in half dB steps."
    ::= { aprisaXE4WirePortControlTableEntry 7 }

aprisaXE4WireEInvert OBJECT-TYPE
    SYNTAX      AprisaXESignalState
    MAX-ACCESS  read-write
    STATUS      current
    DESCRIPTION "Controls E on each channel for NORMAL or INVERT polarity."
    ::= { aprisaXE4WirePortControlTableEntry 8 }

aprisaXE4WireMInvert OBJECT-TYPE
    SYNTAX      AprisaXESignalState
    MAX-ACCESS  read-write
    STATUS      current
    DESCRIPTION "Controls M on each channel for NORMAL or INVERT polarity."
    ::= { aprisaXE4WirePortControlTableEntry 9 }
        
aprisaXE4WireSignalling OBJECT-TYPE
    SYNTAX      INTEGER { signallingOff (0),
                          signallingOn  (1)
                }
    MAX-ACCESS  read-write
    STATUS      current
    DESCRIPTION "Enables or disables E&M signalling for the port."
    ::= { aprisaXE4WirePortControlTableEntry 10 }
        
aprisaXE4WireSignallingConnectionID OBJECT-TYPE
    SYNTAX      AprisaXEConnectionID
    MAX-ACCESS  read-write
    STATUS      current
    DESCRIPTION "Associated signalling cross-connect Backplane Connection ID."
    ::= { aprisaXE4WirePortControlTableEntry 11 }

aprisaXE4WireInputLevel OBJECT-TYPE
    SYNTAX      AprisaXE4WInputLevel
    MAX-ACCESS  read-write
    STATUS      current
    DESCRIPTION "Input Level -14.0 dBr to +4.0 dBr in half dB steps."
    ::= { aprisaXE4WirePortControlTableEntry 12 }

aprisaXE4WireOutputLevel OBJECT-TYPE
    SYNTAX      AprisaXE4WOutputLevel
    MAX-ACCESS  read-write
    STATUS      current
    DESCRIPTION "Output Level -14.0 dBr to +4.0 dBr in 0.5 dB steps."
    ::= { aprisaXE4WirePortControlTableEntry 13 }

--
--  End of aprisaXE4WirePortControlTable
--


aprisaXE4WireStatusControlTable OBJECT-TYPE
    SYNTAX      SEQUENCE OF AprisaXE4WireStatusControlTableEntry
    MAX-ACCESS  not-accessible
    STATUS      current
    DESCRIPTION "Overall card control and status."
    ::= { aprisaXEObjects 121 }

aprisaXE4WireStatusControlTableEntry OBJECT-TYPE
    SYNTAX      AprisaXE4WireStatusControlTableEntry
    MAX-ACCESS  not-accessible
    STATUS      current
    DESCRIPTION "Status control entries."
    INDEX       { aprisaXE4WireStatusControlSlotIndex }
    ::= { aprisaXE4WireStatusControlTable 1 }

AprisaXE4WireStatusControlTableEntry ::= SEQUENCE {
        aprisaXE4WireStatusControlSlotIndex  INTEGER,
        aprisaXE4WirePcmLaw                  INTEGER
    }

aprisaXE4WireStatusControlSlotIndex OBJECT-TYPE
    SYNTAX      AprisaXESlotNumber
    MAX-ACCESS  read-only
    STATUS      current
    DESCRIPTION "Index for table."
    ::= { aprisaXE4WireStatusControlTableEntry 1 }


aprisaXE4WirePcmLaw OBJECT-TYPE
    SYNTAX      AprisaXEPcmLaw
    MAX-ACCESS  read-write
    STATUS      current
    DESCRIPTION "Sets A-law or u-law."
    ::= { aprisaXE4WireStatusControlTableEntry 2 }

-- ***************************************************************************
-- End 4 Wire
-- ***************************************************************************



-- ***************************************************************************
-- FXO
-- ***************************************************************************

aprisaXEFXOPortControlTable OBJECT-TYPE
    SYNTAX      SEQUENCE OF AprisaXEFXOPortControlTableEntry
    MAX-ACCESS  not-accessible
    STATUS      current
    DESCRIPTION "Port Control table for FXO."
    ::= { aprisaXEObjects 130 }

aprisaXEFXOPortControlTableEntry OBJECT-TYPE
    SYNTAX      AprisaXEFXOPortControlTableEntry
    MAX-ACCESS  not-accessible
    STATUS      current
    DESCRIPTION "Entries for FXO table."
    INDEX       { aprisaXEFXOPortControlSlotIndex,
                  aprisaXEFXOPortIndex
    }
    ::= { aprisaXEFXOPortControlTable 1 }

AprisaXEFXOPortControlTableEntry ::= SEQUENCE {
        aprisaXEFXOPortControlSlotIndex     INTEGER,
        aprisaXEFXOPortIndex                INTEGER,
        aprisaXEFXOLoopback                 INTEGER,
        aprisaXEFXOAdpcmCompression         INTEGER,
        aprisaXEFXORxGain                   INTEGER,
        aprisaXEFXOTxGain                   INTEGER,
        aprisaXEFXOConnectionID             INTEGER,
        aprisaXEFXOSignallingConnectionID   INTEGER,
        aprisaXEFXOInputLevel               INTEGER,
        aprisaXEFXOOutputLevel              INTEGER
    }

aprisaXEFXOPortControlSlotIndex OBJECT-TYPE
    SYNTAX      AprisaXESlotNumber
    MAX-ACCESS  read-only
    STATUS      current
    DESCRIPTION "Slot index for FXO Control table."
    ::= { aprisaXEFXOPortControlTableEntry 1 }

aprisaXEFXOPortIndex OBJECT-TYPE
    SYNTAX      AprisaXEPortNumber
    MAX-ACCESS  read-only
    STATUS      current
    DESCRIPTION "Port index for FXO Control table."
    ::= { aprisaXEFXOPortControlTableEntry 2 }
        
aprisaXEFXOLoopback OBJECT-TYPE
    SYNTAX      FourRFLoopback
    MAX-ACCESS  read-write
    STATUS      current
    DESCRIPTION "Loopback control on or off for ports."
    ::= { aprisaXEFXOPortControlTableEntry 3 }

aprisaXEFXOAdpcmCompression OBJECT-TYPE
    SYNTAX      AprisaXEAdpcmCompression
    MAX-ACCESS  read-write
    STATUS      current
    DESCRIPTION "ADPCM compression 16, 24, 32, 64 kbps or none."
    DEFVAL      { none }
    ::= { aprisaXEFXOPortControlTableEntry 4 }

aprisaXEFXORxGain OBJECT-TYPE
    SYNTAX      INTEGER { fxopos100 (0),
                          fxopos95  (1),
                          fxopos90  (2),
                          fxopos85  (3),
                          fxopos80  (4),
                          fxopos75  (5),
                          fxopos70  (6),
                          fxopos65  (7),
                          fxopos60  (8),
                          fxopos55  (9),
                          fxopos50  (10),
                          fxopos45  (11),
                          fxopos40  (12),
                          fxopos35  (13),
                          fxopos30  (14),
                          fxopos25  (15),
                          fxopos20  (16),
                          fxopos15  (17),
                          fxopos10  (18),
                          fxopos05  (19),
                          fxopos0   (20),
                          fxoneg05  (21),
                          fxoneg10  (22),
                          fxoneg15  (23),
                          fxoneg20  (24),
                          fxoneg25  (25),
                          fxoneg30  (26),
                          fxoneg35  (27),
                          fxoneg40  (28),
                          fxoneg45  (29),
                          fxoneg50  (30),
                          fxoneg55  (31),
                          fxoneg60  (32),
                          fxoneg65  (33),
                          fxoneg70  (34),
                          fxoneg75  (35),
                          fxoneg80  (36),
                          fxoneg85  (37),
                          fxoneg90  (38),
                          fxoneg95  (39),
                          fxoneg100 (40)
                }
    MAX-ACCESS  read-write
    STATUS      obsolete
    DESCRIPTION "Rx gain -10 dB to 10 dB in 0.5 dB steps."
    ::= { aprisaXEFXOPortControlTableEntry 5 }

aprisaXEFXOTxGain OBJECT-TYPE
    SYNTAX      INTEGER { fxopos100 (0),
                          fxopos95  (1),
                          fxopos90  (2),
                          fxopos85  (3),
                          fxopos80  (4),
                          fxopos75  (5),
                          fxopos70  (6),
                          fxopos65  (7),
                          fxopos60  (8),
                          fxopos55  (9),
                          fxopos50  (10),
                          fxopos45  (11),
                          fxopos40  (12),
                          fxopos35  (13),
                          fxopos30  (14),
                          fxopos25  (15),
                          fxopos20  (16),
                          fxopos15  (17),
                          fxopos10  (18),
                          fxopos05  (19),
                          fxopos0   (20),
                          fxoneg05  (21),
                          fxoneg10  (22),
                          fxoneg15  (23),
                          fxoneg20  (24),
                          fxoneg25  (25),
                          fxoneg30  (26),
                          fxoneg35  (27),
                          fxoneg40  (28),
                          fxoneg45  (29),
                          fxoneg50  (30),
                          fxoneg55  (31),
                          fxoneg60  (32),
                          fxoneg65  (33),
                          fxoneg70  (34),
                          fxoneg75  (35),
                          fxoneg80  (36),
                          fxoneg85  (37),
                          fxoneg90  (38),
                          fxoneg95  (39),
                          fxoneg100 (40)
                }
    MAX-ACCESS  read-write
    STATUS      obsolete
    DESCRIPTION "Tx gain -10 dB to 10 dB in half dB steps."
    ::= { aprisaXEFXOPortControlTableEntry 6 }

aprisaXEFXOConnectionID OBJECT-TYPE
    SYNTAX      AprisaXEConnectionID
    MAX-ACCESS  read-write
    STATUS      current
    DESCRIPTION "Associated cross-connect Backplane Connection ID."
    ::= { aprisaXEFXOPortControlTableEntry 7 }

aprisaXEFXOSignallingConnectionID OBJECT-TYPE
    SYNTAX      AprisaXEConnectionID
    MAX-ACCESS  read-write
    STATUS      current
    DESCRIPTION "Associated signalling cross-connect Backplane Connection ID."
    ::= { aprisaXEFXOPortControlTableEntry 8 }
        
aprisaXEFXOInputLevel OBJECT-TYPE
    SYNTAX      AprisaXEFXOInputLevel
    MAX-ACCESS  read-write
    STATUS      current
    DESCRIPTION "Input Level -10.0 dBr to +1.0 dBr in half dB steps."
    ::= { aprisaXEFXOPortControlTableEntry 9 }

aprisaXEFXOOutputLevel OBJECT-TYPE
    SYNTAX      AprisaXEFXOOutputLevel
    MAX-ACCESS  read-write
    STATUS      current
    DESCRIPTION "Output Level -10.0 dBr to +1.0 dBr in 0.5 dB steps."
    ::= { aprisaXEFXOPortControlTableEntry 10 }

-- 
-- end of table
--

aprisaXEFXOControlTable OBJECT-TYPE
    SYNTAX      SEQUENCE OF AprisaXEFXOControlTableEntry
    MAX-ACCESS  not-accessible
    STATUS      current
    DESCRIPTION "Control table for FXO."
    ::= { aprisaXEObjects 140 }

aprisaXEFXOControlTableEntry OBJECT-TYPE
    SYNTAX      AprisaXEFXOControlTableEntry
    MAX-ACCESS  not-accessible
    STATUS      current
    DESCRIPTION "Entries for FXO table."
    INDEX       { aprisaXEFXOControlSlotIndex }
    ::= { aprisaXEFXOControlTable 1 }

AprisaXEFXOControlTableEntry ::= SEQUENCE {
        aprisaXEFXOControlSlotIndex INTEGER,
        aprisaXEFXOSPMBandwidth     INTEGER,
        aprisaXEFXOSPMFrequency     INTEGER,
        aprisaXEFXOSPMLevel         INTEGER,
        aprisaXEFXOCasMode          INTEGER,
        aprisaXEFXOCasSignal        INTEGER,
        aprisaXEFXOPCMLaw           INTEGER,
        aprisaXEFXOOnHookSpeed      INTEGER,
        aprisaXEFXORingerImpedance  INTEGER,
        aprisaXEFXORingerThreshold  INTEGER,
        aprisaXEFXOLoopCurrentLimit INTEGER,
        aprisaXEFXOMinLoopCurrent   INTEGER,
        aprisaXEFXOTipRingVoltage   INTEGER,
        aprisaXEFXOLineImpedance    INTEGER,
        aprisaXEFXOLineReversal     INTEGER,
        aprisaXEFXOABitFault        INTEGER,
        aprisaXEFXOBBitRing         INTEGER,
        aprisaXEFXOCBitBilling      INTEGER,
        aprisaXEFXODBitReversals    INTEGER,
        aprisaXEFXOEchoCanceller    INTEGER,
        aprisaXEFXOABitOffHook      INTEGER
    }
        
aprisaXEFXOControlSlotIndex OBJECT-TYPE
    SYNTAX      AprisaXESlotNumber
    MAX-ACCESS  read-only
    STATUS      current
    DESCRIPTION "Slot index for FXO Control table."
    ::= { aprisaXEFXOControlTableEntry 1 }
        
aprisaXEFXOSPMBandwidth OBJECT-TYPE
    SYNTAX      INTEGER { perc15 (0),
                          perc35 (1),
                          perc55 (2),
                          perc75 (3)
                }
    MAX-ACCESS  read-write
    STATUS      current
    DESCRIPTION "Set the spm detector bandwidth to 1.5%, 3.5%, 5.5% or 7.5%."
    ::= { aprisaXEFXOControlTableEntry 2 }
        
aprisaXEFXOSPMFrequency OBJECT-TYPE
    SYNTAX      INTEGER { khz12 (0),
                          khz16 (1)
                }
    MAX-ACCESS  read-write
    STATUS      current
    DESCRIPTION "Set the spm detector frequency to 12kHz or 16kHz."
    ::= { aprisaXEFXOControlTableEntry 3 }

aprisaXEFXOSPMLevel OBJECT-TYPE
    SYNTAX      AprisaXEFXSPMLevel
    MAX-ACCESS  read-write
    STATUS      current
    DESCRIPTION "Set the spm detector level 0 to 27 dB."
    ::= { aprisaXEFXOControlTableEntry 4 }
  
aprisaXEFXOCasMode OBJECT-TYPE
    SYNTAX      INTEGER { casxe (0),
                          casse (1),
                          cas4w (2)
                }
    MAX-ACCESS  read-write
    STATUS      current
    DESCRIPTION "Set the CAS mode to XE,SE or 4Wire compatible."
    ::= { aprisaXEFXOControlTableEntry 5 }
        
aprisaXEFXOCasSignal OBJECT-TYPE
    SYNTAX      AprisaXESignalState
    MAX-ACCESS  read-write
    STATUS      obsolete
    DESCRIPTION "Set the CAS signal to normal or invert."
    ::= { aprisaXEFXOControlTableEntry 6 }
        
aprisaXEFXOPCMLaw OBJECT-TYPE
    SYNTAX      AprisaXEPcmLaw
    MAX-ACCESS  read-write
    STATUS      current
    DESCRIPTION "Set the PCM law to A-law or u-law."
    ::= { aprisaXEFXOControlTableEntry 7 }

aprisaXEFXOOnHookSpeed OBJECT-TYPE
    SYNTAX      INTEGER { ohsFast   (0),
                          ohsMedium (1),
                          ohsSlow   (2)
                }
    MAX-ACCESS  read-write
    STATUS      current
    DESCRIPTION "Set the on hook speed to fast, medium or slow."
    ::= { aprisaXEFXOControlTableEntry 8 }

aprisaXEFXORingerImpedance OBJECT-TYPE
    SYNTAX      INTEGER { rzHigh        (0),
                          rxSynthesized (1)
                }
    MAX-ACCESS  read-write
    STATUS      current
    DESCRIPTION "Set the ringer impedance to high or synthesized."
    ::= { aprisaXEFXOControlTableEntry 9 }

aprisaXEFXORingerThreshold OBJECT-TYPE
    SYNTAX      INTEGER { rtLow    (0),
                          rtMedium (1),
                          rtHigh   (2)
                }
    MAX-ACCESS  read-write
    STATUS      current
    DESCRIPTION "Set the ringer threshold to low, medium or high."
    ::= { aprisaXEFXOControlTableEntry 10 }

aprisaXEFXOLoopCurrentLimit OBJECT-TYPE
    SYNTAX      INTEGER { ilimOff (0),
                          ilimOn  (1)
                }
    MAX-ACCESS  read-write
    STATUS      current
    DESCRIPTION "Set the loop current limiter to off or on."
    ::= { aprisaXEFXOControlTableEntry 11 }

aprisaXEFXOMinLoopCurrent OBJECT-TYPE
    SYNTAX      INTEGER { miniLow    (0),
                          miniMedium (1),
                          miniHigh   (2)
                }
    MAX-ACCESS  read-write
    STATUS      current
    DESCRIPTION "Set the min loop current to low, medium or high."
    ::= { aprisaXEFXOControlTableEntry 12 }

aprisaXEFXOTipRingVoltage OBJECT-TYPE
    SYNTAX      INTEGER { dcvLow    (0),
                          dcvMedium (1),
                          dcvHigh   (2)
                }
    MAX-ACCESS  read-write
    STATUS      current
    DESCRIPTION "Set the tip ring voltage to low, medium or high."
    ::= { aprisaXEFXOControlTableEntry 13 }

aprisaXEFXOLineImpedance OBJECT-TYPE
    SYNTAX      INTEGER { acim0  (0),
                          acim1  (1),
                          acim11 (2),
                          acim13 (3),
                          acim3  (4),
                          acim2  (5),
                          acim4  (6),
                          acim9  (7),
                          acim10 (8)
                }
    MAX-ACCESS  read-write
    STATUS      current
    DESCRIPTION "Set the line impedance to 600 Ohms, 900 Ohms,
                 600 Ohms + 2.16 uF, 900 Ohms + 2.16 uF,
                 TN12 - 220 Ohms + (820 Ohms || 120 nF),
                 TBR21 - 270 Ohms + (750 Ohms || 150 nF),
                 BT3 - 370 Ohms + (620 Ohms || 310 nF),
                 BT Network - 320 Ohms + (1050 Ohms || 210 nF),
                 China - 200 Ohms + (680 Ohms || 100 nF)"
    ::= { aprisaXEFXOControlTableEntry 14 }

aprisaXEFXOLineReversal OBJECT-TYPE
    SYNTAX      INTEGER { fxoLineRevOn  (0),
                          fxoLineRevOff (1)
                }
    MAX-ACCESS  read-write
    STATUS      obsolete
    DESCRIPTION "Set the line reversal on/off."
    ::= { aprisaXEFXOControlTableEntry 15 }

aprisaXEFXOABitFault OBJECT-TYPE
    SYNTAX      AprisaXE2WireSignalState
    MAX-ACCESS  read-write
    STATUS      current
    DESCRIPTION "Set the CAS A fault bit to
                 Transparent Normal, Transparent Inverted,
                 Forced Normal or Forced Inverted."
    ::= { aprisaXEFXOControlTableEntry 16 }

aprisaXEFXOBBitRing OBJECT-TYPE
    SYNTAX      AprisaXE2WireSignalState
    MAX-ACCESS  read-write
    STATUS      current
    DESCRIPTION "Set the CAS B ring bit to
                 Transparent Normal, Transparent Inverted,
                 Forced Normal or Forced Inverted."
    ::= { aprisaXEFXOControlTableEntry 17 }

aprisaXEFXOCBitBilling OBJECT-TYPE
    SYNTAX      AprisaXE2WireSignalState
    MAX-ACCESS  read-write
    STATUS      current
    DESCRIPTION "Set the CAS C billing bit to
                 Transparent Normal, Transparent Inverted,
                 Forced Normal or Forced Inverted."
    ::= { aprisaXEFXOControlTableEntry 18 }

aprisaXEFXODBitReversals OBJECT-TYPE
    SYNTAX      AprisaXE2WireSignalState
    MAX-ACCESS  read-write
    STATUS      current
    DESCRIPTION "Set the CAS D reversals bit to
                 Transparent Normal, Transparent Inverted,
                 Forced Normal or Forced Inverted."
    ::= { aprisaXEFXOControlTableEntry 19 }

aprisaXEFXOEchoCanceller OBJECT-TYPE
    SYNTAX      INTEGER { fxoEchoCancellerOff       (0),
                          fxoEchoCancellerOn        (1),
                          fxoEchoCancellerAutoG164  (2),
                          fxoEchoCancellerAutoG165  (3),
                          fxoEchoCancellerReserved1 (4),
                          fxoEchoCancellerReserved2 (5),
                          fxoEchoCancellerReserved3 (6)
                }
    MAX-ACCESS  read-write
    STATUS      current
    DESCRIPTION "Set the echo canceller to off, on or auto. The
                 reserved values are for internal use only and
                 cannot be set via SNMP."
    ::= { aprisaXEFXOControlTableEntry 20 }
        
aprisaXEFXOABitOffHook OBJECT-TYPE
    SYNTAX      AprisaXE2WireSignalState
    MAX-ACCESS  read-write
    STATUS      current
    DESCRIPTION "Set the CAS A off hook bit to
                 Transparent Normal, Transparent Inverted,
                 Forced Normal or Forced Inverted."
    ::= { aprisaXEFXOControlTableEntry 21 }

-- ***************************************************************************
-- End FXO
-- ***************************************************************************



-- ***************************************************************************
-- Backplane Connections
-- ***************************************************************************

aprisaXEBackplaneConnectionTable OBJECT-TYPE
    SYNTAX      SEQUENCE OF AprisaXEBackplaneConnectionTableEntry
    MAX-ACCESS  not-accessible
    STATUS      current
    DESCRIPTION "Table of AprisaXE Cross connections."
    ::= { aprisaXEObjects 150 }

aprisaXEBackplaneConnectionTableEntry OBJECT-TYPE
    SYNTAX      AprisaXEBackplaneConnectionTableEntry
    MAX-ACCESS  not-accessible
    STATUS      current
    DESCRIPTION "Table entries define a circuit carried ove a TDM bus."
    INDEX       { aprisaXEBackplaneConnectionID }
    ::= { aprisaXEBackplaneConnectionTable 1 }

AprisaXEBackplaneConnectionTableEntry ::= SEQUENCE {
        aprisaXEBackplaneConnectionID   INTEGER,
        aprisaXEBackplaneTdmBus         INTEGER,
        aprisaXEBackplaneStartBitPos    INTEGER,
        aprisaXEBackplaneLength         INTEGER,
        aprisaXEBackplaneInterface      INTEGER
    }

aprisaXEBackplaneConnectionID OBJECT-TYPE
    SYNTAX      AprisaXEConnectionID
    MAX-ACCESS  read-write
    STATUS      current
    DESCRIPTION "Handle to associate circuits with backplane connections."
    ::= { aprisaXEBackplaneConnectionTableEntry 1 }

aprisaXEBackplaneTdmBus OBJECT-TYPE
    SYNTAX      AprisaXETdmBus
    MAX-ACCESS  read-write
    STATUS      current
    DESCRIPTION "TDM Bus to switch: busA - busD."
    ::= { aprisaXEBackplaneConnectionTableEntry 2 }

aprisaXEBackplaneStartBitPos OBJECT-TYPE
    SYNTAX      INTEGER (0..2047)
    MAX-ACCESS  read-write
    STATUS      current
    DESCRIPTION "Start bit position on the associated TDM bus (0 - 2047)."
    DEFVAL      { 0 }
    ::= { aprisaXEBackplaneConnectionTableEntry 3 }

aprisaXEBackplaneLength OBJECT-TYPE
    SYNTAX      INTEGER (0..2047)
    MAX-ACCESS  read-write
    STATUS      current
    DESCRIPTION "Number of bits to place on the backplane TDM bus (0 - 2047)."
    DEFVAL      { 0 }
    ::= { aprisaXEBackplaneConnectionTableEntry 4 }

aprisaXEBackplaneInterface OBJECT-TYPE
    SYNTAX      AprisaXEInterfaceCnxnType
    MAX-ACCESS  read-write
    STATUS      current
    DESCRIPTION "The type of circuit this backplane connection is carrying."
    ::= { aprisaXEBackplaneConnectionTableEntry 5 }


aprisaXEBackplaneControl OBJECT IDENTIFIER ::= { aprisaXEObjects 180 }

aprisaXEBackplaneControlConnectionID OBJECT-TYPE
    SYNTAX      AprisaXEConnectionID
    MAX-ACCESS  read-write
    STATUS      current
    DESCRIPTION "The Backplane Connection ID to add or delete."
    ::= { aprisaXEBackplaneControl 1 }

aprisaXEBackplaneControlTdmBus OBJECT-TYPE
    SYNTAX      AprisaXETdmBus
    MAX-ACCESS  read-write
    STATUS      current
    DESCRIPTION "TDM Bus to switch: busA - busD."
    ::= { aprisaXEBackplaneControl 2 }

aprisaXEBackplaneControlStartBitPos OBJECT-TYPE
    SYNTAX      INTEGER (0..2047)
    MAX-ACCESS  read-write
    STATUS      current
    DESCRIPTION "Start bit position on the associated TDM bus (0 - 2047)."
    DEFVAL      { 0 }
    ::= { aprisaXEBackplaneControl 3 }

aprisaXEBackplaneControlLength OBJECT-TYPE
    SYNTAX      INTEGER (0..2048)
    MAX-ACCESS  read-write
    STATUS      current
    DESCRIPTION "Number of bits to place on the backplane TDM bus (0 - 2048)."
    DEFVAL      { 0 }
    ::= { aprisaXEBackplaneControl 4 }

aprisaXEBackplaneControlInterface OBJECT-TYPE
    SYNTAX      AprisaXEInterfaceCnxnType
    MAX-ACCESS  read-write
    STATUS      current
    DESCRIPTION "The type of circuit this backplane connection is carrying."
    ::= { aprisaXEBackplaneControl 5 }

aprisaXEBackplaneControlCommand OBJECT-TYPE
    SYNTAX      INTEGER { noCommand     (0),
                          addCommand    (1),
                          deleteCommand (2)
                }
    MAX-ACCESS  read-write
    STATUS      current
    DESCRIPTION "Command to send to act upon rows in the Backplane
                 Connection table."
    ::= { aprisaXEBackplaneControl 6 }

-- ***************************************************************************
-- End Backplane Connections
-- ***************************************************************************



-- ***************************************************************************
-- Aggregate Connections
-- ***************************************************************************

aprisaXEAggregateConnectionTable OBJECT-TYPE
    SYNTAX      SEQUENCE OF AprisaXEAggregateConnectionTableEntry
    MAX-ACCESS  not-accessible
    STATUS      current
    DESCRIPTION "Table of Aggregated backplane connections used for
                 interfaces with further cross-connection capability."
    ::= { aprisaXEObjects 160 }

aprisaXEAggregateConnectionTableEntry OBJECT-TYPE
    SYNTAX      AprisaXEAggregateConnectionTableEntry
    MAX-ACCESS  not-accessible
    STATUS      current
    DESCRIPTION ""
    INDEX       { aprisaXEAggregateBackplaneID,
                  aprisaXEAggregateInterfaceID,
                  aprisaXEAggregateStartBitPos
    }
    ::= { aprisaXEAggregateConnectionTable 1 }

AprisaXEAggregateConnectionTableEntry ::= SEQUENCE {
        aprisaXEAggregateBackplaneID    Integer32,
        aprisaXEAggregateInterfaceID    Integer32,
        aprisaXEAggregateStartBitPos    INTEGER,
        aprisaXEAggregateLength         INTEGER,
        aprisaXEAggregateOffset         INTEGER,
        aprisaXEAggregateE1Port         INTEGER
    }

aprisaXEAggregateBackplaneID OBJECT-TYPE
    SYNTAX      Integer32
    MAX-ACCESS  read-only
    STATUS      current
    DESCRIPTION "Backplane Connection identifier."
    ::= { aprisaXEAggregateConnectionTableEntry 1 }

aprisaXEAggregateInterfaceID OBJECT-TYPE
    SYNTAX      Integer32
    MAX-ACCESS  read-only
    STATUS      current
    DESCRIPTION ""
    ::= { aprisaXEAggregateConnectionTableEntry 2 }

aprisaXEAggregateStartBitPos OBJECT-TYPE
    SYNTAX      INTEGER (0..2047)
    MAX-ACCESS  read-only
    STATUS      current
    DESCRIPTION "Start bit position of the data coming into the
                 cross-connection device (SWITI) for this interface connection."
    ::= { aprisaXEAggregateConnectionTableEntry 3 }

aprisaXEAggregateLength OBJECT-TYPE
    SYNTAX      INTEGER (0..2047)
    MAX-ACCESS  read-only
    STATUS      current
    DESCRIPTION "Number of bits required for this interface connection."
    ::= { aprisaXEAggregateConnectionTableEntry 4 }

aprisaXEAggregateOffset OBJECT-TYPE
    SYNTAX      INTEGER (0..2047)
    MAX-ACCESS  read-only
    STATUS      current
    DESCRIPTION "Offset into the aggregate connection where this
                 interface connection is placed."
    ::= { aprisaXEAggregateConnectionTableEntry 5 }

aprisaXEAggregateE1Port OBJECT-TYPE
    SYNTAX      AprisaXEPortNumber
    MAX-ACCESS  read-only
    STATUS      current
    DESCRIPTION "Port number associated with this connection."
    ::= { aprisaXEAggregateConnectionTableEntry 6 }
        

aprisaXEAggregateControl OBJECT IDENTIFIER ::= { aprisaXEObjects 170 }

aprisaXEAggregateControlBackplaneID OBJECT-TYPE
    SYNTAX      INTEGER (0..2047)
    MAX-ACCESS  read-write
    STATUS      current
    DESCRIPTION "The backplane ID to add or delete."
    ::= { aprisaXEAggregateControl 1 }

aprisaXEAggregateControlInterfaceID OBJECT-TYPE
    SYNTAX      INTEGER (0..2047)
    MAX-ACCESS  read-write
    STATUS      current
    DESCRIPTION "Aggregate connection identifier."
    ::= { aprisaXEAggregateControl 2 }

aprisaXEAggregateControlStartBitPos OBJECT-TYPE
    SYNTAX      INTEGER (0..2047)
    MAX-ACCESS  read-write
    STATUS      current
    DESCRIPTION "Start bit position of the data coming into the
                 cross-connection device (SWITI) for this interface connection."
    ::= { aprisaXEAggregateControl 3 }
    
aprisaXEAggregateControlLength OBJECT-TYPE
    SYNTAX      INTEGER (0..2047)
    MAX-ACCESS  read-write
    STATUS      current
    DESCRIPTION "Number of bits required for this interface connection."
    ::= { aprisaXEAggregateControl 4 }
    
aprisaXEAggregateControlOffset OBJECT-TYPE
    SYNTAX      INTEGER (0..2047)
    MAX-ACCESS  read-write
    STATUS      current
    DESCRIPTION "Offset into the aggregate connection where this
                 interface connection is placed."
    ::= { aprisaXEAggregateControl 5 }
        
aprisaXEAggregateControlCommand OBJECT-TYPE
    SYNTAX      INTEGER { noCommand     (0),
                          addCommand    (1),
                          deleteCommand (2)
                }
    MAX-ACCESS  read-write
    STATUS      current
    DESCRIPTION "Command to send to act upon the rows in the Aggregate
                 Connection table."
    ::= { aprisaXEAggregateControl 6 }

-- ***************************************************************************
-- End Aggregate Connections
-- ***************************************************************************



-- ***************************************************************************
-- Cross Connect Control
-- ***************************************************************************

aprisaXECrossConnectControl OBJECT IDENTIFIER ::= { aprisaXEObjects 200 }

aprisaXECrossConnectControlCommand OBJECT-TYPE
    SYNTAX      INTEGER { noCommand       (0),
                          deleteCommand   (1),
                          activateCommand (2)
                }
    MAX-ACCESS  read-write
    STATUS      current
    DESCRIPTION "Command to send to delete all current cross-connections or
                 to activate a new set of cross-connections."
    ::= { aprisaXECrossConnectControl 1 }

aprisaXEMotherboardExtendedModeCapable OBJECT-TYPE
    SYNTAX      INTEGER { extModeNo  (0),
                          extModeYes (1)
                }
    MAX-ACCESS  read-only
    STATUS      current
    DESCRIPTION "Allows the cross connect application to determine whether
                 to stripe cross connections or not."
    ::= { aprisaXECrossConnectControl 2 }

aprisaXEEthernetActivationStatus OBJECT-TYPE
    SYNTAX      AprisaXECCActivationStatus
    MAX-ACCESS  read-only
    STATUS      current
    DESCRIPTION "Ethernet activation status i.e activated, failed or
                 currently busy activating."
    ::= { aprisaXECrossConnectControl 3 }

-- ***************************************************************************
-- End Cross Connect Control
-- ***************************************************************************



-- ***************************************************************************
-- Cross Connect Activation Status Table
-- ***************************************************************************

aprisaXECCActivationStatusTable OBJECT-TYPE
    SYNTAX      SEQUENCE OF AprisaXECCActivationStatusTableEntry
    MAX-ACCESS  not-accessible
    STATUS      current
    DESCRIPTION "CC Activation status table."
    ::= { aprisaXEObjects 202 }

aprisaXECCActivationStatusTableEntry OBJECT-TYPE
    SYNTAX      AprisaXECCActivationStatusTableEntry
    MAX-ACCESS  not-accessible
    STATUS      current
    DESCRIPTION "Entries for CC Activation status table."
    INDEX       { aprisaXECCActivationStatusSlotIndex }
    ::= { aprisaXECCActivationStatusTable 1 }

AprisaXECCActivationStatusTableEntry ::= SEQUENCE {
        aprisaXECCActivationStatusSlotIndex INTEGER,
        aprisaXECCActivationStatus          INTEGER
    }

aprisaXECCActivationStatusSlotIndex OBJECT-TYPE
    SYNTAX      AprisaXESlotNumber
    MAX-ACCESS  read-only
    STATUS      current
    DESCRIPTION "Slot index for CC Activation Status table."
    ::= { aprisaXECCActivationStatusTableEntry 1 }

aprisaXECCActivationStatus OBJECT-TYPE
    SYNTAX      AprisaXECCActivationStatus
    MAX-ACCESS  read-only
    STATUS      current
    DESCRIPTION "Cross-connect activation status i.e activated, failed or
                 currently busy activating."
    ::= { aprisaXECCActivationStatusTableEntry 2 }

-- ***************************************************************************
-- End Cross Connect Activation Status Table
-- ***************************************************************************



-- ***************************************************************************
-- FXS
-- ***************************************************************************

aprisaXEFXSPortControlTable OBJECT-TYPE
    SYNTAX      SEQUENCE OF AprisaXEFXSPortControlTableEntry
    MAX-ACCESS  not-accessible
    STATUS      current
    DESCRIPTION "Port Control table for FXS."
    ::= { aprisaXEObjects 190 }

aprisaXEFXSPortControlTableEntry OBJECT-TYPE
    SYNTAX      AprisaXEFXSPortControlTableEntry
    MAX-ACCESS  not-accessible
    STATUS      current
    DESCRIPTION "Entries for FXS table."
    INDEX       { aprisaXEFXSPortControlSlotIndex,
                  aprisaXEFXSPortIndex
    }
    ::= { aprisaXEFXSPortControlTable 1 }

AprisaXEFXSPortControlTableEntry ::= SEQUENCE {
        aprisaXEFXSPortControlSlotIndex     INTEGER,
        aprisaXEFXSPortIndex                INTEGER,
        aprisaXEFXSLoopback                 INTEGER,
        aprisaXEFXSAdpcmCompression         INTEGER,
        aprisaXEFXSRxGain                   INTEGER,
        aprisaXEFXSTxGain                   INTEGER,
        aprisaXEFXSConnectionID             INTEGER,
        aprisaXEFXSSignallingConnectionID   INTEGER,
        aprisaXEFXSInputLevel               INTEGER,
        aprisaXEFXSOutputLevel              INTEGER,
        aprisaXEFXSPathMute                 INTEGER
    }

aprisaXEFXSPortControlSlotIndex OBJECT-TYPE
    SYNTAX      AprisaXESlotNumber
    MAX-ACCESS  read-only
    STATUS      current
    DESCRIPTION "Slot index for FXS Control table."
    ::= { aprisaXEFXSPortControlTableEntry 1 }

aprisaXEFXSPortIndex OBJECT-TYPE
    SYNTAX      AprisaXEPortNumber
    MAX-ACCESS  read-only
    STATUS      current
    DESCRIPTION "Port index for FXS Control table."
    ::= { aprisaXEFXSPortControlTableEntry 2 }

aprisaXEFXSLoopback OBJECT-TYPE
    SYNTAX      FourRFLoopback
    MAX-ACCESS  read-write
    STATUS      current
    DESCRIPTION "Loopback control on or off for ports."
    ::= { aprisaXEFXSPortControlTableEntry 3 }

aprisaXEFXSAdpcmCompression OBJECT-TYPE
    SYNTAX      AprisaXEAdpcmCompression
    MAX-ACCESS  read-write
    STATUS      current
    DESCRIPTION "ADPCM compression 16, 24, 32, 64 kbps or none."
    DEFVAL      { none }
    ::= { aprisaXEFXSPortControlTableEntry 4 }

aprisaXEFXSRxGain OBJECT-TYPE
    SYNTAX      INTEGER { fxsrxpos30 (0),
                          fxsrxpos25 (1),
                          fxsrxpos20 (2),
                          fxsrxpos15 (3),
                          fxsrxpos10 (4),
                          fxsrxpos05 (5),
                          fxsrxpos0  (6),
                          fxsrxneg05 (7),
                          fxsrxneg10 (8),
                          fxsrxneg15 (9),
                          fxsrxneg20 (10),
                          fxsrxneg25 (11),
                          fxsrxneg30 (12),
                          fxsrxneg35 (13),
                          fxsrxneg40 (14),
                          fxsrxneg45 (15),
                          fxsrxneg50 (16),
                          fxsrxneg55 (17),
                          fxsrxneg60 (18),
                          fxsrxneg65 (19),
                          fxsrxneg70 (20),
                          fxsrxneg75 (21),
                          fxsrxneg80 (22),
                          fxsrxneg85 (23),
                          fxsrxneg90 (24),
                          fxsrxneg95 (25)
                }
    MAX-ACCESS  read-write
    STATUS      obsolete
    DESCRIPTION "Rx gain -9.5 dB to +3 dB in 0.5 dB steps."
    ::= { aprisaXEFXSPortControlTableEntry 5 }

aprisaXEFXSTxGain OBJECT-TYPE
    SYNTAX      INTEGER { fxstxpos95 (0),
                          fxstxpos90 (1),
                          fxstxpos85 (2),
                          fxstxpos80 (3),
                          fxstxpos75 (4),
                          fxstxpos70 (5),
                          fxstxpos65 (6),
                          fxstxpos60 (7),
                          fxstxpos55 (8),
                          fxstxpos50 (9),
                          fxstxpos45 (10),
                          fxstxpos40 (11),
                          fxstxpos35 (12),
                          fxstxpos30 (13),
                          fxstxpos25 (14),
                          fxstxpos20 (15),
                          fxstxpos15 (16),
                          fxstxpos10 (17),
                          fxstxpos05 (18),
                          fxstxpos0  (19),
                          fxstxneg05 (20),
                          fxstxneg10 (21),
                          fxstxneg15 (22),
                          fxstxneg20 (23),
                          fxstxneg25 (24),
                          fxstxneg30 (25)
                }
    MAX-ACCESS  read-write
    STATUS      obsolete
    DESCRIPTION "Tx gain -3 dB to 9.5 dB in 0.5 dB steps."
    ::= { aprisaXEFXSPortControlTableEntry 6 }
    
aprisaXEFXSConnectionID OBJECT-TYPE
    SYNTAX      AprisaXEConnectionID
    MAX-ACCESS  read-write
    STATUS      current
    DESCRIPTION "Associated cross-connect Backplane Connection ID."
    ::= { aprisaXEFXSPortControlTableEntry 7 }

aprisaXEFXSSignallingConnectionID OBJECT-TYPE
    SYNTAX      AprisaXEConnectionID
    MAX-ACCESS  read-write
    STATUS      current
    DESCRIPTION "Associated signalling cross-connect Backplane Connection ID."
    ::= { aprisaXEFXSPortControlTableEntry 8 }
    
aprisaXEFXSInputLevel OBJECT-TYPE
    SYNTAX      AprisaXEFXSInputLevel
    MAX-ACCESS  read-write
    STATUS      current
    DESCRIPTION "Input Level -9.0 dBr to +3.0 dBr in half dB steps."
    ::= { aprisaXEFXSPortControlTableEntry 9 }

aprisaXEFXSOutputLevel OBJECT-TYPE
    SYNTAX      AprisaXEFXSOutputLevel
    MAX-ACCESS  read-write
    STATUS      current
    DESCRIPTION "Output Level -9.5 dBr to +2.5 dBr in 0.5 dB steps."
    ::= { aprisaXEFXSPortControlTableEntry 10 }

aprisaXEFXSPathMute OBJECT-TYPE
    SYNTAX      AprisaXEFXSPathMute
    MAX-ACCESS  read-write
    STATUS      current
    DESCRIPTION "Applies DFXS Mute Function - No Mute, Mute Rx or Mute Tx."
    ::= { aprisaXEFXSPortControlTableEntry 11 }

--
-- end of table
--    

aprisaXEFXSControlTable OBJECT-TYPE
    SYNTAX      SEQUENCE OF AprisaXEFXSControlTableEntry
    MAX-ACCESS  not-accessible
    STATUS      current
    DESCRIPTION "Control table for FXS."
    ::= { aprisaXEObjects 195 }

aprisaXEFXSControlTableEntry OBJECT-TYPE
    SYNTAX      AprisaXEFXSControlTableEntry
    MAX-ACCESS  not-accessible
    STATUS      current
    DESCRIPTION "Entries for FXS table."
    INDEX       { aprisaXEFXSControlSlotIndex }
    ::= { aprisaXEFXSControlTable 1 }

AprisaXEFXSControlTableEntry ::= SEQUENCE {
        aprisaXEFXSControlSlotIndex         INTEGER,
        aprisaXEFXSPCMLaw                   INTEGER,
        aprisaXEFXSEchoCanceller            INTEGER,
        aprisaXEFXSBillingToneFrequency     INTEGER,
        aprisaXEFXSBillingToneAmplitude     INTEGER,
        aprisaXEFXSBillingToneDecay         INTEGER,
        aprisaXEFXSRingerFrequency          INTEGER,
        aprisaXEFXSRingerAmplitude          INTEGER,
        aprisaXEFXSLineImpedance            INTEGER,
        aprisaXEFXSCasMode                  INTEGER,
        aprisaXEFXSCasSignal                INTEGER,
        aprisaXEFXSTransHybridBalance       INTEGER,
        aprisaXEFXSLineReversal             INTEGER,
        aprisaXEFXSCalibrate                INTEGER,
        aprisaXEFXSABitFault                INTEGER,
        aprisaXEFXSBBitRing                 INTEGER,
        aprisaXEFXSCBitBilling              INTEGER,
        aprisaXEFXSDBitReversals            INTEGER,
        aprisaXEFXSLoopParameters           INTEGER,
        aprisaXEFXSABitOffHook              INTEGER
    }

aprisaXEFXSControlSlotIndex OBJECT-TYPE
    SYNTAX      AprisaXESlotNumber
    MAX-ACCESS  read-only
    STATUS      current
    DESCRIPTION "Slot index for FXS Control table."
    ::= { aprisaXEFXSControlTableEntry 1 }

aprisaXEFXSPCMLaw OBJECT-TYPE
    SYNTAX      AprisaXEPcmLaw
    MAX-ACCESS  read-write
    STATUS      current
    DESCRIPTION "Set the PCM law to A-law or u-law."
    ::= { aprisaXEFXSControlTableEntry 2 }

aprisaXEFXSEchoCanceller OBJECT-TYPE
    SYNTAX      INTEGER { echoCancellerOff (0),
                          echoCancellerOn  (1)
                }
    MAX-ACCESS  read-write
    STATUS      current
    DESCRIPTION "Set the echo canceller to on or off."
    ::= { aprisaXEFXSControlTableEntry 3 }

aprisaXEFXSBillingToneFrequency OBJECT-TYPE
    SYNTAX      INTEGER { khz12 (0),
                          khz16 (1)
                }
    MAX-ACCESS  read-write
    STATUS      current
    DESCRIPTION "Set the billing tone generator frequency to 12kHz or 16kHz."
    ::= { aprisaXEFXSControlTableEntry 4 }

aprisaXEFXSBillingToneAmplitude OBJECT-TYPE
    SYNTAX      INTEGER { mv400 (6),
                          mv300 (0),
                          mv250 (1),
                          mv200 (2),
                          mv150 (3),
                          mv100 (4),
                          mv50  (5)
                }
    MAX-ACCESS  read-write
    STATUS      current
    DESCRIPTION "Set the billing tone generator amplitude to 400mV, 300mV,
                 250mV, 200mV, 150mV, 100mV or 50mV. Note, that software
                 release 7.3.x only supports 400mV, 300mV, 200mV and 100mV."
    ::= { aprisaXEFXSControlTableEntry 5 }

aprisaXEFXSBillingToneDecay OBJECT-TYPE
    SYNTAX      INTEGER { ms02 (0),
                          ms05 (1),
                          ms1  (2),
                          ms2  (3),
                          ms5  (4),
                          ms10 (5),
                          ms20 (6)
                }
    MAX-ACCESS  read-write
    STATUS      current
    DESCRIPTION "Set the billing tone generator attack decay ramp
                 to 0.2ms, 0.5ms, 1ms, 2ms, 5ms, 10ms or 20ms."
    ::= { aprisaXEFXSControlTableEntry 6 }

aprisaXEFXSRingerFrequency OBJECT-TYPE
    SYNTAX      INTEGER { hz17 (0),
                          hz25 (1),
                          hz50 (2)
                }
    MAX-ACCESS  read-write
    STATUS      current
    DESCRIPTION "Set the ringer frequency to 17Hz, 25Hz or 50Hz."
    ::= { aprisaXEFXSControlTableEntry 7 }

aprisaXEFXSRingerAmplitude OBJECT-TYPE
    SYNTAX      INTEGER { vrms40 (0),
                          vrms45 (1),
                          vrms50 (2),
                          vrms55 (3),
                          vrms60 (4)
                }
    MAX-ACCESS  read-write
    STATUS      current
    DESCRIPTION "Set the ringer amplitude to 40 V RMS, 45 V RMS,
                 50 V RMS, 55 V RMS or 60 V RMS."
    ::= { aprisaXEFXSControlTableEntry 8 }

aprisaXEFXSLineImpedance OBJECT-TYPE
    SYNTAX      INTEGER { lineImpd1 (0),
                          lineImpd2 (1),
                          lineImpd3 (2),
                          lineImpd4 (3),
                          lineImpd5 (4),
                          lineImpd6 (5),
                          lineImpd7 (6)
                }
    MAX-ACCESS  read-write
    STATUS      current
    DESCRIPTION "Set the subscriber line impedance to 600 Ohms, 900 Ohms,
                 600 Ohms + 2.16 uF, 900 Ohms + 2.16 uF,
                 TN12 - 220 Ohms + (820 Ohms || 120 nF),
                 TBR21 - 270 Ohms + (750 Ohms || 150 nF),
                 BT3 - 370 Ohms + (620 Ohms || 310 nF)"
    ::= { aprisaXEFXSControlTableEntry 9 }

aprisaXEFXSCasMode OBJECT-TYPE
    SYNTAX      INTEGER { casxe (0),
                          casse (1),
                          cas4w (2)
                }
    MAX-ACCESS  read-write
    STATUS      current
    DESCRIPTION "Set the CAS mode to XE,SE or 4Wire compatible."
    ::= { aprisaXEFXSControlTableEntry 10 }

aprisaXEFXSCasSignal OBJECT-TYPE
    SYNTAX      AprisaXESignalState
    MAX-ACCESS  read-write
    STATUS      obsolete
    DESCRIPTION "Set the CAS signal to normal or invert."
    ::= { aprisaXEFXSControlTableEntry 11 }
    
aprisaXEFXSTransHybridBalance OBJECT-TYPE
    SYNTAX      INTEGER { transHybridBal1 (0),
                          transHybridBal2 (1),
                          transHybridBal3 (2),
                          transHybridBal4 (3),
                          transHybridBal5 (4),
                          transHybridBal6 (5),
                          transHybridBal7 (6),
                          transHybridBal8 (7)
                }
    MAX-ACCESS  read-write
    STATUS      current
    DESCRIPTION "Set the trans hybrid balance to 4.08dB, 2.5dB,
                 1.16dB, 0dB, -1.02dB, -1.94dB, -2.77dB, Off"
    ::= { aprisaXEFXSControlTableEntry 12 }
    
aprisaXEFXSLineReversal OBJECT-TYPE
    SYNTAX      INTEGER { fxsLineRevOn  (0),
                          fxsLineRevOff (1)
                }
    MAX-ACCESS  read-write
    STATUS      obsolete
    DESCRIPTION "Set the line reversal on/off."
    ::= { aprisaXEFXSControlTableEntry 13 }

aprisaXEFXSCalibrate OBJECT-TYPE
    SYNTAX      INTEGER { fxsCalibrateNo  (0),
                          fxsCalibrateYes (1)
                }
    MAX-ACCESS  read-write
    STATUS      current
    DESCRIPTION "Recalibrate the card yes/no."
    ::= { aprisaXEFXSControlTableEntry 14 }

aprisaXEFXSABitFault OBJECT-TYPE
    SYNTAX      AprisaXE2WireSignalState
    MAX-ACCESS  read-write
    STATUS      current
    DESCRIPTION "Set the CAS A fault bit to
                 Transparent Normal, Transparent Inverted,
                 Forced Normal or Forced Inverted."
    ::= { aprisaXEFXSControlTableEntry 15 }

aprisaXEFXSBBitRing OBJECT-TYPE
    SYNTAX      AprisaXE2WireSignalState
    MAX-ACCESS  read-write
    STATUS      current
    DESCRIPTION "Set the CAS B ring bit to
                 Transparent Normal, Transparent Inverted,
                 Forced Normal or Forced Inverted."
    ::= { aprisaXEFXSControlTableEntry 16 }

aprisaXEFXSCBitBilling OBJECT-TYPE
    SYNTAX      AprisaXE2WireSignalState
    MAX-ACCESS  read-write
    STATUS      current
    DESCRIPTION "Set the CAS C billing bit to
                 Transparent Normal, Transparent Inverted,
                 Forced Normal or Forced Inverted."
    ::= { aprisaXEFXSControlTableEntry 17 }

aprisaXEFXSDBitReversals OBJECT-TYPE
    SYNTAX      AprisaXE2WireSignalState
    MAX-ACCESS  read-write
    STATUS      current
    DESCRIPTION "Set the CAS D reversals bit to
                 Transparent Normal, Transparent Inverted,
                 Forced Normal or Forced Inverted."
    ::= { aprisaXEFXSControlTableEntry 18 }

aprisaXEFXSLoopParameters OBJECT-TYPE
    SYNTAX      INTEGER { fxsLoopParamDefault  (0),
                          fxsLoopParamTelkomSA (1)
                }
    MAX-ACCESS  read-write
    STATUS      current
    DESCRIPTION "Set the loop parameters to 'default' or 'Telkom SA Limited'."
    ::= { aprisaXEFXSControlTableEntry 19 }

aprisaXEFXSABitOffHook OBJECT-TYPE
    SYNTAX      AprisaXE2WireSignalState
    MAX-ACCESS  read-write
    STATUS      current
    DESCRIPTION "Set the CAS A off hook bit to
                 Transparent Normal, Transparent Inverted,
                 Forced Normal or Forced Inverted."
    ::= { aprisaXEFXSControlTableEntry 20 }

-- ***************************************************************************
-- End FXS
-- ***************************************************************************



-- ***************************************************************************
-- HSS
-- ***************************************************************************

aprisaXEHSSControlTable OBJECT-TYPE
    SYNTAX      SEQUENCE OF AprisaXEHSSControlTableEntry
    MAX-ACCESS  not-accessible
    STATUS      current
    DESCRIPTION "Control table for HSS."
    ::= { aprisaXEObjects 207 }

aprisaXEHSSControlTableEntry OBJECT-TYPE
    SYNTAX      AprisaXEHSSControlTableEntry
    MAX-ACCESS  not-accessible
    STATUS      current
    DESCRIPTION "Entries for HSS table."
    INDEX       { aprisaXEHSSControlSlotIndex }
    ::= { aprisaXEHSSControlTable 1 }

AprisaXEHSSControlTableEntry ::= SEQUENCE {
        aprisaXEHSSControlSlotIndex     INTEGER,
        aprisaXEHSSConnectionID         INTEGER,
        aprisaXEHSSSignallingID         INTEGER,
        aprisaXEHSSEquipmentMode        INTEGER,
        aprisaXEHSSLoopback             INTEGER,
        aprisaXEHSSNetworkClockSource   INTEGER,
        aprisaXEHSSSerialBaudRate       INTEGER,
        aprisaXEHSSV110BaudRate         INTEGER,
        aprisaXEHSSSendHandshakingMode  INTEGER,
        aprisaXEHSSDataReadyMode        INTEGER,
        aprisaXEHSSCarrierDetectMode    INTEGER,
        aprisaXEHSSClockSelection       INTEGER,
        aprisaXEHSSXTxCEnabled          INTEGER,
        aprisaXEHSSSerialMode           INTEGER
    }

aprisaXEHSSControlSlotIndex OBJECT-TYPE
    SYNTAX      AprisaXESlotNumber
    MAX-ACCESS  read-only
    STATUS      current
    DESCRIPTION "Slot index for HSS Control Table."
    ::= { aprisaXEHSSControlTableEntry 1 }

aprisaXEHSSConnectionID OBJECT-TYPE
    SYNTAX      AprisaXEConnectionID
    MAX-ACCESS  read-write
    STATUS      current
    DESCRIPTION "Backplane Connection ID for data connection."
    ::= { aprisaXEHSSControlTableEntry 2 }

aprisaXEHSSSignallingID OBJECT-TYPE
    SYNTAX      AprisaXEConnectionID
    MAX-ACCESS  read-write
    STATUS      current
    DESCRIPTION "Backplane connection ID for signalling/control connection."
    ::= { aprisaXEHSSControlTableEntry 3 }

aprisaXEHSSEquipmentMode OBJECT-TYPE
    SYNTAX      AprisaXESerialEquipmentMode
    MAX-ACCESS  read-only
    STATUS      current
    DESCRIPTION "Terminal Equipment mode, DCE or DTE, this is a direct reflection
                 of the equipment mode based on the type of cable currently
                 connected. The value is not defined if no cable is attached."
    ::= { aprisaXEHSSControlTableEntry 4 }

aprisaXEHSSLoopback OBJECT-TYPE
    SYNTAX      FourRFLoopback
    MAX-ACCESS  read-write
    STATUS      current
    DESCRIPTION "Interface loopback control."
    DEFVAL      { 0 }
    ::= { aprisaXEHSSControlTableEntry 5 }

aprisaXEHSSNetworkClockSource OBJECT-TYPE
    SYNTAX      FourRFNetworkClockSelect
    MAX-ACCESS  read-write
    STATUS      current
    DESCRIPTION "Controls whether the port drive the clock source or not."
    ::= { aprisaXEHSSControlTableEntry 6 }

aprisaXEHSSSerialBaudRate OBJECT-TYPE
    SYNTAX      INTEGER (1..256)
    MAX-ACCESS  read-write
    STATUS      current
    DESCRIPTION "Serial Baud rate where 1 = 8kbps and 256 = 2Mbps."
    ::= { aprisaXEHSSControlTableEntry 7 }

aprisaXEHSSV110BaudRate OBJECT-TYPE
    SYNTAX      INTEGER { v110-600   (0),
                          v110-1200  (1),
                          v110-2400  (2),
                          v110-4800  (3),
                          v110-7200  (4),
                          v110-9600  (5),
                          v110-12000 (6),
                          v110-14400 (7),
                          v110-19200 (8),
                          v110-24000 (9),
                          v110-28800 (10),
                          v110-38400 (11)
                }
    MAX-ACCESS  read-write
    STATUS      current
    DESCRIPTION "V110 baud rate."
    ::= { aprisaXEHSSControlTableEntry 8 }

aprisaXEHSSSendHandshakingMode OBJECT-TYPE
    SYNTAX      INTEGER { rts-ctsOff                 (0),
                          rts-ctsOn                  (1),
                          rts-ctsCarrier             (2),
                          rts-ctsCarrierRemote       (3),
                          rts-ctsCarrierLocalDCD     (4),
                          rts-ctsCarrierLocalRTS     (5),
                          rts-ctsCarrierLocalRTS1ms  (6),
                          rts-ctsCarrierLocalRTS24ms (7)
                }
    MAX-ACCESS  read-write
    STATUS      current
    DESCRIPTION "Select 1 of 8 RTS/CTS modes of operation."
    ::= { aprisaXEHSSControlTableEntry 9 }

aprisaXEHSSDataReadyMode OBJECT-TYPE
    SYNTAX      INTEGER { dsr-dtrOff           (0),
                          dsr-dtrOn            (1),
                          dsr-dtrCarrier       (2),
                          dsr-dtrCarrierRemote (3)
                }
    MAX-ACCESS  read-write
    STATUS      current
    DESCRIPTION "Select 1 of 8 DSR/DTR modes."
    ::= { aprisaXEHSSControlTableEntry 10 }

aprisaXEHSSCarrierDetectMode OBJECT-TYPE
    SYNTAX      INTEGER { dcdOff              (0),
                          dcdOn               (1),
                          dcdCarrierRemoteDCD (2),
                          dcdCarrierLocalDTR  (3)
                }
    MAX-ACCESS  read-write
    STATUS      current
    DESCRIPTION "Select 1 of 4 DCD modes."
    ::= { aprisaXEHSSControlTableEntry 11 }

aprisaXEHSSClockSelection OBJECT-TYPE
    SYNTAX      INTEGER { hssClockInternal       (0),
                          hssClockXTxC           (1),
                          hssClockTxC            (2),
                          hssClockOverhead       (3),
                          hssClockNoOverhead     (4),
                          hssClockXTxC-RxC       (5),
                          hssClockXTxCNoOverhead (6)
                }
    MAX-ACCESS  read-write
    STATUS      current
    DESCRIPTION "Select the clock mode internal to the HSS traffic path."
    ::= { aprisaXEHSSControlTableEntry 12 }

aprisaXEHSSXTxCEnabled OBJECT-TYPE
    SYNTAX      INTEGER { hssxTxCEnabled  (0),
                          hssxTxCDisabled (1)
                }
    MAX-ACCESS  read-write
    STATUS      current
    DESCRIPTION "Select whether XTxC generation is enabled or disabled for
                 the port. The default is enabled."
    ::= { aprisaXEHSSControlTableEntry 13 }

aprisaXEHSSSerialMode OBJECT-TYPE
    SYNTAX      AprisaXEHssSerialMode
    MAX-ACCESS  read-only
    STATUS      current
    DESCRIPTION "Indicates the type of serial interface cable is connected to
                 the HSS port."
    ::= { aprisaXEHSSControlTableEntry 14 }

-- ***************************************************************************
-- End HSS
-- ***************************************************************************



-- ***************************************************************************
-- V24
-- ***************************************************************************

aprisaXEV24PortControlTable OBJECT-TYPE
    SYNTAX      SEQUENCE OF AprisaXEV24PortControlTableEntry
    MAX-ACCESS  not-accessible
    STATUS      current
    DESCRIPTION "Port Control table for V24."
    ::= { aprisaXEObjects 210 }

aprisaXEV24PortControlTableEntry OBJECT-TYPE
    SYNTAX      AprisaXEV24PortControlTableEntry
    MAX-ACCESS  not-accessible
    STATUS      current
    DESCRIPTION "Entries for V24 table."
    INDEX       { aprisaXEV24PortControlSlotIndex,
                  aprisaXEV24PortIndex
    }
    ::= { aprisaXEV24PortControlTable 1 }

AprisaXEV24PortControlTableEntry ::= SEQUENCE {
        aprisaXEV24PortControlSlotIndex  INTEGER,
        aprisaXEV24PortIndex             INTEGER,
        aprisaXEV24BaudRate              INTEGER,
        aprisaXEV24Loopback              INTEGER,
        aprisaXEV24DataBits              INTEGER,
        aprisaXEV24StopBits              INTEGER,
        aprisaXEV24ParityBits            INTEGER,
        aprisaXEV24ConnectionID          INTEGER
    }

aprisaXEV24PortControlSlotIndex OBJECT-TYPE
    SYNTAX      AprisaXESlotNumber
    MAX-ACCESS  read-only
    STATUS      current
    DESCRIPTION "Slot index for V24 Control table."
    ::= { aprisaXEV24PortControlTableEntry 1 }

aprisaXEV24PortIndex OBJECT-TYPE
    SYNTAX      AprisaXEPortNumber
    MAX-ACCESS  read-only
    STATUS      current
    DESCRIPTION "Port index for V24 Control table."
    ::= { aprisaXEV24PortControlTableEntry 2 }

aprisaXEV24BaudRate OBJECT-TYPE
    SYNTAX      INTEGER { v24-300    (0),
                          v24-600    (1),
                          v24-1200   (2),
                          v24-2400   (3),
                          v24-4800   (4),
                          v24-7200   (5),
                          v24-9600   (6),
                          v24-12800  (7),
                          v24-14400  (8),
                          v24-19200  (9),
                          v24-23040  (10),
                          v24-28800  (11),
                          v24-38400  (12),
                          v24-57600  (13),
                          v24-115200 (14)
                }
    MAX-ACCESS  read-write
    STATUS      current
    DESCRIPTION "Baud Rate from 300 baud to 115200 baud."
    DEFVAL      { none }
    ::= { aprisaXEV24PortControlTableEntry 3 }
    
aprisaXEV24Loopback OBJECT-TYPE
    SYNTAX      FourRFLoopback
    MAX-ACCESS  read-write
    STATUS      current
    DESCRIPTION "Loopback control on or off for ports."
    ::= { aprisaXEV24PortControlTableEntry 4 }

aprisaXEV24DataBits OBJECT-TYPE
    SYNTAX      INTEGER { databits7 (0),
                          databits8 (1)
                }
    MAX-ACCESS  read-write
    STATUS      current
    DESCRIPTION "No of data bits used, 7 or 8."
    ::= { aprisaXEV24PortControlTableEntry 5 }

aprisaXEV24StopBits OBJECT-TYPE
    SYNTAX      INTEGER { stopbits1 (0),
                          stopbits2 (1)
                }
    MAX-ACCESS  read-write
    STATUS      current
    DESCRIPTION "No of stop bits used, 1 or 2."
    ::= { aprisaXEV24PortControlTableEntry 6 }
    
aprisaXEV24ParityBits OBJECT-TYPE
    SYNTAX      INTEGER { paritybits0 (0),
                          paritybits1 (1)
                }
    MAX-ACCESS  read-write
    STATUS      current
    DESCRIPTION "No of parity bits used, 0 or 1."
    ::= { aprisaXEV24PortControlTableEntry 7 }

aprisaXEV24ConnectionID OBJECT-TYPE
    SYNTAX      AprisaXEConnectionID
    MAX-ACCESS  read-write
    STATUS      current
    DESCRIPTION "Associated cross-connect Backplane Connection ID."
    ::= { aprisaXEV24PortControlTableEntry 8 }
   
-- ***************************************************************************
-- End V24
-- ***************************************************************************
  


-- ***************************************************************************
-- Upgrade Control
--
-- Software upgrade (using TFTP) can be performed by setting the required
-- software version string and setting the command OID. This results in a
-- file being uploaded from the server release_x_y_z.cfg. This file lists the
-- files required for the specified software release. TFTP is then used to
-- upload any files not currently installed and the required images are 
-- activated. 
--
-- ***************************************************************************

aprisaXESoftwareUpgradeControl OBJECT IDENTIFIER ::= { aprisaXEObjects 300 }

aprisaXESoftwareUpgradeVersion  OBJECT-TYPE
    SYNTAX      DisplayString ( SIZE (0..16) )
    MAX-ACCESS  read-write
    STATUS      current
    DESCRIPTION "New software version details of the form x_y_z."
    ::= { aprisaXESoftwareUpgradeControl 1 }

aprisaXESoftwareUpgradeCommand  OBJECT-TYPE
    SYNTAX      INTEGER { none    (0),
                          upgrade (1)
                }
    MAX-ACCESS  read-write
    STATUS      current
    DESCRIPTION "Command used to instigate a software upgrade."
    ::= { aprisaXESoftwareUpgradeControl 2 }

aprisaXESoftwareUpgradeResult  OBJECT-TYPE
    SYNTAX      FourRFProcessResultType
    MAX-ACCESS  read-only
    STATUS      current
    DESCRIPTION "Status of a software upgrade, this will have to be polled to
                 follow the upload progress."
    ::= { aprisaXESoftwareUpgradeControl 3 }    

aprisaXESoftwareUpgradeControlGroup OBJECT-GROUP
    OBJECTS     { aprisaXESoftwareUpgradeVersion,
                  aprisaXESoftwareUpgradeCommand,
                  aprisaXESoftwareUpgradeResult
    }
    STATUS      current
    DESCRIPTION "The Aprisa XE software upgrade group."
    ::= { aprisaXEGroups 300 } 

-- ***************************************************************************
-- End Upgrade Control
-- ***************************************************************************



-- ***************************************************************************
-- Ethernet Table
--
-- A table which maintains the VLAN and QOS configuration of each of
-- the User Ethernet Ports
--
-- ***************************************************************************

aprisaXEEthernetTable OBJECT-TYPE
    SYNTAX      SEQUENCE OF AprisaXEEthernetTableEntry
    MAX-ACCESS  not-accessible
    STATUS      current
    DESCRIPTION "Table used to display and configure Ethernet settings."
    ::= { aprisaXEObjects 97 }

aprisaXEEthernetTableEntry OBJECT-TYPE
    SYNTAX      AprisaXEEthernetTableEntry
    MAX-ACCESS  not-accessible
    STATUS      current
    DESCRIPTION "Individual Ethernet port settings."
    INDEX       { aprisaXEEthernetPortNum }
    ::= { aprisaXEEthernetTable 1 }

AprisaXEEthernetTableEntry ::= SEQUENCE {
        aprisaXEEthernetPortNum      INTEGER,
        aprisaXEEthernetGroup        INTEGER,
        aprisaXEEthernetIngressRate  INTEGER,
        aprisaXEEthernetPortPriority INTEGER
    }

aprisaXEEthernetPortNum OBJECT-TYPE
    SYNTAX      AprisaXEEthernetPortNumber
    MAX-ACCESS  read-only
    STATUS      current
    DESCRIPTION "The port number, there are four ports on the hub."
    ::= { aprisaXEEthernetTableEntry 1 }

aprisaXEEthernetGroup OBJECT-TYPE
    SYNTAX      AprisaXEEthernetGroup
    MAX-ACCESS  read-write
    STATUS      current
    DESCRIPTION "The Ethernet Group of which this port is a member."
    ::= { aprisaXEEthernetTableEntry 2 }

aprisaXEEthernetIngressRate OBJECT-TYPE
    SYNTAX      AprisaXEEthernetFrameRate
    MAX-ACCESS  read-write
    STATUS      current
    DESCRIPTION "The ingress frame rate limit for this port."
    ::= { aprisaXEEthernetTableEntry 3 }

aprisaXEEthernetPortPriority OBJECT-TYPE
    SYNTAX      AprisaXEEthernetPortPriority
    MAX-ACCESS  read-write
    STATUS      current
    DESCRIPTION "Indicates the bandwidth allocated to this port."
    ::= { aprisaXEEthernetTableEntry 4 }


-- ***************************************************************************
-- Ethernet Settings
--
-- The global VLAN and QOS configuration of the Ethernet Switch
--
-- ***************************************************************************

aprisaXEEthernetVlanQosSettings OBJECT IDENTIFIER ::= { aprisaXEObjects 98 }

aprisaXEEthernetGrouping OBJECT-TYPE
    SYNTAX      AprisaXEEthernetGrouping
    MAX-ACCESS  read-write
    STATUS      current
    DESCRIPTION "Indicates whether Ethernet grouping (VLANs) is enabled or disabled."
    ::= { aprisaXEEthernetVlanQosSettings 1 }

aprisaXEEthernetManagementGroup OBJECT-TYPE
    SYNTAX      AprisaXEEthernetGroup
    MAX-ACCESS  read-only
    STATUS      current
    DESCRIPTION "The Ethernet Group for management."
    ::= { aprisaXEEthernetVlanQosSettings 2 }

aprisaXEEthernetPrioQueueScheduling OBJECT-TYPE
    SYNTAX      AprisaXEEthernetPrioQueueScheduling
    MAX-ACCESS  read-write
    STATUS      current
    DESCRIPTION "Indicates Ethernet priority queue scheduling scheme (either strict or weighted)."
    ::= { aprisaXEEthernetVlanQosSettings 3 }

aprisaXEEthernetPrioQueueMapping OBJECT-TYPE
    SYNTAX      AprisaXEEthernetPrioQueueMapping
    MAX-ACCESS  read-write
    STATUS      current
    DESCRIPTION "Indicates the IEEE 802.1 Ethernet priority queue mapping scheme (either standard or cisco)."
    ::= { aprisaXEEthernetVlanQosSettings 4 }

aprisaXEDefaultEthernetGrouping OBJECT-TYPE
    SYNTAX      AprisaXEDefaultAction
    MAX-ACCESS  read-write
    STATUS      current
    DESCRIPTION "Indicates when Ethernet Grouping settings must be reset to default values."
    ::= { aprisaXEEthernetVlanQosSettings 5 }

aprisaXEDefaultEthernetQos OBJECT-TYPE
    SYNTAX      AprisaXEDefaultAction
    MAX-ACCESS  read-write
    STATUS      current
    DESCRIPTION "Indicates when Ethernet Grouping settings must be reset to default values."
    ::= { aprisaXEEthernetVlanQosSettings 6 }


-- ***************************************************************************
-- Dual E1 Alarms
-- ***************************************************************************    

aprisaXEDualJetBoardTable OBJECT-TYPE
    SYNTAX      SEQUENCE OF AprisaXEDualJetBoardEntry
    MAX-ACCESS  not-accessible
    STATUS      current
    DESCRIPTION "Table of Dual E1 card specific configuration details."
    ::= { aprisaXEObjects 220 }

aprisaXEDualJetBoardEntry OBJECT-TYPE
    SYNTAX      AprisaXEDualJetBoardEntry
    MAX-ACCESS  not-accessible
    STATUS      current
    DESCRIPTION "Dual E1 configuration details."
    INDEX       { aprisaXEDualJetBoardTableIndex }
    ::= { aprisaXEDualJetBoardTable 1 }
        
AprisaXEDualJetBoardEntry ::= SEQUENCE {
        aprisaXEDualJetBoardTableIndex INTEGER
    }

aprisaXEDualJetBoardTableIndex OBJECT-TYPE
    SYNTAX      AprisaXESlotNumber
    MAX-ACCESS  read-only
    STATUS      current
    DESCRIPTION "Dual E1 board indexed by slot."
    ::= { aprisaXEDualJetBoardEntry 1 }

aprisaXEDualJetPortTable OBJECT-TYPE
    SYNTAX      SEQUENCE OF AprisaXEDualJetPortEntry
    MAX-ACCESS  not-accessible
    STATUS      current
    DESCRIPTION "Table based on slot and port of DualJet cards alarms."
    ::= { aprisaXEObjects 221 }

aprisaXEDualJetPortEntry OBJECT-TYPE
    SYNTAX      AprisaXEDualJetPortEntry
    MAX-ACCESS  not-accessible
    STATUS      current
    DESCRIPTION "Dual E1 port alarms."
    INDEX       { aprisaXEDualJetPortTableSlot,
                  aprisaXEDualJetPortTablePort
    }
    ::= { aprisaXEDualJetPortTable 1 }

AprisaXEDualJetPortEntry ::= SEQUENCE {
        aprisaXEDualJetPortTableSlot           INTEGER,
        aprisaXEDualJetPortTablePort           INTEGER,
        aprisaXEDualJetAISAlarmStatus          INTEGER,
        aprisaXEDualJetAISAlarmSeverity        INTEGER,
        aprisaXEDualJetAISAlarmEnabled         INTEGER,
        aprisaXEDualJetLOSAlarmStatus          INTEGER,
        aprisaXEDualJetLOSAlarmSeverity        INTEGER,
        aprisaXEDualJetLOSAlarmEnabled         INTEGER
    }

aprisaXEDualJetPortTableSlot OBJECT-TYPE
    SYNTAX      AprisaXESlotNumber
    MAX-ACCESS  read-only
    STATUS      current
    DESCRIPTION "Port table index based on slot number."
    ::= { aprisaXEDualJetPortEntry 1 }

aprisaXEDualJetPortTablePort OBJECT-TYPE
    SYNTAX      AprisaXEPortNumber
    MAX-ACCESS  read-only
    STATUS      current
    DESCRIPTION "Port table index based on port number."
    ::= { aprisaXEDualJetPortEntry 2 }
        
aprisaXEDualJetAISAlarmStatus OBJECT-TYPE
    SYNTAX      FourRFAlarmStatus
    MAX-ACCESS  read-only
    STATUS      current
    DESCRIPTION "AIS alarm status."
    ::= { aprisaXEDualJetPortEntry 3 }

aprisaXEDualJetAISAlarmSeverity OBJECT-TYPE
    SYNTAX      FourRFAlarmSeverity
    MAX-ACCESS  read-only
    STATUS      current
    DESCRIPTION "AIS alarm severity."
    ::= { aprisaXEDualJetPortEntry 4 }

aprisaXEDualJetAISAlarmEnabled OBJECT-TYPE
    SYNTAX      FourRFAlarmEnabled
    MAX-ACCESS  read-only
    STATUS      current
    DESCRIPTION "AIS alarm enabled or disabled."
    ::= { aprisaXEDualJetPortEntry 5 }

aprisaXEDualJetLOSAlarmStatus OBJECT-TYPE
    SYNTAX      FourRFAlarmStatus
    MAX-ACCESS  read-only
    STATUS      current
    DESCRIPTION "LOS alarm status."
    ::= { aprisaXEDualJetPortEntry 6 }

aprisaXEDualJetLOSAlarmSeverity OBJECT-TYPE
    SYNTAX      FourRFAlarmSeverity
    MAX-ACCESS  read-only
    STATUS      current
    DESCRIPTION "LOS alarm severity."
    ::= { aprisaXEDualJetPortEntry 7 }

aprisaXEDualJetLOSAlarmEnabled OBJECT-TYPE
    SYNTAX      FourRFAlarmEnabled
    MAX-ACCESS  read-only
    STATUS      current
    DESCRIPTION "LOS alarm enabled or disabled."
    ::= { aprisaXEDualJetPortEntry 8 }

aprisaXEDualJetIFConfigTable OBJECT-TYPE
    SYNTAX      SEQUENCE OF AprisaXEDualJetIFConfigEntry
    MAX-ACCESS  not-accessible
    STATUS      current
    DESCRIPTION "Switch data table which describes the
                 allocation of user data on to the TDM busses."
    ::= { aprisaXEObjects 222 }

aprisaXEDualJetIFConfigEntry OBJECT-TYPE
    SYNTAX      AprisaXEDualJetIFConfigEntry
    MAX-ACCESS  not-accessible
    STATUS      current
    DESCRIPTION "Dual JET config data."
    INDEX       { aprisaXEDualJetIFConfigSlotIndex,
                  aprisaXEDualJetIFConfigPortIndex
    }
    ::= { aprisaXEDualJetIFConfigTable 1 }

AprisaXEDualJetIFConfigEntry ::= SEQUENCE {
        aprisaXEDualJetIFConfigSlotIndex INTEGER,
        aprisaXEDualJetIFConfigPortIndex INTEGER,
        aprisaXEDualJetTrafficType       INTEGER,
        aprisaXEDualJetLoopback          INTEGER,
        aprisaXEDualJetLineEncoding      INTEGER,
        aprisaXEDualJetPcmMode           INTEGER,
        aprisaXEDualJetClockSource       INTEGER,
        aprisaXEDualJetLineRadioLoopback INTEGER,
        aprisaXEDualJetTxWaveFormShaper  INTEGER
    }

aprisaXEDualJetIFConfigSlotIndex OBJECT-TYPE
    SYNTAX      AprisaXESlotNumber
    MAX-ACCESS  read-only
    STATUS      current
    DESCRIPTION "Index to the port table based on port number."
    ::= { aprisaXEDualJetIFConfigEntry 1 }
    
aprisaXEDualJetIFConfigPortIndex OBJECT-TYPE
    SYNTAX      AprisaXEPortNumber
    MAX-ACCESS  read-only
    STATUS      current
    DESCRIPTION "Index to the port table based on port number."
    ::= { aprisaXEDualJetIFConfigEntry 2 }
           
aprisaXEDualJetTrafficType OBJECT-TYPE
    SYNTAX      AprisaXEQuadJetTrafficType
    MAX-ACCESS  read-write
    STATUS      current
    DESCRIPTION "Controls the traffic type on a Dual JET port."
    ::= { aprisaXEDualJetIFConfigEntry 3 }
        
aprisaXEDualJetLoopback OBJECT-TYPE
    SYNTAX      FourRFLoopback
    MAX-ACCESS  read-write
    STATUS      obsolete
    DESCRIPTION "Controls the traffic loopback on a Dual JET port."
    ::= { aprisaXEDualJetIFConfigEntry 4 }
        
aprisaXEDualJetLineEncoding OBJECT-TYPE
    SYNTAX      AprisaXEQuadJetLineEncoding
    MAX-ACCESS  read-write
    STATUS      current
    DESCRIPTION "Controls the line encoding, the default is
                 HDB3 for E1, B8ZS for T1."
    ::= { aprisaXEDualJetIFConfigEntry 5 }

aprisaXEDualJetPcmMode OBJECT-TYPE
    SYNTAX      AprisaXEPcmMode
    MAX-ACCESS  read-write
    STATUS      current
    DESCRIPTION "Controls the PCM mode, PCM31 or PCM30C."
    ::= { aprisaXEDualJetIFConfigEntry 6 }
        
aprisaXEDualJetClockSource OBJECT-TYPE
    SYNTAX       FourRFNetworkClockSelect
    MAX-ACCESS   read-write
    STATUS       current
    DESCRIPTION  "Controls whether the port drives the clock soure or not."
    ::= { aprisaXEDualJetIFConfigEntry 7 }
       
aprisaXEDualJetLineRadioLoopback OBJECT-TYPE
    SYNTAX      AprisaXEQuadJetLoopbacks
    MAX-ACCESS  read-write
    STATUS      current
    DESCRIPTION "This indicates the E1 loopback setting on a port;
                 OFF, Line or Radio Facing."
    ::= { aprisaXEDualJetIFConfigEntry 8 }

aprisaXEDualJetTxWaveFormShaper OBJECT-TYPE
    SYNTAX      AprisaXEQuadJetWaveFormShapers
    MAX-ACCESS  read-write
    STATUS      current
    DESCRIPTION "This indicates the T1 Tx Waveform Shaper for a port;
                 0~133 ft, 133~266 ft, 266~399 ft, 399~533 ft, 533~655 ft."
    ::= { aprisaXEDualJetIFConfigEntry 9 }


-- ***************************************************************************
-- End Dual JET
-- ***************************************************************************


-- ***************************************************************************
-- Single E1 Alarms
-- ***************************************************************************    

aprisaXESingleJetBoardTable OBJECT-TYPE
    SYNTAX      SEQUENCE OF AprisaXESingleJetBoardEntry
    MAX-ACCESS  not-accessible
    STATUS      current
    DESCRIPTION "Table of Single E1 card specific configuration details."
    ::= { aprisaXEObjects 225 }

aprisaXESingleJetBoardEntry OBJECT-TYPE
    SYNTAX      AprisaXESingleJetBoardEntry
    MAX-ACCESS  not-accessible
    STATUS      current
    DESCRIPTION "Single E1 configuration details."
    INDEX       { aprisaXESingleJetBoardTableIndex }
    ::= { aprisaXESingleJetBoardTable 1 }
        
AprisaXESingleJetBoardEntry ::= SEQUENCE {
        aprisaXESingleJetBoardTableIndex INTEGER
    }

aprisaXESingleJetBoardTableIndex OBJECT-TYPE
    SYNTAX      AprisaXESlotNumber
    MAX-ACCESS  read-only
    STATUS      current
    DESCRIPTION "Single E1 board indexed by slot."
    ::= { aprisaXESingleJetBoardEntry 1 }

aprisaXESingleJetPortTable OBJECT-TYPE
    SYNTAX      SEQUENCE OF AprisaXESingleJetPortEntry
    MAX-ACCESS  not-accessible
    STATUS      current
    DESCRIPTION "Table based on slot and port of SingleJet cards alarms."
    ::= { aprisaXEObjects 226 }

aprisaXESingleJetPortEntry OBJECT-TYPE
    SYNTAX      AprisaXESingleJetPortEntry
    MAX-ACCESS  not-accessible
    STATUS      current
    DESCRIPTION "Single E1 port alarms."
    INDEX       { aprisaXESingleJetPortTableSlot,
                  aprisaXESingleJetPortTablePort
    }
    ::= { aprisaXESingleJetPortTable 1 }

AprisaXESingleJetPortEntry ::= SEQUENCE {
        aprisaXESingleJetPortTableSlot           INTEGER,
        aprisaXESingleJetPortTablePort           INTEGER,
        aprisaXESingleJetAISAlarmStatus          INTEGER,
        aprisaXESingleJetAISAlarmSeverity        INTEGER,
        aprisaXESingleJetAISAlarmEnabled         INTEGER,
        aprisaXESingleJetLOSAlarmStatus          INTEGER,
        aprisaXESingleJetLOSAlarmSeverity        INTEGER,
        aprisaXESingleJetLOSAlarmEnabled         INTEGER
    }

aprisaXESingleJetPortTableSlot OBJECT-TYPE
    SYNTAX      AprisaXESlotNumber
    MAX-ACCESS  read-only
    STATUS      current
    DESCRIPTION "Port table index based on slot number."
    ::= { aprisaXESingleJetPortEntry 1 }

aprisaXESingleJetPortTablePort OBJECT-TYPE
    SYNTAX      AprisaXEPortNumber
    MAX-ACCESS  read-only
    STATUS      current
    DESCRIPTION "Port table index based on port number."
    ::= { aprisaXESingleJetPortEntry 2 }
        
aprisaXESingleJetAISAlarmStatus OBJECT-TYPE
    SYNTAX      FourRFAlarmStatus
    MAX-ACCESS  read-only
    STATUS      current
    DESCRIPTION "AIS alarm status."
    ::= { aprisaXESingleJetPortEntry 3 }

aprisaXESingleJetAISAlarmSeverity OBJECT-TYPE
    SYNTAX      FourRFAlarmSeverity
    MAX-ACCESS  read-only
    STATUS      current
    DESCRIPTION "AIS alarm severity."
    ::= { aprisaXESingleJetPortEntry 4 }

aprisaXESingleJetAISAlarmEnabled OBJECT-TYPE
    SYNTAX      FourRFAlarmEnabled
    MAX-ACCESS  read-only
    STATUS      current
    DESCRIPTION "AIS alarm enabled or disabled."
    ::= { aprisaXESingleJetPortEntry 5 }

aprisaXESingleJetLOSAlarmStatus OBJECT-TYPE
    SYNTAX      FourRFAlarmStatus
    MAX-ACCESS  read-only
    STATUS      current
    DESCRIPTION "LOS alarm status."
    ::= { aprisaXESingleJetPortEntry 6 }

aprisaXESingleJetLOSAlarmSeverity OBJECT-TYPE
    SYNTAX      FourRFAlarmSeverity
    MAX-ACCESS  read-only
    STATUS      current
    DESCRIPTION "LOS alarm severity."
    ::= { aprisaXESingleJetPortEntry 7 }

aprisaXESingleJetLOSAlarmEnabled OBJECT-TYPE
    SYNTAX      FourRFAlarmEnabled
    MAX-ACCESS  read-only
    STATUS      current
    DESCRIPTION "LOS alarm enabled or disabled."
    ::= { aprisaXESingleJetPortEntry 8 }

aprisaXESingleJetIFConfigTable OBJECT-TYPE
    SYNTAX      SEQUENCE OF AprisaXESingleJetIFConfigEntry
    MAX-ACCESS  not-accessible
    STATUS      current
    DESCRIPTION "Switch data table which describes the
                 allocation of user data on to the TDM busses."
    ::= { aprisaXEObjects 227 }

aprisaXESingleJetIFConfigEntry OBJECT-TYPE
    SYNTAX      AprisaXESingleJetIFConfigEntry
    MAX-ACCESS  not-accessible
    STATUS      current
    DESCRIPTION "Single JET config data."
    INDEX       { aprisaXESingleJetIFConfigSlotIndex,
                  aprisaXESingleJetIFConfigPortIndex
    }
    ::= { aprisaXESingleJetIFConfigTable 1 }

AprisaXESingleJetIFConfigEntry ::= SEQUENCE {
        aprisaXESingleJetIFConfigSlotIndex INTEGER,
        aprisaXESingleJetIFConfigPortIndex INTEGER,
        aprisaXESingleJetTrafficType       INTEGER,
        aprisaXESingleJetLoopback          INTEGER,
        aprisaXESingleJetLineEncoding      INTEGER,
        aprisaXESingleJetPcmMode           INTEGER,
        aprisaXESingleJetClockSource       INTEGER,
        aprisaXESingleJetLineRadioLoopback INTEGER,
        aprisaXESingleJetTxWaveFormShaper  INTEGER
    }

aprisaXESingleJetIFConfigSlotIndex OBJECT-TYPE
    SYNTAX      AprisaXESlotNumber
    MAX-ACCESS  read-only
    STATUS      current
    DESCRIPTION "Index to the port table based on port number."
    ::= { aprisaXESingleJetIFConfigEntry 1 }
    
aprisaXESingleJetIFConfigPortIndex OBJECT-TYPE
    SYNTAX      AprisaXEPortNumber
    MAX-ACCESS  read-only
    STATUS      current
    DESCRIPTION "Index to the port table based on port number."
    ::= { aprisaXESingleJetIFConfigEntry 2 }
           
aprisaXESingleJetTrafficType OBJECT-TYPE
    SYNTAX      AprisaXEQuadJetTrafficType
    MAX-ACCESS  read-write
    STATUS      current
    DESCRIPTION "Controls the traffic type on a Single JET port."
    ::= { aprisaXESingleJetIFConfigEntry 3 }
        
aprisaXESingleJetLoopback OBJECT-TYPE
    SYNTAX      FourRFLoopback
    MAX-ACCESS  read-write
    STATUS      obsolete
    DESCRIPTION "Controls the traffic loopback on a Single JET port."
    ::= { aprisaXESingleJetIFConfigEntry 4 }
        
aprisaXESingleJetLineEncoding OBJECT-TYPE
    SYNTAX      AprisaXEQuadJetLineEncoding
    MAX-ACCESS  read-write
    STATUS      current
    DESCRIPTION "Controls the line encoding, the default is
                 HDB3 for E1, B8ZS for T1."
    ::= { aprisaXESingleJetIFConfigEntry 5 }

aprisaXESingleJetPcmMode OBJECT-TYPE
    SYNTAX      AprisaXEPcmMode
    MAX-ACCESS  read-write
    STATUS      current
    DESCRIPTION "Controls the PCM mode, PCM31 or PCM30C."
    ::= { aprisaXESingleJetIFConfigEntry 6 }
        
aprisaXESingleJetClockSource OBJECT-TYPE
    SYNTAX       FourRFNetworkClockSelect
    MAX-ACCESS   read-write
    STATUS       current
    DESCRIPTION  "Controls whether the port drives the clock soure or not."
    ::= { aprisaXESingleJetIFConfigEntry 7 }
       
aprisaXESingleJetLineRadioLoopback OBJECT-TYPE
    SYNTAX      AprisaXEQuadJetLoopbacks
    MAX-ACCESS  read-write
    STATUS      current
    DESCRIPTION "This indicates the E1 loopback setting on a port;
                 OFF, Line or Radio Facing."
    ::= { aprisaXESingleJetIFConfigEntry 8 }

aprisaXESingleJetTxWaveFormShaper OBJECT-TYPE
    SYNTAX      AprisaXEQuadJetWaveFormShapers
    MAX-ACCESS  read-write
    STATUS      current
    DESCRIPTION "This indicates the T1 Tx Waveform Shaper for a port;
                 0~133 ft, 133~266 ft, 266~399 ft, 399~533 ft, 533~655 ft."
    ::= { aprisaXESingleJetIFConfigEntry 9 }


-- ***************************************************************************
-- End Single JET
-- ***************************************************************************



-- ***************************************************************************
-- PSC
-- ***************************************************************************

aprisaXEPSCControlTable OBJECT-TYPE
    SYNTAX      SEQUENCE OF AprisaXEPSCControlTableEntry
    MAX-ACCESS  not-accessible
    STATUS      current
    DESCRIPTION "Control table for PSC."
    ::= { aprisaXEObjects 230 }

aprisaXEPSCControlTableEntry OBJECT-TYPE
    SYNTAX      AprisaXEPSCControlTableEntry
    MAX-ACCESS  not-accessible
    STATUS      current
    DESCRIPTION "Entries for PSC table."
    INDEX       { aprisaXEPSCControlSlotIndex }
    ::= { aprisaXEPSCControlTable 1 }

AprisaXEPSCControlTableEntry ::= SEQUENCE {
        aprisaXEPSCControlSlotIndex        INTEGER,
        aprisaXEPSCActiveRadio             AprisaXEPSCActiveRadio,
        aprisaXEPSCActiveTx                AprisaXEPSCActiveTx,
	aprisaXEPSCDemodAligmentStatusPSC  FourRFAlarmStatus,
	aprisaXEPSCDemodAligmentStatusPIC  FourRFAlarmStatus
    }

aprisaXEPSCControlSlotIndex OBJECT-TYPE
    SYNTAX      AprisaXESlotNumber
    MAX-ACCESS  read-only
    STATUS      current
    DESCRIPTION "Slot index for PSC Control Table."
    ::= { aprisaXEPSCControlTableEntry 1 }

aprisaXEPSCActiveRadio OBJECT-TYPE
    SYNTAX      AprisaXEPSCActiveRadio
    MAX-ACCESS  read-write
    STATUS      current
    DESCRIPTION "Indicates the reception mode of the PSC."
    ::= { aprisaXEPSCControlTableEntry 2 }

aprisaXEPSCActiveTx OBJECT-TYPE
    SYNTAX      AprisaXEPSCActiveTx
    MAX-ACCESS  read-only
    STATUS      current
    DESCRIPTION "Indicates the currently active transmitter."
    ::= { aprisaXEPSCControlTableEntry 3 }

aprisaXEPSCDemodAlignmentStatusPSC OBJECT-TYPE
    SYNTAX      FourRFAlarmStatus
    MAX-ACCESS  read-only
    STATUS      current
    DESCRIPTION "Status of the demodulator alignment on the PSC."
    ::= { aprisaXEPSCControlTableEntry 4 }

aprisaXEPSCDemodAlignmentStatusPIC OBJECT-TYPE
    SYNTAX      FourRFAlarmStatus
    MAX-ACCESS  read-only
    STATUS      current
    DESCRIPTION "Status of the demodulator alignment on the PIC."
    ::= { aprisaXEPSCControlTableEntry 5 }

-- ***************************************************************************
-- End PSC
-- ***************************************************************************


-- ***************************************************************************
-- HSD Parameter Comparison
-- ***************************************************************************

aprisaXEHSDParameterCompare OBJECT IDENTIFIER ::= { aprisaXEObjects 235 }

aprisaXEHSDParameterMismatch OBJECT-TYPE
    SYNTAX      FourRFAlarmStatus
    MAX-ACCESS  read-only
    STATUS      current
    DESCRIPTION "If there is a parameter (OID) mismatch between 
		 Radio A and Radio B"
    ::= { aprisaXEHSDParameterCompare 1 }

aprisaXEHSDParameterCompareChecking OBJECT-TYPE
    SYNTAX      INTEGER { off (0),
                          on  (1)
                }
    MAX-ACCESS  read-write
    STATUS      current
    DESCRIPTION "Enables/disables HSD paramter compare checking between 
		 Radio A and Radio B"
    ::= { aprisaXEHSDParameterCompare 2 }

aprisaXEHSDParameterCompareGroup OBJECT-GROUP
    OBJECTS     { aprisaXEHSDParameterMismatch,
		  aprisaXEHSDParameterCompareChecking
    }
    STATUS      current
    DESCRIPTION "The AprisaXE HSD Parameter Comparison group."
    ::= { aprisaXEGroups 305 } 

-- ***************************************************************************
-- HSD Parameter Comparison
-- ***************************************************************************


END
