-- *****************************************************************
-- TN-RFC2544-MIB.smi:  Transition Networks RFC2544 MIB.
--
-- Copyright (c) 2014 by Transition Networks, Inc.
-- All rights reserved.
--
-- *****************************************************************

TN-DEV-RFC2544-MIB DEFINITIONS ::= BEGIN

IMPORTS
    MODULE-IDENTITY, OBJECT-TYPE, Integer32 FROM SNMPv2-SMI
    DisplayString, RowStatus FROM SNMPv2-TC
    tnDevMgmt FROM TN-MGMT-MIB;

tnDevRFC2544    MODULE-IDENTITY
     LAST-UPDATED "201408220000Z"
     ORGANIZATION "Transition Networks, Inc."
     CONTACT-INFO
                 "       Transition Networks
                         Technical Support
                         10900 Red Circle Drive
                         Minnetonka, MN 55343 USA
                         Tel: +1-800-526-9267

                     E-mail: techsupport@transition.com"
     DESCRIPTION
         "The MIB provides functionalities for system user management in TN modules."
     REVISION      "201408220000Z"
     DESCRIPTION
         "Initial Revision of this module"
     ::= { tnDevMgmt 42 }



tnDevRFC2544ProfileTable OBJECT-TYPE
    SYNTAX SEQUENCE OF TnDevRFC2544ProfileEntry
    MAX-ACCESS not-accessible
    STATUS current
    DESCRIPTION
        "This table is used to maintain the RFC2544 Profile Entries."
    ::= { tnDevRFC2544 1 }

tnDevRFC2544ProfileEntry OBJECT-TYPE
    SYNTAX TnDevRFC2544ProfileEntry
    MAX-ACCESS not-accessible
    STATUS current
    DESCRIPTION
        "Entries in this table correspond to the RFC2544 Profile Entries."
    INDEX { tnDevRFC2544ProfileIndex }
    ::= { tnDevRFC2544ProfileTable 1 }

TnDevRFC2544ProfileEntry ::=
    SEQUENCE {
         tnDevRFC2544ProfileIndex        Integer32,
         tnDevRFC2544ProfileName         DisplayString
    }

tnDevRFC2544ProfileIndex OBJECT-TYPE
    SYNTAX      Integer32 (1..128)
    MAX-ACCESS  not-accessible
    STATUS      current
    DESCRIPTION
        "Index of this table."
    ::= { tnDevRFC2544ProfileEntry 1 }

tnDevRFC2544ProfileName OBJECT-TYPE
    SYNTAX      DisplayString (SIZE (1..32))
    MAX-ACCESS  read-create
    STATUS      current
    DESCRIPTION
        "The name, ASCII range 33-126, of this table."
    ::= { tnDevRFC2544ProfileEntry 2 }



tnDevRFC2544ProfileConfigurationCommonParametersTable OBJECT-TYPE
    SYNTAX SEQUENCE OF TnDevRFC2544ProfileConfigurationCommonParametersEntry
    MAX-ACCESS not-accessible
    STATUS current
    DESCRIPTION
        "This table is used to maintain the RFC2544 Profile Configuration Common Parameters Entries."
    ::= { tnDevRFC2544 2 }

tnDevRFC2544ProfileConfigurationCommonParametersEntry OBJECT-TYPE
    SYNTAX TnDevRFC2544ProfileConfigurationCommonParametersEntry
    MAX-ACCESS not-accessible
    STATUS current
    DESCRIPTION
        "Entries in this table correspond to the RFC2544 Profile Configuration Common Parameters Entries."
    INDEX { tnDevRFC2544ProfileConfigurationCommonParametersIndex }
    ::= { tnDevRFC2544ProfileConfigurationCommonParametersTable 1 }

TnDevRFC2544ProfileConfigurationCommonParametersEntry ::=
    SEQUENCE {
         tnDevRFC2544ProfileConfigurationCommonParametersIndex                       Integer32,
         tnDevRFC2544ProfileConfigurationCommonParametersDescription                 DisplayString,
         tnDevRFC2544ProfileConfigurationCommonParametersMEGLevel                    Integer32,
         tnDevRFC2544ProfileConfigurationCommonParametersEgressPort                  Integer32,
         tnDevRFC2544ProfileConfigurationCommonParametersSequenceNumberCheck         INTEGER,
         tnDevRFC2544ProfileConfigurationCommonParametersDwellTime                   Integer32,
         tnDevRFC2544ProfileConfigurationCommonParametersType                        INTEGER,
         tnDevRFC2544ProfileConfigurationCommonParametersVLANID                      Integer32,
         tnDevRFC2544ProfileConfigurationCommonParametersPCP                         Integer32,
         tnDevRFC2544ProfileConfigurationCommonParametersDEI                         Integer32,
         tnDevRFC2544ProfileConfigurationCommonParametersDMAC                        DisplayString,
         tnDevRFC2544ProfileConfigurationCommonParametersFrameSizeMask               Integer32,
         tnDevRFC2544ProfileConfigurationCommonParametersTestsToRunMask              Integer32
    }

tnDevRFC2544ProfileConfigurationCommonParametersIndex OBJECT-TYPE
    SYNTAX      Integer32 (1..128)
    MAX-ACCESS  not-accessible
    STATUS      current
    DESCRIPTION
        "Index of this table."
    ::= { tnDevRFC2544ProfileConfigurationCommonParametersEntry 1 }

tnDevRFC2544ProfileConfigurationCommonParametersDescription OBJECT-TYPE
    SYNTAX      DisplayString (SIZE (0..127))
    MAX-ACCESS  read-create
    STATUS      current
    DESCRIPTION
        "The description of this table."
    ::= { tnDevRFC2544ProfileConfigurationCommonParametersEntry 2 }

tnDevRFC2544ProfileConfigurationCommonParametersMEGLevel OBJECT-TYPE
    SYNTAX      Integer32 (1..7)
    MAX-ACCESS  not-accessible
    STATUS      current
    DESCRIPTION
        "MEG Level of this table."
    ::= { tnDevRFC2544ProfileConfigurationCommonParametersEntry 3 }

tnDevRFC2544ProfileConfigurationCommonParametersEgressPort OBJECT-TYPE
    SYNTAX      Integer32 (1..6)
    MAX-ACCESS  not-accessible
    STATUS      current
    DESCRIPTION
        "Egress Port of this table."
    ::= { tnDevRFC2544ProfileConfigurationCommonParametersEntry 4 }

tnDevRFC2544ProfileConfigurationCommonParametersSequenceNumberCheck OBJECT-TYPE
    SYNTAX      INTEGER{
                   disable         (0),
                   enable          (1)
                }
    MAX-ACCESS  read-write
    STATUS      current
    DESCRIPTION
        "Sequence Number Check disable/enable of this table."
    ::= { tnDevRFC2544ProfileConfigurationCommonParametersEntry 5 }

tnDevRFC2544ProfileConfigurationCommonParametersDwellTime OBJECT-TYPE
    SYNTAX      Integer32 (1..10)
    MAX-ACCESS  not-accessible
    STATUS      current
    DESCRIPTION
        "Dwell Time, in seconds, of this table."
    ::= { tnDevRFC2544ProfileConfigurationCommonParametersEntry 6 }

tnDevRFC2544ProfileConfigurationCommonParametersType OBJECT-TYPE
    SYNTAX      INTEGER{
                   portDownMEP         (0),
                   vlanBasedDownMEP    (1)
                }
    MAX-ACCESS  read-write
    STATUS      current
    DESCRIPTION
        "Type of this table."
    ::= { tnDevRFC2544ProfileConfigurationCommonParametersEntry 7 }

tnDevRFC2544ProfileConfigurationCommonParametersVLANID OBJECT-TYPE
    SYNTAX      Integer32 (1..4094)
    MAX-ACCESS  not-accessible
    STATUS      current
    DESCRIPTION
        "VLAN ID of this table."
    ::= { tnDevRFC2544ProfileConfigurationCommonParametersEntry 8 }

tnDevRFC2544ProfileConfigurationCommonParametersPCP OBJECT-TYPE
    SYNTAX      Integer32 (1..7)
    MAX-ACCESS  not-accessible
    STATUS      current
    DESCRIPTION
        "PCP of this table."
    ::= { tnDevRFC2544ProfileConfigurationCommonParametersEntry 9 }

tnDevRFC2544ProfileConfigurationCommonParametersDEI OBJECT-TYPE
    SYNTAX      Integer32 (0..1)
    MAX-ACCESS  not-accessible
    STATUS      current
    DESCRIPTION
        "DEI of this table."
    ::= { tnDevRFC2544ProfileConfigurationCommonParametersEntry 10 }

tnDevRFC2544ProfileConfigurationCommonParametersDMAC OBJECT-TYPE
    SYNTAX      DisplayString (SIZE (1..128))
    MAX-ACCESS  read-create
    STATUS      current
    DESCRIPTION
        "The DMAC, 00-00-00-00-00-00 formatted, of this table."
    ::= { tnDevRFC2544ProfileConfigurationCommonParametersEntry 11 }

tnDevRFC2544ProfileConfigurationCommonParametersFrameSizeMask OBJECT-TYPE
    SYNTAX      Integer32 (0..511)
    MAX-ACCESS  not-accessible
    STATUS      current
    DESCRIPTION
        "Frame Size Mask of this table.
		 Bit 0 - 64 byte frames enabled if set to 1.
		 Bit 1 - 128 byte frames enabled if set to 1.
		 Bit 2 - 256 byte frames enabled if set to 1.
		 Bit 3 - 512 byte frames enabled if set to 1.
		 Bit 4 - 1024 byte frames enabled if set to 1.
		 Bit 5 - 1280 byte frames enabled if set to 1.
		 Bit 6 - 1518 byte frames enabled if set to 1.
		 Bit 7 - 2000 byte frames enabled if set to 1.
		 Bit 8 - 9600 byte frames enabled if set to 1.
		 "	
    ::= { tnDevRFC2544ProfileConfigurationCommonParametersEntry 12 }

tnDevRFC2544ProfileConfigurationCommonParametersTestsToRunMask OBJECT-TYPE
    SYNTAX      Integer32 (0..15)
    MAX-ACCESS  not-accessible
    STATUS      current
    DESCRIPTION
        "Tests To Run Mask of this table.
		 Bit 0 - Throughput Test enabled if set to 1.
		 Bit 1 - Latency Test enabled if set to 1.
		 Bit 2 - Frame Loss Test enabled if set to 1.
		 Bit 3 - Back To Back Test enabled if set to 1.
		 "	
    ::= { tnDevRFC2544ProfileConfigurationCommonParametersEntry 13 }



tnDevRFC2544ProfileConfigurationThroughputTestParametersTable OBJECT-TYPE
    SYNTAX SEQUENCE OF TnDevRFC2544ProfileConfigurationThroughputTestParametersEntry
    MAX-ACCESS not-accessible
    STATUS current
    DESCRIPTION
        "This table is used to maintain the RFC2544 Profile Configuration Throughput Test Parameters Entries."
    ::= { tnDevRFC2544 3 }

tnDevRFC2544ProfileConfigurationThroughputTestParametersEntry OBJECT-TYPE
    SYNTAX TnDevRFC2544ProfileConfigurationThroughputTestParametersEntry
    MAX-ACCESS not-accessible
    STATUS current
    DESCRIPTION
        "Entries in this table correspond to the RFC2544 Profile Configuration Throughput Test Parameters Entries."
    INDEX { tnDevRFC2544ProfileConfigurationThroughputTestParametersIndex }
    ::= { tnDevRFC2544ProfileConfigurationThroughputTestParametersTable 1 }

TnDevRFC2544ProfileConfigurationThroughputTestParametersEntry ::=
    SEQUENCE {
         tnDevRFC2544ProfileConfigurationThroughputTestParametersIndex                       Integer32,
         tnDevRFC2544ProfileConfigurationThroughputTestParametersTrialDuration               Integer32,
         tnDevRFC2544ProfileConfigurationThroughputTestParametersMinimumRate                 Integer32,
         tnDevRFC2544ProfileConfigurationThroughputTestParametersMaximumRate                 Integer32,
         tnDevRFC2544ProfileConfigurationThroughputTestParametersAccuracy                    Integer32,
         tnDevRFC2544ProfileConfigurationThroughputTestParametersAllowedFrameLoss            Integer32
    }

tnDevRFC2544ProfileConfigurationThroughputTestParametersIndex OBJECT-TYPE
    SYNTAX      Integer32 (1..128)
    MAX-ACCESS  not-accessible
    STATUS      current
    DESCRIPTION
        "Index of this table."
    ::= { tnDevRFC2544ProfileConfigurationThroughputTestParametersEntry 1 }

tnDevRFC2544ProfileConfigurationThroughputTestParametersTrialDuration OBJECT-TYPE
    SYNTAX      Integer32 (1..1800)
    MAX-ACCESS  not-accessible
    STATUS      current
    DESCRIPTION
        "Trial Duration, in seconds, of this table."
    ::= { tnDevRFC2544ProfileConfigurationThroughputTestParametersEntry 2 }

tnDevRFC2544ProfileConfigurationThroughputTestParametersTrialMinimumRate OBJECT-TYPE
    SYNTAX      Integer32 (1..1000)
    MAX-ACCESS  not-accessible
    STATUS      current
    DESCRIPTION
        "Minimum Rate, in permille, of this table."
    ::= { tnDevRFC2544ProfileConfigurationThroughputTestParametersEntry 3 }

tnDevRFC2544ProfileConfigurationThroughputTestParametersTrialMaximumRate OBJECT-TYPE
    SYNTAX      Integer32 (1..1000)
    MAX-ACCESS  not-accessible
    STATUS      current
    DESCRIPTION
        "Maximum Rate, in permille, of this table."
    ::= { tnDevRFC2544ProfileConfigurationThroughputTestParametersEntry 4 }

tnDevRFC2544ProfileConfigurationThroughputTestParametersTrialAccuracy OBJECT-TYPE
    SYNTAX      Integer32 (1..1000)
    MAX-ACCESS  not-accessible
    STATUS      current
    DESCRIPTION
        "Accuracy, in permille, of this table."
    ::= { tnDevRFC2544ProfileConfigurationThroughputTestParametersEntry 5 }

tnDevRFC2544ProfileConfigurationThroughputTestParametersTrialAllowedFrameLoss OBJECT-TYPE
    SYNTAX      Integer32 (0..100)
    MAX-ACCESS  not-accessible
    STATUS      current
    DESCRIPTION
        "Allowed Frame Loss, in permille, of this table."
    ::= { tnDevRFC2544ProfileConfigurationThroughputTestParametersEntry 6 }



tnDevRFC2544ProfileConfigurationLatencyTestParametersTable OBJECT-TYPE
    SYNTAX SEQUENCE OF TnDevRFC2544ProfileConfigurationLatencyTestParametersEntry
    MAX-ACCESS not-accessible
    STATUS current
    DESCRIPTION
        "This table is used to maintain the RFC2544 Profile Configuration Latency Test Parameters Entries."
    ::= { tnDevRFC2544 4 }

tnDevRFC2544ProfileConfigurationLatencyTestParametersEntry OBJECT-TYPE
    SYNTAX TnDevRFC2544ProfileConfigurationLatencyTestParametersEntry
    MAX-ACCESS not-accessible
    STATUS current
    DESCRIPTION
        "Entries in this table correspond to the RFC2544 Profile Configuration Latency Test Parameters Entries."
    INDEX { tnDevRFC2544ProfileConfigurationLatencyTestParametersIndex }
    ::= { tnDevRFC2544ProfileConfigurationLatencyTestParametersTable 1 }

TnDevRFC2544ProfileConfigurationLatencyTestParametersEntry ::=
    SEQUENCE {
         tnDevRFC2544ProfileConfigurationLatencyTestParametersIndex                       Integer32,
         tnDevRFC2544ProfileConfigurationLatencyTestParametersTrialDuration               Integer32,
         tnDevRFC2544ProfileConfigurationLatencyTestParametersDelayMeasurementInterval    Integer32,
         tnDevRFC2544ProfileConfigurationLatencyTestParametersAllowedFrameLoss            Integer32
    }

tnDevRFC2544ProfileConfigurationLatencyTestParametersIndex OBJECT-TYPE
    SYNTAX      Integer32 (1..128)
    MAX-ACCESS  not-accessible
    STATUS      current
    DESCRIPTION
        "Index of this table."
    ::= { tnDevRFC2544ProfileConfigurationLatencyTestParametersEntry 1 }

tnDevRFC2544ProfileConfigurationLatencyTestParametersTrialDuration OBJECT-TYPE
    SYNTAX      Integer32 (10..1800)
    MAX-ACCESS  not-accessible
    STATUS      current
    DESCRIPTION
        "Trial Duration, in seconds, of this table."
    ::= { tnDevRFC2544ProfileConfigurationLatencyTestParametersEntry 2 }

tnDevRFC2544ProfileConfigurationLatencyTestParametersDelayMeasurementInterval OBJECT-TYPE
    SYNTAX      Integer32 (1..60)
    MAX-ACCESS  not-accessible
    STATUS      current
    DESCRIPTION
        "Delay Measurement Interval, in seconds, of this table."
    ::= { tnDevRFC2544ProfileConfigurationLatencyTestParametersEntry 3 }

tnDevRFC2544ProfileConfigurationLatencyTestParametersAllowedFrameLoss OBJECT-TYPE
    SYNTAX      Integer32 (0..100)
    MAX-ACCESS  not-accessible
    STATUS      current
    DESCRIPTION
        "Allowed Frame Loss, in permille, of this table."
    ::= { tnDevRFC2544ProfileConfigurationLatencyTestParametersEntry 4 }



tnDevRFC2544ProfileConfigurationFrameLossTestParametersTable OBJECT-TYPE
    SYNTAX SEQUENCE OF TnDevRFC2544ProfileConfigurationFrameLossTestParametersEntry
    MAX-ACCESS not-accessible
    STATUS current
    DESCRIPTION
        "This table is used to maintain the RFC2544 Profile Configuration Frame Loss Test Parameters Entries."
    ::= { tnDevRFC2544 4 }

tnDevRFC2544ProfileConfigurationFrameLossTestParametersEntry OBJECT-TYPE
    SYNTAX TnDevRFC2544ProfileConfigurationFrameLossTestParametersEntry
    MAX-ACCESS not-accessible
    STATUS current
    DESCRIPTION
        "Entries in this table correspond to the RFC2544 Profile Configuration Frame Loss Test Parameters Entries."
    INDEX { tnDevRFC2544ProfileConfigurationFrameLossTestParametersIndex }
    ::= { tnDevRFC2544ProfileConfigurationFrameLossTestParametersTable 1 }

TnDevRFC2544ProfileConfigurationFrameLossTestParametersEntry ::=
    SEQUENCE {
         tnDevRFC2544ProfileConfigurationFrameLossTestParametersIndex                       Integer32,
         tnDevRFC2544ProfileConfigurationFrameLossTestParametersTrialDuration               Integer32,
         tnDevRFC2544ProfileConfigurationFrameLossTestParametersMinimumRate                 Integer32,
         tnDevRFC2544ProfileConfigurationFrameLossTestParametersMaximumRate                 Integer32,
         tnDevRFC2544ProfileConfigurationFrameLossTestParametersRateStep                    Integer32
    }

tnDevRFC2544ProfileConfigurationFrameLossTestParametersIndex OBJECT-TYPE
    SYNTAX      Integer32 (1..128)
    MAX-ACCESS  not-accessible
    STATUS      current
    DESCRIPTION
        "Index of this table."
    ::= { tnDevRFC2544ProfileConfigurationFrameLossTestParametersEntry 1 }

tnDevRFC2544ProfileConfigurationFrameLossTestParametersTrialDuration OBJECT-TYPE
    SYNTAX      Integer32 (1..1800)
    MAX-ACCESS  not-accessible
    STATUS      current
    DESCRIPTION
        "Trial Duration, in seconds, of this table."
    ::= { tnDevRFC2544ProfileConfigurationFrameLossTestParametersEntry 2 }

tnDevRFC2544ProfileConfigurationFrameLossTestParametersMinimumRate OBJECT-TYPE
    SYNTAX      Integer32 (1..1000)
    MAX-ACCESS  not-accessible
    STATUS      current
    DESCRIPTION
        "Minimum Rate, in permille, of this table."
    ::= { tnDevRFC2544ProfileConfigurationFrameLossTestParametersEntry 3 }

tnDevRFC2544ProfileConfigurationFrameLossTestParametersMaximumRate OBJECT-TYPE
    SYNTAX      Integer32 (1..1000)
    MAX-ACCESS  not-accessible
    STATUS      current
    DESCRIPTION
        "Maximum Rate, in permille, of this table."
    ::= { tnDevRFC2544ProfileConfigurationFrameLossTestParametersEntry 4 }

tnDevRFC2544ProfileConfigurationFrameLossTestParametersRateStep OBJECT-TYPE
    SYNTAX      Integer32 (1..1000)
    MAX-ACCESS  not-accessible
    STATUS      current
    DESCRIPTION
        "Rate Step, in permille, of this table."
    ::= { tnDevRFC2544ProfileConfigurationFrameLossTestParametersEntry 5 }



tnDevRFC2544ProfileConfigurationBackToBackTestParametersTable OBJECT-TYPE
    SYNTAX SEQUENCE OF TnDevRFC2544ProfileConfigurationBackToBackTestParametersEntry
    MAX-ACCESS not-accessible
    STATUS current
    DESCRIPTION
        "This table is used to maintain the RFC2544 Profile Configuration Back To Back Test Parameters Entries."
    ::= { tnDevRFC2544 5 }

tnDevRFC2544ProfileConfigurationBackToBackTestParametersEntry OBJECT-TYPE
    SYNTAX TnDevRFC2544ProfileConfigurationBackToBackTestParametersEntry
    MAX-ACCESS not-accessible
    STATUS current
    DESCRIPTION
        "Entries in this table correspond to the RFC2544 Profile Configuration Back To Back Test Parameters Entries."
    INDEX { tnDevRFC2544ProfileConfigurationBackToBackTestParametersIndex }
    ::= { tnDevRFC2544ProfileConfigurationBackToBackTestParametersTable 1 }

TnDevRFC2544ProfileConfigurationBackToBackTestParametersEntry ::=
    SEQUENCE {
         tnDevRFC2544ProfileConfigurationBackToBackTestParametersIndex                       Integer32,
         tnDevRFC2544ProfileConfigurationBackToBackTestParametersTrialDuration               Integer32,
         tnDevRFC2544ProfileConfigurationBackToBackTestParametersTrialCount                  Integer32
    }

tnDevRFC2544ProfileConfigurationBackToBackTestParametersIndex OBJECT-TYPE
    SYNTAX      Integer32 (1..128)
    MAX-ACCESS  not-accessible
    STATUS      current
    DESCRIPTION
        "Index of this table."
    ::= { tnDevRFC2544ProfileConfigurationBackToBackTestParametersEntry 1 }

tnDevRFC2544ProfileConfigurationBackToBackTestParametersTrialDuration OBJECT-TYPE
    SYNTAX      Integer32 (100..10000)
    MAX-ACCESS  not-accessible
    STATUS      current
    DESCRIPTION
        "Trial Duration, in seconds, of this table."
    ::= { tnDevRFC2544ProfileConfigurationBackToBackTestParametersEntry 2 }

tnDevRFC2544ProfileConfigurationBackToBackTestParametersTrialCount OBJECT-TYPE
    SYNTAX      Integer32 (1..100)
    MAX-ACCESS  not-accessible
    STATUS      current
    DESCRIPTION
        "Trial count of this table."
    ::= { tnDevRFC2544ProfileConfigurationBackToBackTestParametersEntry 3 }

END
