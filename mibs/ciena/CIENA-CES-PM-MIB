-- This file was included in WWP MIB release 04-16-00-0047
--                                                      
-- CIENA-CES-PM-MIB.my
--
--

 CIENA-CES-PM DEFINITIONS ::= BEGIN
                                                                          
  IMPORTS                
   Integer32,Counter64,Unsigned32, NOTIFICATION-TYPE, OBJECT-TYPE, MODULE-IDENTITY
        FROM SNMPv2-SMI                 
   DisplayString, RowStatus, TruthValue, TEXTUAL-CONVENTION
       FROM SNMPv2-TC                
   cienaGlobalSeverity, cienaGlobalMacAddress
        FROM CIENA-GLOBAL-MIB
   cienaCesStatistics, cienaCesNotifications
        FROM CIENA-SMI
   CienaGlobalState, CienaStatsClear
   		FROM CIENA-TC;
	
	cienaCesPmMib MODULE-IDENTITY
			LAST-UPDATED "201609140000Z"
			ORGANIZATION
				"Ciena Corp."
			CONTACT-INFO
        	"  Mib Meister
               115 North Sullivan Road
               Spokane Valley, WA 99037
               USA            
               Phone:  +1 509 242 9000
               Email:  support@ciena.com"  
          DESCRIPTION
				"This module defines the performance monitor statistics objects."

          REVISION    "201609140000Z"
          DESCRIPTION
                                "The following tables have been expanded with additional statitistics
                                 added to the ExtendedTxRxProfile:
                                  cienaCesPmExtendedTxRxHistoryBinTable, cienaCesPmExtendedTxRxCurrBinTable, 
                                  cienaCesPmExtendedTxRxCurr24HBinTable, cienaCesPmExtendedTxRxHist24HBinTable, 
                                  cienaCesPmExtendedTxRxStatisticsBinTable, cienaCesPmExtendedTxRxTotalStatisticsBinTable
                                 The stats that were added:
                                  RxUcastPkts, RxInErrorPkts, 1519To2047OctsPkts, 2048To4095OctsPkts, 4096To9216OctsPkts,
                                  TxUcastPkts, Tx64OctsPkts, Tx65To127OctsPkts, Tx128To255OctsPkts, Tx256To511OctsPkts,
                                  Tx512To1023OctsPkts, Tx1024To1518OctsPkts, Tx1519To2047OctsPkts, Tx2048To4095OctsPkts,
                                  Tx4096To9216OctsPkts,TxDeferPkts, LinkUp, LinkDown, LinkFlap
                                 The cienaCesPmExtendedTxRxAllTimeBinTable was also made obsolete."
                                    

          REVISION    "201605270000Z"
          DESCRIPTION
				"Defined cienaCesPmBasicTxStats branch to support the BasicTx PM Profile statistics.
				 Defined cienaCesPmThreshold and all corresponding objects that fall beneath its OID
				  for support of PM Threshold Crossing Alerts (TCA) features.
				 Defined cienaCesPmMIBNotifications to contain PM NOTIFICATION-TYPE macros, along
				  with trap definitions supporting the PM TCA features.
				 Defined the following TEXTUAL-CONVENTIONs as part of PM TCA feature support:
				  PmTcaUnsigned64, PmTcaConfigStatus, PmTcaUnits, PmTcaAlertState, PmTcaWatermarkType,
				  PmTcaScheme, PmTcaThresholdType, PmTcaIntProfCfgAttrs, PmStatBitmap, PmTimeDate.
				 Added tpRsvpIngressCorout(20) enumeration to PmInterfaceType.
				 Removed the range restrictions of cienaCesPmInstanceNextIndex and
				  cienaCesPmInstanceIndex objects.
				 Clarified the DESCRIPTION clauses of objects cienaCesPmInstanceNextIndex,
				  cienaCesPmInstanceInterfaceId, cienaCesPmInstanceInterfaceId2,
				  cienaCesPmInstanceRowStatus.
				 Updated cienaCesPmInstanceInterfaceId2 object to read-create, allowing support for
				  row creations to specify secondary interface id for instances where single interface
				  id is not sufficient to uniquely identify an interface."

          REVISION    "201604080000Z"
          DESCRIPTION
                                "Added ETSI stats for the follwing profile types:
                                    tdmOcnPortStats"



          REVISION    "201603080000Z"
          DESCRIPTION
                                "Added the following new profile types:
                                    tdmOcnPortStats
                                    tdmDs3PortStats"

          REVISION    "201602240000Z"
          DESCRIPTION
                                "Added the following tables, and all objects defined within:
                                    cienaCesPmTdmDS3PortTotalStatisticsBinTable
                                    cienaCesPmTdmDS3PortStatisticsBinTable
                                    cienaCesPmTdmDS3PortHist24HBinTable
                                    cienaCesPmTdmDS3PortCurr24HBinTable
                                    cienaCesPmTdmDS3PortCurrBinTable
                                    cienaCesPmTdmDS3PortHistoryBinTable"

          REVISION    "201512180000Z"
          DESCRIPTION
				"Added the following objects:
                                    cienaCesPmTdmPwHistoryBinTxPkt
                                    cienaCesPmTdmPwHistoryBinEsp
                                    cienaCesPmTdmPwHistoryBinSesp
                                    cienaCesPmTdmPwHistoryBinUasp
                                    cienaCesPmTdmPwHistoryBinCvp
                                    cienaCesPmTdmPwHistoryBinFcp
                                    cienaCesPmTdmPwHistoryBinAsp
                                    cienaCesPmTdmPwHistoryBinTtp
                                    cienaCesPmTdmPwCurrBinTxPkt
                                    cienaCesPmTdmPwCurrBinEsp
                                    cienaCesPmTdmPwCurrBinSesp
                                    cienaCesPmTdmPwCurrBinUasp
                                    cienaCesPmTdmPwCurrBinCvp
                                    cienaCesPmTdmPwCurrBinFcp
                                    cienaCesPmTdmPwCurrBinAsp
                                    cienaCesPmTdmPwCurrBinTtp
                                    cienaCesPmTdmPwCurr24HBinTxPkt
                                    cienaCesPmTdmPwCurr24HBinEsp
                                    cienaCesPmTdmPwCurr24HBinSesp
                                    cienaCesPmTdmPwCurr24HBinUasp
                                    cienaCesPmTdmPwCurr24HBinCvp
                                    cienaCesPmTdmPwCurr24HBinFcp
                                    cienaCesPmTdmPwCurr24HBinAsp
                                    cienaCesPmTdmPwCurr24HBinTtp
                                    cienaCesPmTdmPwHist24HBinTxPkt
                                    cienaCesPmTdmPwHist24HBinEsp
                                    cienaCesPmTdmPwHist24HBinSesp
                                    cienaCesPmTdmPwHist24HBinUasp
                                    cienaCesPmTdmPwHist24HBinCvp
                                    cienaCesPmTdmPwHist24HBinFcp
                                    cienaCesPmTdmPwHist24HBinAsp
                                    cienaCesPmTdmPwHist24HBinTtp
                                    cienaCesPmTdmPwStatisticsBinTxPkt
                                    cienaCesPmTdmPwStatisticsBinEsp
                                    cienaCesPmTdmPwStatisticsBinSesp
                                    cienaCesPmTdmPwStatisticsBinUasp
                                    cienaCesPmTdmPwStatisticsBinCvp
                                    cienaCesPmTdmPwStatisticsBinFcp
                                    cienaCesPmTdmPwStatisticsBinAsp
                                    cienaCesPmTdmPwStatisticsBinTtp
                                    cienaCesPmTdmPwTotalStatisticsBinTxPkt
                                    cienaCesPmTdmPwTotalStatisticsBinEsp
                                    cienaCesPmTdmPwTotalStatisticsBinSesp
                                    cienaCesPmTdmPwTotalStatisticsBinUasp
                                    cienaCesPmTdmPwTotalStatisticsBinCvp
                                    cienaCesPmTdmPwTotalStatisticsBinFcp
                                    cienaCesPmTdmPwTotalStatisticsBinAsp
                                    cienaCesPmTdmPwTotalStatisticsBinTtp
                                 Added the following tables, and all objects defined within:
                                    cienaCesPmTdmOCnPortTotalStatisticsBinTable
                                    cienaCesPmTdmOCnPortStatisticsBinTable
                                    cienaCesPmTdmOCnPortHist24HBinTable
                                    cienaCesPmTdmOCnPortCurr24HBinTable
                                    cienaCesPmTdmOCnPortCurrBinTable
                                    cienaCesPmTdmOCnPortHistoryBinTable"

          REVISION    "201511300000Z"
          DESCRIPTION
				"Renamed tdmT1PortStats to tdmAnsiPortStats(11), and renamed 
                                 tdmE1PortStats to tdmEtsiPortStats(12), in PmProfileType."

          REVISION    "201508140000Z"
          DESCRIPTION
				"Defined nodes: cienaCesPmInstanceIndexXref and cienaCesPmInstanceIndexXrefAuto.
				 Defined cienaCesPmInstanceIndexXrefAutoTable."

          REVISION    "201501190000Z"
          DESCRIPTION
				"Added ptp(17), otu(18), and odu(19) enumerations to PmInterfaceType.
				 Added basicPtp(15), basicOtu(16), and basicOdu(17) to PmProfileType.
				 Defined PmProfileFieldMapBasicPtp,PmProfileFieldMapBasicOtu,PmProfileFieldMapBasicOdu.
				 Defined PmInteger32Milli and PmCounter64Atto.
				 Defined cienaCesPmBasicPtpStats and all corresponding objects that fall beneath its OID.
				 Defined cienaCesPmBasicOtuStats and all corresponding objects that fall beneath its OID.
				 Defined cienaCesPmBasicOduStats and all corresponding objects that fall beneath its OID."

          REVISION    "201403190000Z"
          DESCRIPTION
				"Added tpStaticTransitUnidir(15) and tpStaticTransitCorout(16) enumerations to PmInterfaceType.
				 Added basictxrxBiDir(14) enumeration to PmProfileType.
				 Defined cienaCesPmBasicTxRxBiDirStats and all corresponding objects that fall beneath its OID."

          REVISION    "201309170000Z"
          DESCRIPTION
				"Added cienaCesPmInstanceHistoryClear."

          REVISION    "201308080000Z"
          DESCRIPTION           "Added the following objects:
                                    cienaCesPmExtendedTxRxHist24HBinEndTime
                                    cienaCesPmExtendedTxRxHist24HBinClearTime
                                    cienaCesPmBasicTxRxHist24HBinEndTime
                                    cienaCesPmBasicTxRxHist24HBinClearTime
                                    cienaCesPmIGMPHist24HBinClearTime
                                    cienaCesPmAccessHist24HBinEndTime
                                    cienaCesPmAccessHist24HBinClearTime
                                    cienaCesPmFloodContainerHist24HBinEndTime
                                    cienaCesPmFloodContainerHist24HBinClearTime
                                    cienaCesPmBasicRxHist24HBinEndTime
                                    cienaCesPmBasicRxHist24HBinClearTime
                                    cienaCesPmQueueGroupHist24HBinEndTime
                                    cienaCesPmQueueGroupHist24HBinClearTime
                                    cienaCesPmEgressQueueHist24HBinEndTime
                                    cienaCesPmEgressQueueHist24HBinClearTime
                                 Added the following tables, and all objects defined within:
                                    cienaCesPmExtendedTxRxStatisticsBinTable
                                    cienaCesPmExtendedTxRxTotalStatisticsBinTable
                                    cienaCesPmBasicTxRxStatisticsBinTable
                                    cienaCesPmBasicTxRxTotalStatisticsBinTable
                                    cienaCesPmIGMPStatisticsBinTable
                                    cienaCesPmIGMPTotalStatisticsBinTable
                                    cienaCesPmAccessStatisticsBinTable
                                    cienaCesPmAccessTotalStatisticsBinTable
                                    cienaCesPmFloodContainerStatisticsBinTable
                                    cienaCesPmFloodContainerTotalStatisticsBinTable
                                    cienaCesPmBasicRxStatisticsBinTable
                                    cienaCesPmBasicRxTotalStatisticsBinTable
                                    cienaCesPmQueueGroupStatisticsBinTable
                                    cienaCesPmQueueGroupTotalStatisticsBinTable
                                    cienaCesPmEgressQueueStatisticsBinTable
                                    cienaCesPmEgressQueueTotalStatisticsBinTable
                                 Changed STATUS clause to deprecated for the following tables, and all objects defined within:
                                    cienaCesPmExtendedTxRxAllTimeBinTable
                                    cienaCesPmBasicTxRxAllTimeBinTable
                                    cienaCesPmIGMPAllTimeBinTable
                                    cienaCesPmAccessAllTimeBinTable
                                    cienaCesPmFloodContainerAllTimeBinTable
                                    cienaCesPmBasicRxAllTimeBinTable
                                    cienaCesPmQueueGroupAllTimeBinTable
                                    cienaCesPmEgressQueueAllTimeBinTable"

          REVISION    "201305150000Z"
          DESCRIPTION
				"Added enumeration overflow(7) to PmBinState.
				Modified cienaCesPmInstanceBinCount to accept 0 bins.
				Added cienaCesPmInstanceInterfaceOperState."
          REVISION    "201303280000Z"
          DESCRIPTION
				"Added object: cienaCesPmInstanceConfigurationMode.
				Added object: cienaCesPmInstanceAlignment.
				Added enumeration idf(6) to PmBinState.
				Added tdmPort(13), tdmVc(14) to PmInterfaceType.
				Added tdmT1PortStats(11), tdmE1PortStats(12), tdmPwStats(13), to PmProfileType.
				Changed the MAX-ACCESS clause of cienaCesPmInstanceType from read-only to read-create.
				Defined cienaCesPmTdmT1PortStats and all corresponding objects that fall beneath its OID.
				Defined cienaCesPmTdmE1PortStats and all corresponding objects that fall beneath its OID.
				Defined cienaCesPmTdmPwStats and all corresponding objects that fall beneath its OID."
          REVISION    "201203290000Z"
          DESCRIPTION
				"Added the new RxLOutRangePkts counter to all applicable tables"
          REVISION    "201203280000Z"
          DESCRIPTION
				"Changed the behavior of cienaCesPmInstanceStartTime,
				cienaCesPmInstanceStartDate, cienaCesPmInstanceEndTime and
				cienaCesPmInstanceEndDate.
				If only the start date is set, the start time is set to the
				first second on that day, i.e., 00:00:00. If only the end date
				is set, the end time is set to the last second of that day,
				i.e., 23:59:59. Previously, a time or date not set by one of
				these OIDs would be set to the current time or date. End dates
				set in the past are now rejected. They were previously accepted.
				When read, dates and times are in UTC or local time, depending
				on the system 'timestamp' setting. They were previously in UTC.
				The trailing newline has been removed from the date/time string.
				A trailing Z is added to indicate UTC."

          REVISION    "201202200000Z"
          DESCRIPTION
				"Changed the type of cienaCesPmInstanceStartTimeValue and
				cienaCesPmInstanceEndTimeValue from TimeTicks to Integer32.
				The values had previously been treated as Integer32.
				Changed the DEFVAL of cienaCesPmInstanceCollectionTimeFormat
				from utc to none. The actual default value used previously was none."

          REVISION    "201110260000Z"
          DESCRIPTION
          		"Added  new types in PmInterfaceType and PmProfileType. Added a new object 
          		cienaCesPmInstanceDynamic in cienaCesPmInstanceTable."
          REVISION    "201106200000Z"
          DESCRIPTION
          		"Added  cienaCesPmEgressQueueStats and cienaCesPmQueueGroupStats."

          REVISION    "201103060000Z"
          DESCRIPTION
          		"Added  cienaCesPmPersistenceInterval and cienaCesPmPersistenceStorage"

			::= { cienaCesStatistics 1 }

--
-- Node definitions
--
    cienaCesPmGlobal                         OBJECT IDENTIFIER ::= { cienaCesPmMib 1}
    cienaCesPmMIBObjects                     OBJECT IDENTIFIER ::= { cienaCesPmMib 2 } 
    cienaCesPmInstance                       OBJECT IDENTIFIER ::= { cienaCesPmMIBObjects 2 }  
    cienaCesPmStatistics                     OBJECT IDENTIFIER ::= { cienaCesPmMIBObjects 3 }
    cienaCesPmExtendedTxRxStats              OBJECT IDENTIFIER ::= { cienaCesPmStatistics 1 }
    cienaCesPmBasicTxRxStats                 OBJECT IDENTIFIER ::= { cienaCesPmStatistics 2 }
    cienaCesPmIgmpStats                      OBJECT IDENTIFIER ::= { cienaCesPmStatistics 3 }
    cienaCesPmAccessStats                    OBJECT IDENTIFIER ::= { cienaCesPmStatistics 4 }
    cienaCesPmFloodContainerStats            OBJECT IDENTIFIER ::= { cienaCesPmStatistics 5 } 
    cienaCesPmBasicRxStats                   OBJECT IDENTIFIER ::= { cienaCesPmStatistics 6 }
    cienaCesPmEgressQueueStats               OBJECT IDENTIFIER ::= { cienaCesPmStatistics 7 }
    cienaCesPmQueueGroupStats                OBJECT IDENTIFIER ::= { cienaCesPmStatistics 8 }
    cienaCesPmTdmT1PortStats                 OBJECT IDENTIFIER ::= { cienaCesPmStatistics 9 }
    cienaCesPmTdmE1PortStats                 OBJECT IDENTIFIER ::= { cienaCesPmStatistics 10 }
    cienaCesPmTdmPwStats                     OBJECT IDENTIFIER ::= { cienaCesPmStatistics 11 }
    cienaCesPmBasicTxRxBiDirStats            OBJECT IDENTIFIER ::= { cienaCesPmStatistics 12 }
    cienaCesPmBasicPtpStats                  OBJECT IDENTIFIER ::= { cienaCesPmStatistics 13 }
    cienaCesPmBasicOtuStats                  OBJECT IDENTIFIER ::= { cienaCesPmStatistics 14 }
    cienaCesPmBasicOduStats                  OBJECT IDENTIFIER ::= { cienaCesPmStatistics 15 }
    cienaCesPmTdmOCnPortStats                OBJECT IDENTIFIER ::= { cienaCesPmStatistics 16 }
    cienaCesPmTdmDS3PortStats                OBJECT IDENTIFIER ::= { cienaCesPmStatistics 17 }
    cienaCesPmBasicTxStats                   OBJECT IDENTIFIER ::= { cienaCesPmStatistics 18 }
    cienaCesPmInstanceIndexXref              OBJECT IDENTIFIER ::= { cienaCesPmMIBObjects 4 }
    cienaCesPmInstanceIndexXrefAuto          OBJECT IDENTIFIER ::= { cienaCesPmInstanceIndexXref 1 }
    cienaCesPmThreshold                      OBJECT IDENTIFIER ::= { cienaCesPmMib 3 }
    cienaCesPmIntervalProfile                OBJECT IDENTIFIER ::= { cienaCesPmThreshold 1 }
    cienaCesPmInstanceThreshold              OBJECT IDENTIFIER ::= { cienaCesPmThreshold 2 }
    cienaCesPmInstanceAdjustmentTca          OBJECT IDENTIFIER ::= { cienaCesPmThreshold 3 }
    cienaCesPmInstanceAlertTca               OBJECT IDENTIFIER ::= { cienaCesPmThreshold 4 }
    cienaCesPmMIBNotificationPrefix          OBJECT IDENTIFIER ::= { cienaCesNotifications 40 }
    cienaCesPmMIBNotifications               OBJECT IDENTIFIER ::= { cienaCesPmMIBNotificationPrefix 0 }


-- 
--Textual Conventions                                         
--

 PmConfigurationMode ::= TEXTUAL-CONVENTION
     STATUS       current
     DESCRIPTION  "Configuration mode of the PM."
     SYNTAX       INTEGER {
                     auto(1),
                     user(2)
                  } 

 PmAlignment ::= TEXTUAL-CONVENTION
     STATUS       current
     DESCRIPTION  "Alignment value of the PM."
     SYNTAX       INTEGER {
                     startTime(1),
                     localClock(2)
                  }
 
 PmInstanceType ::= TEXTUAL-CONVENTION
     STATUS       current
     DESCRIPTION  "Instance type of the PM."
     SYNTAX       INTEGER {
                     proactive(1),
                     ondemand(2)
                  } 
 
  PmBinState ::= TEXTUAL-CONVENTION
     STATUS       current
     DESCRIPTION  "State of the PM Bin."
     SYNTAX       INTEGER {
                      notValid(1),
                      valid(2),
                      partial(3),
                      timeChange(4),
                      cleared(5),
                      idf(6),
                      overflow(7)
                  }
  PmInterfaceType ::= TEXTUAL-CONVENTION
     STATUS       current
     DESCRIPTION  "Interface type of the PM instance."
     SYNTAX       INTEGER {
                        port(1),
    			subport(2),
    			pbttransit(3),
   			pbtservice(4),
   			datasource(5),
   			igmpvs(6),
   			accessflow(7),
   			mplsVc(8),
   			qosflow(9),
   			queueGroupInstance(10),
 			lineModule(11),
 			mplsTransitLsp(12),
 			tdmPort(13),
 			tdmVc(14),
 			tpStaticTransitUnidir(15),
 			tpStaticTransitCorout(16),
 			ptp(17),
 			otu(18),
 			odu(19),
 			tpRsvpIngressCorout(20),
			unknown(99)
                    }
  PmProfileType ::= TEXTUAL-CONVENTION
     STATUS       current
     DESCRIPTION  "Profile type of the PM instance."
     SYNTAX       INTEGER {
                           basictxrx(1),
   			   extendedtxrx(2),
   			   basiccounter(3),
   			   accessstats(4),
   			   igmpvsstats(5), 
   			   floodcontainer(6),
   			   basicrx(7),
 			   queueGroupStats(8),
 			   egressQueueStats(9), 
 			   basictx(10),
 			   tdmAnsiPortStats(11),
 			   tdmEtsiPortStats(12),
 			   tdmPwStats(13),
 			   basictxrxBiDir(14),
 			   basicPtp(15),
 			   basicOtu(16),
 			   basicOdu(17),
			   tdmOcnPortStats(18),
			   tdmDs3PortStats(19),
   			   unknown(99)
   			} 
  PmProfileFieldMapBasicPtp ::= TEXTUAL-CONVENTION
     STATUS       current
     DESCRIPTION  "Provides a bitmap where each bit represents a field defined within the PM Profile.
                   This may be used within a table to define an object that may highlight a particular
                   characteristic about each field defined within the PM Profile.

                   Each bit should correspond to a particular field within the PM Profile and, as such,
                   correspond to a particular object within the same table row with matching ordering
                   and naming conventions as specified by the field names, as defined below."
     SYNTAX       BITS {
                           oprOch(0),
                           oprnOch(1),
                           oprMinOch(2),
                           oprMaxOch(3),
                           oprAvgOch(4),
                           optOch(5),
                           optMinOch(6),
                           optMaxOch(7),
                           optAvgOch(8),
                           oprOts(9),
                           oprnOts(10),
                           oprMinOts(11),
                           oprMaxOts(12),
                           oprAvgOts(13),
                           dgdAvgOch(14),
                           dgdMaxOch(15)
   			}
  PmProfileFieldMapBasicOtu ::= TEXTUAL-CONVENTION
     STATUS       current
     DESCRIPTION  "Provides a bitmap where each bit represents a field defined within the PM Profile.
                   This may be used within a table to define an object that may highlight a particular
                   characteristic about each field defined within the PM Profile.

                   Each bit should correspond to a particular field within the PM Profile and, as such,
                   correspond to a particular object within the same table row with matching ordering
                   and naming conventions as specified by the field names, as defined below."
     SYNTAX       BITS {
                           cvOtu(0),
                           esOtu(1),
                           sesOtu(2),
                           sefsOtu(3),
                           fecOtu(4),
                           hccsOtu(5),
                           prfBerOtu(6),
                           prfBerMaxOtu(7),
                           pfBerEOtu(8),
                           qMinOtu(9),
                           qMaxOtu(10),
                           qAvgOtu(11),
                           qStdevOtu(12),
                           uncFecBlkOtu(13)
   			}
  PmProfileFieldMapBasicOdu ::= TEXTUAL-CONVENTION
     STATUS       current
     DESCRIPTION  "Provides a bitmap where each bit represents a field defined within the PM Profile.
                   This may be used within a table to define an object that may highlight a particular
                   characteristic about each field defined within the PM Profile.

                   Each bit should correspond to a particular field within the PM Profile and, as such,
                   correspond to a particular object within the same table row with matching ordering
                   and naming conventions as specified by the field names, as defined below."
     SYNTAX       BITS {
                           cvOdu(0),
                           esOdu(1),
                           sesOdu(2),
                           uasOdu(3),
                           fcOdu(4)
   			}
  PmInteger32Milli ::= TEXTUAL-CONVENTION
     STATUS       current
     DESCRIPTION  "A value using Integer32 to represent a decimal number in units of thousandths.
                   To derive the decimal equivalent of an object with this SYNTAX, divide the
                   Integer32 value by 1000."
     SYNTAX       Integer32
  PmCounter64Atto ::= TEXTUAL-CONVENTION
     STATUS       current
     DESCRIPTION  "A value using Counter64 to represent a decimal number in units of quintillionths.
                   To derive the decimal equivalent of an object with this SYNTAX, divide the
                   Counter64 value by 1000000000000000000."
     SYNTAX       Counter64

  PmTcaUnsigned64 ::= TEXTUAL-CONVENTION
     STATUS       current
     DESCRIPTION  "A value using Counter64 to represent a decimal number for use
                   by the PM TCA feature for purposes of representing values for
                   TCA related data fields such as basis, boundary and watermark
                   data."
     SYNTAX       Counter64
  PmTcaConfigStatus ::= TEXTUAL-CONVENTION
     STATUS       current
     DESCRIPTION  "This object represents the status of configuration of a PM
                   Threshold Crossing Alert (TCA) feature.  For features which
                   require multiple optional attributes, this status may
                   indicate when such attributes are not configured in a way to
                   enable such feature.  Objects using this textual convention
                   should indicate the feature it represents and the necessary
                   attributes for its configuration."
     SYNTAX       INTEGER {
                           unspecified(1),
                           notSupported(2),
                           noProfile(3),
                           notConfigured(4),
                           partiallyConfigured(5),
                           configured(6)
                  }
  PmTcaUnits ::= TEXTUAL-CONVENTION
     STATUS       current
     DESCRIPTION  "The way in which data is intrepreted, handled, and
                   represented by the PM Threshold Crossing Alert (TCA) feature."
     SYNTAX       INTEGER {
                           unspecified(1),
                           bitsPerSecond(2)
                  }
  PmTcaAlertState ::= TEXTUAL-CONVENTION
     STATUS       current
     DESCRIPTION  "Value used by state driven PM TCA features to incidate the
                   current or historical alert state of a PM instance."
     SYNTAX       INTEGER {
                           unspecified(1),
                           normal(2),
                           alert(3)
                  }
  PmTcaWatermarkType ::= TEXTUAL-CONVENTION
     STATUS       current
     DESCRIPTION  "Value used by objects to indicate an accompanying watermark
                   object type.  The DESCRIPTION clause of objects using this
                   textual convention should indicate the accompanying watermark
                   object to which this type applies.

                   A value of high indicates the watermark represents a high
                   watermark, representing the highest value during a specified
                   interval."
     SYNTAX       INTEGER {
                           unspecified(1),
                           high(2)
                  }
  PmTcaScheme ::= TEXTUAL-CONVENTION
     STATUS       current
     DESCRIPTION  "Value used to define the way in which statistics are used by
                   the PM TCA features.

                   A value of inclusiveOr is used to indicate that any single
                   statistic which matches the criteria used by the feature will
                   be used.  For high watermark determination, this means that
                   for a given sample interval, the highest single applicable
                   statistic will be used to set a new high watermark value and
                   all other applicable statistics are ignored."
     SYNTAX       INTEGER {
                           unspecified(1),
                           inclusiveOr(2)
                  }
  PmTcaThresholdType ::= TEXTUAL-CONVENTION
     STATUS       current
     DESCRIPTION  "Value used to describe configuration related to PM TCA
                   thresholds.  Objects using this textual convention should
                   specify in their DESCRIPTION clause the corresponding object
                   to which this type applies, thereby defining how its value
                   should be intrepreted."
     SYNTAX       INTEGER {
                           unspecified(1),
                           absoluteValue(2),
                           percentage(3)
                  }
  PmTcaIntProfCfgAttrs ::= TEXTUAL-CONVENTION
     STATUS       current
     DESCRIPTION  "Bitmap representing configuration attributes associated with
                   an interval profile used by the PM TCA features.  This is
                   intended to represent attributes which may be modified after
                   an interval profile has been created.  For this reason,
                   attributes which may not be modified are not included in
                   this textual convention."
     SYNTAX       BITS {
                        adjustmentInterval(0),
                        adjustmentThreshold(1),
                        adjustmentThresholdPercentage(2),
                        overflowThreshold(3),
                        overflowThresholdPercentage(4),
                        overflowCount(5),
                        underflowThreshold(6),
                        underflowThresholdPercentage(7),
                        underflowCount(8),
                        alertInterval(9),
                        alertThresholdPercentage(10)
                  }

  PmStatBitmap ::= TEXTUAL-CONVENTION
     STATUS       current
     DESCRIPTION  "Objects of this type represent a group of zero or more
                   statistics applicable to the data model as described in such
                   object's DESCRIPTION clause.  An object may use this textual
                   convention to represent a set of statistics for a particular
                   PM profile, depending on the profile associated with the data
                   set used by the object.

                   The bitmap represents sub-identifier values for a particular
                   bin type branch underneath a particular pm profile branch in
                   the cienaCesPmStatistics branch.

                   The DESCRIPTION clause of an object using this textual
                   convention should indicate the way in which the appropriate
                   PM profile branch is identified, and the particular bin type
                   branch to which the data applies.

                   For example, an object using this textual convention returns
                   a value with single bit set at statisticSubIdentifier9(9).  
                   The object is discovered to be associated with a PM instance
                   with an accompanying value of 'basictxrx' for its
                   cienaCesPmInstanceProfileType object.  The DESCRIPTION clause
                   of the object with this textual convention indicates that the
                   object value is applicable to statistics in the Current Bin
                   of the PM profile.  The provided information means that the
                   applicable cienaCesPmStatistics branch is
                   cienaCesPmBasicTxRxStats.  Within the
                   cienaCesPmBasicTxRxStats branch, the branch for the Current
                   Bin, cienaCesPmBasicTxRxCurrBinTable, should be used.  Within
                   the cienaCesPmBasicTxRxCurrBinTable is the listing of objects
                   defined in cienaCesPmBasicTxRxCurrBinEntry.  The object value
                   statisticSubIdentifier9(9) would then apply to the row with
                   object sub-identifier value of 9.  In this case the statistic
                   is cienaCesPmBasicTxRxCurrBinRxDroppedBytes at OID ending 
                   with the sub-identifier value of 9."
     SYNTAX       BITS {
                           statisticSubIdentifier0(0),
                           statisticSubIdentifier1(1),
                           statisticSubIdentifier2(2),
                           statisticSubIdentifier3(3),
                           statisticSubIdentifier4(4),
                           statisticSubIdentifier5(5),
                           statisticSubIdentifier6(6),
                           statisticSubIdentifier7(7),
                           statisticSubIdentifier8(8),
                           statisticSubIdentifier9(9),
                           statisticSubIdentifier10(10),
                           statisticSubIdentifier11(11),
                           statisticSubIdentifier12(12),
                           statisticSubIdentifier13(13),
                           statisticSubIdentifier14(14),
                           statisticSubIdentifier15(15),
                           statisticSubIdentifier16(16),
                           statisticSubIdentifier17(17),
                           statisticSubIdentifier18(18),
                           statisticSubIdentifier19(19),
                           statisticSubIdentifier20(20),
                           statisticSubIdentifier21(21),
                           statisticSubIdentifier22(22),
                           statisticSubIdentifier23(23),
                           statisticSubIdentifier24(24),
                           statisticSubIdentifier25(25),
                           statisticSubIdentifier26(26),
                           statisticSubIdentifier27(27),
                           statisticSubIdentifier28(28),
                           statisticSubIdentifier29(29),
                           statisticSubIdentifier30(30),
                           statisticSubIdentifier31(31),
                           statisticSubIdentifier32(32),
                           statisticSubIdentifier33(33),
                           statisticSubIdentifier34(34),
                           statisticSubIdentifier35(35),
                           statisticSubIdentifier36(36),
                           statisticSubIdentifier37(37),
                           statisticSubIdentifier38(38),
                           statisticSubIdentifier39(39),
                           statisticSubIdentifier40(40),
                           statisticSubIdentifier41(41),
                           statisticSubIdentifier42(42),
                           statisticSubIdentifier43(43),
                           statisticSubIdentifier44(44),
                           statisticSubIdentifier45(45),
                           statisticSubIdentifier46(46),
                           statisticSubIdentifier47(47),
                           statisticSubIdentifier48(48),
                           statisticSubIdentifier49(49),
                           statisticSubIdentifier50(50)
   			}

  PmTimeDate ::= TEXTUAL-CONVENTION
     STATUS       current
     DESCRIPTION  "String representing time and date of a specified event.
                   Value will be reported in local time or UTC as determined by
                   the system 'timestamp' setting, formatted as
                   'Wed Jun 30 21:49:03 2016'.  A trailing 'Z' indicates UTC.
                   When there is no time value to report, objects using this
                   textual convention may return a string of characters
                   describing condition in a way that is applicable to the
                   data being represented by the object."
     SYNTAX      OCTET STRING (SIZE (0..255))

 cienaCesPmGlobalState OBJECT-TYPE
    SYNTAX      CienaGlobalState
    MAX-ACCESS  read-write
   	STATUS      current
    DESCRIPTION
        	"This object allows the user to globally configure the PM administrative state.
          	This object must be enabled in order for a PM instance to be operationally enabled."
    ::= { cienaCesPmGlobal 1 } 
 
 cienaCesPmPersistenceInterval	OBJECT-TYPE
    SYNTAX      Unsigned32 (60..86400)
    UNITS		"seconds"
    MAX-ACCESS  read-write
   	STATUS      current
    DESCRIPTION
        	"This object allows the user to globally configure the PM persistence interval."
    ::= { cienaCesPmGlobal 2 }
  
 cienaCesPmPersistenceStorage	OBJECT-TYPE
    SYNTAX      INTEGER
    			{
    			externalUsb(1),
    			onBoard(2)
    			}	
    MAX-ACCESS  read-write
   	STATUS      current
    DESCRIPTION
        	"This object allows the user to globally configure the PM persistence storage."
    ::= { cienaCesPmGlobal 3 }
   
 cienaCesPmInstanceNextIndex	OBJECT-TYPE
 	SYNTAX	Unsigned32
 	MAX-ACCESS read-only
 	STATUS 	   current
 	DESCRIPTION "This object contains an unused value for cienaCesPmInstanceIndex, 
 		   		 or a zero to indicate that none exist.  When creating a PM instance entry in
 		   		 the cienaCesPmInstanceTable, the cienaCesPmNextAvailablePmInstanceIndex value may
 		   		 be used for cienaCesPmInstanceIndex in the new table entry."
 	::= { cienaCesPmMIBObjects 1 }
  --
  -- PM instance Table  
  --
  cienaCesPmInstanceTable OBJECT-TYPE
     SYNTAX     SEQUENCE OF CienaCesPmInstanceEntry
     MAX-ACCESS not-accessible
     STATUS     current
     DESCRIPTION
            "The (conceptual) table listing the configuration 
            parameters for the PM instance table.
            
            To create an entry in this table, cienaCesPmPmProfileType,
            cienaCesPmInterfaceType, cienaCesPmInterfaceId and 
            cienaCesPmInstanceName must be specified and 
            cienaCesPmInstanceRowStatus must be set to createAndGo."  
     ::= { cienaCesPmInstance 1 }
                
 cienaCesPmInstanceEntry OBJECT-TYPE
     SYNTAX      CienaCesPmInstanceEntry
     MAX-ACCESS  not-accessible
     STATUS      current
     DESCRIPTION
           "An entry (conceptual row) in the cienaCesPmInstanceTable."
     INDEX {cienaCesPmInstanceIndex}
     ::= { cienaCesPmInstanceTable 1 }
        
 CienaCesPmInstanceEntry ::=  SEQUENCE {               
     cienaCesPmInstanceIndex                          	Unsigned32,
     cienaCesPmInstanceName                           	DisplayString,
     cienaCesPmInstanceType                           	PmInstanceType,        
     cienaCesPmInstanceInterfaceType                  	PmInterfaceType,
     cienaCesPmInstanceInterfaceId			Unsigned32,   
     cienaCesPmInstanceInterfaceName                  	DisplayString, 
     cienaCesPmInstanceProfileType                   	PmProfileType,  
     cienaCesPmInstanceStartTime			DisplayString,
     cienaCesPmInstanceStartDate			DisplayString,
     cienaCesPmInstanceEndTime				DisplayString,
     cienaCesPmInstanceEndDate				DisplayString,
     cienaCesPmInstanceBinCount	 		        Unsigned32,
     cienaCesPmInstanceBinDuration			INTEGER,
     cienaCesPmInstanceAdminState                     	CienaGlobalState,
     cienaCesPmInstanceOperState                      	CienaGlobalState, 
     cienaCesPmInstanceCollectionTimeFormat		INTEGER,
     cienaCesPmInstanceStartTimeValue			Integer32,
     cienaCesPmInstanceEndTimeValue			Integer32,
     cienaCesPmInstanceRowStatus			RowStatus,
     cienaCesPmInstanceClear				CienaStatsClear,
     cienaCesPmInstanceInterfaceId2			Unsigned32,
     cienaCesPmInstanceDynamic                           TruthValue,
     cienaCesPmInstanceConfigurationMode                PmConfigurationMode,
     cienaCesPmInstanceAlignment                        PmAlignment,
     cienaCesPmInstanceInterfaceOperState               CienaGlobalState,
     cienaCesPmInstanceHistoryClear                     CienaStatsClear
 }
 cienaCesPmInstanceIndex OBJECT-TYPE
     SYNTAX      Unsigned32
     MAX-ACCESS  not-accessible
     STATUS      current
     DESCRIPTION
             "A unique identifier for the PM instance entry."
     ::= { cienaCesPmInstanceEntry 1 } 
     
 cienaCesPmInstanceName OBJECT-TYPE
     SYNTAX		DisplayString (SIZE (1..31))
     MAX-ACCESS	read-create
     STATUS 	current
     DESCRIPTION  "Name for the PM instance."
     
     ::=	{ cienaCesPmInstanceEntry 2 }

   cienaCesPmInstanceType OBJECT-TYPE
     SYNTAX		PmInstanceType
     MAX-ACCESS	read-create
     STATUS 	current
     DESCRIPTION   "Type for the PM instance."
     DEFVAL			{ondemand}
     ::=	{ cienaCesPmInstanceEntry 3 }
      
   cienaCesPmInstanceInterfaceType OBJECT-TYPE
     SYNTAX		PmInterfaceType
     MAX-ACCESS	read-create
     STATUS 	current
     DESCRIPTION		"Interface type associated with the PM instance."
     
     ::=	{ cienaCesPmInstanceEntry 4 }
   
   cienaCesPmInstanceInterfaceId OBJECT-TYPE
     SYNTAX		Unsigned32
     MAX-ACCESS	read-create
     STATUS 	current
     DESCRIPTION	
     	"Interface ID associated with the PM instance uniquely identifying the interface
         associated with the PM instance.

         The value of this object depends on the interface type and may be encoded to
         suit.  For example, when the cienaCesPmInstanceInterfaceType is of type port(1)
         the value of this object refers to a port identifier (PGID).

         For some interface types, the value of this object is not sufficient to uniquely
         identify an interface.  In such cases, the cienaCesPmInstanceInterfaceId2 object
         is used to provide further resolution for uniquely identifying the interface.
         For such interfaces, the value of this object and the cienaCesPmInstanceInterfaceId2
         object may be normalized during row creation as evident by subsequent get of this
         object and the cienaCesPmInstanceInterfaceId2 object."
     ::=	{ cienaCesPmInstanceEntry 5 }

   
   cienaCesPmInstanceInterfaceName OBJECT-TYPE
     SYNTAX		DisplayString
     MAX-ACCESS	read-only
     STATUS 	current
     DESCRIPTION		"Interface name associated with the PM instance."
     
     ::=	{ cienaCesPmInstanceEntry 6 }
   
  cienaCesPmInstanceProfileType OBJECT-TYPE
     SYNTAX		PmProfileType
     MAX-ACCESS	read-create
     STATUS 	current
     DESCRIPTION		"Profile type of the PM instance statistics."
     
     ::=	{ cienaCesPmInstanceEntry 7 }
 
  cienaCesPmInstanceStartTime OBJECT-TYPE
  SYNTAX 		DisplayString 
  MAX-ACCESS	read-create
  STATUS		current
  DESCRIPTION	"When set, specifies the collection start time for the PM instance in the local time
				zone. The input time format is hh:mm or hh:mm:ss. If not set, but
				cienaCesPmInstanceStartDate is set, the time defaults to 00:00:00.
				When read, indicates the collection start date and time for the PM instance in
				local time or UTC, as determined by the system 'timestamp' setting, formatted as
				'Wed Jun 30 21:49:08 1993'. A trailing 'Z' indicates UTC."
  	::=	{ cienaCesPmInstanceEntry 8 }
  
  cienaCesPmInstanceStartDate OBJECT-TYPE
  SYNTAX 		DisplayString 
  MAX-ACCESS	read-create
  STATUS		current
  DESCRIPTION	"When set, specifies the collection start date for the PM instance in the local time
				zone. The input date format is [yy]yy-mm-dd or mm-dd. If the year is omitted, the
				current year is used.
				When read, indicates the collection start date and time for the PM instance in
				local time or UTC, as determined by the system 'timestamp' setting, formatted as
				'Wed Jun 30 21:49:08 1993'. A trailing 'Z' indicates UTC."
    ::=	{ cienaCesPmInstanceEntry 9 }

  cienaCesPmInstanceEndTime OBJECT-TYPE
  SYNTAX 		DisplayString 
  MAX-ACCESS	read-create
  STATUS		current
  DESCRIPTION	"When set, specifies the collection end time for the PM instance in the local time
				zone. The input time format is hh:mm or hh:mm:ss. If not set, but
				cienaCesPmInstanceEndDate is set, the time defaults to 23:59:59.
				When read, indicates the collection end date and time for the PM instance in
				local time or UTC, as determined by the system 'timestamp' setting, formatted
				as 'Wed Jun 30 21:49:08 1993'. A trailing 'Z' indicates UTC."
  	::=	{ cienaCesPmInstanceEntry 10 }
  	
  cienaCesPmInstanceEndDate OBJECT-TYPE
  SYNTAX 		DisplayString 
  MAX-ACCESS	read-create
  STATUS		current
  DESCRIPTION	"When set, specifies the collection end date for the PM instance in the local time
				zone. The input date format is [yy]yy-mm-dd or mm-dd. If the year is omitted, the
				current year is used.
				When read, indicates the collection end date and time for the PM instance in
				local time or UTC, as determined by the system 'timestamp' setting, formatted
				as 'Wed Jun 30 21:49:08 1993'. A trailing 'Z' indicates UTC."
  	::=	{ cienaCesPmInstanceEntry 11 }
 
  cienaCesPmInstanceBinCount OBJECT-TYPE
     SYNTAX      Unsigned32 (0..65535) 
     MAX-ACCESS  read-create
     STATUS      current        
     DESCRIPTION
             "Represents the number of history bins for the PM instance. A value of 0 indicates that
	     there are no history bins other than the 24hrHistoryBin.  The current and current24Hr bins
	     are not included in this bin count and still exist as well."
      DEFVAL 	 {32}
     ::= { cienaCesPmInstanceEntry 12 }
  
  cienaCesPmInstanceBinDuration OBJECT-TYPE  
    SYNTAX		INTEGER	 {
    						minutes-1(1),
    						minutes-5(2),
    						minutes-10(3),
    						minutes-15(4),
    						minutes-30(5),   
    						minutes-60(6),
    						hours-24(7)
    }
    MAX-ACCESS  read-create
    STATUS      current    
    DESCRIPTION
             "Represents the bin duration for the PM instance." 
    DEFVAL		{minutes-15}
     ::= { cienaCesPmInstanceEntry 13 }
	
  cienaCesPmInstanceAdminState OBJECT-TYPE
     SYNTAX      CienaGlobalState
     MAX-ACCESS  read-create
     STATUS      current   
     DESCRIPTION
             "Administrative state of the PM instance."
     ::= { cienaCesPmInstanceEntry 14 } 

  
  cienaCesPmInstanceOperState OBJECT-TYPE
     SYNTAX      CienaGlobalState
     MAX-ACCESS  read-only
     STATUS      current
     DESCRIPTION
             "Operational state for the PM instance."
     ::= { cienaCesPmInstanceEntry 15 }
    
   cienaCesPmInstanceCollectionTimeFormat  OBJECT-TYPE
      SYNTAX		INTEGER { 
      						 none(0),
      						 utc(1),
      						 relative-to-now(2)
      						}
      MAX-ACCESS		read-create
      STATUS			current
      DESCRIPTION
			"This object allows the user to choose the reference time of PM instance collection
			start and end times. The value none(0) sets the start time to now and the end time to
			none, ignoring any time values specified by the user. The value utc(1) sets the start
			and end time value references to the Unix Epoch, January 1, 1970, 00:00:00 UTC. The
			value relative-to-now(2) sets the start and end time value references to now. The
			default value is none(0).
      		This object returns a value of none(0) on GET."    
      DEFVAL 	  {none}
      ::= { cienaCesPmInstanceEntry 16 }
      
   cienaCesPmInstanceStartTimeValue		 OBJECT-TYPE
       SYNTAX		Integer32 
       MAX-ACCESS	read-create
       STATUS		current
       DESCRIPTION
			"This object specifies the collection start time of the PM instance in seconds from the
			reference time specified by the value of the cienaCesPmInstanceCollectionTimeFormat
			object.
			If the collection time format is set to utc(1), then this object specifies the start
			time value in the Unix Epoch, starting January 1, 1970, 00:00:00 UTC. If the
			cienaCesPmInstanceCollectionTimeFormat is set to relative-to-now(2), this object
			specifies the start time in seconds from now. If the
			cienaCesPmInstanceCollectionTimeFormat object has a value of none(0), the value of this
			object is ignored and the start time is set to now.
       		This object returns a value of 0 on GET. The start date/time for the PM instance is displayed
       		using the cienaCesPmInstanceStartDate/cienaCesPmInstanceStartTime objects."
       	::= { cienaCesPmInstanceEntry 17 }
     
      
   cienaCesPmInstanceEndTimeValue		 OBJECT-TYPE
       SYNTAX		Integer32 
       MAX-ACCESS	read-create
       STATUS		current
       DESCRIPTION
			"This object specifies the collection end time of the PM instance in seconds from the
			reference time specified by the value of the cienaCesPmInstanceCollectionTimeFormat
			object.
			If the collection time format is set to utc(1), then this object specifies the end time
			value relative to the Unix Epoch, January 1, 1970, 00:00:00 UTC. If the
			cienaCesPmInstanceCollectionTimeFormat is set to relative-to-now(2), this object
			specifies the end time in seconds from now. If the value of the
			cienaCesPmInstanceCollectionTimeFormat object is none(0), the value of this object is
			ignored and no specific collection end time is specified. 
			This object returns a value of 0 on GET. The end date/time for the PM instance is displayed
       		using the cienaCesPmInstanceEndDate/cienaCesPmInstanceEndTime objects."
       	::= { cienaCesPmInstanceEntry 18 }
   	     
   --row status
   cienaCesPmInstanceRowStatus OBJECT-TYPE
     SYNTAX       RowStatus      
     MAX-ACCESS   read-create
     STATUS       current
     DESCRIPTION
        "Used to manage the creation and deletion of the conceptual rows in this table.
         To create a row in this table, set this object to 'createAndGo'. 
         To delete a row in this table, set this object to 'destroy'.

         When creating a row in this table, the index object cienaCesPmInstanceIndex
         must specify a valid, unused index or specify value zero which will cause
         the new row to be created at the next available index.  Prior to creating the
         new row, the cienaCesPmInstanceNextIndex object may be referenced to fetch
         the next available index."
     ::= { cienaCesPmInstanceEntry 19 }
   
   cienaCesPmInstanceClear OBJECT-TYPE
     SYNTAX      CienaStatsClear     				 
     MAX-ACCESS  read-create
     STATUS      current   
     DESCRIPTION
             "Clears the current counts for the bins associated with given instance."
     ::= { cienaCesPmInstanceEntry 20 } 
 
 cienaCesPmInstanceInterfaceId2 OBJECT-TYPE
     SYNTAX        Unsigned32
     MAX-ACCESS    read-create
     STATUS        current
     DESCRIPTION
             "InterfaceId2 in the PM instance acts as a secondary identifying index in cases where
              the cienaCesPmInstanceInterfaceId object cannot uniquely identify the interface
              associated with the PM instance.

              For interfaces which do not utilize this secondary object, the value of this object
              is zero and unused during new row creation.

              For interfaces which utilize this secondary object, the value of this object is specific
              to the interface type.  During new row creation, the value of this object may be used
              along with the cienaCesPmInstanceInterfaceId object value to uniquely identify the
              interface, and such usage may result in the normalization of the values for this object
              and the cienaCesPmInstanceInterface object, as evident by subsequent get of this
              object and the cienaCesPmInstanceInterfaceId object."
     ::=      { cienaCesPmInstanceEntry 21}
 
  cienaCesPmInstanceDynamic OBJECT-TYPE
     SYNTAX        TruthValue
     MAX-ACCESS    read-only
     STATUS        current
     DESCRIPTION
             "Dynamic PM instances are not created via CLI or SNMP."
     ::=      { cienaCesPmInstanceEntry 22}

   cienaCesPmInstanceConfigurationMode OBJECT-TYPE
     SYNTAX      PmConfigurationMode
     MAX-ACCESS  read-only
     STATUS      current
     DESCRIPTION "Configuration mode for the PM instance."
     DEFVAL      {user}
     ::=         { cienaCesPmInstanceEntry 23 }

   cienaCesPmInstanceAlignment OBJECT-TYPE
     SYNTAX      PmAlignment
     MAX-ACCESS  read-create
     STATUS      current
     DESCRIPTION "Alignment value for the PM instance."
     DEFVAL      {localClock}
     ::=         { cienaCesPmInstanceEntry 24 }

  cienaCesPmInstanceInterfaceOperState OBJECT-TYPE
     SYNTAX      CienaGlobalState
     MAX-ACCESS  read-only
     STATUS      current
     DESCRIPTION
             "Operational state for the attached interface monitored by the PM instance."
     ::= { cienaCesPmInstanceEntry 25 }

   cienaCesPmInstanceHistoryClear OBJECT-TYPE
     SYNTAX      CienaStatsClear
     MAX-ACCESS  read-create
     STATUS      current   
     DESCRIPTION
             "Setting this object to clear(1) will clear the History and 24HrHistory bins associated
              with the given instance."
     ::= { cienaCesPmInstanceEntry 26 } 


 --ExtendedTxRx Profile for ports
 
  cienaCesPmExtendedTxRxHistoryBinTable OBJECT-TYPE
     SYNTAX     SEQUENCE OF CienaCesPmExtendedTxRxHistoryBinEntry
     MAX-ACCESS not-accessible
     STATUS     current
     DESCRIPTION
            "The (conceptual) read-only table listing the extended TxRx profile statistics."  
     ::= { cienaCesPmExtendedTxRxStats 1 }
     
   cienaCesPmExtendedTxRxHistoryBinEntry OBJECT-TYPE
     SYNTAX      CienaCesPmExtendedTxRxHistoryBinEntry
     MAX-ACCESS  not-accessible
     STATUS      current
     DESCRIPTION
           "An entry (conceptual row) in the cienaCesPmExtendedTxRxHistoryBinTable.

           This table lists the stats for all the history bins of the PM instance, as 
           specified by the bin-count object of the PM instance. History bins are displayed in the order
           so that #1 bin always represents the most recently completed bin and #2 - the bin previous to that
           and so on. The statistics are displayed for only the instances with valid bins (with start time >0), 
	       as indicated by the operational state of the corresponding PM instance."  

     INDEX { cienaCesPmInstanceIndex, cienaCesPmExtendedTxRxHistoryBinIndex }
     ::= { cienaCesPmExtendedTxRxHistoryBinTable 1 }
        
 CienaCesPmExtendedTxRxHistoryBinEntry ::=  SEQUENCE { 
 	 cienaCesPmExtendedTxRxHistoryBinIndex                   	Unsigned32,
     cienaCesPmExtendedTxRxHistoryBinStartTime		       	   	DisplayString,
     cienaCesPmExtendedTxRxHistoryBinEndTime					DisplayString,
     cienaCesPmExtendedTxRxHistoryBinClearTime					DisplayString,
     cienaCesPmExtendedTxRxHistoryBinDuration			  	   	Unsigned32,   
     cienaCesPmExtendedTxRxHistoryBinState					   	PmBinState,   
     cienaCesPmExtendedTxRxHistoryBinRxBytes                  	Counter64,
     cienaCesPmExtendedTxRxHistoryBinRxPkts                   	Counter64,
     cienaCesPmExtendedTxRxHistoryBinRxCrcErrorPkts           	Counter64,
     cienaCesPmExtendedTxRxHistoryBinRxMcastPkts              	Counter64,
     cienaCesPmExtendedTxRxHistoryBinRxBcastPkts              	Counter64,
     cienaCesPmExtendedTxRxHistoryBinUndersizePkts            	Counter64,
     cienaCesPmExtendedTxRxHistoryBinOversizePkts             	Counter64,
     cienaCesPmExtendedTxRxHistoryBinFragmentsPkts            	Counter64,
     cienaCesPmExtendedTxRxHistoryBinJabbersPkts              	Counter64,
     cienaCesPmExtendedTxRxHistoryBin64OctsPkts               	Counter64,
     cienaCesPmExtendedTxRxHistoryBin65To127OctsPkts          	Counter64,
     cienaCesPmExtendedTxRxHistoryBin128To255OctsPkts         	Counter64,
     cienaCesPmExtendedTxRxHistoryBin256To511OctsPkts         	Counter64,
     cienaCesPmExtendedTxRxHistoryBin512To1023OctsPkts        	Counter64,
     cienaCesPmExtendedTxRxHistoryBin1024To1518OctsPkts       	Counter64,
     cienaCesPmExtendedTxRxHistoryBinTxBytes                  	Counter64,
     cienaCesPmExtendedTxRxHistoryBinTxTBytes                 	Counter64,
     cienaCesPmExtendedTxRxHistoryBinTxPkts                   	Counter64,
     cienaCesPmExtendedTxRxHistoryBinTxBcastPkts              	Counter64,
     cienaCesPmExtendedTxRxHistoryBinTxMcastPkts              	Counter64,
     cienaCesPmExtendedTxRxHistoryBinTxExDeferPkts            	Counter64,
     cienaCesPmExtendedTxRxHistoryBinTxGiantPkts              	Counter64,
     cienaCesPmExtendedTxRxHistoryBinTxUnderRunPkts           	Counter64,
     cienaCesPmExtendedTxRxHistoryBinTxCrcErrorPkts           	Counter64,
     cienaCesPmExtendedTxRxHistoryBinTxLCheckErrorPkts        	Counter64,
     cienaCesPmExtendedTxRxHistoryBinTxLOutRangePkts          	Counter64,
     cienaCesPmExtendedTxRxHistoryBinTxLateCollPkts           	Counter64,
     cienaCesPmExtendedTxRxHistoryBinTxExCollPkts             	Counter64,
     cienaCesPmExtendedTxRxHistoryBinTxSingleCollPkts         	Counter64,
     cienaCesPmExtendedTxRxHistoryBinTxCollPkts               	Counter64,
     cienaCesPmExtendedTxRxHistoryBinDropEvents               	Counter64,
     cienaCesPmExtendedTxRxHistoryBinInDiscards               	Counter64,
     cienaCesPmExtendedTxRxHistoryBinTxPausePkts              	Counter64,
     cienaCesPmExtendedTxRxHistoryBinRxPausePkts              	Counter64,
     cienaCesPmExtendedTxRxHistoryBinRxBytesPerSec          	Counter64,
     cienaCesPmExtendedTxRxHistoryBinRxFramesPerSec         	Counter64,
     cienaCesPmExtendedTxRxHistoryBinTxBytesPerSec          	Counter64,
     cienaCesPmExtendedTxRxHistoryBinTxFramesPerSec         	Counter64,
     cienaCesPmExtendedTxRxHistoryBinRxLOutRangePkts            Counter64,
     cienaCesPmExtendedTxRxHistoryBinRxUcastPkts                Counter64,
     cienaCesPmExtendedTxRxHistoryBinRxInErrorPkts              Counter64,
     cienaCesPmExtendedTxRxHistoryBin1519To2047OctsPkts         Counter64,
     cienaCesPmExtendedTxRxHistoryBin2048To4095OctsPkts         Counter64,
     cienaCesPmExtendedTxRxHistoryBin4096To9216OctsPkts         Counter64,
     cienaCesPmExtendedTxRxHistoryBinTxUcastPkts                Counter64,
     cienaCesPmExtendedTxRxHistoryBinTx64OctsPkts               Counter64,
     cienaCesPmExtendedTxRxHistoryBinTx65To127OctsPkts          Counter64,
     cienaCesPmExtendedTxRxHistoryBinTx128To255OctsPkts         Counter64,
     cienaCesPmExtendedTxRxHistoryBinTx256To511OctsPkts         Counter64,
     cienaCesPmExtendedTxRxHistoryBinTx512To1023OctsPkts        Counter64,
     cienaCesPmExtendedTxRxHistoryBinTx1024To1518OctsPkts       Counter64,
     cienaCesPmExtendedTxRxHistoryBinTx1519To2047OctsPkts       Counter64,
     cienaCesPmExtendedTxRxHistoryBinTx2048To4095OctsPkts       Counter64,
     cienaCesPmExtendedTxRxHistoryBinTx4096To9216OctsPkts       Counter64,
     cienaCesPmExtendedTxRxHistoryBinTxDeferPkts                Counter64,
     cienaCesPmExtendedTxRxHistoryBinLinkUp                     Counter64,
     cienaCesPmExtendedTxRxHistoryBinLinkDown                   Counter64,
     cienaCesPmExtendedTxRxHistoryBinLinkFlap                   Counter64
  }                                                        
  cienaCesPmExtendedTxRxHistoryBinIndex OBJECT-TYPE
     SYNTAX      Unsigned32 (1..65535) 
     MAX-ACCESS  not-accessible
     STATUS      current
     DESCRIPTION
             "Bin Number associated with the ExtendedTxRxHistoryBin entry."
     ::= { cienaCesPmExtendedTxRxHistoryBinEntry 1 }

   cienaCesPmExtendedTxRxHistoryBinStartTime   OBJECT-TYPE
     SYNTAX		DisplayString
     MAX-ACCESS	read-only
     STATUS		current
     DESCRIPTION "Collection start time of the bin."
     ::= { cienaCesPmExtendedTxRxHistoryBinEntry 2	}
   
   cienaCesPmExtendedTxRxHistoryBinEndTime		OBJECT-TYPE
   	SYNTAX 	DisplayString
   	MAX-ACCESS read-only
   	STATUS 		current
   	DESCRIPTION	"Collection end time of the bin."
   	::= {  cienaCesPmExtendedTxRxHistoryBinEntry 3 }
   	
  cienaCesPmExtendedTxRxHistoryBinClearTime	OBJECT-TYPE
  	SYNTAX	DisplayString
   	MAX-ACCESS read-only
   	STATUS 		current
   	DESCRIPTION	"Collection clear time of the bin."
   	::= {  cienaCesPmExtendedTxRxHistoryBinEntry 4 }
 	
   cienaCesPmExtendedTxRxHistoryBinDuration OBJECT-TYPE
     SYNTAX      Unsigned32 (1..65535) 
     UNITS		"minutes"
     MAX-ACCESS  read-only
     STATUS      current
     DESCRIPTION
             "Duration of the bin."
     ::= { cienaCesPmExtendedTxRxHistoryBinEntry 5 }
  
  cienaCesPmExtendedTxRxHistoryBinState OBJECT-TYPE
     SYNTAX      PmBinState 
     MAX-ACCESS  read-only
     STATUS      current
     DESCRIPTION
             "State of the bin."
     ::= { cienaCesPmExtendedTxRxHistoryBinEntry 6 }
  
  cienaCesPmExtendedTxRxHistoryBinRxBytes OBJECT-TYPE
     SYNTAX      Counter64
     MAX-ACCESS  read-only
     STATUS      current
     DESCRIPTION
             "The number of bytes received by this port."
     ::= { cienaCesPmExtendedTxRxHistoryBinEntry 7 }

 cienaCesPmExtendedTxRxHistoryBinRxPkts OBJECT-TYPE
     SYNTAX      Counter64
     MAX-ACCESS  read-only
     STATUS      current
     DESCRIPTION
             "The number of packets received by this port."
     ::= { cienaCesPmExtendedTxRxHistoryBinEntry 8 } 
  
  cienaCesPmExtendedTxRxHistoryBinRxCrcErrorPkts OBJECT-TYPE
     SYNTAX      Counter64
     MAX-ACCESS  read-only
     STATUS      current
     DESCRIPTION
             "The number of packets received with CRC errors by this port."
     ::= { cienaCesPmExtendedTxRxHistoryBinEntry 9 }   
  
  cienaCesPmExtendedTxRxHistoryBinRxMcastPkts OBJECT-TYPE
     SYNTAX      Counter64
     MAX-ACCESS  read-only
     STATUS      current
     DESCRIPTION
             "The total number of multicast packets received for the given port."
     ::= { cienaCesPmExtendedTxRxHistoryBinEntry 10 }
     
  cienaCesPmExtendedTxRxHistoryBinRxBcastPkts OBJECT-TYPE
     SYNTAX      Counter64
     MAX-ACCESS  read-only
     STATUS      current
     DESCRIPTION
             "The number of broadcast packets received by this port."
     ::= { cienaCesPmExtendedTxRxHistoryBinEntry 11 }
  
  cienaCesPmExtendedTxRxHistoryBinUndersizePkts OBJECT-TYPE
     SYNTAX      Counter64
     MAX-ACCESS  read-only
     STATUS      current
     DESCRIPTION
             "The total number of packets received that were
            less than 64 octets long (excluding framing bits,
            but including FCS octets) and were otherwise well
            formed."
     ::= { cienaCesPmExtendedTxRxHistoryBinEntry 12 }
  
  cienaCesPmExtendedTxRxHistoryBinOversizePkts OBJECT-TYPE
     SYNTAX      Counter64
     MAX-ACCESS  read-only
     STATUS      current
     DESCRIPTION
             "The total number of packets received that were
            longer than 1518 octets  but less than or equal to the MTU
            (excluding framing bits, but including FCS octets)
            and were otherwise well formed."
     ::= { cienaCesPmExtendedTxRxHistoryBinEntry 13 }
  
  cienaCesPmExtendedTxRxHistoryBinFragmentsPkts OBJECT-TYPE
     SYNTAX      Counter64
     MAX-ACCESS  read-only
     STATUS      current
     DESCRIPTION
             "The total number of packets received that were less
            than 64 octets in length (excluding framing bits but
            including FCS octets) and had either a bad Frame
            Check Sequence (FCS) with an integral number of
            octets (FCS Error) or a bad FCS with a non-integral
            number of octets (Alignment Error)."
     ::= { cienaCesPmExtendedTxRxHistoryBinEntry 14 }
  
  cienaCesPmExtendedTxRxHistoryBinJabbersPkts OBJECT-TYPE
     SYNTAX      Counter64
     MAX-ACCESS  read-only
     STATUS      current
     DESCRIPTION
             "The total number of packets received that were
            longer than 1518 octets (excluding framing bits,
            but including FCS octets), and had either a bad
            Frame Check Sequence (FCS) with an integral number
            of octets (FCS Error) or a bad FCS with a
            non-integral number of octets (Alignment Error)."
     ::= { cienaCesPmExtendedTxRxHistoryBinEntry 15 }
  
  cienaCesPmExtendedTxRxHistoryBin64OctsPkts OBJECT-TYPE
     SYNTAX      Counter64
     MAX-ACCESS  read-only
     STATUS      current
     DESCRIPTION
             "The total number of packets (including bad
            packets) received that were 64 octets in length
            (excluding framing bits but including FCS octets)."
     ::= { cienaCesPmExtendedTxRxHistoryBinEntry 16 }
  
  cienaCesPmExtendedTxRxHistoryBin65To127OctsPkts OBJECT-TYPE
     SYNTAX      Counter64
     MAX-ACCESS  read-only
     STATUS      current
     DESCRIPTION
             "The total number of packets (including bad
            packets) received that were between
            65 and 127 octets in length inclusive
            (excluding framing bits but including FCS octets)."
     ::= { cienaCesPmExtendedTxRxHistoryBinEntry 17 }
  
  cienaCesPmExtendedTxRxHistoryBin128To255OctsPkts OBJECT-TYPE
     SYNTAX      Counter64
     MAX-ACCESS  read-only
     STATUS      current
     DESCRIPTION
             "The total number of packets (including bad
            packets) received that were between
            128 and 255 octets in length inclusive
            (excluding framing bits but including FCS octets)."
     ::= { cienaCesPmExtendedTxRxHistoryBinEntry 18 }
  
  cienaCesPmExtendedTxRxHistoryBin256To511OctsPkts OBJECT-TYPE
     SYNTAX      Counter64
     MAX-ACCESS  read-only
     STATUS      current
     DESCRIPTION
             "The total number of packets (including bad
            packets) received that were between
            256 and 511 octets in length inclusive
            (excluding framing bits but including FCS octets)."
     ::= { cienaCesPmExtendedTxRxHistoryBinEntry 19 }
  
  cienaCesPmExtendedTxRxHistoryBin512To1023OctsPkts OBJECT-TYPE
     SYNTAX      Counter64
     MAX-ACCESS  read-only
     STATUS      current
     DESCRIPTION
             "The total number of packets (including bad
            packets) received that were between
            512 and 1023 octets in length inclusive
            (excluding framing bits but including FCS octets)."
     ::= { cienaCesPmExtendedTxRxHistoryBinEntry 20 }
  
  cienaCesPmExtendedTxRxHistoryBin1024To1518OctsPkts OBJECT-TYPE
     SYNTAX      Counter64
     MAX-ACCESS  read-only
     STATUS      current
     DESCRIPTION
             "The total number of packets (including bad
            packets) received that were between
            1024 and 1518 octets in length inclusive
            (excluding framing bits but including FCS octets)."
     ::= { cienaCesPmExtendedTxRxHistoryBinEntry 21 }
  
  cienaCesPmExtendedTxRxHistoryBinTxBytes OBJECT-TYPE
     SYNTAX      Counter64
     MAX-ACCESS  read-only
     STATUS      current
     DESCRIPTION
             "The number of octets transmitted on this port."
     ::= { cienaCesPmExtendedTxRxHistoryBinEntry 22 }
  
  cienaCesPmExtendedTxRxHistoryBinTxTBytes OBJECT-TYPE
     SYNTAX      Counter64
     MAX-ACCESS  read-only
     STATUS      current
     DESCRIPTION
             "The total number of octets transmitted on this port."
     ::= { cienaCesPmExtendedTxRxHistoryBinEntry 23 }
  
  cienaCesPmExtendedTxRxHistoryBinTxPkts OBJECT-TYPE
     SYNTAX      Counter64
     MAX-ACCESS  read-only
     STATUS      current
     DESCRIPTION
             "The total number of packets transmitted on this port."
     ::= { cienaCesPmExtendedTxRxHistoryBinEntry 24 }
  
  cienaCesPmExtendedTxRxHistoryBinTxBcastPkts OBJECT-TYPE
     SYNTAX      Counter64
     MAX-ACCESS  read-only
     STATUS      current
     DESCRIPTION
             "The number of broadcast packets transmitted on the port."
     ::= { cienaCesPmExtendedTxRxHistoryBinEntry 25 }
  
  cienaCesPmExtendedTxRxHistoryBinTxMcastPkts OBJECT-TYPE
     SYNTAX      Counter64
     MAX-ACCESS  read-only
     STATUS      current
     DESCRIPTION
             "The number of multicast packets transmitted on the port."
     ::= { cienaCesPmExtendedTxRxHistoryBinEntry 26 }
  
  cienaCesPmExtendedTxRxHistoryBinTxExDeferPkts OBJECT-TYPE
     SYNTAX      Counter64
     MAX-ACCESS  read-only
     STATUS      current
     DESCRIPTION
             "The number of excessive defer packets transmitted on a port."
     ::= { cienaCesPmExtendedTxRxHistoryBinEntry 27}
  
  cienaCesPmExtendedTxRxHistoryBinTxGiantPkts OBJECT-TYPE
     SYNTAX      Counter64
     MAX-ACCESS  read-only
     STATUS      current
     DESCRIPTION
             "The number of too big packets transmitted on a port."
     ::= { cienaCesPmExtendedTxRxHistoryBinEntry 28 }
  
  cienaCesPmExtendedTxRxHistoryBinTxUnderRunPkts OBJECT-TYPE
     SYNTAX      Counter64
     MAX-ACCESS  read-only
     STATUS      current
     DESCRIPTION
             "The number of underrun packets transmitted on a port."
     ::= { cienaCesPmExtendedTxRxHistoryBinEntry 29 }
  
  cienaCesPmExtendedTxRxHistoryBinTxCrcErrorPkts OBJECT-TYPE
     SYNTAX      Counter64
     MAX-ACCESS  read-only
     STATUS      current
     DESCRIPTION
             "The number of CRC error packets transmitted on a port."
     ::= { cienaCesPmExtendedTxRxHistoryBinEntry 30 }
  
  cienaCesPmExtendedTxRxHistoryBinTxLCheckErrorPkts OBJECT-TYPE
     SYNTAX      Counter64
     MAX-ACCESS  read-only
     STATUS      current
     DESCRIPTION
             "The number of length check error packets transmitted on a port."
     ::= { cienaCesPmExtendedTxRxHistoryBinEntry 31 }
  
  cienaCesPmExtendedTxRxHistoryBinTxLOutRangePkts OBJECT-TYPE
     SYNTAX      Counter64
     MAX-ACCESS  read-only
     STATUS      current
     DESCRIPTION
             "The number of out of range packets transmitted on a port."
     ::= { cienaCesPmExtendedTxRxHistoryBinEntry 32 }
  
  cienaCesPmExtendedTxRxHistoryBinTxLateCollPkts OBJECT-TYPE
     SYNTAX      Counter64
     MAX-ACCESS  read-only
     STATUS      current
     DESCRIPTION
             "The number of late collision packets transmitted on a port."
     ::= { cienaCesPmExtendedTxRxHistoryBinEntry 33 }
  
  cienaCesPmExtendedTxRxHistoryBinTxExCollPkts OBJECT-TYPE
     SYNTAX      Counter64
     MAX-ACCESS  read-only
     STATUS      current
     DESCRIPTION
             "The number of excessive collision packets transmitted on a port."
     ::= { cienaCesPmExtendedTxRxHistoryBinEntry 34 }
  
  cienaCesPmExtendedTxRxHistoryBinTxSingleCollPkts OBJECT-TYPE
     SYNTAX      Counter64
     MAX-ACCESS  read-only
     STATUS      current
     DESCRIPTION
             "The number of single collision packets transmitted on a port."
     ::= { cienaCesPmExtendedTxRxHistoryBinEntry 35 }
  
  cienaCesPmExtendedTxRxHistoryBinTxCollPkts OBJECT-TYPE
     SYNTAX      Counter64
     MAX-ACCESS  read-only
     STATUS      current
     DESCRIPTION
             "The number of collision packets transmitted on a port."
     ::= { cienaCesPmExtendedTxRxHistoryBinEntry 36 }

  
  cienaCesPmExtendedTxRxHistoryBinDropEvents OBJECT-TYPE
     SYNTAX      Counter64
     MAX-ACCESS  read-only
     STATUS      current
     DESCRIPTION
             "The number of packet drop events on a port."
     ::= { cienaCesPmExtendedTxRxHistoryBinEntry 37 }
  
  cienaCesPmExtendedTxRxHistoryBinInDiscards OBJECT-TYPE
     SYNTAX      Counter64
     MAX-ACCESS  read-only
     STATUS      current
     DESCRIPTION
             "The number of packet discards on a port."
     ::= { cienaCesPmExtendedTxRxHistoryBinEntry 38 }
  
  cienaCesPmExtendedTxRxHistoryBinTxPausePkts OBJECT-TYPE
     SYNTAX      Counter64
     MAX-ACCESS  read-only
     STATUS      current
     DESCRIPTION
             "The pause packets transmitted on the port."
     ::= { cienaCesPmExtendedTxRxHistoryBinEntry 39 }
  
  cienaCesPmExtendedTxRxHistoryBinRxPausePkts OBJECT-TYPE
     SYNTAX      Counter64
     MAX-ACCESS  read-only
     STATUS      current
     DESCRIPTION
             "The pause packets received on the port."
     ::= { cienaCesPmExtendedTxRxHistoryBinEntry 40 }
  
  cienaCesPmExtendedTxRxHistoryBinRxBytesPerSec OBJECT-TYPE
     SYNTAX      Counter64
     MAX-ACCESS  read-only
     STATUS      current
     DESCRIPTION
             "The number of bytes received per second on this port."
     ::= { cienaCesPmExtendedTxRxHistoryBinEntry 41 }
  
  cienaCesPmExtendedTxRxHistoryBinRxFramesPerSec OBJECT-TYPE
     SYNTAX      Counter64
     MAX-ACCESS  read-only
     STATUS      current
     DESCRIPTION
             "The number of frames received per second on this port."
     ::= { cienaCesPmExtendedTxRxHistoryBinEntry 42 }
  
  cienaCesPmExtendedTxRxHistoryBinTxBytesPerSec OBJECT-TYPE
     SYNTAX      Counter64
     MAX-ACCESS  read-only
     STATUS      current
     DESCRIPTION
             "The number of bytes transmitted per second on this port."
     ::= { cienaCesPmExtendedTxRxHistoryBinEntry 43 }
  
  cienaCesPmExtendedTxRxHistoryBinTxFramesPerSec OBJECT-TYPE
     SYNTAX      Counter64
     MAX-ACCESS  read-only
     STATUS      current
     DESCRIPTION
             "The number of frames transmitted per second on this port."
     ::= { cienaCesPmExtendedTxRxHistoryBinEntry 44 }		
     	
  cienaCesPmExtendedTxRxHistoryBinRxLOutRangePkts OBJECT-TYPE
     SYNTAX      Counter64
     MAX-ACCESS  read-only
     STATUS      current
     DESCRIPTION
             "The total number of packets received that were
             longer than than the MTU
             (excluding framing bits,
             but including FCS octets) and were otherwise
             well formed."
     ::= { cienaCesPmExtendedTxRxHistoryBinEntry 45 }	

  cienaCesPmExtendedTxRxHistoryBinRxUcastPkts OBJECT-TYPE
     SYNTAX      Counter64
     MAX-ACCESS  read-only
     STATUS      current
     DESCRIPTION
             "The number of unicast packets received on the port."
     ::= { cienaCesPmExtendedTxRxHistoryBinEntry 46 }	

  cienaCesPmExtendedTxRxHistoryBinRxInErrorPkts OBJECT-TYPE
     SYNTAX      Counter64
     MAX-ACCESS  read-only
     STATUS      current
     DESCRIPTION
             "The number of in error packets received on the port."
     ::= { cienaCesPmExtendedTxRxHistoryBinEntry 47 }

  cienaCesPmExtendedTxRxHistoryBin1519To2047OctsPkts OBJECT-TYPE
     SYNTAX      Counter64
     MAX-ACCESS  read-only
     STATUS      current
     DESCRIPTION
             "The total number of packets (including bad
             packets) received that were between
             1519 and 2047 octets in length inclusive
             (excluding framing bits but including FCS octets)."
     ::= { cienaCesPmExtendedTxRxHistoryBinEntry 48 }

  cienaCesPmExtendedTxRxHistoryBin2048To4095OctsPkts OBJECT-TYPE
     SYNTAX      Counter64
     MAX-ACCESS  read-only
     STATUS      current
     DESCRIPTION
             "The total number of packets (including bad
             packets) received that were between
             2048 and 4095 octets in length inclusive
             (excluding framing bits but including FCS octets)."
     ::= { cienaCesPmExtendedTxRxHistoryBinEntry 49 }

  cienaCesPmExtendedTxRxHistoryBin4096To9216OctsPkts OBJECT-TYPE
     SYNTAX      Counter64
     MAX-ACCESS  read-only
     STATUS      current
     DESCRIPTION
             "The total number of packets (including bad
             packets) received that were between
             4096 and 9216 octets in length inclusive
             (excluding framing bits but including FCS octets)."
     ::= { cienaCesPmExtendedTxRxHistoryBinEntry 50 }

  cienaCesPmExtendedTxRxHistoryBinTxUcastPkts OBJECT-TYPE
     SYNTAX      Counter64
     MAX-ACCESS  read-only
     STATUS      current
     DESCRIPTION
             "The number of unicast packets transmitted on the port."
     ::= { cienaCesPmExtendedTxRxHistoryBinEntry 51 }

  cienaCesPmExtendedTxRxHistoryBinTx64OctsPkts OBJECT-TYPE
     SYNTAX      Counter64
     MAX-ACCESS  read-only
     STATUS      current
     DESCRIPTION
             "The total number of packets (including bad
             packets) transmitted that were between
             64 octets in length inclusive
             (excluding framing bits but including FCS octets)."
     ::= { cienaCesPmExtendedTxRxHistoryBinEntry 52 }

  cienaCesPmExtendedTxRxHistoryBinTx65To127OctsPkts OBJECT-TYPE
     SYNTAX      Counter64
     MAX-ACCESS  read-only
     STATUS      current
     DESCRIPTION
             "The total number of packets (including bad
             packets) transmitted that were between
             65 and 127 octets in length inclusive
             (excluding framing bits but including FCS octets)."
     ::= { cienaCesPmExtendedTxRxHistoryBinEntry 53 }

  cienaCesPmExtendedTxRxHistoryBinTx128To255OctsPkts OBJECT-TYPE
     SYNTAX      Counter64
     MAX-ACCESS  read-only
     STATUS      current
     DESCRIPTION
             "The total number of packets (including bad
             packets) transmitted that were between
             128 and 255 octets in length inclusive
             (excluding framing bits but including FCS octets)."
     ::= { cienaCesPmExtendedTxRxHistoryBinEntry 54 }

  cienaCesPmExtendedTxRxHistoryBinTx256To511OctsPkts OBJECT-TYPE
     SYNTAX      Counter64
     MAX-ACCESS  read-only
     STATUS      current
     DESCRIPTION
             "The total number of packets (including bad
             packets) transmitted that were between
             256 and 511 octets in length inclusive
             (excluding framing bits but including FCS octets)."
     ::= { cienaCesPmExtendedTxRxHistoryBinEntry 55 }

  cienaCesPmExtendedTxRxHistoryBinTx512To1023OctsPkts OBJECT-TYPE
     SYNTAX      Counter64
     MAX-ACCESS  read-only
     STATUS      current
     DESCRIPTION
             "The total number of packets (including bad
             packets) transmitted that were between
             512 and 1023 octets in length inclusive
             (excluding framing bits but including FCS octets)."
     ::= { cienaCesPmExtendedTxRxHistoryBinEntry 56 }

  cienaCesPmExtendedTxRxHistoryBinTx1024To1518OctsPkts OBJECT-TYPE
     SYNTAX      Counter64
     MAX-ACCESS  read-only
     STATUS      current
     DESCRIPTION
             "The total number of packets (including bad
             packets) transmitted that were between
             1024 and 1518 octets in length inclusive
             (excluding framing bits but including FCS octets)."
     ::= { cienaCesPmExtendedTxRxHistoryBinEntry 57 }

  cienaCesPmExtendedTxRxHistoryBinTx1519To2047OctsPkts OBJECT-TYPE
     SYNTAX      Counter64
     MAX-ACCESS  read-only
     STATUS      current
     DESCRIPTION
             "The total number of packets (including bad
             packets) transmitted that were between
             1519 and 2047 octets in length inclusive
             (excluding framing bits but including FCS octets)."
     ::= { cienaCesPmExtendedTxRxHistoryBinEntry 58 }

  cienaCesPmExtendedTxRxHistoryBinTx2048To4095OctsPkts OBJECT-TYPE
     SYNTAX      Counter64
     MAX-ACCESS  read-only
     STATUS      current
     DESCRIPTION
             "The total number of packets (including bad
             packets) transmitted that were between
             2048 and 4095 octets in length inclusive
             (excluding framing bits but including FCS octets)."
     ::= { cienaCesPmExtendedTxRxHistoryBinEntry 59 }

  cienaCesPmExtendedTxRxHistoryBinTx4096To9216OctsPkts OBJECT-TYPE
     SYNTAX      Counter64
     MAX-ACCESS  read-only
     STATUS      current
     DESCRIPTION
             "The total number of packets (including bad
             packets) transmitted that were between
             4096 and 9216 octets in length inclusive
             (excluding framing bits but including FCS octets)."
     ::= { cienaCesPmExtendedTxRxHistoryBinEntry 60 }

  cienaCesPmExtendedTxRxHistoryBinTxDeferPkts OBJECT-TYPE
     SYNTAX      Counter64
     MAX-ACCESS  read-only
     STATUS      current
     DESCRIPTION
             "The number of defer packets transmitted on the port."
     ::= { cienaCesPmExtendedTxRxHistoryBinEntry 61 }

  cienaCesPmExtendedTxRxHistoryBinLinkUp OBJECT-TYPE
     SYNTAX      Counter64
     MAX-ACCESS  read-only
     STATUS      current
     DESCRIPTION
             "The number of link up events on the port."
     ::= { cienaCesPmExtendedTxRxHistoryBinEntry 62 }

  cienaCesPmExtendedTxRxHistoryBinLinkDown OBJECT-TYPE
     SYNTAX      Counter64
     MAX-ACCESS  read-only
     STATUS      current
     DESCRIPTION
             "The number of link down events on the port."
     ::= { cienaCesPmExtendedTxRxHistoryBinEntry 63 }

  cienaCesPmExtendedTxRxHistoryBinLinkFlap OBJECT-TYPE
     SYNTAX      Counter64
     MAX-ACCESS  read-only
     STATUS      current
     DESCRIPTION
             "The number of link flap events on the port."
     ::= { cienaCesPmExtendedTxRxHistoryBinEntry 64 }

  --Extended Tx Rx Curr Bin Statistics Table

  cienaCesPmExtendedTxRxCurrBinTable OBJECT-TYPE
     SYNTAX     SEQUENCE OF CienaCesPmExtendedTxRxCurrBinEntry
     MAX-ACCESS not-accessible
     STATUS     current
     DESCRIPTION
            "The (conceptual) read-only table listing the extended TxRx profile statistics."  
     ::= { cienaCesPmExtendedTxRxStats 2 }
     
   cienaCesPmExtendedTxRxCurrBinEntry OBJECT-TYPE
     SYNTAX      CienaCesPmExtendedTxRxCurrBinEntry
     MAX-ACCESS  not-accessible
     STATUS      current
     DESCRIPTION
           "An entry (conceptual row) in the cienaCesPmExtendedTxRxCurrBinTable.

           This table lists the statistics for the current bin of the PM instance."  

     INDEX {cienaCesPmInstanceIndex }
     ::= { cienaCesPmExtendedTxRxCurrBinTable 1 }
        
 CienaCesPmExtendedTxRxCurrBinEntry ::=  SEQUENCE {
 	 cienaCesPmExtendedTxRxCurrBinStartTime					DisplayString,
 	 cienaCesPmExtendedTxRxCurrBinClearedTime					DisplayString,
     cienaCesPmExtendedTxRxCurrBinDuration						Unsigned32,   
     cienaCesPmExtendedTxRxCurrBinState						PmBinState,   
     cienaCesPmExtendedTxRxCurrBinRxBytes                  	Counter64,
     cienaCesPmExtendedTxRxCurrBinRxPkts                    	Counter64,
     cienaCesPmExtendedTxRxCurrBinRxCrcErrorPkts            	Counter64,
     cienaCesPmExtendedTxRxCurrBinRxMcastPkts               	Counter64,
     cienaCesPmExtendedTxRxCurrBinRxBcastPkts               	Counter64,
     cienaCesPmExtendedTxRxCurrBinUndersizePkts             	Counter64,
     cienaCesPmExtendedTxRxCurrBinOversizePkts              	Counter64,
     cienaCesPmExtendedTxRxCurrBinFragmentsPkts             	Counter64,
     cienaCesPmExtendedTxRxCurrBinJabbersPkts               	Counter64,
     cienaCesPmExtendedTxRxCurrBin64OctsPkts                	Counter64,
     cienaCesPmExtendedTxRxCurrBin65To127OctsPkts           	Counter64,
     cienaCesPmExtendedTxRxCurrBin128To255OctsPkts          	Counter64,
     cienaCesPmExtendedTxRxCurrBin256To511OctsPkts         	Counter64,
     cienaCesPmExtendedTxRxCurrBin512To1023OctsPkts         	Counter64,
     cienaCesPmExtendedTxRxCurrBin1024To1518OctsPkts        	Counter64,
     cienaCesPmExtendedTxRxCurrBinTxBytes                   	Counter64,
     cienaCesPmExtendedTxRxCurrBinTxTBytes                  	Counter64,
     cienaCesPmExtendedTxRxCurrBinTxPkts                    	Counter64,
     cienaCesPmExtendedTxRxCurrBinTxBcastPkts               	Counter64,
     cienaCesPmExtendedTxRxCurrBinTxMcastPkts               	Counter64,
     cienaCesPmExtendedTxRxCurrBinTxExDeferPkts             	Counter64,
     cienaCesPmExtendedTxRxCurrBinTxGiantPkts               	Counter64,
     cienaCesPmExtendedTxRxCurrBinTxUnderRunPkts            	Counter64,
     cienaCesPmExtendedTxRxCurrBinTxCrcErrorPkts            	Counter64,
     cienaCesPmExtendedTxRxCurrBinTxLCheckErrorPkts         	Counter64,
     cienaCesPmExtendedTxRxCurrBinTxLOutRangePkts           	Counter64,
     cienaCesPmExtendedTxRxCurrBinTxLateCollPkts            	Counter64,
     cienaCesPmExtendedTxRxCurrBinTxExCollPkts              	Counter64,
     cienaCesPmExtendedTxRxCurrBinTxSingleCollPkts          	Counter64,
     cienaCesPmExtendedTxRxCurrBinTxCollPkts                	Counter64,
     cienaCesPmExtendedTxRxCurrBinDropEvents                	Counter64,
     cienaCesPmExtendedTxRxCurrBinInDiscards                	Counter64,
     cienaCesPmExtendedTxRxCurrBinTxPausePkts               	Counter64,
     cienaCesPmExtendedTxRxCurrBinRxPausePkts               	Counter64,
     cienaCesPmExtendedTxRxCurrBinRxBytesPerSec             	Counter64,
     cienaCesPmExtendedTxRxCurrBinRxFramesPerSec            	Counter64,
     cienaCesPmExtendedTxRxCurrBinTxBytesPerSec             	Counter64,
     cienaCesPmExtendedTxRxCurrBinTxFramesPerSec            	Counter64,
     cienaCesPmExtendedTxRxCurrBinRxLOutRangePkts               Counter64,
     cienaCesPmExtendedTxRxCurrBinRxUcastPkts                   Counter64,
     cienaCesPmExtendedTxRxCurrBinRxInErrorPkts                 Counter64,
     cienaCesPmExtendedTxRxCurrBin1519To2047OctsPkts            Counter64,
     cienaCesPmExtendedTxRxCurrBin2048To4095OctsPkts            Counter64,
     cienaCesPmExtendedTxRxCurrBin4096To9216OctsPkts            Counter64,
     cienaCesPmExtendedTxRxCurrBinTxUcastPkts                   Counter64,
     cienaCesPmExtendedTxRxCurrBinTx64OctsPkts                  Counter64,
     cienaCesPmExtendedTxRxCurrBinTx65To127OctsPkts             Counter64,
     cienaCesPmExtendedTxRxCurrBinTx128To255OctsPkts            Counter64,
     cienaCesPmExtendedTxRxCurrBinTx256To511OctsPkts            Counter64,
     cienaCesPmExtendedTxRxCurrBinTx512To1023OctsPkts           Counter64,
     cienaCesPmExtendedTxRxCurrBinTx1024To1518OctsPkts          Counter64,
     cienaCesPmExtendedTxRxCurrBinTx1519To2047OctsPkts          Counter64,
     cienaCesPmExtendedTxRxCurrBinTx2048To4095OctsPkts          Counter64,
     cienaCesPmExtendedTxRxCurrBinTx4096To9216OctsPkts          Counter64,
     cienaCesPmExtendedTxRxCurrBinTxDeferPkts                   Counter64,
     cienaCesPmExtendedTxRxCurrBinLinkUp                        Counter64,
     cienaCesPmExtendedTxRxCurrBinLinkDown                      Counter64,
     cienaCesPmExtendedTxRxCurrBinLinkFlap                      Counter64
 } 
  
  cienaCesPmExtendedTxRxCurrBinStartTime   OBJECT-TYPE
     SYNTAX		DisplayString
     MAX-ACCESS	read-only
     STATUS		current
     DESCRIPTION "Collection start time for this PM instance."
     ::= { cienaCesPmExtendedTxRxCurrBinEntry 1 }
   
  cienaCesPmExtendedTxRxCurrBinClearedTime   OBJECT-TYPE
     SYNTAX		DisplayString
     MAX-ACCESS	read-only
     STATUS		current
     DESCRIPTION "Cleared time of current statistics for this PM instance."
     ::= { cienaCesPmExtendedTxRxCurrBinEntry 2}
                   
   cienaCesPmExtendedTxRxCurrBinDuration OBJECT-TYPE
     SYNTAX      Unsigned32 (1..65535) 
     UNITS		 "minutes"
     MAX-ACCESS  read-only
     STATUS      current
     DESCRIPTION
             "Duration to collect current statistics for this PM instance."
     ::= { cienaCesPmExtendedTxRxCurrBinEntry 3}
  
  cienaCesPmExtendedTxRxCurrBinState OBJECT-TYPE
     SYNTAX      PmBinState 
     MAX-ACCESS  read-only
     STATUS      current
     DESCRIPTION
             "State of the current statistics."
     ::= { cienaCesPmExtendedTxRxCurrBinEntry 4 }
  
  cienaCesPmExtendedTxRxCurrBinRxBytes OBJECT-TYPE
     SYNTAX      Counter64
     MAX-ACCESS  read-only
     STATUS      current
     DESCRIPTION
             "The number of bytes received by this PM instance."
     ::= { cienaCesPmExtendedTxRxCurrBinEntry 5 }

 cienaCesPmExtendedTxRxCurrBinRxPkts OBJECT-TYPE
     SYNTAX      Counter64
     MAX-ACCESS  read-only
     STATUS      current
     DESCRIPTION
             "The number of packets received by this PM instance."
     ::= { cienaCesPmExtendedTxRxCurrBinEntry 6 } 
  
  cienaCesPmExtendedTxRxCurrBinRxCrcErrorPkts OBJECT-TYPE
     SYNTAX      Counter64
     MAX-ACCESS  read-only
     STATUS      current
     DESCRIPTION
             "The number of packets received with CRC errors by this PM instance."
     ::= { cienaCesPmExtendedTxRxCurrBinEntry 7 }   
  
  cienaCesPmExtendedTxRxCurrBinRxMcastPkts OBJECT-TYPE
     SYNTAX      Counter64
     MAX-ACCESS  read-only
     STATUS      current
     DESCRIPTION
             "The total number of multicast packets received by this PM instance."
     ::= { cienaCesPmExtendedTxRxCurrBinEntry 8 }
     
  cienaCesPmExtendedTxRxCurrBinRxBcastPkts OBJECT-TYPE
     SYNTAX      Counter64
     MAX-ACCESS  read-only
     STATUS      current
     DESCRIPTION
             "The number of broadcast packets received by this PM instance."
     ::= { cienaCesPmExtendedTxRxCurrBinEntry 9 }
  
  cienaCesPmExtendedTxRxCurrBinUndersizePkts OBJECT-TYPE
     SYNTAX      Counter64
     MAX-ACCESS  read-only
     STATUS      current
     DESCRIPTION
             "The total number of packets received that were
            less than 64 octets long (excluding framing bits,
            but including FCS octets) and were otherwise well
            formed."
     ::= { cienaCesPmExtendedTxRxCurrBinEntry 10 }
  
  cienaCesPmExtendedTxRxCurrBinOversizePkts OBJECT-TYPE
     SYNTAX      Counter64
     MAX-ACCESS  read-only
     STATUS      current
     DESCRIPTION
             "The total number of packets received that were
            longer than 1518 octets  but less than or equal to the MTU
            (excluding framing bits, but including FCS octets)
            and were otherwise well formed."
     ::= { cienaCesPmExtendedTxRxCurrBinEntry 11 }
  
  cienaCesPmExtendedTxRxCurrBinFragmentsPkts OBJECT-TYPE
     SYNTAX      Counter64
     MAX-ACCESS  read-only
     STATUS      current
     DESCRIPTION
             "The total number of packets received that were less
            than 64 octets in length (excluding framing bits but
            including FCS octets) and had either a bad Frame
            Check Sequence (FCS) with an integral number of
            octets (FCS Error) or a bad FCS with a non-integral
            number of octets (Alignment Error)."
     ::= { cienaCesPmExtendedTxRxCurrBinEntry 12 }
  
  cienaCesPmExtendedTxRxCurrBinJabbersPkts OBJECT-TYPE
     SYNTAX      Counter64
     MAX-ACCESS  read-only
     STATUS      current
     DESCRIPTION
             "The total number of packets received that were
            longer than 1518 octets (excluding framing bits,
            but including FCS octets), and had either a bad
            Frame Check Sequence (FCS) with an integral number
            of octets (FCS Error) or a bad FCS with a
            non-integral number of octets (Alignment Error)."
     ::= { cienaCesPmExtendedTxRxCurrBinEntry 13 }
  
  cienaCesPmExtendedTxRxCurrBin64OctsPkts OBJECT-TYPE
     SYNTAX      Counter64
     MAX-ACCESS  read-only
     STATUS      current
     DESCRIPTION
             "The total number of packets (including bad
            packets) received that were 64 octets in length
            (excluding framing bits but including FCS octets)."
     ::= { cienaCesPmExtendedTxRxCurrBinEntry 14 }
  
  cienaCesPmExtendedTxRxCurrBin65To127OctsPkts OBJECT-TYPE
     SYNTAX      Counter64
     MAX-ACCESS  read-only
     STATUS      current
     DESCRIPTION
             "The total number of packets (including bad
            packets) received that were between
            65 and 127 octets in length inclusive
            (excluding framing bits but including FCS octets)."
     ::= { cienaCesPmExtendedTxRxCurrBinEntry 15 }
  
  cienaCesPmExtendedTxRxCurrBin128To255OctsPkts OBJECT-TYPE
     SYNTAX      Counter64
     MAX-ACCESS  read-only
     STATUS      current
     DESCRIPTION
             "The total number of packets (including bad
            packets) received that were between
            128 and 255 octets in length inclusive
            (excluding framing bits but including FCS octets)."
     ::= { cienaCesPmExtendedTxRxCurrBinEntry 16 }
  
  cienaCesPmExtendedTxRxCurrBin256To511OctsPkts OBJECT-TYPE
     SYNTAX      Counter64
     MAX-ACCESS  read-only
     STATUS      current
     DESCRIPTION
             "The total number of packets (including bad
            packets) received that were between
            256 and 511 octets in length inclusive
            (excluding framing bits but including FCS octets)."
     ::= { cienaCesPmExtendedTxRxCurrBinEntry 17 }
  
  cienaCesPmExtendedTxRxCurrBin512To1023OctsPkts OBJECT-TYPE
     SYNTAX      Counter64
     MAX-ACCESS  read-only
     STATUS      current
     DESCRIPTION
             "The total number of packets (including bad
            packets) received that were between
            512 and 1023 octets in length inclusive
            (excluding framing bits but including FCS octets)."
     ::= { cienaCesPmExtendedTxRxCurrBinEntry 18 }
  
  cienaCesPmExtendedTxRxCurrBin1024To1518OctsPkts OBJECT-TYPE
     SYNTAX      Counter64
     MAX-ACCESS  read-only
     STATUS      current
     DESCRIPTION
             "The total number of packets (including bad
            packets) received that were between
            1024 and 1518 octets in length inclusive
            (excluding framing bits but including FCS octets)."
     ::= { cienaCesPmExtendedTxRxCurrBinEntry 19 }
  
  cienaCesPmExtendedTxRxCurrBinTxBytes OBJECT-TYPE
     SYNTAX      Counter64
     MAX-ACCESS  read-only
     STATUS      current
     DESCRIPTION
             "The number of octets transmitted on this port."
     ::= { cienaCesPmExtendedTxRxCurrBinEntry 20 }
  
  cienaCesPmExtendedTxRxCurrBinTxTBytes OBJECT-TYPE
     SYNTAX      Counter64
     MAX-ACCESS  read-only
     STATUS      current
     DESCRIPTION
             "The total number of octets transmitted on this port."
     ::= { cienaCesPmExtendedTxRxCurrBinEntry 21 }
  
  cienaCesPmExtendedTxRxCurrBinTxPkts OBJECT-TYPE
     SYNTAX      Counter64
     MAX-ACCESS  read-only
     STATUS      current
     DESCRIPTION
             "The total number of packets transmitted on this port."
     ::= { cienaCesPmExtendedTxRxCurrBinEntry 22 }
  
  cienaCesPmExtendedTxRxCurrBinTxBcastPkts OBJECT-TYPE
     SYNTAX      Counter64
     MAX-ACCESS  read-only
     STATUS      current
     DESCRIPTION
             "The number of broadcast packets transmitted on the port."
     ::= { cienaCesPmExtendedTxRxCurrBinEntry 23 }
  
  cienaCesPmExtendedTxRxCurrBinTxMcastPkts OBJECT-TYPE
     SYNTAX      Counter64
     MAX-ACCESS  read-only
     STATUS      current
     DESCRIPTION
             "The number of multicast packets transmitted on the port."
     ::= { cienaCesPmExtendedTxRxCurrBinEntry 24 }
  
  cienaCesPmExtendedTxRxCurrBinTxExDeferPkts OBJECT-TYPE
     SYNTAX      Counter64
     MAX-ACCESS  read-only
     STATUS      current
     DESCRIPTION
             "The number of excessive defer packets transmitted on this PM instance."
     ::= { cienaCesPmExtendedTxRxCurrBinEntry 25 }
  
  cienaCesPmExtendedTxRxCurrBinTxGiantPkts OBJECT-TYPE
     SYNTAX      Counter64
     MAX-ACCESS  read-only
     STATUS      current
     DESCRIPTION
             "The number of too big packets transmitted on this PM instance."
     ::= { cienaCesPmExtendedTxRxCurrBinEntry 26 }
  
  cienaCesPmExtendedTxRxCurrBinTxUnderRunPkts OBJECT-TYPE
     SYNTAX      Counter64
     MAX-ACCESS  read-only
     STATUS      current
     DESCRIPTION
             "The number of underrun packets transmitted on this PM instance."
     ::= { cienaCesPmExtendedTxRxCurrBinEntry 27 }
  
  cienaCesPmExtendedTxRxCurrBinTxCrcErrorPkts OBJECT-TYPE
     SYNTAX      Counter64
     MAX-ACCESS  read-only
     STATUS      current
     DESCRIPTION
             "The number of CRC error packets transmitted on this PM instance."
     ::= { cienaCesPmExtendedTxRxCurrBinEntry 28 }
  
  cienaCesPmExtendedTxRxCurrBinTxLCheckErrorPkts OBJECT-TYPE
     SYNTAX      Counter64
     MAX-ACCESS  read-only
     STATUS      current
     DESCRIPTION
             "The number of length check error packets transmitted on this PM instance."
     ::= { cienaCesPmExtendedTxRxCurrBinEntry 29 }
  
  cienaCesPmExtendedTxRxCurrBinTxLOutRangePkts OBJECT-TYPE
     SYNTAX      Counter64
     MAX-ACCESS  read-only
     STATUS      current
     DESCRIPTION
             "The number of out of range packets transmitted on this PM instance."
     ::= { cienaCesPmExtendedTxRxCurrBinEntry 30 }
  
  cienaCesPmExtendedTxRxCurrBinTxLateCollPkts OBJECT-TYPE
     SYNTAX      Counter64
     MAX-ACCESS  read-only
     STATUS      current
     DESCRIPTION
             "The number of collision packets transmitted on this PM instance."
     ::= { cienaCesPmExtendedTxRxCurrBinEntry 31 }
  
  cienaCesPmExtendedTxRxCurrBinTxExCollPkts OBJECT-TYPE
     SYNTAX      Counter64
     MAX-ACCESS  read-only
     STATUS      current
     DESCRIPTION
             "The number of excessive collision packets transmitted on this PM instance."
     ::= { cienaCesPmExtendedTxRxCurrBinEntry 32 }
  
  cienaCesPmExtendedTxRxCurrBinTxSingleCollPkts OBJECT-TYPE
     SYNTAX      Counter64
     MAX-ACCESS  read-only
     STATUS      current
     DESCRIPTION
             "The number of single collision packets transmitted on this PM instance."
     ::= { cienaCesPmExtendedTxRxCurrBinEntry 33 }
  
  cienaCesPmExtendedTxRxCurrBinTxCollPkts OBJECT-TYPE
     SYNTAX      Counter64
     MAX-ACCESS  read-only
     STATUS      current
     DESCRIPTION
             "The number of collision packets transmitted on this PM instance."
     ::= { cienaCesPmExtendedTxRxCurrBinEntry 34 }

  
  cienaCesPmExtendedTxRxCurrBinDropEvents OBJECT-TYPE
     SYNTAX      Counter64
     MAX-ACCESS  read-only
     STATUS      current
     DESCRIPTION
             "The number of packet drop events on this PM instance."
     ::= { cienaCesPmExtendedTxRxCurrBinEntry 35 }
  
  cienaCesPmExtendedTxRxCurrBinInDiscards OBJECT-TYPE
     SYNTAX      Counter64
     MAX-ACCESS  read-only
     STATUS      current
     DESCRIPTION
             "The number of packet discard events on this PM instance."
     ::= { cienaCesPmExtendedTxRxCurrBinEntry 36 }
  
  cienaCesPmExtendedTxRxCurrBinTxPausePkts OBJECT-TYPE
     SYNTAX      Counter64
     MAX-ACCESS  read-only
     STATUS      current
     DESCRIPTION
             "The pause packets transmitted on the port."
     ::= { cienaCesPmExtendedTxRxCurrBinEntry 37 }
  
  cienaCesPmExtendedTxRxCurrBinRxPausePkts OBJECT-TYPE
     SYNTAX      Counter64
     MAX-ACCESS  read-only
     STATUS      current
     DESCRIPTION
             "The pause packets received on the port."
     ::= { cienaCesPmExtendedTxRxCurrBinEntry 38 }
  
  cienaCesPmExtendedTxRxCurrBinRxBytesPerSec OBJECT-TYPE
     SYNTAX      Counter64
     MAX-ACCESS  read-only
     STATUS      current
     DESCRIPTION
             "The number of bytes received per second on this port."
     ::= { cienaCesPmExtendedTxRxCurrBinEntry 39 }
  
  cienaCesPmExtendedTxRxCurrBinRxFramesPerSec OBJECT-TYPE
     SYNTAX      Counter64
     MAX-ACCESS  read-only
     STATUS      current
     DESCRIPTION
             "The number of frames received per second on this port."
     ::= { cienaCesPmExtendedTxRxCurrBinEntry 40 }
  
  cienaCesPmExtendedTxRxCurrBinTxBytesPerSec OBJECT-TYPE
     SYNTAX      Counter64
     MAX-ACCESS  read-only
     STATUS      current
     DESCRIPTION
             "The number of bytes transmitted per second on this port."
     ::= { cienaCesPmExtendedTxRxCurrBinEntry 41 }
  
  cienaCesPmExtendedTxRxCurrBinTxFramesPerSec OBJECT-TYPE
     SYNTAX      Counter64
     MAX-ACCESS  read-only
     STATUS      current
     DESCRIPTION
             "The number of frames transmitted per second on this port."
     ::= { cienaCesPmExtendedTxRxCurrBinEntry 42 }

  cienaCesPmExtendedTxRxCurrBinRxLOutRangePkts OBJECT-TYPE
     SYNTAX      Counter64
     MAX-ACCESS  read-only
     STATUS      current
     DESCRIPTION
             "The total number of packets received that were
             longer than than the MTU
             (excluding framing bits,
             but including FCS octets) and were otherwise
             well formed."
    ::= {cienaCesPmExtendedTxRxCurrBinEntry 43 }

  cienaCesPmExtendedTxRxCurrBinRxUcastPkts OBJECT-TYPE
     SYNTAX      Counter64
     MAX-ACCESS  read-only
     STATUS      current
     DESCRIPTION
             "The number of unicast packets received on the port."
     ::= { cienaCesPmExtendedTxRxCurrBinEntry 44 }	

  cienaCesPmExtendedTxRxCurrBinRxInErrorPkts OBJECT-TYPE
     SYNTAX      Counter64
     MAX-ACCESS  read-only
     STATUS      current
     DESCRIPTION
             "The number of in error packets received on the port."
     ::= { cienaCesPmExtendedTxRxCurrBinEntry 45 }

  cienaCesPmExtendedTxRxCurrBin1519To2047OctsPkts OBJECT-TYPE
     SYNTAX      Counter64
     MAX-ACCESS  read-only
     STATUS      current
     DESCRIPTION
             "The total number of packets (including bad
             packets) received that were between
             1519 and 2047 octets in length inclusive
             (excluding framing bits but including FCS octets)."
     ::= { cienaCesPmExtendedTxRxCurrBinEntry 46 }

  cienaCesPmExtendedTxRxCurrBin2048To4095OctsPkts OBJECT-TYPE
     SYNTAX      Counter64
     MAX-ACCESS  read-only
     STATUS      current
     DESCRIPTION
             "The total number of packets (including bad
             packets) received that were between
             2048 and 4095 octets in length inclusive
             (excluding framing bits but including FCS octets)."
     ::= { cienaCesPmExtendedTxRxCurrBinEntry 47 }

  cienaCesPmExtendedTxRxCurrBin4096To9216OctsPkts OBJECT-TYPE
     SYNTAX      Counter64
     MAX-ACCESS  read-only
     STATUS      current
     DESCRIPTION
             "The total number of packets (including bad
             packets) received that were between
             4096 and 9216 octets in length inclusive
             (excluding framing bits but including FCS octets)."
     ::= { cienaCesPmExtendedTxRxCurrBinEntry 48 }

  cienaCesPmExtendedTxRxCurrBinTxUcastPkts OBJECT-TYPE
     SYNTAX      Counter64
     MAX-ACCESS  read-only
     STATUS      current
     DESCRIPTION
             "The number of unicast packets transmitted on the port."
     ::= { cienaCesPmExtendedTxRxCurrBinEntry 49 }

  cienaCesPmExtendedTxRxCurrBinTx64OctsPkts OBJECT-TYPE
     SYNTAX      Counter64
     MAX-ACCESS  read-only
     STATUS      current
     DESCRIPTION
             "The total number of packets (including bad
             packets) transmitted that were between
             64 octets in length inclusive
             (excluding framing bits but including FCS octets)."
     ::= { cienaCesPmExtendedTxRxCurrBinEntry 50 }

  cienaCesPmExtendedTxRxCurrBinTx65To127OctsPkts OBJECT-TYPE
     SYNTAX      Counter64
     MAX-ACCESS  read-only
     STATUS      current
     DESCRIPTION
             "The total number of packets (including bad
             packets) transmitted that were between
             65 and 127 octets in length inclusive
             (excluding framing bits but including FCS octets)."
     ::= { cienaCesPmExtendedTxRxCurrBinEntry 51 }

  cienaCesPmExtendedTxRxCurrBinTx128To255OctsPkts OBJECT-TYPE
     SYNTAX      Counter64
     MAX-ACCESS  read-only
     STATUS      current
     DESCRIPTION
             "The total number of packets (including bad
             packets) transmitted that were between
             128 and 255 octets in length inclusive
             (excluding framing bits but including FCS octets)."
     ::= { cienaCesPmExtendedTxRxCurrBinEntry 52 }

  cienaCesPmExtendedTxRxCurrBinTx256To511OctsPkts OBJECT-TYPE
     SYNTAX      Counter64
     MAX-ACCESS  read-only
     STATUS      current
     DESCRIPTION
             "The total number of packets (including bad
             packets) transmitted that were between
             256 and 511 octets in length inclusive
             (excluding framing bits but including FCS octets)."
     ::= { cienaCesPmExtendedTxRxCurrBinEntry 53 }

  cienaCesPmExtendedTxRxCurrBinTx512To1023OctsPkts OBJECT-TYPE
     SYNTAX      Counter64
     MAX-ACCESS  read-only
     STATUS      current
     DESCRIPTION
             "The total number of packets (including bad
             packets) transmitted that were between
             512 and 1023 octets in length inclusive
             (excluding framing bits but including FCS octets)."
     ::= { cienaCesPmExtendedTxRxCurrBinEntry 54 }

  cienaCesPmExtendedTxRxCurrBinTx1024To1518OctsPkts OBJECT-TYPE
     SYNTAX      Counter64
     MAX-ACCESS  read-only
     STATUS      current
     DESCRIPTION
             "The total number of packets (including bad
             packets) transmitted that were between
             1024 and 1518 octets in length inclusive
             (excluding framing bits but including FCS octets)."
     ::= { cienaCesPmExtendedTxRxCurrBinEntry 55 }

  cienaCesPmExtendedTxRxCurrBinTx1519To2047OctsPkts OBJECT-TYPE
     SYNTAX      Counter64
     MAX-ACCESS  read-only
     STATUS      current
     DESCRIPTION
             "The total number of packets (including bad
             packets) transmitted that were between
             1519 and 2047 octets in length inclusive
             (excluding framing bits but including FCS octets)."
     ::= { cienaCesPmExtendedTxRxCurrBinEntry 56 }

  cienaCesPmExtendedTxRxCurrBinTx2048To4095OctsPkts OBJECT-TYPE
     SYNTAX      Counter64
     MAX-ACCESS  read-only
     STATUS      current
     DESCRIPTION
             "The total number of packets (including bad
             packets) transmitted that were between
             2048 and 4095 octets in length inclusive
             (excluding framing bits but including FCS octets)."
     ::= { cienaCesPmExtendedTxRxCurrBinEntry 57 }

  cienaCesPmExtendedTxRxCurrBinTx4096To9216OctsPkts OBJECT-TYPE
     SYNTAX      Counter64
     MAX-ACCESS  read-only
     STATUS      current
     DESCRIPTION
             "The total number of packets (including bad
             packets) transmitted that were between
             4096 and 9216 octets in length inclusive
             (excluding framing bits but including FCS octets)."
     ::= { cienaCesPmExtendedTxRxCurrBinEntry 58 }

  cienaCesPmExtendedTxRxCurrBinTxDeferPkts OBJECT-TYPE
     SYNTAX      Counter64
     MAX-ACCESS  read-only
     STATUS      current
     DESCRIPTION
             "The number of defer packets transmitted on the port."
     ::= { cienaCesPmExtendedTxRxCurrBinEntry 59 }

  cienaCesPmExtendedTxRxCurrBinLinkUp OBJECT-TYPE
     SYNTAX      Counter64
     MAX-ACCESS  read-only
     STATUS      current
     DESCRIPTION
             "The number of link up events on the port."
     ::= { cienaCesPmExtendedTxRxCurrBinEntry 60 }

  cienaCesPmExtendedTxRxCurrBinLinkDown OBJECT-TYPE
     SYNTAX      Counter64
     MAX-ACCESS  read-only
     STATUS      current
     DESCRIPTION
             "The number of link down events on the port."
     ::= { cienaCesPmExtendedTxRxCurrBinEntry 61 }

  cienaCesPmExtendedTxRxCurrBinLinkFlap OBJECT-TYPE
     SYNTAX      Counter64
     MAX-ACCESS  read-only
     STATUS      current
     DESCRIPTION
             "The number of link flap events on the port."
     ::= { cienaCesPmExtendedTxRxCurrBinEntry 62 }
  
 --24 Hours Current Bin
 
 cienaCesPmExtendedTxRxCurr24HBinTable OBJECT-TYPE
     SYNTAX     SEQUENCE OF CienaCesPmExtendedTxRxCurr24HBinEntry
     MAX-ACCESS not-accessible
     STATUS     current
     DESCRIPTION
            "The (conceptual) read-only table listing the extended TxRx profile statistics."  
     ::= { cienaCesPmExtendedTxRxStats 3 }
     
   cienaCesPmExtendedTxRxCurr24HBinEntry OBJECT-TYPE
     SYNTAX      CienaCesPmExtendedTxRxCurr24HBinEntry
     MAX-ACCESS  not-accessible
     STATUS      current
     DESCRIPTION
           "An entry (conceptual row) in the cienaCesPmExtendedTxRxCurr24HBinTable.

           This table lists the statistics for the current 24 hours."  

     INDEX {cienaCesPmInstanceIndex}
     ::= { cienaCesPmExtendedTxRxCurr24HBinTable 1 }
        
 CienaCesPmExtendedTxRxCurr24HBinEntry ::=  SEQUENCE { 
 	 cienaCesPmExtendedTxRxCurr24HBinStartTime				   DisplayString, 
     cienaCesPmExtendedTxRxCurr24HBinEndTime				   DisplayString,
     cienaCesPmExtendedTxRxCurr24HBinClearedTime			   DisplayString,
     cienaCesPmExtendedTxRxCurr24HBinDuration				   Unsigned32,   
     cienaCesPmExtendedTxRxCurr24HBinState					   PmBinState,   
     cienaCesPmExtendedTxRxCurr24HBinRxBytes                  Counter64,
     cienaCesPmExtendedTxRxCurr24HBinRxPkts                   Counter64,
     cienaCesPmExtendedTxRxCurr24HBinRxCrcErrorPkts           Counter64,
     cienaCesPmExtendedTxRxCurr24HBinRxMcastPkts              Counter64,
     cienaCesPmExtendedTxRxCurr24HBinRxBcastPkts              Counter64,
     cienaCesPmExtendedTxRxCurr24HBinUndersizePkts            Counter64,
     cienaCesPmExtendedTxRxCurr24HBinOversizePkts             Counter64,
     cienaCesPmExtendedTxRxCurr24HBinFragmentsPkts            Counter64,
     cienaCesPmExtendedTxRxCurr24HBinJabbersPkts              Counter64,
     cienaCesPmExtendedTxRxCurr24HBin64OctsPkts               Counter64,
     cienaCesPmExtendedTxRxCurr24HBin65To127OctsPkts          Counter64,
     cienaCesPmExtendedTxRxCurr24HBin128To255OctsPkts         Counter64,
     cienaCesPmExtendedTxRxCurr24HBin256To511OctsPkts         Counter64,
     cienaCesPmExtendedTxRxCurr24HBin512To1023OctsPkts        Counter64,
     cienaCesPmExtendedTxRxCurr24HBin1024To1518OctsPkts       Counter64,
     cienaCesPmExtendedTxRxCurr24HBinTxBytes                  Counter64,
     cienaCesPmExtendedTxRxCurr24HBinTxTBytes                 Counter64,
     cienaCesPmExtendedTxRxCurr24HBinTxPkts                   Counter64,
     cienaCesPmExtendedTxRxCurr24HBinTxBcastPkts              Counter64,
     cienaCesPmExtendedTxRxCurr24HBinTxMcastPkts              Counter64,
     cienaCesPmExtendedTxRxCurr24HBinTxExDeferPkts            Counter64,
     cienaCesPmExtendedTxRxCurr24HBinTxGiantPkts              Counter64,
     cienaCesPmExtendedTxRxCurr24HBinTxUnderRunPkts           Counter64,
     cienaCesPmExtendedTxRxCurr24HBinTxCrcErrorPkts           Counter64,
     cienaCesPmExtendedTxRxCurr24HBinTxLCheckErrorPkts        Counter64,
     cienaCesPmExtendedTxRxCurr24HBinTxLOutRangePkts          Counter64,
     cienaCesPmExtendedTxRxCurr24HBinTxLateCollPkts           Counter64,
     cienaCesPmExtendedTxRxCurr24HBinTxExCollPkts             Counter64,
     cienaCesPmExtendedTxRxCurr24HBinTxSingleCollPkts         Counter64,
     cienaCesPmExtendedTxRxCurr24HBinTxCollPkts               Counter64,
     cienaCesPmExtendedTxRxCurr24HBinDropEvents               Counter64,
     cienaCesPmExtendedTxRxCurr24HBinInDiscards               Counter64,
     cienaCesPmExtendedTxRxCurr24HBinTxPausePkts              Counter64,
     cienaCesPmExtendedTxRxCurr24HBinRxPausePkts              Counter64,
     cienaCesPmExtendedTxRxCurr24HBinRxBytesPerSec            Counter64,
     cienaCesPmExtendedTxRxCurr24HBinRxFramesPerSec           Counter64,
     cienaCesPmExtendedTxRxCurr24HBinTxBytesPerSec            Counter64,
     cienaCesPmExtendedTxRxCurr24HBinTxFramesPerSec           Counter64,
     cienaCesPmExtendedTxRxCurr24HBinRxLOutRangePkts          Counter64,
     cienaCesPmExtendedTxRxCurr24HBinRxUcastPkts              Counter64,
     cienaCesPmExtendedTxRxCurr24HBinRxInErrorPkts            Counter64,
     cienaCesPmExtendedTxRxCurr24HBin1519To2047OctsPkts       Counter64,
     cienaCesPmExtendedTxRxCurr24HBin2048To4095OctsPkts       Counter64,
     cienaCesPmExtendedTxRxCurr24HBin4096To9216OctsPkts       Counter64,
     cienaCesPmExtendedTxRxCurr24HBinTxUcastPkts              Counter64,
     cienaCesPmExtendedTxRxCurr24HBinTx64OctsPkts             Counter64,
     cienaCesPmExtendedTxRxCurr24HBinTx65To127OctsPkts        Counter64,
     cienaCesPmExtendedTxRxCurr24HBinTx128To255OctsPkts       Counter64,
     cienaCesPmExtendedTxRxCurr24HBinTx256To511OctsPkts       Counter64,
     cienaCesPmExtendedTxRxCurr24HBinTx512To1023OctsPkts      Counter64,
     cienaCesPmExtendedTxRxCurr24HBinTx1024To1518OctsPkts     Counter64,
     cienaCesPmExtendedTxRxCurr24HBinTx1519To2047OctsPkts     Counter64,
     cienaCesPmExtendedTxRxCurr24HBinTx2048To4095OctsPkts     Counter64,
     cienaCesPmExtendedTxRxCurr24HBinTx4096To9216OctsPkts     Counter64,
     cienaCesPmExtendedTxRxCurr24HBinTxDeferPkts              Counter64,
     cienaCesPmExtendedTxRxCurr24HBinLinkUp                   Counter64,
     cienaCesPmExtendedTxRxCurr24HBinLinkDown                 Counter64,
     cienaCesPmExtendedTxRxCurr24HBinLinkFlap                 Counter64
   }
   cienaCesPmExtendedTxRxCurr24HBinStartTime   OBJECT-TYPE
     SYNTAX		DisplayString
     MAX-ACCESS	read-only
     STATUS		current
     DESCRIPTION "Collection start time for the current 24 hour statistics for this PM instance."
     ::= { cienaCesPmExtendedTxRxCurr24HBinEntry 1	}
    
  cienaCesPmExtendedTxRxCurr24HBinEndTime   OBJECT-TYPE
     SYNTAX		DisplayString
     MAX-ACCESS	read-only
     STATUS		current
     DESCRIPTION "Collection end time for the current 24 hour statistics for this PM instance."
     ::= { cienaCesPmExtendedTxRxCurr24HBinEntry 2	}
 
   cienaCesPmExtendedTxRxCurr24HBinClearedTime   OBJECT-TYPE
     SYNTAX		DisplayString
     MAX-ACCESS	read-only
     STATUS		current
     DESCRIPTION "Cleared time of current 24 hour statistics for this PM instance."
     ::= { cienaCesPmExtendedTxRxCurr24HBinEntry 3	}
                   
   cienaCesPmExtendedTxRxCurr24HBinDuration OBJECT-TYPE
     SYNTAX      Unsigned32 (1..65535) 
     UNITS		"minutes"
     MAX-ACCESS  read-only
     STATUS      current
     DESCRIPTION
             "Duration of the current 24 hour statistics collection for this PM instance."
     ::= { cienaCesPmExtendedTxRxCurr24HBinEntry 4 }
  
  cienaCesPmExtendedTxRxCurr24HBinState OBJECT-TYPE
     SYNTAX      PmBinState 
     MAX-ACCESS  read-only
     STATUS      current
     DESCRIPTION
             "State of the current 24 hour statistics for this PM instance."
     ::= { cienaCesPmExtendedTxRxCurr24HBinEntry 5 }
  
  cienaCesPmExtendedTxRxCurr24HBinRxBytes OBJECT-TYPE
     SYNTAX      Counter64
     MAX-ACCESS  read-only
     STATUS      current
     DESCRIPTION
             "The number of bytes received by this PM instance."
     ::= { cienaCesPmExtendedTxRxCurr24HBinEntry 6 }

 cienaCesPmExtendedTxRxCurr24HBinRxPkts OBJECT-TYPE
     SYNTAX      Counter64
     MAX-ACCESS  read-only
     STATUS      current
     DESCRIPTION
             "The number of packets received by this PM instance."
     ::= { cienaCesPmExtendedTxRxCurr24HBinEntry 7 } 
  
  cienaCesPmExtendedTxRxCurr24HBinRxCrcErrorPkts OBJECT-TYPE
     SYNTAX      Counter64
     MAX-ACCESS  read-only
     STATUS      current
     DESCRIPTION
             "The number of packets received with CRC errors by this PM instance."
     ::= { cienaCesPmExtendedTxRxCurr24HBinEntry 8 }   
  
  cienaCesPmExtendedTxRxCurr24HBinRxMcastPkts OBJECT-TYPE
     SYNTAX      Counter64
     MAX-ACCESS  read-only
     STATUS      current
     DESCRIPTION
             "The total number of multicast packets received by this PM instance."
     ::= { cienaCesPmExtendedTxRxCurr24HBinEntry 9 }
     
  cienaCesPmExtendedTxRxCurr24HBinRxBcastPkts OBJECT-TYPE
     SYNTAX      Counter64
     MAX-ACCESS  read-only
     STATUS      current
     DESCRIPTION
             "The number of broadcast packets received by this PM instance."
     ::= { cienaCesPmExtendedTxRxCurr24HBinEntry 10 }
  
  cienaCesPmExtendedTxRxCurr24HBinUndersizePkts OBJECT-TYPE
     SYNTAX      Counter64
     MAX-ACCESS  read-only
     STATUS      current
     DESCRIPTION
             "The total number of packets received that were
            less than 64 octets long (excluding framing bits,
            but including FCS octets) and were otherwise well
            formed."
     ::= { cienaCesPmExtendedTxRxCurr24HBinEntry 11 }
  
  cienaCesPmExtendedTxRxCurr24HBinOversizePkts OBJECT-TYPE
     SYNTAX      Counter64
     MAX-ACCESS  read-only
     STATUS      current
     DESCRIPTION
             "The total number of packets received that were
            longer than 1518 octets  but less than or equal to the MTU
            (excluding framing bits, but including FCS octets)
            and were otherwise well formed."
     ::= { cienaCesPmExtendedTxRxCurr24HBinEntry 12 }
  
  cienaCesPmExtendedTxRxCurr24HBinFragmentsPkts OBJECT-TYPE
     SYNTAX      Counter64
     MAX-ACCESS  read-only
     STATUS      current
     DESCRIPTION
             "The total number of packets received that were less
            than 64 octets in length (excluding framing bits but
            including FCS octets) and had either a bad Frame
            Check Sequence (FCS) with an integral number of
            octets (FCS Error) or a bad FCS with a non-integral
            number of octets (Alignment Error)."
     ::= { cienaCesPmExtendedTxRxCurr24HBinEntry 13 }
  
  cienaCesPmExtendedTxRxCurr24HBinJabbersPkts OBJECT-TYPE
     SYNTAX      Counter64
     MAX-ACCESS  read-only
     STATUS      current
     DESCRIPTION
             "The total number of packets received that were
            longer than 1518 octets (excluding framing bits,
            but including FCS octets), and had either a bad
            Frame Check Sequence (FCS) with an integral number
            of octets (FCS Error) or a bad FCS with a
            non-integral number of octets (Alignment Error)."
     ::= { cienaCesPmExtendedTxRxCurr24HBinEntry 14 }
  
  cienaCesPmExtendedTxRxCurr24HBin64OctsPkts OBJECT-TYPE
     SYNTAX      Counter64
     MAX-ACCESS  read-only
     STATUS      current
     DESCRIPTION
             "The total number of packets (including bad
            packets) received that were 64 octets in length
            (excluding framing bits but including FCS octets)."
     ::= { cienaCesPmExtendedTxRxCurr24HBinEntry 15 }
  
  cienaCesPmExtendedTxRxCurr24HBin65To127OctsPkts OBJECT-TYPE
     SYNTAX      Counter64
     MAX-ACCESS  read-only
     STATUS      current
     DESCRIPTION
             "The total number of packets (including bad
            packets) received that were between
            65 and 127 octets in length inclusive
            (excluding framing bits but including FCS octets)."
     ::= { cienaCesPmExtendedTxRxCurr24HBinEntry 16 }
  
  cienaCesPmExtendedTxRxCurr24HBin128To255OctsPkts OBJECT-TYPE
     SYNTAX      Counter64
     MAX-ACCESS  read-only
     STATUS      current
     DESCRIPTION
             "The total number of packets (including bad
            packets) received that were between
            128 and 255 octets in length inclusive
            (excluding framing bits but including FCS octets)."
     ::= { cienaCesPmExtendedTxRxCurr24HBinEntry 17 }
  
  cienaCesPmExtendedTxRxCurr24HBin256To511OctsPkts OBJECT-TYPE
     SYNTAX      Counter64
     MAX-ACCESS  read-only
     STATUS      current
     DESCRIPTION
             "The total number of packets (including bad
            packets) received that were between
            256 and 511 octets in length inclusive
            (excluding framing bits but including FCS octets)."
     ::= { cienaCesPmExtendedTxRxCurr24HBinEntry 18 }
  
  cienaCesPmExtendedTxRxCurr24HBin512To1023OctsPkts OBJECT-TYPE
     SYNTAX      Counter64
     MAX-ACCESS  read-only
     STATUS      current
     DESCRIPTION
             "The total number of packets (including bad
            packets) received that were between
            512 and 1023 octets in length inclusive
            (excluding framing bits but including FCS octets)."
     ::= { cienaCesPmExtendedTxRxCurr24HBinEntry 19 }
  
  cienaCesPmExtendedTxRxCurr24HBin1024To1518OctsPkts OBJECT-TYPE
     SYNTAX      Counter64
     MAX-ACCESS  read-only
     STATUS      current
     DESCRIPTION
             "The total number of packets (including bad
            packets) received that were between
            1024 and 1518 octets in length inclusive
            (excluding framing bits but including FCS octets)."
     ::= { cienaCesPmExtendedTxRxCurr24HBinEntry 20 }
  
  cienaCesPmExtendedTxRxCurr24HBinTxBytes OBJECT-TYPE
     SYNTAX      Counter64
     MAX-ACCESS  read-only
     STATUS      current
     DESCRIPTION
             "The number of octets transmitted on this PM instance."
     ::= { cienaCesPmExtendedTxRxCurr24HBinEntry 21 }
  
  cienaCesPmExtendedTxRxCurr24HBinTxTBytes OBJECT-TYPE
     SYNTAX      Counter64
     MAX-ACCESS  read-only
     STATUS      current
     DESCRIPTION
             "The total number of octets transmitted on this PM instance."
     ::= { cienaCesPmExtendedTxRxCurr24HBinEntry 22 }
  
  cienaCesPmExtendedTxRxCurr24HBinTxPkts OBJECT-TYPE
     SYNTAX      Counter64
     MAX-ACCESS  read-only
     STATUS      current
     DESCRIPTION
             "The total number of packets transmitted on this PM instance."
     ::= { cienaCesPmExtendedTxRxCurr24HBinEntry 23 }
  
  cienaCesPmExtendedTxRxCurr24HBinTxBcastPkts OBJECT-TYPE
     SYNTAX      Counter64
     MAX-ACCESS  read-only
     STATUS      current
     DESCRIPTION
             "The number of broadcast packets transmitted on this PM instance."
     ::= { cienaCesPmExtendedTxRxCurr24HBinEntry 24 }
  
  cienaCesPmExtendedTxRxCurr24HBinTxMcastPkts OBJECT-TYPE
     SYNTAX      Counter64
     MAX-ACCESS  read-only
     STATUS      current
     DESCRIPTION
             "The number of multicast packets transmitted on this PM instance."
     ::= { cienaCesPmExtendedTxRxCurr24HBinEntry 25 }
  
  cienaCesPmExtendedTxRxCurr24HBinTxExDeferPkts OBJECT-TYPE
     SYNTAX      Counter64
     MAX-ACCESS  read-only
     STATUS      current
     DESCRIPTION
             "The number of excessive defer packets transmitted on this PM instance."
     ::= { cienaCesPmExtendedTxRxCurr24HBinEntry 26 }
  
  cienaCesPmExtendedTxRxCurr24HBinTxGiantPkts OBJECT-TYPE
     SYNTAX      Counter64
     MAX-ACCESS  read-only
     STATUS      current
     DESCRIPTION
             "The number of too big packets transmitted on this PM instance."
     ::= { cienaCesPmExtendedTxRxCurr24HBinEntry 27 }
  
  cienaCesPmExtendedTxRxCurr24HBinTxUnderRunPkts OBJECT-TYPE
     SYNTAX      Counter64
     MAX-ACCESS  read-only
     STATUS      current
     DESCRIPTION
             "The number of underrun packets transmitted on this PM instance."
     ::= { cienaCesPmExtendedTxRxCurr24HBinEntry 28 }
  
  cienaCesPmExtendedTxRxCurr24HBinTxCrcErrorPkts OBJECT-TYPE
     SYNTAX      Counter64
     MAX-ACCESS  read-only
     STATUS      current
     DESCRIPTION
             "The number of CRC error packets transmitted on this PM instance."
     ::= { cienaCesPmExtendedTxRxCurr24HBinEntry 29 }
  
  cienaCesPmExtendedTxRxCurr24HBinTxLCheckErrorPkts OBJECT-TYPE
     SYNTAX      Counter64
     MAX-ACCESS  read-only
     STATUS      current
     DESCRIPTION
             "The number of length check error packets transmitted on this PM instance."
     ::= { cienaCesPmExtendedTxRxCurr24HBinEntry 30 }
  
  cienaCesPmExtendedTxRxCurr24HBinTxLOutRangePkts OBJECT-TYPE
     SYNTAX      Counter64
     MAX-ACCESS  read-only
     STATUS      current
     DESCRIPTION
             "The number of out of range packets transmitted on this PM instance."
     ::= { cienaCesPmExtendedTxRxCurr24HBinEntry 31 }
  
  cienaCesPmExtendedTxRxCurr24HBinTxLateCollPkts OBJECT-TYPE
     SYNTAX      Counter64
     MAX-ACCESS  read-only
     STATUS      current
     DESCRIPTION
             "The number of late collision packets transmitted on this PM instance."
     ::= { cienaCesPmExtendedTxRxCurr24HBinEntry 32 }
  
  cienaCesPmExtendedTxRxCurr24HBinTxExCollPkts OBJECT-TYPE
     SYNTAX      Counter64
     MAX-ACCESS  read-only
     STATUS      current
     DESCRIPTION
             "The number of excessive collision packets transmitted on this PM instance."
     ::= { cienaCesPmExtendedTxRxCurr24HBinEntry 33 }
  
  cienaCesPmExtendedTxRxCurr24HBinTxSingleCollPkts OBJECT-TYPE
     SYNTAX      Counter64
     MAX-ACCESS  read-only
     STATUS      current
     DESCRIPTION
             "The number of single collision packets transmitted on this PM instance."
     ::= { cienaCesPmExtendedTxRxCurr24HBinEntry 34 }
  
  cienaCesPmExtendedTxRxCurr24HBinTxCollPkts OBJECT-TYPE
     SYNTAX      Counter64
     MAX-ACCESS  read-only
     STATUS      current
     DESCRIPTION
             "The number of collision packets transmitted on this PM instance."
     ::= { cienaCesPmExtendedTxRxCurr24HBinEntry 35 }

  
  cienaCesPmExtendedTxRxCurr24HBinDropEvents OBJECT-TYPE
     SYNTAX      Counter64
     MAX-ACCESS  read-only
     STATUS      current
     DESCRIPTION
             "The number of packet drop events on this PM instance."
     ::= { cienaCesPmExtendedTxRxCurr24HBinEntry 36 }
  
  cienaCesPmExtendedTxRxCurr24HBinInDiscards OBJECT-TYPE
     SYNTAX      Counter64
     MAX-ACCESS  read-only
     STATUS      current
     DESCRIPTION
             "The number of packet discard events on this PM instance."
     ::= { cienaCesPmExtendedTxRxCurr24HBinEntry 37 }
  
  cienaCesPmExtendedTxRxCurr24HBinTxPausePkts OBJECT-TYPE
     SYNTAX      Counter64
     MAX-ACCESS  read-only
     STATUS      current
     DESCRIPTION
             "The pause packets transmitted on this PM instance."
     ::= { cienaCesPmExtendedTxRxCurr24HBinEntry 38 }
  
  cienaCesPmExtendedTxRxCurr24HBinRxPausePkts OBJECT-TYPE
     SYNTAX      Counter64
     MAX-ACCESS  read-only
     STATUS      current
     DESCRIPTION
             "The pause packets received on this PM instance."
     ::= { cienaCesPmExtendedTxRxCurr24HBinEntry 39 }
  
  cienaCesPmExtendedTxRxCurr24HBinRxBytesPerSec OBJECT-TYPE
     SYNTAX      Counter64
     MAX-ACCESS  read-only
     STATUS      current
     DESCRIPTION
             "The number of bytes received per second on this PM instance."
     ::= { cienaCesPmExtendedTxRxCurr24HBinEntry 40 }
  
  cienaCesPmExtendedTxRxCurr24HBinRxFramesPerSec OBJECT-TYPE
     SYNTAX      Counter64
     MAX-ACCESS  read-only
     STATUS      current
     DESCRIPTION
             "The number of frames received per second on this PM instance."
     ::= { cienaCesPmExtendedTxRxCurr24HBinEntry 41 }
  
  cienaCesPmExtendedTxRxCurr24HBinTxBytesPerSec OBJECT-TYPE
     SYNTAX      Counter64
     MAX-ACCESS  read-only
     STATUS      current
     DESCRIPTION
             "The number of bytes transmitted per second on this PM instance."
     ::= { cienaCesPmExtendedTxRxCurr24HBinEntry 42 }
  
  cienaCesPmExtendedTxRxCurr24HBinTxFramesPerSec OBJECT-TYPE
     SYNTAX      Counter64
     MAX-ACCESS  read-only
     STATUS      current
     DESCRIPTION
             "The number of frames transmitted per second on this PM instance."
     ::= { cienaCesPmExtendedTxRxCurr24HBinEntry 43 }

  cienaCesPmExtendedTxRxCurr24HBinRxLOutRangePkts OBJECT-TYPE
     SYNTAX      Counter64
     MAX-ACCESS  read-only
     STATUS      current
     DESCRIPTION
             "The total number of packets received that were
             longer than than the MTU
             (excluding framing bits,
             but including FCS octets) and were otherwise
             well formed."
     ::= { cienaCesPmExtendedTxRxCurr24HBinEntry 44 }

  cienaCesPmExtendedTxRxCurr24HBinRxUcastPkts OBJECT-TYPE
     SYNTAX      Counter64
     MAX-ACCESS  read-only
     STATUS      current
     DESCRIPTION
             "The number of unicast packets received on the port."
     ::= { cienaCesPmExtendedTxRxCurr24HBinEntry 45 }	

  cienaCesPmExtendedTxRxCurr24HBinRxInErrorPkts OBJECT-TYPE
     SYNTAX      Counter64
     MAX-ACCESS  read-only
     STATUS      current
     DESCRIPTION
             "The number of in error packets received on the port."
     ::= { cienaCesPmExtendedTxRxCurr24HBinEntry 46 }

  cienaCesPmExtendedTxRxCurr24HBin1519To2047OctsPkts OBJECT-TYPE
     SYNTAX      Counter64
     MAX-ACCESS  read-only
     STATUS      current
     DESCRIPTION
             "The total number of packets (including bad
             packets) received that were between
             1519 and 2047 octets in length inclusive
             (excluding framing bits but including FCS octets)."
     ::= { cienaCesPmExtendedTxRxCurr24HBinEntry 47 }

  cienaCesPmExtendedTxRxCurr24HBin2048To4095OctsPkts OBJECT-TYPE
     SYNTAX      Counter64
     MAX-ACCESS  read-only
     STATUS      current
     DESCRIPTION
             "The total number of packets (including bad
             packets) received that were between
             2048 and 4095 octets in length inclusive
             (excluding framing bits but including FCS octets)."
     ::= { cienaCesPmExtendedTxRxCurr24HBinEntry 48 }

  cienaCesPmExtendedTxRxCurr24HBin4096To9216OctsPkts OBJECT-TYPE
     SYNTAX      Counter64
     MAX-ACCESS  read-only
     STATUS      current
     DESCRIPTION
             "The total number of packets (including bad
             packets) received that were between
             4096 and 9216 octets in length inclusive
             (excluding framing bits but including FCS octets)."
     ::= { cienaCesPmExtendedTxRxCurr24HBinEntry 49 }

  cienaCesPmExtendedTxRxCurr24HBinTxUcastPkts OBJECT-TYPE
     SYNTAX      Counter64
     MAX-ACCESS  read-only
     STATUS      current
     DESCRIPTION
             "The number of unicast packets transmitted on the port."
     ::= { cienaCesPmExtendedTxRxCurr24HBinEntry 50 }

  cienaCesPmExtendedTxRxCurr24HBinTx64OctsPkts OBJECT-TYPE
     SYNTAX      Counter64
     MAX-ACCESS  read-only
     STATUS      current
     DESCRIPTION
             "The total number of packets (including bad
             packets) transmitted that were between
             64 octets in length inclusive
             (excluding framing bits but including FCS octets)."
     ::= { cienaCesPmExtendedTxRxCurr24HBinEntry 51 }

  cienaCesPmExtendedTxRxCurr24HBinTx65To127OctsPkts OBJECT-TYPE
     SYNTAX      Counter64
     MAX-ACCESS  read-only
     STATUS      current
     DESCRIPTION
             "The total number of packets (including bad
             packets) transmitted that were between
             65 and 127 octets in length inclusive
             (excluding framing bits but including FCS octets)."
     ::= { cienaCesPmExtendedTxRxCurr24HBinEntry 52 }

  cienaCesPmExtendedTxRxCurr24HBinTx128To255OctsPkts OBJECT-TYPE
     SYNTAX      Counter64
     MAX-ACCESS  read-only
     STATUS      current
     DESCRIPTION
             "The total number of packets (including bad
             packets) transmitted that were between
             128 and 255 octets in length inclusive
             (excluding framing bits but including FCS octets)."
     ::= { cienaCesPmExtendedTxRxCurr24HBinEntry 53 }

  cienaCesPmExtendedTxRxCurr24HBinTx256To511OctsPkts OBJECT-TYPE
     SYNTAX      Counter64
     MAX-ACCESS  read-only
     STATUS      current
     DESCRIPTION
             "The total number of packets (including bad
             packets) transmitted that were between
             256 and 511 octets in length inclusive
             (excluding framing bits but including FCS octets)."
     ::= { cienaCesPmExtendedTxRxCurr24HBinEntry 54 }

  cienaCesPmExtendedTxRxCurr24HBinTx512To1023OctsPkts OBJECT-TYPE
     SYNTAX      Counter64
     MAX-ACCESS  read-only
     STATUS      current
     DESCRIPTION
             "The total number of packets (including bad
             packets) transmitted that were between
             512 and 1023 octets in length inclusive
             (excluding framing bits but including FCS octets)."
     ::= { cienaCesPmExtendedTxRxCurr24HBinEntry 55 }

  cienaCesPmExtendedTxRxCurr24HBinTx1024To1518OctsPkts OBJECT-TYPE
     SYNTAX      Counter64
     MAX-ACCESS  read-only
     STATUS      current
     DESCRIPTION
             "The total number of packets (including bad
             packets) transmitted that were between
             1024 and 1518 octets in length inclusive
             (excluding framing bits but including FCS octets)."
     ::= { cienaCesPmExtendedTxRxCurr24HBinEntry 56 }

  cienaCesPmExtendedTxRxCurr24HBinTx1519To2047OctsPkts OBJECT-TYPE
     SYNTAX      Counter64
     MAX-ACCESS  read-only
     STATUS      current
     DESCRIPTION
             "The total number of packets (including bad
             packets) transmitted that were between
             1519 and 2047 octets in length inclusive
             (excluding framing bits but including FCS octets)."
     ::= { cienaCesPmExtendedTxRxCurr24HBinEntry 57 }

  cienaCesPmExtendedTxRxCurr24HBinTx2048To4095OctsPkts OBJECT-TYPE
     SYNTAX      Counter64
     MAX-ACCESS  read-only
     STATUS      current
     DESCRIPTION
             "The total number of packets (including bad
             packets) transmitted that were between
             2048 and 4095 octets in length inclusive
             (excluding framing bits but including FCS octets)."
     ::= { cienaCesPmExtendedTxRxCurr24HBinEntry 58 }

  cienaCesPmExtendedTxRxCurr24HBinTx4096To9216OctsPkts OBJECT-TYPE
     SYNTAX      Counter64
     MAX-ACCESS  read-only
     STATUS      current
     DESCRIPTION
             "The total number of packets (including bad
             packets) transmitted that were between
             4096 and 9216 octets in length inclusive
             (excluding framing bits but including FCS octets)."
     ::= { cienaCesPmExtendedTxRxCurr24HBinEntry 59 }

  cienaCesPmExtendedTxRxCurr24HBinTxDeferPkts OBJECT-TYPE
     SYNTAX      Counter64
     MAX-ACCESS  read-only
     STATUS      current
     DESCRIPTION
             "The number of defer packets transmitted on the port."
     ::= { cienaCesPmExtendedTxRxCurr24HBinEntry 60 }

  cienaCesPmExtendedTxRxCurr24HBinLinkUp OBJECT-TYPE
     SYNTAX      Counter64
     MAX-ACCESS  read-only
     STATUS      current
     DESCRIPTION
             "The number of link up events on the port."
     ::= { cienaCesPmExtendedTxRxCurr24HBinEntry 61 }

  cienaCesPmExtendedTxRxCurr24HBinLinkDown OBJECT-TYPE
     SYNTAX      Counter64
     MAX-ACCESS  read-only
     STATUS      current
     DESCRIPTION
             "The number of link down events on the port."
     ::= { cienaCesPmExtendedTxRxCurr24HBinEntry 62 }

  cienaCesPmExtendedTxRxCurr24HBinLinkFlap OBJECT-TYPE
     SYNTAX      Counter64
     MAX-ACCESS  read-only
     STATUS      current
     DESCRIPTION
             "The number of link flap events on the port."
     ::= { cienaCesPmExtendedTxRxCurr24HBinEntry 63 }

 --24 Hours History Bin
 
 cienaCesPmExtendedTxRxHist24HBinTable OBJECT-TYPE
     SYNTAX     SEQUENCE OF CienaCesPmExtendedTxRxHist24HBinEntry
     MAX-ACCESS not-accessible
     STATUS     current
     DESCRIPTION
            "The (conceptual) read-only table listing the extended TxRx profile statistics."  
     ::= { cienaCesPmExtendedTxRxStats 4 }
     
   cienaCesPmExtendedTxRxHist24HBinEntry OBJECT-TYPE
     SYNTAX      CienaCesPmExtendedTxRxHist24HBinEntry
     MAX-ACCESS  not-accessible
     STATUS      current
     DESCRIPTION
           "An entry (conceptual row) in the cienaCesPmExtendedTxRxHist24HBinTable.

           This table lists the statistics for the history 24 hour bins."  

     INDEX {cienaCesPmInstanceIndex }
     ::= { cienaCesPmExtendedTxRxHist24HBinTable 1 }
        
 CienaCesPmExtendedTxRxHist24HBinEntry ::=  SEQUENCE {      
 	 cienaCesPmExtendedTxRxHist24HBinStartTime					DisplayString,
     cienaCesPmExtendedTxRxHist24HBinDuration					Unsigned32,   
     cienaCesPmExtendedTxRxHist24HBinState					   	PmBinState,   
     cienaCesPmExtendedTxRxHist24HBinRxBytes                  	Counter64,
     cienaCesPmExtendedTxRxHist24HBinRxPkts                   	Counter64,
     cienaCesPmExtendedTxRxHist24HBinRxCrcErrorPkts           Counter64,
     cienaCesPmExtendedTxRxHist24HBinRxMcastPkts              Counter64,
     cienaCesPmExtendedTxRxHist24HBinRxBcastPkts              Counter64,
     cienaCesPmExtendedTxRxHist24HBinUndersizePkts            Counter64,
     cienaCesPmExtendedTxRxHist24HBinOversizePkts             Counter64,
     cienaCesPmExtendedTxRxHist24HBinFragmentsPkts            Counter64,
     cienaCesPmExtendedTxRxHist24HBinJabbersPkts              Counter64,
     cienaCesPmExtendedTxRxHist24HBin64OctsPkts               Counter64,
     cienaCesPmExtendedTxRxHist24HBin65To127OctsPkts          Counter64,
     cienaCesPmExtendedTxRxHist24HBin128To255OctsPkts         Counter64,
     cienaCesPmExtendedTxRxHist24HBin256To511OctsPkts         Counter64,
     cienaCesPmExtendedTxRxHist24HBin512To1023OctsPkts        Counter64,
     cienaCesPmExtendedTxRxHist24HBin1024To1518OctsPkts       Counter64,
     cienaCesPmExtendedTxRxHist24HBinTxBytes                  Counter64,
     cienaCesPmExtendedTxRxHist24HBinTxTBytes                 Counter64,
     cienaCesPmExtendedTxRxHist24HBinTxPkts                   Counter64,
     cienaCesPmExtendedTxRxHist24HBinTxBcastPkts              Counter64,
     cienaCesPmExtendedTxRxHist24HBinTxMcastPkts              Counter64,
     cienaCesPmExtendedTxRxHist24HBinTxExDeferPkts            Counter64,
     cienaCesPmExtendedTxRxHist24HBinTxGiantPkts              Counter64,
     cienaCesPmExtendedTxRxHist24HBinTxUnderRunPkts           Counter64,
     cienaCesPmExtendedTxRxHist24HBinTxCrcErrorPkts           Counter64,
     cienaCesPmExtendedTxRxHist24HBinTxLCheckErrorPkts        Counter64,
     cienaCesPmExtendedTxRxHist24HBinTxLOutRangePkts          Counter64,
     cienaCesPmExtendedTxRxHist24HBinTxLateCollPkts           Counter64,
     cienaCesPmExtendedTxRxHist24HBinTxExCollPkts             Counter64,
     cienaCesPmExtendedTxRxHist24HBinTxSingleCollPkts         Counter64,
     cienaCesPmExtendedTxRxHist24HBinTxCollPkts               Counter64,
     cienaCesPmExtendedTxRxHist24HBinDropEvents               Counter64,
     cienaCesPmExtendedTxRxHist24HBinInDiscards               Counter64,
     cienaCesPmExtendedTxRxHist24HBinTxPausePkts              Counter64,
     cienaCesPmExtendedTxRxHist24HBinRxPausePkts              Counter64,
     cienaCesPmExtendedTxRxHist24HBinRxBytesPerSec            Counter64,
     cienaCesPmExtendedTxRxHist24HBinRxFramesPerSec           Counter64,
     cienaCesPmExtendedTxRxHist24HBinTxBytesPerSec            Counter64,
     cienaCesPmExtendedTxRxHist24HBinTxFramesPerSec           Counter64,
     cienaCesPmExtendedTxRxHist24HBinRxLOutRangePkts          Counter64,
     cienaCesPmExtendedTxRxHist24HBinEndTime                  DisplayString,
     cienaCesPmExtendedTxRxHist24HBinClearTime                DisplayString,
     cienaCesPmExtendedTxRxHist24HBinRxUcastPkts              Counter64,
     cienaCesPmExtendedTxRxHist24HBinRxInErrorPkts            Counter64,
     cienaCesPmExtendedTxRxHist24HBin1519To2047OctsPkts       Counter64,
     cienaCesPmExtendedTxRxHist24HBin2048To4095OctsPkts       Counter64,
     cienaCesPmExtendedTxRxHist24HBin4096To9216OctsPkts       Counter64,
     cienaCesPmExtendedTxRxHist24HBinTxUcastPkts              Counter64,
     cienaCesPmExtendedTxRxHist24HBinTx64OctsPkts             Counter64,
     cienaCesPmExtendedTxRxHist24HBinTx65To127OctsPkts        Counter64,
     cienaCesPmExtendedTxRxHist24HBinTx128To255OctsPkts       Counter64,
     cienaCesPmExtendedTxRxHist24HBinTx256To511OctsPkts       Counter64,
     cienaCesPmExtendedTxRxHist24HBinTx512To1023OctsPkts      Counter64,
     cienaCesPmExtendedTxRxHist24HBinTx1024To1518OctsPkts     Counter64,
     cienaCesPmExtendedTxRxHist24HBinTx1519To2047OctsPkts     Counter64,
     cienaCesPmExtendedTxRxHist24HBinTx2048To4095OctsPkts     Counter64,
     cienaCesPmExtendedTxRxHist24HBinTx4096To9216OctsPkts     Counter64,
     cienaCesPmExtendedTxRxHist24HBinTxDeferPkts              Counter64,
     cienaCesPmExtendedTxRxHist24HBinLinkUp                   Counter64,
     cienaCesPmExtendedTxRxHist24HBinLinkDown                 Counter64,
     cienaCesPmExtendedTxRxHist24HBinLinkFlap                 Counter64

   } 
   cienaCesPmExtendedTxRxHist24HBinStartTime   OBJECT-TYPE
     SYNTAX		DisplayString
     MAX-ACCESS	read-only
     STATUS		current
     DESCRIPTION "Collection start time of the bin."
     ::= { cienaCesPmExtendedTxRxHist24HBinEntry 1	}
   
   cienaCesPmExtendedTxRxHist24HBinDuration OBJECT-TYPE
     SYNTAX      Unsigned32 (1..65535) 
     UNITS		"minutes"
     MAX-ACCESS  read-only
     STATUS      current
     DESCRIPTION
             "Duration of the bin."
     ::= { cienaCesPmExtendedTxRxHist24HBinEntry 2 }
  
  cienaCesPmExtendedTxRxHist24HBinState OBJECT-TYPE
     SYNTAX      PmBinState 
     MAX-ACCESS  read-only
     STATUS      current
     DESCRIPTION
             "State of the bin."
     ::= { cienaCesPmExtendedTxRxHist24HBinEntry 3 }
  
  cienaCesPmExtendedTxRxHist24HBinRxBytes OBJECT-TYPE
     SYNTAX      Counter64
     MAX-ACCESS  read-only
     STATUS      current
     DESCRIPTION
             "The number of bytes received by this PM instance."
     ::= { cienaCesPmExtendedTxRxHist24HBinEntry 4 }

 cienaCesPmExtendedTxRxHist24HBinRxPkts OBJECT-TYPE
     SYNTAX      Counter64
     MAX-ACCESS  read-only
     STATUS      current
     DESCRIPTION
             "The number of packets received by this PM instance."
     ::= { cienaCesPmExtendedTxRxHist24HBinEntry 5 } 
  
  cienaCesPmExtendedTxRxHist24HBinRxCrcErrorPkts OBJECT-TYPE
     SYNTAX      Counter64
     MAX-ACCESS  read-only
     STATUS      current
     DESCRIPTION
             "The number of packets received with CRC errors by this PM instance."
     ::= { cienaCesPmExtendedTxRxHist24HBinEntry 6 }   
  
  cienaCesPmExtendedTxRxHist24HBinRxMcastPkts OBJECT-TYPE
     SYNTAX      Counter64
     MAX-ACCESS  read-only
     STATUS      current
     DESCRIPTION
             "The total number of multicast packets received for the given PM instance."
     ::= { cienaCesPmExtendedTxRxHist24HBinEntry 7 }
     
  cienaCesPmExtendedTxRxHist24HBinRxBcastPkts OBJECT-TYPE
     SYNTAX      Counter64
     MAX-ACCESS  read-only
     STATUS      current
     DESCRIPTION
             "The number of broadcast packets received by this PM instance."
     ::= { cienaCesPmExtendedTxRxHist24HBinEntry 8 }
  
  cienaCesPmExtendedTxRxHist24HBinUndersizePkts OBJECT-TYPE
     SYNTAX      Counter64
     MAX-ACCESS  read-only
     STATUS      current
     DESCRIPTION
             "The total number of packets received that were
            less than 64 octets long (excluding framing bits,
            but including FCS octets) and were otherwise well
            formed."
     ::= { cienaCesPmExtendedTxRxHist24HBinEntry 9 }
  
  cienaCesPmExtendedTxRxHist24HBinOversizePkts OBJECT-TYPE
     SYNTAX      Counter64
     MAX-ACCESS  read-only
     STATUS      current
     DESCRIPTION
             "The total number of packets received that were
            longer than 1518 octets  but less than or equal to the MTU
            (excluding framing bits, but including FCS octets)
            and were otherwise well formed."
     ::= { cienaCesPmExtendedTxRxHist24HBinEntry 10 }
  
  cienaCesPmExtendedTxRxHist24HBinFragmentsPkts OBJECT-TYPE
     SYNTAX      Counter64
     MAX-ACCESS  read-only
     STATUS      current
     DESCRIPTION
             "The total number of packets received that were less
            than 64 octets in length (excluding framing bits but
            including FCS octets) and had either a bad Frame
            Check Sequence (FCS) with an integral number of
            octets (FCS Error) or a bad FCS with a non-integral
            number of octets (Alignment Error)."
     ::= { cienaCesPmExtendedTxRxHist24HBinEntry 11 }
  
  cienaCesPmExtendedTxRxHist24HBinJabbersPkts OBJECT-TYPE
     SYNTAX      Counter64
     MAX-ACCESS  read-only
     STATUS      current
     DESCRIPTION
             "The total number of packets received that were
            longer than 1518 octets (excluding framing bits,
            but including FCS octets), and had either a bad
            Frame Check Sequence (FCS) with an integral number
            of octets (FCS Error) or a bad FCS with a
            non-integral number of octets (Alignment Error)."
     ::= { cienaCesPmExtendedTxRxHist24HBinEntry 12 }
  
  cienaCesPmExtendedTxRxHist24HBin64OctsPkts OBJECT-TYPE
     SYNTAX      Counter64
     MAX-ACCESS  read-only
     STATUS      current
     DESCRIPTION
             "The total number of packets (including bad
            packets) received that were 64 octets in length
            (excluding framing bits but including FCS octets)."
     ::= { cienaCesPmExtendedTxRxHist24HBinEntry 13 }
  
  cienaCesPmExtendedTxRxHist24HBin65To127OctsPkts OBJECT-TYPE
     SYNTAX      Counter64
     MAX-ACCESS  read-only
     STATUS      current
     DESCRIPTION
             "The total number of packets (including bad
            packets) received that were between
            65 and 127 octets in length inclusive
            (excluding framing bits but including FCS octets)."
     ::= { cienaCesPmExtendedTxRxHist24HBinEntry 14 }
  
  cienaCesPmExtendedTxRxHist24HBin128To255OctsPkts OBJECT-TYPE
     SYNTAX      Counter64
     MAX-ACCESS  read-only
     STATUS      current
     DESCRIPTION
             "The total number of packets (including bad
            packets) received that were between
            128 and 255 octets in length inclusive
            (excluding framing bits but including FCS octets)."
     ::= { cienaCesPmExtendedTxRxHist24HBinEntry 15 }
  
  cienaCesPmExtendedTxRxHist24HBin256To511OctsPkts OBJECT-TYPE
     SYNTAX      Counter64
     MAX-ACCESS  read-only
     STATUS      current
     DESCRIPTION
             "The total number of packets (including bad
            packets) received that were between
            256 and 511 octets in length inclusive
            (excluding framing bits but including FCS octets)."
     ::= { cienaCesPmExtendedTxRxHist24HBinEntry 16 }
  
  cienaCesPmExtendedTxRxHist24HBin512To1023OctsPkts OBJECT-TYPE
     SYNTAX      Counter64
     MAX-ACCESS  read-only
     STATUS      current
     DESCRIPTION
             "The total number of packets (including bad
            packets) received that were between
            512 and 1023 octets in length inclusive
            (excluding framing bits but including FCS octets)."
     ::= { cienaCesPmExtendedTxRxHist24HBinEntry 17 }
  
  cienaCesPmExtendedTxRxHist24HBin1024To1518OctsPkts OBJECT-TYPE
     SYNTAX      Counter64
     MAX-ACCESS  read-only
     STATUS      current
     DESCRIPTION
             "The total number of packets (including bad
            packets) received that were between
            1024 and 1518 octets in length inclusive
            (excluding framing bits but including FCS octets)."
     ::= { cienaCesPmExtendedTxRxHist24HBinEntry 18 }
  
  cienaCesPmExtendedTxRxHist24HBinTxBytes OBJECT-TYPE
     SYNTAX      Counter64
     MAX-ACCESS  read-only
     STATUS      current
     DESCRIPTION
             "The number of octets transmitted on this PM instance."
     ::= { cienaCesPmExtendedTxRxHist24HBinEntry 19 }
  
  cienaCesPmExtendedTxRxHist24HBinTxTBytes OBJECT-TYPE
     SYNTAX      Counter64
     MAX-ACCESS  read-only
     STATUS      current
     DESCRIPTION
             "The total number of octets transmitted on this PM instance."
     ::= { cienaCesPmExtendedTxRxHist24HBinEntry 20 }
  
  cienaCesPmExtendedTxRxHist24HBinTxPkts OBJECT-TYPE
     SYNTAX      Counter64
     MAX-ACCESS  read-only
     STATUS      current
     DESCRIPTION
             "The total number of packets transmitted on this PM instance."
     ::= { cienaCesPmExtendedTxRxHist24HBinEntry 21 }
  
  cienaCesPmExtendedTxRxHist24HBinTxBcastPkts OBJECT-TYPE
     SYNTAX      Counter64
     MAX-ACCESS  read-only
     STATUS      current
     DESCRIPTION
             "The number of broadcast packets transmitted on this PM instance."
     ::= { cienaCesPmExtendedTxRxHist24HBinEntry 22 }
  
  cienaCesPmExtendedTxRxHist24HBinTxMcastPkts OBJECT-TYPE
     SYNTAX      Counter64
     MAX-ACCESS  read-only
     STATUS      current
     DESCRIPTION
             "The number of multicast packets transmitted on this PM instance."
     ::= { cienaCesPmExtendedTxRxHist24HBinEntry 23 }
  
  cienaCesPmExtendedTxRxHist24HBinTxExDeferPkts OBJECT-TYPE
     SYNTAX      Counter64
     MAX-ACCESS  read-only
     STATUS      current
     DESCRIPTION
             "The number of excessive defer packets transmitted on this PM instance."
     ::= { cienaCesPmExtendedTxRxHist24HBinEntry 24 }
  
  cienaCesPmExtendedTxRxHist24HBinTxGiantPkts OBJECT-TYPE
     SYNTAX      Counter64
     MAX-ACCESS  read-only
     STATUS      current
     DESCRIPTION
             "The number of too big packets transmitted on this PM instance."
     ::= { cienaCesPmExtendedTxRxHist24HBinEntry 25 }
  
  cienaCesPmExtendedTxRxHist24HBinTxUnderRunPkts OBJECT-TYPE
     SYNTAX      Counter64
     MAX-ACCESS  read-only
     STATUS      current
     DESCRIPTION
             "The number of underrun packets transmitted on this PM instance."
     ::= { cienaCesPmExtendedTxRxHist24HBinEntry 26 }
  
  cienaCesPmExtendedTxRxHist24HBinTxCrcErrorPkts OBJECT-TYPE
     SYNTAX      Counter64
     MAX-ACCESS  read-only
     STATUS      current
     DESCRIPTION
             "The number of CRC error packets transmitted on this PM instance."
     ::= { cienaCesPmExtendedTxRxHist24HBinEntry 27 }
  
  cienaCesPmExtendedTxRxHist24HBinTxLCheckErrorPkts OBJECT-TYPE
     SYNTAX      Counter64
     MAX-ACCESS  read-only
     STATUS      current
     DESCRIPTION
             "The number of length check error packets transmitted on this PM instance."
     ::= { cienaCesPmExtendedTxRxHist24HBinEntry 28 }
  
  cienaCesPmExtendedTxRxHist24HBinTxLOutRangePkts OBJECT-TYPE
     SYNTAX      Counter64
     MAX-ACCESS  read-only
     STATUS      current
     DESCRIPTION
             "The number of out of range packets transmitted on this PM instance."
     ::= { cienaCesPmExtendedTxRxHist24HBinEntry 29 }
  
  cienaCesPmExtendedTxRxHist24HBinTxLateCollPkts OBJECT-TYPE
     SYNTAX      Counter64
     MAX-ACCESS  read-only
     STATUS      current
     DESCRIPTION
             "The number of late collision packets transmitted on this PM instance."
     ::= { cienaCesPmExtendedTxRxHist24HBinEntry 30 }
  
  cienaCesPmExtendedTxRxHist24HBinTxExCollPkts OBJECT-TYPE
     SYNTAX      Counter64
     MAX-ACCESS  read-only
     STATUS      current
     DESCRIPTION
             "The number of excessive collision packets transmitted on this PM instance."
     ::= { cienaCesPmExtendedTxRxHist24HBinEntry 31 }
  
  cienaCesPmExtendedTxRxHist24HBinTxSingleCollPkts OBJECT-TYPE
     SYNTAX      Counter64
     MAX-ACCESS  read-only
     STATUS      current
     DESCRIPTION
             "The number of single collision packets transmitted on this PM instance."   
     ::= { cienaCesPmExtendedTxRxHist24HBinEntry 32 }
  
  cienaCesPmExtendedTxRxHist24HBinTxCollPkts OBJECT-TYPE
     SYNTAX      Counter64
     MAX-ACCESS  read-only
     STATUS      current
     DESCRIPTION
             "The number of collision packets transmitted on this PM instance."
     ::= { cienaCesPmExtendedTxRxHist24HBinEntry 33 }

  
  cienaCesPmExtendedTxRxHist24HBinDropEvents OBJECT-TYPE
     SYNTAX      Counter64
     MAX-ACCESS  read-only
     STATUS      current
     DESCRIPTION
             "The number of packet drop events on this PM instance."
     ::= { cienaCesPmExtendedTxRxHist24HBinEntry 34 }
  
  cienaCesPmExtendedTxRxHist24HBinInDiscards OBJECT-TYPE
     SYNTAX      Counter64
     MAX-ACCESS  read-only
     STATUS      current
     DESCRIPTION
             "The number of packet discards on this PM instance."
     ::= { cienaCesPmExtendedTxRxHist24HBinEntry 35 }
  
  cienaCesPmExtendedTxRxHist24HBinTxPausePkts OBJECT-TYPE
     SYNTAX      Counter64
     MAX-ACCESS  read-only
     STATUS      current
     DESCRIPTION
             "The pause packets transmitted on this PM instance."
     ::= { cienaCesPmExtendedTxRxHist24HBinEntry 36 }
  
  cienaCesPmExtendedTxRxHist24HBinRxPausePkts OBJECT-TYPE
     SYNTAX      Counter64
     MAX-ACCESS  read-only
     STATUS      current
     DESCRIPTION
             "The pause packets received on this PM instance."
     ::= { cienaCesPmExtendedTxRxHist24HBinEntry 37 }
  
  cienaCesPmExtendedTxRxHist24HBinRxBytesPerSec OBJECT-TYPE
     SYNTAX      Counter64
     MAX-ACCESS  read-only
     STATUS      current
     DESCRIPTION
             "The number of bytes received per second on this PM instance."
     ::= { cienaCesPmExtendedTxRxHist24HBinEntry 38 }
  
  cienaCesPmExtendedTxRxHist24HBinRxFramesPerSec OBJECT-TYPE
     SYNTAX      Counter64
     MAX-ACCESS  read-only
     STATUS      current
     DESCRIPTION
             "The number of frames received per second on this PM instance."
     ::= { cienaCesPmExtendedTxRxHist24HBinEntry 39 }
  
  cienaCesPmExtendedTxRxHist24HBinTxBytesPerSec OBJECT-TYPE
     SYNTAX      Counter64
     MAX-ACCESS  read-only
     STATUS      current
     DESCRIPTION
             "The number of bytes transmitted per second on this PM instance."
     ::= { cienaCesPmExtendedTxRxHist24HBinEntry 40 }
  
  cienaCesPmExtendedTxRxHist24HBinTxFramesPerSec OBJECT-TYPE
     SYNTAX      Counter64
     MAX-ACCESS  read-only
     STATUS      current
     DESCRIPTION
             "The number of frames transmitted per second on this PM instance."
     ::= { cienaCesPmExtendedTxRxHist24HBinEntry 41 }

  cienaCesPmExtendedTxRxHist24HBinRxLOutRangePkts OBJECT-TYPE
     SYNTAX      Counter64
     MAX-ACCESS  read-only
     STATUS      current
     DESCRIPTION
             "The total number of packets received that were
             longer than the MTU (excluding framing bits,
             but including FCS octets) and were otherwise
             well formed."
     ::= { cienaCesPmExtendedTxRxHist24HBinEntry 42 }

  cienaCesPmExtendedTxRxHist24HBinEndTime OBJECT-TYPE
     SYNTAX      DisplayString
     MAX-ACCESS  read-only
     STATUS      current
     DESCRIPTION "Collection end time of the bin."
     ::= { cienaCesPmExtendedTxRxHist24HBinEntry 43 }

  cienaCesPmExtendedTxRxHist24HBinClearTime OBJECT-TYPE
     SYNTAX      DisplayString
     MAX-ACCESS  read-only
     STATUS      current
     DESCRIPTION "Collection clear time of the bin."
     ::= { cienaCesPmExtendedTxRxHist24HBinEntry 44 }

  cienaCesPmExtendedTxRxHist24HBinRxUcastPkts OBJECT-TYPE
     SYNTAX      Counter64
     MAX-ACCESS  read-only
     STATUS      current
     DESCRIPTION
            "The number of unicast packets received on the port."
     ::= { cienaCesPmExtendedTxRxHist24HBinEntry 45 }	

  cienaCesPmExtendedTxRxHist24HBinRxInErrorPkts OBJECT-TYPE
     SYNTAX      Counter64
     MAX-ACCESS  read-only
     STATUS      current
     DESCRIPTION
             "The number of in error packets received on the port."
     ::= { cienaCesPmExtendedTxRxHist24HBinEntry 46 }

  cienaCesPmExtendedTxRxHist24HBin1519To2047OctsPkts OBJECT-TYPE
     SYNTAX      Counter64
     MAX-ACCESS  read-only
     STATUS      current
     DESCRIPTION
             "The total number of packets (including bad
             packets) received that were between
             1519 and 2047 octets in length inclusive
             (excluding framing bits but including FCS octets)."
     ::= { cienaCesPmExtendedTxRxHist24HBinEntry 47 }

  cienaCesPmExtendedTxRxHist24HBin2048To4095OctsPkts OBJECT-TYPE
     SYNTAX      Counter64
     MAX-ACCESS  read-only
     STATUS      current
     DESCRIPTION
             "The total number of packets (including bad
             packets) received that were between
             2048 and 4095 octets in length inclusive
             (excluding framing bits but including FCS octets)."
     ::= { cienaCesPmExtendedTxRxHist24HBinEntry 48 }

  cienaCesPmExtendedTxRxHist24HBin4096To9216OctsPkts OBJECT-TYPE
     SYNTAX      Counter64
     MAX-ACCESS  read-only
     STATUS      current
     DESCRIPTION
             "The total number of packets (including bad
             packets) received that were between
             4096 and 9216 octets in length inclusive
             (excluding framing bits but including FCS octets)."
     ::= { cienaCesPmExtendedTxRxHist24HBinEntry 49 }

  cienaCesPmExtendedTxRxHist24HBinTxUcastPkts OBJECT-TYPE
     SYNTAX      Counter64
     MAX-ACCESS  read-only
     STATUS      current
     DESCRIPTION
             "The number of unicast packets transmitted on the port."
     ::= { cienaCesPmExtendedTxRxHist24HBinEntry 50 }

  cienaCesPmExtendedTxRxHist24HBinTx64OctsPkts OBJECT-TYPE
     SYNTAX      Counter64
     MAX-ACCESS  read-only
     STATUS      current
     DESCRIPTION
             "The total number of packets (including bad
             packets) transmitted that were between
             64 octets in length inclusive
             (excluding framing bits but including FCS octets)."
     ::= { cienaCesPmExtendedTxRxHist24HBinEntry 51 }

  cienaCesPmExtendedTxRxHist24HBinTx65To127OctsPkts OBJECT-TYPE
     SYNTAX      Counter64
     MAX-ACCESS  read-only
     STATUS      current
     DESCRIPTION
             "The total number of packets (including bad
             packets) transmitted that were between
             65 and 127 octets in length inclusive
             (excluding framing bits but including FCS octets)."
     ::= { cienaCesPmExtendedTxRxHist24HBinEntry 52 }

  cienaCesPmExtendedTxRxHist24HBinTx128To255OctsPkts OBJECT-TYPE
     SYNTAX      Counter64
     MAX-ACCESS  read-only
     STATUS      current
     DESCRIPTION
             "The total number of packets (including bad
             packets) transmitted that were between
             128 and 255 octets in length inclusive
             (excluding framing bits but including FCS octets)."
     ::= { cienaCesPmExtendedTxRxHist24HBinEntry 53 }

  cienaCesPmExtendedTxRxHist24HBinTx256To511OctsPkts OBJECT-TYPE
     SYNTAX      Counter64
     MAX-ACCESS  read-only
     STATUS      current
     DESCRIPTION
             "The total number of packets (including bad
             packets) transmitted that were between
             256 and 511 octets in length inclusive
             (excluding framing bits but including FCS octets)."
     ::= { cienaCesPmExtendedTxRxHist24HBinEntry 54 }

  cienaCesPmExtendedTxRxHist24HBinTx512To1023OctsPkts OBJECT-TYPE
     SYNTAX      Counter64
     MAX-ACCESS  read-only
     STATUS      current
     DESCRIPTION
             "The total number of packets (including bad
             packets) transmitted that were between
             512 and 1023 octets in length inclusive
             (excluding framing bits but including FCS octets)."
     ::= { cienaCesPmExtendedTxRxHist24HBinEntry 55 }

  cienaCesPmExtendedTxRxHist24HBinTx1024To1518OctsPkts OBJECT-TYPE
     SYNTAX      Counter64
     MAX-ACCESS  read-only
     STATUS      current
     DESCRIPTION
             "The total number of packets (including bad
             packets) transmitted that were between
             1024 and 1518 octets in length inclusive
             (excluding framing bits but including FCS octets)."
     ::= { cienaCesPmExtendedTxRxHist24HBinEntry 56 }

  cienaCesPmExtendedTxRxHist24HBinTx1519To2047OctsPkts OBJECT-TYPE
     SYNTAX      Counter64
     MAX-ACCESS  read-only
     STATUS      current
     DESCRIPTION
             "The total number of packets (including bad
             packets) transmitted that were between
             1519 and 2047 octets in length inclusive
             (excluding framing bits but including FCS octets)."
     ::= { cienaCesPmExtendedTxRxHist24HBinEntry 57 }

  cienaCesPmExtendedTxRxHist24HBinTx2048To4095OctsPkts OBJECT-TYPE
     SYNTAX      Counter64
     MAX-ACCESS  read-only
     STATUS      current
     DESCRIPTION
             "The total number of packets (including bad
             packets) transmitted that were between
             2048 and 4095 octets in length inclusive
             (excluding framing bits but including FCS octets)."
     ::= { cienaCesPmExtendedTxRxHist24HBinEntry 58 }

  cienaCesPmExtendedTxRxHist24HBinTx4096To9216OctsPkts OBJECT-TYPE
     SYNTAX      Counter64
     MAX-ACCESS  read-only
     STATUS      current
     DESCRIPTION
             "The total number of packets (including bad
             packets) transmitted that were between
             4096 and 9216 octets in length inclusive
             (excluding framing bits but including FCS octets)."
     ::= { cienaCesPmExtendedTxRxHist24HBinEntry 59 }

  cienaCesPmExtendedTxRxHist24HBinTxDeferPkts OBJECT-TYPE
     SYNTAX      Counter64
     MAX-ACCESS  read-only
     STATUS      current
     DESCRIPTION
             "The number of defer packets transmitted on the port."
     ::= { cienaCesPmExtendedTxRxHist24HBinEntry 60 }

  cienaCesPmExtendedTxRxHist24HBinLinkUp OBJECT-TYPE
     SYNTAX      Counter64
     MAX-ACCESS  read-only
     STATUS      current
     DESCRIPTION
             "The number of link up events on the port."
     ::= { cienaCesPmExtendedTxRxHist24HBinEntry 61 }

  cienaCesPmExtendedTxRxHist24HBinLinkDown OBJECT-TYPE
     SYNTAX      Counter64
     MAX-ACCESS  read-only
     STATUS      current
     DESCRIPTION
             "The number of link down events on the port."
     ::= { cienaCesPmExtendedTxRxHist24HBinEntry 62 }

  cienaCesPmExtendedTxRxHist24HBinLinkFlap OBJECT-TYPE
     SYNTAX      Counter64
     MAX-ACCESS  read-only
     STATUS      current
     DESCRIPTION
             "The number of link flap events on the port."
     ::= { cienaCesPmExtendedTxRxHist24HBinEntry 63 }

 --AllTime Bin
 
 cienaCesPmExtendedTxRxAllTimeBinTable OBJECT-TYPE
     SYNTAX     SEQUENCE OF CienaCesPmExtendedTxRxAllTimeBinEntry
     MAX-ACCESS not-accessible
     STATUS     obsolete
     DESCRIPTION
            "The (conceptual) read-only table listing the extended TxRx profile statistics."  
     ::= { cienaCesPmExtendedTxRxStats 5 }
     
   cienaCesPmExtendedTxRxAllTimeBinEntry OBJECT-TYPE
     SYNTAX      CienaCesPmExtendedTxRxAllTimeBinEntry
     MAX-ACCESS  not-accessible
     STATUS      obsolete
     DESCRIPTION
           "An entry (conceptual row) in the cienaCesPmExtendedTxRxAllTimeBinTable.

           This table lists the stats for the All Time bin of the PM instance."  

     INDEX {cienaCesPmInstanceIndex }
     ::= { cienaCesPmExtendedTxRxAllTimeBinTable 1 }
        
 CienaCesPmExtendedTxRxAllTimeBinEntry ::=  SEQUENCE {
 	 cienaCesPmExtendedTxRxAllTimeBinRxBytes                   	Counter64,
     cienaCesPmExtendedTxRxAllTimeBinRxPkts                    	Counter64,
     cienaCesPmExtendedTxRxAllTimeBinRxCrcErrorPkts            	Counter64,
     cienaCesPmExtendedTxRxAllTimeBinRxMcastPkts               	Counter64,
     cienaCesPmExtendedTxRxAllTimeBinRxBcastPkts               	Counter64,
     cienaCesPmExtendedTxRxAllTimeBinUndersizePkts             	Counter64,
     cienaCesPmExtendedTxRxAllTimeBinOversizePkts              	Counter64,
     cienaCesPmExtendedTxRxAllTimeBinFragmentsPkts             	Counter64,
     cienaCesPmExtendedTxRxAllTimeBinJabbersPkts               	Counter64,
     cienaCesPmExtendedTxRxAllTimeBin64OctsPkts                	Counter64,
     cienaCesPmExtendedTxRxAllTimeBin65To127OctsPkts           	Counter64,
     cienaCesPmExtendedTxRxAllTimeBin128To255OctsPkts          	Counter64,
     cienaCesPmExtendedTxRxAllTimeBin256To511OctsPkts          	Counter64,
     cienaCesPmExtendedTxRxAllTimeBin512To1023OctsPkts         	Counter64,
     cienaCesPmExtendedTxRxAllTimeBin1024To1518OctsPkts        	Counter64,
     cienaCesPmExtendedTxRxAllTimeBinTxBytes                   	Counter64,
     cienaCesPmExtendedTxRxAllTimeBinTxTBytes                  	Counter64,
     cienaCesPmExtendedTxRxAllTimeBinTxPkts                    	Counter64,
     cienaCesPmExtendedTxRxAllTimeBinTxBcastPkts               	Counter64,
     cienaCesPmExtendedTxRxAllTimeBinTxMcastPkts               	Counter64,
     cienaCesPmExtendedTxRxAllTimeBinTxExDeferPkts             	Counter64,
     cienaCesPmExtendedTxRxAllTimeBinTxGiantPkts               	Counter64,
     cienaCesPmExtendedTxRxAllTimeBinTxUnderRunPkts            	Counter64,
     cienaCesPmExtendedTxRxAllTimeBinTxCrcErrorPkts            	Counter64,
     cienaCesPmExtendedTxRxAllTimeBinTxLCheckErrorPkts         	Counter64,
     cienaCesPmExtendedTxRxAllTimeBinTxLOutRangePkts           	Counter64,
     cienaCesPmExtendedTxRxAllTimeBinTxLateCollPkts            	Counter64,
     cienaCesPmExtendedTxRxAllTimeBinTxExCollPkts              	Counter64,
     cienaCesPmExtendedTxRxAllTimeBinTxSingleCollPkts          	Counter64,
     cienaCesPmExtendedTxRxAllTimeBinTxCollPkts                	Counter64,
     cienaCesPmExtendedTxRxAllTimeBinDropEvents                	Counter64,
     cienaCesPmExtendedTxRxAllTimeBinInDiscards                	Counter64,
     cienaCesPmExtendedTxRxAllTimeBinTxPausePkts               	Counter64,
     cienaCesPmExtendedTxRxAllTimeBinRxPausePkts               	Counter64,
     cienaCesPmExtendedTxRxAllTimeBinRxBytesPerSec           	   Counter64,
     cienaCesPmExtendedTxRxAllTimeBinRxFramesPerSec          	   Counter64,
     cienaCesPmExtendedTxRxAllTimeBinTxBytesPerSec                Counter64,
     cienaCesPmExtendedTxRxAllTimeBinTxFramesPerSec          	   Counter64,
     cienaCesPmExtendedTxRxAllTimeBinRxLOutRangePkts          	   Counter64
   }
   cienaCesPmExtendedTxRxAllTimeBinRxBytes OBJECT-TYPE
     SYNTAX      Counter64
     MAX-ACCESS  read-only
     STATUS      obsolete
     DESCRIPTION
             "The number of bytes received by this PM instance."
     ::= { cienaCesPmExtendedTxRxAllTimeBinEntry 1 }

 cienaCesPmExtendedTxRxAllTimeBinRxPkts OBJECT-TYPE
     SYNTAX      Counter64
     MAX-ACCESS  read-only
     STATUS      obsolete
     DESCRIPTION
             "The number of packets received by this PM instance."
     ::= { cienaCesPmExtendedTxRxAllTimeBinEntry 2 } 
  
  cienaCesPmExtendedTxRxAllTimeBinRxCrcErrorPkts OBJECT-TYPE
     SYNTAX      Counter64
     MAX-ACCESS  read-only
     STATUS      obsolete
     DESCRIPTION
             "The number of packets received with CRC errors by this PM instance."
     ::= { cienaCesPmExtendedTxRxAllTimeBinEntry 3 }   
  
  cienaCesPmExtendedTxRxAllTimeBinRxMcastPkts OBJECT-TYPE
     SYNTAX      Counter64
     MAX-ACCESS  read-only
     STATUS      obsolete
     DESCRIPTION
             "The total number of multicast packets received for the given PM instance."
     ::= { cienaCesPmExtendedTxRxAllTimeBinEntry 4 }
     
  cienaCesPmExtendedTxRxAllTimeBinRxBcastPkts OBJECT-TYPE
     SYNTAX      Counter64
     MAX-ACCESS  read-only
     STATUS      obsolete
     DESCRIPTION
             "The number of broadcast packets received by this PM instance."
     ::= { cienaCesPmExtendedTxRxAllTimeBinEntry 5 }
  
  cienaCesPmExtendedTxRxAllTimeBinUndersizePkts OBJECT-TYPE
     SYNTAX      Counter64
     MAX-ACCESS  read-only
     STATUS      obsolete
     DESCRIPTION
             "The total number of packets received that were
            less than 64 octets long (excluding framing bits,
            but including FCS octets) and were otherwise well
            formed."
     ::= { cienaCesPmExtendedTxRxAllTimeBinEntry 6 }
  
  cienaCesPmExtendedTxRxAllTimeBinOversizePkts OBJECT-TYPE
     SYNTAX      Counter64
     MAX-ACCESS  read-only
     STATUS      obsolete
     DESCRIPTION
             "The total number of packets received that were
            longer than 1518 octets  but less than or equal to the MTU
            (excluding framing bits, but including FCS octets)
            and were otherwise well formed."
     ::= { cienaCesPmExtendedTxRxAllTimeBinEntry 7 }
  
  cienaCesPmExtendedTxRxAllTimeBinFragmentsPkts OBJECT-TYPE
     SYNTAX      Counter64
     MAX-ACCESS  read-only
     STATUS      obsolete
     DESCRIPTION
             "The total number of packets received that were less
            than 64 octets in length (excluding framing bits but
            including FCS octets) and had either a bad Frame
            Check Sequence (FCS) with an integral number of
            octets (FCS Error) or a bad FCS with a non-integral
            number of octets (Alignment Error)."
     ::= { cienaCesPmExtendedTxRxAllTimeBinEntry 8 }
  
  cienaCesPmExtendedTxRxAllTimeBinJabbersPkts OBJECT-TYPE
     SYNTAX      Counter64
     MAX-ACCESS  read-only
     STATUS      obsolete
     DESCRIPTION
             "The total number of packets received that were
            longer than 1518 octets (excluding framing bits,
            but including FCS octets), and had either a bad
            Frame Check Sequence (FCS) with an integral number
            of octets (FCS Error) or a bad FCS with a
            non-integral number of octets (Alignment Error)."
     ::= { cienaCesPmExtendedTxRxAllTimeBinEntry 9 }
  
  cienaCesPmExtendedTxRxAllTimeBin64OctsPkts OBJECT-TYPE
     SYNTAX      Counter64
     MAX-ACCESS  read-only
     STATUS      obsolete
     DESCRIPTION
             "The total number of packets (including bad
            packets) received that were 64 octets in length
            (excluding framing bits but including FCS octets)."
     ::= { cienaCesPmExtendedTxRxAllTimeBinEntry 10 }
  
  cienaCesPmExtendedTxRxAllTimeBin65To127OctsPkts OBJECT-TYPE
     SYNTAX      Counter64
     MAX-ACCESS  read-only
     STATUS      obsolete
     DESCRIPTION
             "The total number of packets (including bad
            packets) received that were between
            65 and 127 octets in length inclusive
            (excluding framing bits but including FCS octets)."
     ::= { cienaCesPmExtendedTxRxAllTimeBinEntry 11 }
  
  cienaCesPmExtendedTxRxAllTimeBin128To255OctsPkts OBJECT-TYPE
     SYNTAX      Counter64
     MAX-ACCESS  read-only
     STATUS      obsolete
     DESCRIPTION
             "The total number of packets (including bad
            packets) received that were between
            128 and 255 octets in length inclusive
            (excluding framing bits but including FCS octets)."
     ::= { cienaCesPmExtendedTxRxAllTimeBinEntry 12 }
  
  cienaCesPmExtendedTxRxAllTimeBin256To511OctsPkts OBJECT-TYPE
     SYNTAX      Counter64
     MAX-ACCESS  read-only
     STATUS      obsolete
     DESCRIPTION
             "The total number of packets (including bad
            packets) received that were between
            256 and 511 octets in length inclusive
            (excluding framing bits but including FCS octets)."
     ::= { cienaCesPmExtendedTxRxAllTimeBinEntry 13 }
  
  cienaCesPmExtendedTxRxAllTimeBin512To1023OctsPkts OBJECT-TYPE
     SYNTAX      Counter64
     MAX-ACCESS  read-only
     STATUS      obsolete
     DESCRIPTION
             "The total number of packets (including bad
            packets) received that were between
            512 and 1023 octets in length inclusive
            (excluding framing bits but including FCS octets)."
     ::= { cienaCesPmExtendedTxRxAllTimeBinEntry 14 }
  
  cienaCesPmExtendedTxRxAllTimeBin1024To1518OctsPkts OBJECT-TYPE
     SYNTAX      Counter64
     MAX-ACCESS  read-only
     STATUS      obsolete
     DESCRIPTION
             "The total number of packets (including bad packets) received that were between
            1024 and 1518 octets in length inclusive (excluding framing bits but including FCS octets)."
     ::= { cienaCesPmExtendedTxRxAllTimeBinEntry 15 }
  
  cienaCesPmExtendedTxRxAllTimeBinTxBytes OBJECT-TYPE
     SYNTAX      Counter64
     MAX-ACCESS  read-only
     STATUS      obsolete
     DESCRIPTION
             "The number of octets transmitted on this PM instance."
     ::= { cienaCesPmExtendedTxRxAllTimeBinEntry 16 }
  
  cienaCesPmExtendedTxRxAllTimeBinTxTBytes OBJECT-TYPE
     SYNTAX      Counter64
     MAX-ACCESS  read-only
     STATUS      obsolete
     DESCRIPTION
             "The total number of octets transmitted on this PM instance."
     ::= { cienaCesPmExtendedTxRxAllTimeBinEntry 17 }
  
  cienaCesPmExtendedTxRxAllTimeBinTxPkts OBJECT-TYPE
     SYNTAX      Counter64
     MAX-ACCESS  read-only
     STATUS      obsolete
     DESCRIPTION
             "The total number of packets transmitted on this PM instance."
     ::= { cienaCesPmExtendedTxRxAllTimeBinEntry 18 }
  
  cienaCesPmExtendedTxRxAllTimeBinTxBcastPkts OBJECT-TYPE
     SYNTAX      Counter64
     MAX-ACCESS  read-only
     STATUS      obsolete
     DESCRIPTION
             "The number of broadcast packets transmitted on this PM instance."
     ::= { cienaCesPmExtendedTxRxAllTimeBinEntry 19 }
  
  cienaCesPmExtendedTxRxAllTimeBinTxMcastPkts OBJECT-TYPE
     SYNTAX      Counter64
     MAX-ACCESS  read-only
     STATUS      obsolete
     DESCRIPTION
             "The number of multicast packets transmitted on the interface."
     ::= { cienaCesPmExtendedTxRxAllTimeBinEntry 20 }
  
  cienaCesPmExtendedTxRxAllTimeBinTxExDeferPkts OBJECT-TYPE
     SYNTAX      Counter64
     MAX-ACCESS  read-only
     STATUS      obsolete
     DESCRIPTION
             "The number of excessive defer packets transmitted on the interface."
     ::= { cienaCesPmExtendedTxRxAllTimeBinEntry 21 }
  
  cienaCesPmExtendedTxRxAllTimeBinTxGiantPkts OBJECT-TYPE
     SYNTAX      Counter64
     MAX-ACCESS  read-only
     STATUS      obsolete
     DESCRIPTION
             "The number of too big packets transmitted on the interface."
     ::= { cienaCesPmExtendedTxRxAllTimeBinEntry 22 }
  
  cienaCesPmExtendedTxRxAllTimeBinTxUnderRunPkts OBJECT-TYPE
     SYNTAX      Counter64
     MAX-ACCESS  read-only
     STATUS      obsolete
     DESCRIPTION
             "The number of underrun packets transmitted on the interface."
     ::= { cienaCesPmExtendedTxRxAllTimeBinEntry 23 }
  
  cienaCesPmExtendedTxRxAllTimeBinTxCrcErrorPkts OBJECT-TYPE
     SYNTAX      Counter64
     MAX-ACCESS  read-only
     STATUS      obsolete
     DESCRIPTION
             "The number of CRC error packets transmitted on the interface."
     ::= { cienaCesPmExtendedTxRxAllTimeBinEntry 24 }
  
  cienaCesPmExtendedTxRxAllTimeBinTxLCheckErrorPkts OBJECT-TYPE
     SYNTAX      Counter64
     MAX-ACCESS  read-only
     STATUS      obsolete
     DESCRIPTION
             "The number of length check error packets transmitted on the interface."
     ::= { cienaCesPmExtendedTxRxAllTimeBinEntry 25 }
  
  cienaCesPmExtendedTxRxAllTimeBinTxLOutRangePkts OBJECT-TYPE
     SYNTAX      Counter64
     MAX-ACCESS  read-only
     STATUS      obsolete
     DESCRIPTION
             "The number of out of range packets transmitted on the interface."
     ::= { cienaCesPmExtendedTxRxAllTimeBinEntry 26 }
  
  cienaCesPmExtendedTxRxAllTimeBinTxLateCollPkts OBJECT-TYPE
     SYNTAX      Counter64
     MAX-ACCESS  read-only
     STATUS      obsolete
     DESCRIPTION
             "The number of late collision packets transmitted on the interface."
     ::= { cienaCesPmExtendedTxRxAllTimeBinEntry 27 }
  
  cienaCesPmExtendedTxRxAllTimeBinTxExCollPkts OBJECT-TYPE
     SYNTAX      Counter64
     MAX-ACCESS  read-only
     STATUS      obsolete
     DESCRIPTION
             "The number of excessive collision packets transmitted on the interface."
     ::= { cienaCesPmExtendedTxRxAllTimeBinEntry 28 }
  
  cienaCesPmExtendedTxRxAllTimeBinTxSingleCollPkts OBJECT-TYPE
     SYNTAX      Counter64
     MAX-ACCESS  read-only
     STATUS      obsolete
     DESCRIPTION
             "The number of single collision packets transmitted on the interface."
     ::= { cienaCesPmExtendedTxRxAllTimeBinEntry 29 }
  
  cienaCesPmExtendedTxRxAllTimeBinTxCollPkts OBJECT-TYPE
     SYNTAX      Counter64
     MAX-ACCESS  read-only
     STATUS      obsolete
     DESCRIPTION
             "The number of collision packets transmitted on the interface."
     ::= { cienaCesPmExtendedTxRxAllTimeBinEntry 30 }

  
  cienaCesPmExtendedTxRxAllTimeBinDropEvents OBJECT-TYPE
     SYNTAX      Counter64
     MAX-ACCESS  read-only
     STATUS      obsolete
     DESCRIPTION
             "The number of packet drop events on this PM instance."
     ::= { cienaCesPmExtendedTxRxAllTimeBinEntry 31 }
  
  cienaCesPmExtendedTxRxAllTimeBinInDiscards OBJECT-TYPE
     SYNTAX      Counter64
     MAX-ACCESS  read-only
     STATUS      obsolete
     DESCRIPTION
             "The number of packet discards on this PM instance."
     ::= { cienaCesPmExtendedTxRxAllTimeBinEntry 32 }
  
  cienaCesPmExtendedTxRxAllTimeBinTxPausePkts OBJECT-TYPE
     SYNTAX      Counter64
     MAX-ACCESS  read-only
     STATUS      obsolete
     DESCRIPTION
             "The pause packets transmitted on this PM instance."
     ::= { cienaCesPmExtendedTxRxAllTimeBinEntry 33 }
  
  cienaCesPmExtendedTxRxAllTimeBinRxPausePkts OBJECT-TYPE
     SYNTAX      Counter64
     MAX-ACCESS  read-only
     STATUS      obsolete
     DESCRIPTION
             "The pause packets received on this PM instance."
     ::= { cienaCesPmExtendedTxRxAllTimeBinEntry 34 }
  
  cienaCesPmExtendedTxRxAllTimeBinRxBytesPerSec OBJECT-TYPE
     SYNTAX      Counter64
     MAX-ACCESS  read-only
     STATUS      obsolete
     DESCRIPTION
             "The number of bytes received per second on this PM instance."
     ::= { cienaCesPmExtendedTxRxAllTimeBinEntry 35 }
  
  cienaCesPmExtendedTxRxAllTimeBinRxFramesPerSec OBJECT-TYPE
     SYNTAX      Counter64
     MAX-ACCESS  read-only
     STATUS      obsolete
     DESCRIPTION
             "The number of frames received per second on this PM instance."
     ::= { cienaCesPmExtendedTxRxAllTimeBinEntry 36 }
  
  cienaCesPmExtendedTxRxAllTimeBinTxBytesPerSec OBJECT-TYPE
     SYNTAX      Counter64
     MAX-ACCESS  read-only
     STATUS      obsolete
     DESCRIPTION
             "The number of bytes transmitted per second on this PM instance."
     ::= { cienaCesPmExtendedTxRxAllTimeBinEntry 37 }
  
  cienaCesPmExtendedTxRxAllTimeBinTxFramesPerSec OBJECT-TYPE
     SYNTAX      Counter64
     MAX-ACCESS  read-only
     STATUS      obsolete
     DESCRIPTION
             "The number of frames transmitted per second on this PM instance."
     ::= { cienaCesPmExtendedTxRxAllTimeBinEntry 38 }

  cienaCesPmExtendedTxRxAllTimeBinRxLOutRangePkts OBJECT-TYPE
     SYNTAX      Counter64
     MAX-ACCESS  read-only
     STATUS      obsolete
     DESCRIPTION
             "The total number of packets received that were
             longer than the MTU (excluding framing bits,
             but including FCS octets) and were otherwise
             well formed."
     ::= { cienaCesPmExtendedTxRxAllTimeBinEntry 39 }


   --ExtendedTxRx Profile Stats, statistics bin
 
   cienaCesPmExtendedTxRxStatisticsBinTable OBJECT-TYPE
     SYNTAX     SEQUENCE OF CienaCesPmExtendedTxRxStatisticsBinEntry
     MAX-ACCESS not-accessible
     STATUS     current
     DESCRIPTION
            "The (conceptual) read-only table listing the bin statistics."  
     ::= { cienaCesPmExtendedTxRxStats 6 }
     
   cienaCesPmExtendedTxRxStatisticsBinEntry OBJECT-TYPE
     SYNTAX      CienaCesPmExtendedTxRxStatisticsBinEntry
     MAX-ACCESS  not-accessible
     STATUS      current
     DESCRIPTION
           "An entry (conceptual row) in the cienaCesPmExtendedTxRxStatisticsBinTable.
           This table lists the statistics for the statistics bin of the PM instance."  
     INDEX {cienaCesPmInstanceIndex}
     ::= { cienaCesPmExtendedTxRxStatisticsBinTable 1 }
        
   CienaCesPmExtendedTxRxStatisticsBinEntry ::=  SEQUENCE {
     cienaCesPmExtendedTxRxStatsBinStartTime                        DisplayString,
     cienaCesPmExtendedTxRxStatsBinClearTime                        DisplayString,
     cienaCesPmExtendedTxRxStatsBinRxBytes                          Counter64,
     cienaCesPmExtendedTxRxStatsBinRxPkts                           Counter64,
     cienaCesPmExtendedTxRxStatsBinRxCrcErrorPkts                   Counter64,
     cienaCesPmExtendedTxRxStatsBinRxMcastPkts                      Counter64,
     cienaCesPmExtendedTxRxStatsBinRxBcastPkts                      Counter64,
     cienaCesPmExtendedTxRxStatsBinUndersizePkts                    Counter64,
     cienaCesPmExtendedTxRxStatsBinOversizePkts                     Counter64,
     cienaCesPmExtendedTxRxStatsBinFragmentsPkts                    Counter64,
     cienaCesPmExtendedTxRxStatsBinJabbersPkts                      Counter64,
     cienaCesPmExtendedTxRxStatsBin64OctsPkts                       Counter64,
     cienaCesPmExtendedTxRxStatsBin65To127OctsPkts                  Counter64,
     cienaCesPmExtendedTxRxStatsBin128To255OctsPkts                 Counter64,
     cienaCesPmExtendedTxRxStatsBin256To511OctsPkts                 Counter64,
     cienaCesPmExtendedTxRxStatsBin512To1023OctsPkts                Counter64,
     cienaCesPmExtendedTxRxStatsBin1024To1518OctsPkts               Counter64,
     cienaCesPmExtendedTxRxStatsBinTxBytes                          Counter64,
     cienaCesPmExtendedTxRxStatsBinTxTBytes                         Counter64,
     cienaCesPmExtendedTxRxStatsBinTxPkts                           Counter64,
     cienaCesPmExtendedTxRxStatsBinTxBcastPkts                      Counter64,
     cienaCesPmExtendedTxRxStatsBinTxMcastPkts                      Counter64,
     cienaCesPmExtendedTxRxStatsBinTxExDeferPkts                    Counter64,
     cienaCesPmExtendedTxRxStatsBinTxGiantPkts                      Counter64,
     cienaCesPmExtendedTxRxStatsBinTxUnderRunPkts                   Counter64,
     cienaCesPmExtendedTxRxStatsBinTxCrcErrorPkts                   Counter64,
     cienaCesPmExtendedTxRxStatsBinTxLCheckErrorPkts                Counter64,
     cienaCesPmExtendedTxRxStatsBinTxLOutRangePkts                  Counter64,
     cienaCesPmExtendedTxRxStatsBinTxLateCollPkts                   Counter64,
     cienaCesPmExtendedTxRxStatsBinTxExCollPkts                     Counter64,
     cienaCesPmExtendedTxRxStatsBinTxSingleCollPkts                 Counter64,
     cienaCesPmExtendedTxRxStatsBinTxCollPkts                       Counter64,
     cienaCesPmExtendedTxRxStatsBinDropEvents                       Counter64,
     cienaCesPmExtendedTxRxStatsBinInDiscards                       Counter64,
     cienaCesPmExtendedTxRxStatsBinTxPausePkts                      Counter64,
     cienaCesPmExtendedTxRxStatsBinRxPausePkts                      Counter64,
     cienaCesPmExtendedTxRxStatsBinRxBytesPerSec                    Counter64,
     cienaCesPmExtendedTxRxStatsBinRxFramesPerSec                   Counter64,
     cienaCesPmExtendedTxRxStatsBinTxBytesPerSec                    Counter64,
     cienaCesPmExtendedTxRxStatsBinTxFramesPerSec                   Counter64,
     cienaCesPmExtendedTxRxStatsBinRxLOutRangePkts                  Counter64,
     cienaCesPmExtendedTxRxStatsBinRxUcastPkts                      Counter64,
     cienaCesPmExtendedTxRxStatsBinRxInErrorPkts                    Counter64,
     cienaCesPmExtendedTxRxStatsBin1519To2047OctsPkts               Counter64,
     cienaCesPmExtendedTxRxStatsBin2048To4095OctsPkts               Counter64,
     cienaCesPmExtendedTxRxStatsBin4096To9216OctsPkts               Counter64,
     cienaCesPmExtendedTxRxStatsBinTxUcastPkts                      Counter64,
     cienaCesPmExtendedTxRxStatsBinTx64OctsPkts                     Counter64,
     cienaCesPmExtendedTxRxStatsBinTx65To127OctsPkts                Counter64,
     cienaCesPmExtendedTxRxStatsBinTx128To255OctsPkts               Counter64,
     cienaCesPmExtendedTxRxStatsBinTx256To511OctsPkts               Counter64,
     cienaCesPmExtendedTxRxStatsBinTx512To1023OctsPkts              Counter64,
     cienaCesPmExtendedTxRxStatsBinTx1024To1518OctsPkts             Counter64,
     cienaCesPmExtendedTxRxStatsBinTx1519To2047OctsPkts             Counter64,
     cienaCesPmExtendedTxRxStatsBinTx2048To4095OctsPkts             Counter64,
     cienaCesPmExtendedTxRxStatsBinTx4096To9216OctsPkts             Counter64,
     cienaCesPmExtendedTxRxStatsBinTxDeferPkts                      Counter64,
     cienaCesPmExtendedTxRxStatsBinLinkUp                           Counter64,
     cienaCesPmExtendedTxRxStatsBinLinkDown                         Counter64,
     cienaCesPmExtendedTxRxStatsBinLinkFlap                         Counter64
   }

   cienaCesPmExtendedTxRxStatsBinStartTime OBJECT-TYPE
     SYNTAX      DisplayString
     MAX-ACCESS  read-only
     STATUS      current
     DESCRIPTION
             "Collection start time of the bin."
     ::= { cienaCesPmExtendedTxRxStatisticsBinEntry 1 }

   cienaCesPmExtendedTxRxStatsBinClearTime OBJECT-TYPE
     SYNTAX      DisplayString
     MAX-ACCESS  read-only
     STATUS      current
     DESCRIPTION
             "Collection clear time of the bin."
     ::= { cienaCesPmExtendedTxRxStatisticsBinEntry 2 }

   cienaCesPmExtendedTxRxStatsBinRxBytes OBJECT-TYPE
     SYNTAX      Counter64
     MAX-ACCESS  read-only
     STATUS      current
     DESCRIPTION
             "The number of bytes received by this PM instance."
     ::= { cienaCesPmExtendedTxRxStatisticsBinEntry 3 }

   cienaCesPmExtendedTxRxStatsBinRxPkts OBJECT-TYPE
     SYNTAX      Counter64
     MAX-ACCESS  read-only
     STATUS      current
     DESCRIPTION
             "The number of packets received by this PM instance."
     ::= { cienaCesPmExtendedTxRxStatisticsBinEntry 4 } 
  
   cienaCesPmExtendedTxRxStatsBinRxCrcErrorPkts OBJECT-TYPE
     SYNTAX      Counter64
     MAX-ACCESS  read-only
     STATUS      current
     DESCRIPTION
             "The number of packets received with CRC errors by this PM instance."
     ::= { cienaCesPmExtendedTxRxStatisticsBinEntry 5 }   
  
   cienaCesPmExtendedTxRxStatsBinRxMcastPkts OBJECT-TYPE
     SYNTAX      Counter64
     MAX-ACCESS  read-only
     STATUS      current
     DESCRIPTION
             "The total number of multicast packets received for the given PM instance."
     ::= { cienaCesPmExtendedTxRxStatisticsBinEntry 6 }
     
   cienaCesPmExtendedTxRxStatsBinRxBcastPkts OBJECT-TYPE
     SYNTAX      Counter64
     MAX-ACCESS  read-only
     STATUS      current
     DESCRIPTION
             "The number of broadcast packets received by this PM instance."
     ::= { cienaCesPmExtendedTxRxStatisticsBinEntry 7 }
  
   cienaCesPmExtendedTxRxStatsBinUndersizePkts OBJECT-TYPE
     SYNTAX      Counter64
     MAX-ACCESS  read-only
     STATUS      current
     DESCRIPTION
             "The total number of packets received that were
            less than 64 octets long (excluding framing bits,
            but including FCS octets) and were otherwise well
            formed."
     ::= { cienaCesPmExtendedTxRxStatisticsBinEntry 8 }
  
   cienaCesPmExtendedTxRxStatsBinOversizePkts OBJECT-TYPE
     SYNTAX      Counter64
     MAX-ACCESS  read-only
     STATUS      current
     DESCRIPTION
             "The total number of packets received that were
            longer than 1518 octets  but less than or equal to the MTU
            (excluding framing bits, but including FCS octets)
            and were otherwise well formed."
     ::= { cienaCesPmExtendedTxRxStatisticsBinEntry 9 }
  
   cienaCesPmExtendedTxRxStatsBinFragmentsPkts OBJECT-TYPE
     SYNTAX      Counter64
     MAX-ACCESS  read-only
     STATUS      current
     DESCRIPTION
             "The total number of packets received that were less
            than 64 octets in length (excluding framing bits but
            including FCS octets) and had either a bad Frame
            Check Sequence (FCS) with an integral number of
            octets (FCS Error) or a bad FCS with a non-integral
            number of octets (Alignment Error)."
     ::= { cienaCesPmExtendedTxRxStatisticsBinEntry 10 }
  
   cienaCesPmExtendedTxRxStatsBinJabbersPkts OBJECT-TYPE
     SYNTAX      Counter64
     MAX-ACCESS  read-only
     STATUS      current
     DESCRIPTION
             "The total number of packets received that were
            longer than 1518 octets (excluding framing bits,
            but including FCS octets), and had either a bad
            Frame Check Sequence (FCS) with an integral number
            of octets (FCS Error) or a bad FCS with a
            non-integral number of octets (Alignment Error)."
     ::= { cienaCesPmExtendedTxRxStatisticsBinEntry 11 }
  
   cienaCesPmExtendedTxRxStatsBin64OctsPkts OBJECT-TYPE
     SYNTAX      Counter64
     MAX-ACCESS  read-only
     STATUS      current
     DESCRIPTION
             "The total number of packets (including bad
            packets) received that were 64 octets in length
            (excluding framing bits but including FCS octets)."
     ::= { cienaCesPmExtendedTxRxStatisticsBinEntry 12 }
  
   cienaCesPmExtendedTxRxStatsBin65To127OctsPkts OBJECT-TYPE
     SYNTAX      Counter64
     MAX-ACCESS  read-only
     STATUS      current
     DESCRIPTION
             "The total number of packets (including bad
            packets) received that were between
            65 and 127 octets in length inclusive
            (excluding framing bits but including FCS octets)."
     ::= { cienaCesPmExtendedTxRxStatisticsBinEntry 13 }
  
   cienaCesPmExtendedTxRxStatsBin128To255OctsPkts OBJECT-TYPE
     SYNTAX      Counter64
     MAX-ACCESS  read-only
     STATUS      current
     DESCRIPTION
             "The total number of packets (including bad
            packets) received that were between
            128 and 255 octets in length inclusive
            (excluding framing bits but including FCS octets)."
     ::= { cienaCesPmExtendedTxRxStatisticsBinEntry 14 }
  
   cienaCesPmExtendedTxRxStatsBin256To511OctsPkts OBJECT-TYPE
     SYNTAX      Counter64
     MAX-ACCESS  read-only
     STATUS      current
     DESCRIPTION
             "The total number of packets (including bad
            packets) received that were between
            256 and 511 octets in length inclusive
            (excluding framing bits but including FCS octets)."
     ::= { cienaCesPmExtendedTxRxStatisticsBinEntry 15 }
  
   cienaCesPmExtendedTxRxStatsBin512To1023OctsPkts OBJECT-TYPE
     SYNTAX      Counter64
     MAX-ACCESS  read-only
     STATUS      current
     DESCRIPTION
             "The total number of packets (including bad
            packets) received that were between
            512 and 1023 octets in length inclusive
            (excluding framing bits but including FCS octets)."
     ::= { cienaCesPmExtendedTxRxStatisticsBinEntry 16 }
  
   cienaCesPmExtendedTxRxStatsBin1024To1518OctsPkts OBJECT-TYPE
     SYNTAX      Counter64
     MAX-ACCESS  read-only
     STATUS      current
     DESCRIPTION
             "The total number of packets (including bad packets) received that were between
            1024 and 1518 octets in length inclusive (excluding framing bits but including FCS octets)."
     ::= { cienaCesPmExtendedTxRxStatisticsBinEntry 17 }
  
   cienaCesPmExtendedTxRxStatsBinTxBytes OBJECT-TYPE
     SYNTAX      Counter64
     MAX-ACCESS  read-only
     STATUS      current
     DESCRIPTION
             "The number of octets transmitted on this PM instance."
     ::= { cienaCesPmExtendedTxRxStatisticsBinEntry 18 }
  
   cienaCesPmExtendedTxRxStatsBinTxTBytes OBJECT-TYPE
     SYNTAX      Counter64
     MAX-ACCESS  read-only
     STATUS      current
     DESCRIPTION
             "The total number of octets transmitted on this PM instance."
     ::= { cienaCesPmExtendedTxRxStatisticsBinEntry 19 }
  
   cienaCesPmExtendedTxRxStatsBinTxPkts OBJECT-TYPE
     SYNTAX      Counter64
     MAX-ACCESS  read-only
     STATUS      current
     DESCRIPTION
             "The total number of packets transmitted on this PM instance."
     ::= { cienaCesPmExtendedTxRxStatisticsBinEntry 20 }
  
   cienaCesPmExtendedTxRxStatsBinTxBcastPkts OBJECT-TYPE
     SYNTAX      Counter64
     MAX-ACCESS  read-only
     STATUS      current
     DESCRIPTION
             "The number of broadcast packets transmitted on this PM instance."
     ::= { cienaCesPmExtendedTxRxStatisticsBinEntry 21 }
  
   cienaCesPmExtendedTxRxStatsBinTxMcastPkts OBJECT-TYPE
     SYNTAX      Counter64
     MAX-ACCESS  read-only
     STATUS      current
     DESCRIPTION
             "The number of multicast packets transmitted on the interface."
     ::= { cienaCesPmExtendedTxRxStatisticsBinEntry 22 }
  
   cienaCesPmExtendedTxRxStatsBinTxExDeferPkts OBJECT-TYPE
     SYNTAX      Counter64
     MAX-ACCESS  read-only
     STATUS      current
     DESCRIPTION
             "The number of excessive defer packets transmitted on the interface."
     ::= { cienaCesPmExtendedTxRxStatisticsBinEntry 23 }
  
   cienaCesPmExtendedTxRxStatsBinTxGiantPkts OBJECT-TYPE
     SYNTAX      Counter64
     MAX-ACCESS  read-only
     STATUS      current
     DESCRIPTION
             "The number of too big packets transmitted on the interface."
     ::= { cienaCesPmExtendedTxRxStatisticsBinEntry 24 }
  
   cienaCesPmExtendedTxRxStatsBinTxUnderRunPkts OBJECT-TYPE
     SYNTAX      Counter64
     MAX-ACCESS  read-only
     STATUS      current
     DESCRIPTION
             "The number of underrun packets transmitted on the interface."
     ::= { cienaCesPmExtendedTxRxStatisticsBinEntry 25 }
  
   cienaCesPmExtendedTxRxStatsBinTxCrcErrorPkts OBJECT-TYPE
     SYNTAX      Counter64
     MAX-ACCESS  read-only
     STATUS      current
     DESCRIPTION
             "The number of CRC error packets transmitted on the interface."
     ::= { cienaCesPmExtendedTxRxStatisticsBinEntry 26 }
  
   cienaCesPmExtendedTxRxStatsBinTxLCheckErrorPkts OBJECT-TYPE
     SYNTAX      Counter64
     MAX-ACCESS  read-only
     STATUS      current
     DESCRIPTION
             "The number of length check error packets transmitted on the interface."
     ::= { cienaCesPmExtendedTxRxStatisticsBinEntry 27 }
  
   cienaCesPmExtendedTxRxStatsBinTxLOutRangePkts OBJECT-TYPE
     SYNTAX      Counter64
     MAX-ACCESS  read-only
     STATUS      current
     DESCRIPTION
             "The number of out of range packets transmitted on the interface."
     ::= { cienaCesPmExtendedTxRxStatisticsBinEntry 28 }
  
   cienaCesPmExtendedTxRxStatsBinTxLateCollPkts OBJECT-TYPE
     SYNTAX      Counter64
     MAX-ACCESS  read-only
     STATUS      current
     DESCRIPTION
             "The number of late collision packets transmitted on the interface."
     ::= { cienaCesPmExtendedTxRxStatisticsBinEntry 29 }
  
   cienaCesPmExtendedTxRxStatsBinTxExCollPkts OBJECT-TYPE
     SYNTAX      Counter64
     MAX-ACCESS  read-only
     STATUS      current
     DESCRIPTION
             "The number of excessive collision packets transmitted on the interface."
     ::= { cienaCesPmExtendedTxRxStatisticsBinEntry 30 }
  
   cienaCesPmExtendedTxRxStatsBinTxSingleCollPkts OBJECT-TYPE
     SYNTAX      Counter64
     MAX-ACCESS  read-only
     STATUS      current
     DESCRIPTION
             "The number of single collision packets transmitted on the interface."
     ::= { cienaCesPmExtendedTxRxStatisticsBinEntry 31 }
  
   cienaCesPmExtendedTxRxStatsBinTxCollPkts OBJECT-TYPE
     SYNTAX      Counter64
     MAX-ACCESS  read-only
     STATUS      current
     DESCRIPTION
             "The number of collision packets transmitted on the interface."
     ::= { cienaCesPmExtendedTxRxStatisticsBinEntry 32 }

   cienaCesPmExtendedTxRxStatsBinDropEvents OBJECT-TYPE
     SYNTAX      Counter64
     MAX-ACCESS  read-only
     STATUS      current
     DESCRIPTION
             "The number of packet drop events on this PM instance."
     ::= { cienaCesPmExtendedTxRxStatisticsBinEntry 33 }
  
   cienaCesPmExtendedTxRxStatsBinInDiscards OBJECT-TYPE
     SYNTAX      Counter64
     MAX-ACCESS  read-only
     STATUS      current
     DESCRIPTION
             "The number of packet discards on this PM instance."
     ::= { cienaCesPmExtendedTxRxStatisticsBinEntry 34 }
  
   cienaCesPmExtendedTxRxStatsBinTxPausePkts OBJECT-TYPE
     SYNTAX      Counter64
     MAX-ACCESS  read-only
     STATUS      current
     DESCRIPTION
             "The pause packets transmitted on this PM instance."
     ::= { cienaCesPmExtendedTxRxStatisticsBinEntry 35 }
  
   cienaCesPmExtendedTxRxStatsBinRxPausePkts OBJECT-TYPE
     SYNTAX      Counter64
     MAX-ACCESS  read-only
     STATUS      current
     DESCRIPTION
             "The pause packets received on this PM instance."
     ::= { cienaCesPmExtendedTxRxStatisticsBinEntry 36 }
  
   cienaCesPmExtendedTxRxStatsBinRxBytesPerSec OBJECT-TYPE
     SYNTAX      Counter64
     MAX-ACCESS  read-only
     STATUS      current
     DESCRIPTION
             "The number of bytes received per second on this PM instance."
     ::= { cienaCesPmExtendedTxRxStatisticsBinEntry 37 }
  
   cienaCesPmExtendedTxRxStatsBinRxFramesPerSec OBJECT-TYPE
     SYNTAX      Counter64
     MAX-ACCESS  read-only
     STATUS      current
     DESCRIPTION
             "The number of frames received per second on this PM instance."
     ::= { cienaCesPmExtendedTxRxStatisticsBinEntry 38 }
  
   cienaCesPmExtendedTxRxStatsBinTxBytesPerSec OBJECT-TYPE
     SYNTAX      Counter64
     MAX-ACCESS  read-only
     STATUS      current
     DESCRIPTION
             "The number of bytes transmitted per second on this PM instance."
     ::= { cienaCesPmExtendedTxRxStatisticsBinEntry 39 }
  
   cienaCesPmExtendedTxRxStatsBinTxFramesPerSec OBJECT-TYPE
     SYNTAX      Counter64
     MAX-ACCESS  read-only
     STATUS      current
     DESCRIPTION
             "The number of frames transmitted per second on this PM instance."
     ::= { cienaCesPmExtendedTxRxStatisticsBinEntry 40 }

   cienaCesPmExtendedTxRxStatsBinRxLOutRangePkts OBJECT-TYPE
     SYNTAX      Counter64
     MAX-ACCESS  read-only
     STATUS      current
     DESCRIPTION
             "The total number of packets received that were
             longer than the MTU (excluding framing bits,
             but including FCS octets) and were otherwise
             well formed."
     ::= { cienaCesPmExtendedTxRxStatisticsBinEntry 41 }

   cienaCesPmExtendedTxRxStatsBinRxUcastPkts OBJECT-TYPE
     SYNTAX      Counter64
     MAX-ACCESS  read-only
     STATUS      current
     DESCRIPTION
             "The number of unicast packets received on the port."
     ::= { cienaCesPmExtendedTxRxStatisticsBinEntry 42 }	

   cienaCesPmExtendedTxRxStatsBinRxInErrorPkts OBJECT-TYPE
     SYNTAX      Counter64
     MAX-ACCESS  read-only
     STATUS      current
     DESCRIPTION
             "The number of in error packets received on the port."
     ::= { cienaCesPmExtendedTxRxStatisticsBinEntry 43 }

   cienaCesPmExtendedTxRxStatsBin1519To2047OctsPkts OBJECT-TYPE
     SYNTAX      Counter64
     MAX-ACCESS  read-only
     STATUS      current
     DESCRIPTION
             "The total number of packets (including bad
             packets) received that were between
             1519 and 2047 octets in length inclusive
             (excluding framing bits but including FCS octets)."
     ::= { cienaCesPmExtendedTxRxStatisticsBinEntry 44 }
	 
   cienaCesPmExtendedTxRxStatsBin2048To4095OctsPkts OBJECT-TYPE
     SYNTAX      Counter64
     MAX-ACCESS  read-only
     STATUS      current
     DESCRIPTION
             "The total number of packets (including bad
             packets) received that were between
             2048 and 4095 octets in length inclusive
             (excluding framing bits but including FCS octets)."
     ::= { cienaCesPmExtendedTxRxStatisticsBinEntry 45 }

   cienaCesPmExtendedTxRxStatsBin4096To9216OctsPkts OBJECT-TYPE
     SYNTAX      Counter64
     MAX-ACCESS  read-only
     STATUS      current
     DESCRIPTION
            "The total number of packets (including bad
            packets) received that were between
            4096 and 9216 octets in length inclusive
            (excluding framing bits but including FCS octets)."
     ::= { cienaCesPmExtendedTxRxStatisticsBinEntry 46 }

   cienaCesPmExtendedTxRxStatsBinTxUcastPkts OBJECT-TYPE
    SYNTAX      Counter64
    MAX-ACCESS  read-only
    STATUS      current
    DESCRIPTION
            "The number of unicast packets transmitted on the port."
     ::= { cienaCesPmExtendedTxRxStatisticsBinEntry 47 }

   cienaCesPmExtendedTxRxStatsBinTx64OctsPkts OBJECT-TYPE
    SYNTAX      Counter64
    MAX-ACCESS  read-only
    STATUS      current
    DESCRIPTION
            "The total number of packets (including bad
            packets) transmitted that were between
            64 octets in length inclusive
            (excluding framing bits but including FCS octets)."
     ::= { cienaCesPmExtendedTxRxStatisticsBinEntry 48 }

   cienaCesPmExtendedTxRxStatsBinTx65To127OctsPkts OBJECT-TYPE
    SYNTAX      Counter64
    MAX-ACCESS  read-only
    STATUS      current
    DESCRIPTION
            "The total number of packets (including bad
            packets) transmitted that were between
            65 and 127 octets in length inclusive
            (excluding framing bits but including FCS octets)."
     ::= { cienaCesPmExtendedTxRxStatisticsBinEntry 49 }

   cienaCesPmExtendedTxRxStatsBinTx128To255OctsPkts OBJECT-TYPE
    SYNTAX      Counter64
    MAX-ACCESS  read-only
    STATUS      current
    DESCRIPTION
            "The total number of packets (including bad
            packets) transmitted that were between
            128 and 255 octets in length inclusive
            (excluding framing bits but including FCS octets)."
     ::= { cienaCesPmExtendedTxRxStatisticsBinEntry 50 }

   cienaCesPmExtendedTxRxStatsBinTx256To511OctsPkts OBJECT-TYPE
    SYNTAX      Counter64
    MAX-ACCESS  read-only
    STATUS      current
    DESCRIPTION
            "The total number of packets (including bad
            packets) transmitted that were between
            256 and 511 octets in length inclusive
            (excluding framing bits but including FCS octets)."
     ::= { cienaCesPmExtendedTxRxStatisticsBinEntry 51 }

   cienaCesPmExtendedTxRxStatsBinTx512To1023OctsPkts OBJECT-TYPE
    SYNTAX      Counter64
    MAX-ACCESS  read-only
    STATUS      current
    DESCRIPTION
            "The total number of packets (including bad
            packets) transmitted that were between
            512 and 1023 octets in length inclusive
            (excluding framing bits but including FCS octets)."
     ::= { cienaCesPmExtendedTxRxStatisticsBinEntry 52 }

   cienaCesPmExtendedTxRxStatsBinTx1024To1518OctsPkts OBJECT-TYPE
    SYNTAX      Counter64
    MAX-ACCESS  read-only
    STATUS      current
    DESCRIPTION
            "The total number of packets (including bad
            packets) transmitted that were between
            1024 and 1518 octets in length inclusive
            (excluding framing bits but including FCS octets)."
     ::= { cienaCesPmExtendedTxRxStatisticsBinEntry 53 }

   cienaCesPmExtendedTxRxStatsBinTx1519To2047OctsPkts OBJECT-TYPE
    SYNTAX      Counter64
    MAX-ACCESS  read-only
    STATUS      current
    DESCRIPTION
            "The total number of packets (including bad
            packets) transmitted that were between
            1519 and 2047 octets in length inclusive
            (excluding framing bits but including FCS octets)."
     ::= { cienaCesPmExtendedTxRxStatisticsBinEntry 54 }

   cienaCesPmExtendedTxRxStatsBinTx2048To4095OctsPkts OBJECT-TYPE
    SYNTAX      Counter64
    MAX-ACCESS  read-only
    STATUS      current
    DESCRIPTION
            "The total number of packets (including bad
            packets) transmitted that were between
            2048 and 4095 octets in length inclusive
            (excluding framing bits but including FCS octets)."
     ::= { cienaCesPmExtendedTxRxStatisticsBinEntry 55 }

   cienaCesPmExtendedTxRxStatsBinTx4096To9216OctsPkts OBJECT-TYPE
    SYNTAX      Counter64
    MAX-ACCESS  read-only
    STATUS      current
    DESCRIPTION
            "The total number of packets (including bad
            packets) transmitted that were between
            4096 and 9216 octets in length inclusive
            (excluding framing bits but including FCS octets)."
     ::= { cienaCesPmExtendedTxRxStatisticsBinEntry 56 }

   cienaCesPmExtendedTxRxStatsBinTxDeferPkts OBJECT-TYPE
    SYNTAX      Counter64
    MAX-ACCESS  read-only
    STATUS      current
    DESCRIPTION
            "The number of defer packets transmitted on the port."
     ::= { cienaCesPmExtendedTxRxStatisticsBinEntry 57 }

  cienaCesPmExtendedTxRxStatsBinLinkUp OBJECT-TYPE
     SYNTAX      Counter64
     MAX-ACCESS  read-only
     STATUS      current
     DESCRIPTION
             "The number of link up events on the port."
     ::= { cienaCesPmExtendedTxRxStatisticsBinEntry 58 }

  cienaCesPmExtendedTxRxStatsBinLinkDown OBJECT-TYPE
     SYNTAX      Counter64
     MAX-ACCESS  read-only
     STATUS      current
     DESCRIPTION
             "The number of link down events on the port."
     ::= { cienaCesPmExtendedTxRxStatisticsBinEntry 59 }

  cienaCesPmExtendedTxRxStatsBinLinkFlap OBJECT-TYPE
     SYNTAX      Counter64
     MAX-ACCESS  read-only
     STATUS      current
     DESCRIPTION
             "The number of link flap events on the port."
     ::= { cienaCesPmExtendedTxRxStatisticsBinEntry 60 }

   --ExtendedTxRx Profile Stats, totalstatistics bin
 
 cienaCesPmExtendedTxRxTotalStatisticsBinTable OBJECT-TYPE
     SYNTAX     SEQUENCE OF CienaCesPmExtendedTxRxTotalStatisticsBinEntry
     MAX-ACCESS not-accessible
     STATUS     current
     DESCRIPTION "The (conceptual) read-only table listing the bin statistics."
     ::= { cienaCesPmExtendedTxRxStats 7 }
     
   cienaCesPmExtendedTxRxTotalStatisticsBinEntry OBJECT-TYPE
     SYNTAX      CienaCesPmExtendedTxRxTotalStatisticsBinEntry
     MAX-ACCESS  not-accessible
     STATUS      current
     DESCRIPTION
           "An entry (conceptual row) in the cienaCesPmExtendedTxRxTotalStatisticsBinTable.
           This table lists the statistics for the total statistics bin of the PM instance."  
     INDEX {cienaCesPmInstanceIndex}
     ::= { cienaCesPmExtendedTxRxTotalStatisticsBinTable 1 }
        
   CienaCesPmExtendedTxRxTotalStatisticsBinEntry ::=  SEQUENCE {
     cienaCesPmExtendedTxRxTotalStatsBinStartTime                   DisplayString,
     cienaCesPmExtendedTxRxTotalStatsBinRxBytes                     Counter64,
     cienaCesPmExtendedTxRxTotalStatsBinRxPkts                      Counter64,
     cienaCesPmExtendedTxRxTotalStatsBinRxCrcErrorPkts              Counter64,
     cienaCesPmExtendedTxRxTotalStatsBinRxMcastPkts                 Counter64,
     cienaCesPmExtendedTxRxTotalStatsBinRxBcastPkts                 Counter64,
     cienaCesPmExtendedTxRxTotalStatsBinUndersizePkts               Counter64,
     cienaCesPmExtendedTxRxTotalStatsBinOversizePkts                Counter64,
     cienaCesPmExtendedTxRxTotalStatsBinFragmentsPkts               Counter64,
     cienaCesPmExtendedTxRxTotalStatsBinJabbersPkts                 Counter64,
     cienaCesPmExtendedTxRxTotalStatsBin64OctsPkts                  Counter64,
     cienaCesPmExtendedTxRxTotalStatsBin65To127OctsPkts             Counter64,
     cienaCesPmExtendedTxRxTotalStatsBin128To255OctsPkts            Counter64,
     cienaCesPmExtendedTxRxTotalStatsBin256To511OctsPkts            Counter64,
     cienaCesPmExtendedTxRxTotalStatsBin512To1023OctsPkts           Counter64,
     cienaCesPmExtendedTxRxTotalStatsBin1024To1518OctsPkts          Counter64,
     cienaCesPmExtendedTxRxTotalStatsBinTxBytes                     Counter64,
     cienaCesPmExtendedTxRxTotalStatsBinTxTBytes                    Counter64,
     cienaCesPmExtendedTxRxTotalStatsBinTxPkts                      Counter64,
     cienaCesPmExtendedTxRxTotalStatsBinTxBcastPkts                 Counter64,
     cienaCesPmExtendedTxRxTotalStatsBinTxMcastPkts                 Counter64,
     cienaCesPmExtendedTxRxTotalStatsBinTxExDeferPkts               Counter64,
     cienaCesPmExtendedTxRxTotalStatsBinTxGiantPkts                 Counter64,
     cienaCesPmExtendedTxRxTotalStatsBinTxUnderRunPkts              Counter64,
     cienaCesPmExtendedTxRxTotalStatsBinTxCrcErrorPkts              Counter64,
     cienaCesPmExtendedTxRxTotalStatsBinTxLCheckErrorPkts           Counter64,
     cienaCesPmExtendedTxRxTotalStatsBinTxLOutRangePkts             Counter64,
     cienaCesPmExtendedTxRxTotalStatsBinTxLateCollPkts              Counter64,
     cienaCesPmExtendedTxRxTotalStatsBinTxExCollPkts                Counter64,
     cienaCesPmExtendedTxRxTotalStatsBinTxSingleCollPkts            Counter64,
     cienaCesPmExtendedTxRxTotalStatsBinTxCollPkts                  Counter64,
     cienaCesPmExtendedTxRxTotalStatsBinDropEvents                  Counter64,
     cienaCesPmExtendedTxRxTotalStatsBinInDiscards                  Counter64,
     cienaCesPmExtendedTxRxTotalStatsBinTxPausePkts                 Counter64,
     cienaCesPmExtendedTxRxTotalStatsBinRxPausePkts                 Counter64,
     cienaCesPmExtendedTxRxTotalStatsBinRxBytesPerSec               Counter64,
     cienaCesPmExtendedTxRxTotalStatsBinRxFramesPerSec              Counter64,
     cienaCesPmExtendedTxRxTotalStatsBinTxBytesPerSec               Counter64,
     cienaCesPmExtendedTxRxTotalStatsBinTxFramesPerSec              Counter64,
     cienaCesPmExtendedTxRxTotalStatsBinRxLOutRangePkts             Counter64,
     cienaCesPmExtendedTxRxTotalStatsBinRxUcastPkts                 Counter64,
     cienaCesPmExtendedTxRxTotalStatsBinRxInErrorPkts               Counter64,
     cienaCesPmExtendedTxRxTotalStatsBin1519To2047OctsPkts          Counter64,
     cienaCesPmExtendedTxRxTotalStatsBin2048To4095OctsPkts          Counter64,
     cienaCesPmExtendedTxRxTotalStatsBin4096To9216OctsPkts          Counter64,
     cienaCesPmExtendedTxRxTotalStatsBinTxUcastPkts                 Counter64,
     cienaCesPmExtendedTxRxTotalStatsBinTx64OctsPkts                Counter64,
     cienaCesPmExtendedTxRxTotalStatsBinTx65To127OctsPkts           Counter64,
     cienaCesPmExtendedTxRxTotalStatsBinTx128To255OctsPkts          Counter64,
     cienaCesPmExtendedTxRxTotalStatsBinTx256To511OctsPkts          Counter64,
     cienaCesPmExtendedTxRxTotalStatsBinTx512To1023OctsPkts         Counter64,
     cienaCesPmExtendedTxRxTotalStatsBinTx1024To1518OctsPkts        Counter64,
     cienaCesPmExtendedTxRxTotalStatsBinTx1519To2047OctsPkts        Counter64,
     cienaCesPmExtendedTxRxTotalStatsBinTx2048To4095OctsPkts        Counter64,
     cienaCesPmExtendedTxRxTotalStatsBinTx4096To9216OctsPkts        Counter64,
     cienaCesPmExtendedTxRxTotalStatsBinTxDeferPkts                 Counter64,
     cienaCesPmExtendedTxRxTotalStatsBinLinkUp                      Counter64,
     cienaCesPmExtendedTxRxTotalStatsBinLinkDown                    Counter64,
     cienaCesPmExtendedTxRxTotalStatsBinLinkFlap                    Counter64
   }

   cienaCesPmExtendedTxRxTotalStatsBinStartTime OBJECT-TYPE
     SYNTAX      DisplayString
     MAX-ACCESS  read-only
     STATUS      current
     DESCRIPTION
             "Collection start time of the bin."
     ::= { cienaCesPmExtendedTxRxTotalStatisticsBinEntry 1 }

   cienaCesPmExtendedTxRxTotalStatsBinRxBytes OBJECT-TYPE
     SYNTAX      Counter64
     MAX-ACCESS  read-only
     STATUS      current
     DESCRIPTION
             "The number of bytes received by this PM instance."
     ::= { cienaCesPmExtendedTxRxTotalStatisticsBinEntry 2 }

   cienaCesPmExtendedTxRxTotalStatsBinRxPkts OBJECT-TYPE
     SYNTAX      Counter64
     MAX-ACCESS  read-only
     STATUS      current
     DESCRIPTION
             "The number of packets received by this PM instance."
     ::= { cienaCesPmExtendedTxRxTotalStatisticsBinEntry 3 } 
  
   cienaCesPmExtendedTxRxTotalStatsBinRxCrcErrorPkts OBJECT-TYPE
     SYNTAX      Counter64
     MAX-ACCESS  read-only
     STATUS      current
     DESCRIPTION
             "The number of packets received with CRC errors by this PM instance."
     ::= { cienaCesPmExtendedTxRxTotalStatisticsBinEntry 4 }   
  
   cienaCesPmExtendedTxRxTotalStatsBinRxMcastPkts OBJECT-TYPE
     SYNTAX      Counter64
     MAX-ACCESS  read-only
     STATUS      current
     DESCRIPTION
             "The total number of multicast packets received for the given PM instance."
     ::= { cienaCesPmExtendedTxRxTotalStatisticsBinEntry 5 }
     
   cienaCesPmExtendedTxRxTotalStatsBinRxBcastPkts OBJECT-TYPE
     SYNTAX      Counter64
     MAX-ACCESS  read-only
     STATUS      current
     DESCRIPTION
             "The number of broadcast packets received by this PM instance."
     ::= { cienaCesPmExtendedTxRxTotalStatisticsBinEntry 6 }
  
   cienaCesPmExtendedTxRxTotalStatsBinUndersizePkts OBJECT-TYPE
     SYNTAX      Counter64
     MAX-ACCESS  read-only
     STATUS      current
     DESCRIPTION
             "The total number of packets received that were
            less than 64 octets long (excluding framing bits,
            but including FCS octets) and were otherwise well
            formed."
     ::= { cienaCesPmExtendedTxRxTotalStatisticsBinEntry 7 }
  
   cienaCesPmExtendedTxRxTotalStatsBinOversizePkts OBJECT-TYPE
     SYNTAX      Counter64
     MAX-ACCESS  read-only
     STATUS      current
     DESCRIPTION
             "The total number of packets received that were
            longer than 1518 octets  but less than or equal to the MTU
            (excluding framing bits, but including FCS octets)
            and were otherwise well formed."
     ::= { cienaCesPmExtendedTxRxTotalStatisticsBinEntry 8 }
  
   cienaCesPmExtendedTxRxTotalStatsBinFragmentsPkts OBJECT-TYPE
     SYNTAX      Counter64
     MAX-ACCESS  read-only
     STATUS      current
     DESCRIPTION
             "The total number of packets received that were less
            than 64 octets in length (excluding framing bits but
            including FCS octets) and had either a bad Frame
            Check Sequence (FCS) with an integral number of
            octets (FCS Error) or a bad FCS with a non-integral
            number of octets (Alignment Error)."
     ::= { cienaCesPmExtendedTxRxTotalStatisticsBinEntry 9 }
  
   cienaCesPmExtendedTxRxTotalStatsBinJabbersPkts OBJECT-TYPE
     SYNTAX      Counter64
     MAX-ACCESS  read-only
     STATUS      current
     DESCRIPTION
             "The total number of packets received that were
            longer than 1518 octets (excluding framing bits,
            but including FCS octets), and had either a bad
            Frame Check Sequence (FCS) with an integral number
            of octets (FCS Error) or a bad FCS with a
            non-integral number of octets (Alignment Error)."
     ::= { cienaCesPmExtendedTxRxTotalStatisticsBinEntry 10 }
  
   cienaCesPmExtendedTxRxTotalStatsBin64OctsPkts OBJECT-TYPE
     SYNTAX      Counter64
     MAX-ACCESS  read-only
     STATUS      current
     DESCRIPTION
             "The total number of packets (including bad
            packets) received that were 64 octets in length
            (excluding framing bits but including FCS octets)."
     ::= { cienaCesPmExtendedTxRxTotalStatisticsBinEntry 11 }
  
   cienaCesPmExtendedTxRxTotalStatsBin65To127OctsPkts OBJECT-TYPE
     SYNTAX      Counter64
     MAX-ACCESS  read-only
     STATUS      current
     DESCRIPTION
             "The total number of packets (including bad
            packets) received that were between
            65 and 127 octets in length inclusive
            (excluding framing bits but including FCS octets)."
     ::= { cienaCesPmExtendedTxRxTotalStatisticsBinEntry 12 }
  
   cienaCesPmExtendedTxRxTotalStatsBin128To255OctsPkts OBJECT-TYPE
     SYNTAX      Counter64
     MAX-ACCESS  read-only
     STATUS      current
     DESCRIPTION
             "The total number of packets (including bad
            packets) received that were between
            128 and 255 octets in length inclusive
            (excluding framing bits but including FCS octets)."
     ::= { cienaCesPmExtendedTxRxTotalStatisticsBinEntry 13 }
  
   cienaCesPmExtendedTxRxTotalStatsBin256To511OctsPkts OBJECT-TYPE
     SYNTAX      Counter64
     MAX-ACCESS  read-only
     STATUS      current
     DESCRIPTION
             "The total number of packets (including bad
            packets) received that were between
            256 and 511 octets in length inclusive
            (excluding framing bits but including FCS octets)."
     ::= { cienaCesPmExtendedTxRxTotalStatisticsBinEntry 14 }
  
   cienaCesPmExtendedTxRxTotalStatsBin512To1023OctsPkts OBJECT-TYPE
     SYNTAX      Counter64
     MAX-ACCESS  read-only
     STATUS      current
     DESCRIPTION
             "The total number of packets (including bad
            packets) received that were between
            512 and 1023 octets in length inclusive
            (excluding framing bits but including FCS octets)."
     ::= { cienaCesPmExtendedTxRxTotalStatisticsBinEntry 15 }
  
   cienaCesPmExtendedTxRxTotalStatsBin1024To1518OctsPkts OBJECT-TYPE
     SYNTAX      Counter64
     MAX-ACCESS  read-only
     STATUS      current
     DESCRIPTION
             "The total number of packets (including bad packets) received that were between
            1024 and 1518 octets in length inclusive (excluding framing bits but including FCS octets)."
     ::= { cienaCesPmExtendedTxRxTotalStatisticsBinEntry 16 }
  
   cienaCesPmExtendedTxRxTotalStatsBinTxBytes OBJECT-TYPE
     SYNTAX      Counter64
     MAX-ACCESS  read-only
     STATUS      current
     DESCRIPTION
             "The number of octets transmitted on this PM instance."
     ::= { cienaCesPmExtendedTxRxTotalStatisticsBinEntry 17 }
  
   cienaCesPmExtendedTxRxTotalStatsBinTxTBytes OBJECT-TYPE
     SYNTAX      Counter64
     MAX-ACCESS  read-only
     STATUS      current
     DESCRIPTION
             "The total number of octets transmitted on this PM instance."
     ::= { cienaCesPmExtendedTxRxTotalStatisticsBinEntry 18 }
  
   cienaCesPmExtendedTxRxTotalStatsBinTxPkts OBJECT-TYPE
     SYNTAX      Counter64
     MAX-ACCESS  read-only
     STATUS      current
     DESCRIPTION
             "The total number of packets transmitted on this PM instance."
     ::= { cienaCesPmExtendedTxRxTotalStatisticsBinEntry 19 }
  
   cienaCesPmExtendedTxRxTotalStatsBinTxBcastPkts OBJECT-TYPE
     SYNTAX      Counter64
     MAX-ACCESS  read-only
     STATUS      current
     DESCRIPTION
             "The number of broadcast packets transmitted on this PM instance."
     ::= { cienaCesPmExtendedTxRxTotalStatisticsBinEntry 20 }
  
   cienaCesPmExtendedTxRxTotalStatsBinTxMcastPkts OBJECT-TYPE
     SYNTAX      Counter64
     MAX-ACCESS  read-only
     STATUS      current
     DESCRIPTION
             "The number of multicast packets transmitted on the interface."
     ::= { cienaCesPmExtendedTxRxTotalStatisticsBinEntry 21 }
  
   cienaCesPmExtendedTxRxTotalStatsBinTxExDeferPkts OBJECT-TYPE
     SYNTAX      Counter64
     MAX-ACCESS  read-only
     STATUS      current
     DESCRIPTION
             "The number of excessive defer packets transmitted on the interface."
     ::= { cienaCesPmExtendedTxRxTotalStatisticsBinEntry 22 }
  
   cienaCesPmExtendedTxRxTotalStatsBinTxGiantPkts OBJECT-TYPE
     SYNTAX      Counter64
     MAX-ACCESS  read-only
     STATUS      current
     DESCRIPTION
             "The number of too big packets transmitted on the interface."
     ::= { cienaCesPmExtendedTxRxTotalStatisticsBinEntry 23 }
  
   cienaCesPmExtendedTxRxTotalStatsBinTxUnderRunPkts OBJECT-TYPE
     SYNTAX      Counter64
     MAX-ACCESS  read-only
     STATUS      current
     DESCRIPTION
             "The number of underrun packets transmitted on the interface."
     ::= { cienaCesPmExtendedTxRxTotalStatisticsBinEntry 24 }
  
   cienaCesPmExtendedTxRxTotalStatsBinTxCrcErrorPkts OBJECT-TYPE
     SYNTAX      Counter64
     MAX-ACCESS  read-only
     STATUS      current
     DESCRIPTION
             "The number of CRC error packets transmitted on the interface."
     ::= { cienaCesPmExtendedTxRxTotalStatisticsBinEntry 25 }
  
   cienaCesPmExtendedTxRxTotalStatsBinTxLCheckErrorPkts OBJECT-TYPE
     SYNTAX      Counter64
     MAX-ACCESS  read-only
     STATUS      current
     DESCRIPTION
             "The number of length check error packets transmitted on the interface."
     ::= { cienaCesPmExtendedTxRxTotalStatisticsBinEntry 26 }
  
   cienaCesPmExtendedTxRxTotalStatsBinTxLOutRangePkts OBJECT-TYPE
     SYNTAX      Counter64
     MAX-ACCESS  read-only
     STATUS      current
     DESCRIPTION
             "The number of out of range packets transmitted on the interface."
     ::= { cienaCesPmExtendedTxRxTotalStatisticsBinEntry 27 }
  
   cienaCesPmExtendedTxRxTotalStatsBinTxLateCollPkts OBJECT-TYPE
     SYNTAX      Counter64
     MAX-ACCESS  read-only
     STATUS      current
     DESCRIPTION
             "The number of late collision packets transmitted on the interface."
     ::= { cienaCesPmExtendedTxRxTotalStatisticsBinEntry 28 }
  
   cienaCesPmExtendedTxRxTotalStatsBinTxExCollPkts OBJECT-TYPE
     SYNTAX      Counter64
     MAX-ACCESS  read-only
     STATUS      current
     DESCRIPTION
             "The number of excessive collision packets transmitted on the interface."
     ::= { cienaCesPmExtendedTxRxTotalStatisticsBinEntry 29 }
  
   cienaCesPmExtendedTxRxTotalStatsBinTxSingleCollPkts OBJECT-TYPE
     SYNTAX      Counter64
     MAX-ACCESS  read-only
     STATUS      current
     DESCRIPTION
             "The number of single collision packets transmitted on the interface."
     ::= { cienaCesPmExtendedTxRxTotalStatisticsBinEntry 30 }
  
   cienaCesPmExtendedTxRxTotalStatsBinTxCollPkts OBJECT-TYPE
     SYNTAX      Counter64
     MAX-ACCESS  read-only
     STATUS      current
     DESCRIPTION
             "The number of collision packets transmitted on the interface."
     ::= { cienaCesPmExtendedTxRxTotalStatisticsBinEntry 31 }

  
   cienaCesPmExtendedTxRxTotalStatsBinDropEvents OBJECT-TYPE
     SYNTAX      Counter64
     MAX-ACCESS  read-only
     STATUS      current
     DESCRIPTION
             "The number of packet drop events on this PM instance."
     ::= { cienaCesPmExtendedTxRxTotalStatisticsBinEntry 32 }
  
   cienaCesPmExtendedTxRxTotalStatsBinInDiscards OBJECT-TYPE
     SYNTAX      Counter64
     MAX-ACCESS  read-only
     STATUS      current
     DESCRIPTION
             "The number of packet discards on this PM instance."
     ::= { cienaCesPmExtendedTxRxTotalStatisticsBinEntry 33 }
  
   cienaCesPmExtendedTxRxTotalStatsBinTxPausePkts OBJECT-TYPE
     SYNTAX      Counter64
     MAX-ACCESS  read-only
     STATUS      current
     DESCRIPTION
             "The pause packets transmitted on this PM instance."
     ::= { cienaCesPmExtendedTxRxTotalStatisticsBinEntry 34 }
  
   cienaCesPmExtendedTxRxTotalStatsBinRxPausePkts OBJECT-TYPE
     SYNTAX      Counter64
     MAX-ACCESS  read-only
     STATUS      current
     DESCRIPTION
             "The pause packets received on this PM instance."
     ::= { cienaCesPmExtendedTxRxTotalStatisticsBinEntry 35 }
  
   cienaCesPmExtendedTxRxTotalStatsBinRxBytesPerSec OBJECT-TYPE
     SYNTAX      Counter64
     MAX-ACCESS  read-only
     STATUS      current
     DESCRIPTION
             "The number of bytes received per second on this PM instance."
     ::= { cienaCesPmExtendedTxRxTotalStatisticsBinEntry 36 }
  
   cienaCesPmExtendedTxRxTotalStatsBinRxFramesPerSec OBJECT-TYPE
     SYNTAX      Counter64
     MAX-ACCESS  read-only
     STATUS      current
     DESCRIPTION
             "The number of frames received per second on this PM instance."
     ::= { cienaCesPmExtendedTxRxTotalStatisticsBinEntry 37 }
  
   cienaCesPmExtendedTxRxTotalStatsBinTxBytesPerSec OBJECT-TYPE
     SYNTAX      Counter64
     MAX-ACCESS  read-only
     STATUS      current
     DESCRIPTION
             "The number of bytes transmitted per second on this PM instance."
     ::= { cienaCesPmExtendedTxRxTotalStatisticsBinEntry 38 }
  
   cienaCesPmExtendedTxRxTotalStatsBinTxFramesPerSec OBJECT-TYPE
     SYNTAX      Counter64
     MAX-ACCESS  read-only
     STATUS      current
     DESCRIPTION
             "The number of frames transmitted per second on this PM instance."
     ::= { cienaCesPmExtendedTxRxTotalStatisticsBinEntry 39 }

   cienaCesPmExtendedTxRxTotalStatsBinRxLOutRangePkts OBJECT-TYPE
     SYNTAX      Counter64
     MAX-ACCESS  read-only
     STATUS      current
     DESCRIPTION
             "The total number of packets received that were
             longer than the MTU (excluding framing bits,
             but including FCS octets) and were otherwise
             well formed."
     ::= { cienaCesPmExtendedTxRxTotalStatisticsBinEntry 40 }

   cienaCesPmExtendedTxRxTotalStatsBinRxUcastPkts OBJECT-TYPE
     SYNTAX      Counter64
     MAX-ACCESS  read-only
     STATUS      current
     DESCRIPTION
             "The number of unicast packets received on the port."
    ::= { cienaCesPmExtendedTxRxTotalStatisticsBinEntry 41 }	

   cienaCesPmExtendedTxRxTotalStatsBinRxInErrorPkts OBJECT-TYPE
     SYNTAX      Counter64
     MAX-ACCESS  read-only
     STATUS      current
     DESCRIPTION
             "The number of in error packets received on the port."
     ::= { cienaCesPmExtendedTxRxTotalStatisticsBinEntry 42 }

   cienaCesPmExtendedTxRxTotalStatsBin1519To2047OctsPkts OBJECT-TYPE
     SYNTAX      Counter64
     MAX-ACCESS  read-only
     STATUS      current
     DESCRIPTION
             "The total number of packets (including bad
             packets) received that were between
             1519 and 2047 octets in length inclusive
             (excluding framing bits but including FCS octets)."
     ::= { cienaCesPmExtendedTxRxTotalStatisticsBinEntry 43 }
	 
   cienaCesPmExtendedTxRxTotalStatsBin2048To4095OctsPkts OBJECT-TYPE
     SYNTAX      Counter64
     MAX-ACCESS  read-only
     STATUS      current
     DESCRIPTION
             "The total number of packets (including bad
             packets) received that were between
             2048 and 4095 octets in length inclusive
             (excluding framing bits but including FCS octets)."
     ::= { cienaCesPmExtendedTxRxTotalStatisticsBinEntry 44 }

   cienaCesPmExtendedTxRxTotalStatsBin4096To9216OctsPkts OBJECT-TYPE
     SYNTAX      Counter64
     MAX-ACCESS  read-only
     STATUS      current
     DESCRIPTION
             "The total number of packets (including bad
             packets) received that were between
             4096 and 9216 octets in length inclusive
             (excluding framing bits but including FCS octets)."
     ::= { cienaCesPmExtendedTxRxTotalStatisticsBinEntry 45 }

   cienaCesPmExtendedTxRxTotalStatsBinTxUcastPkts OBJECT-TYPE
     SYNTAX      Counter64
     MAX-ACCESS  read-only
     STATUS      current
     DESCRIPTION
             "The number of unicast packets transmitted on the port."
     ::= { cienaCesPmExtendedTxRxTotalStatisticsBinEntry 46 }

   cienaCesPmExtendedTxRxTotalStatsBinTx64OctsPkts OBJECT-TYPE
     SYNTAX      Counter64
     MAX-ACCESS  read-only
     STATUS      current
     DESCRIPTION
             "The total number of packets (including bad
             packets) transmitted that were between
             64 octets in length inclusive
             (excluding framing bits but including FCS octets)."
     ::= { cienaCesPmExtendedTxRxTotalStatisticsBinEntry 47 }

   cienaCesPmExtendedTxRxTotalStatsBinTx65To127OctsPkts OBJECT-TYPE
     SYNTAX      Counter64
     MAX-ACCESS  read-only
     STATUS      current
     DESCRIPTION
             "The total number of packets (including bad
             packets) transmitted that were between
             65 and 127 octets in length inclusive
             (excluding framing bits but including FCS octets)."
     ::= { cienaCesPmExtendedTxRxTotalStatisticsBinEntry 48 }

   cienaCesPmExtendedTxRxTotalStatsBinTx128To255OctsPkts OBJECT-TYPE
     SYNTAX      Counter64
     MAX-ACCESS  read-only
     STATUS      current
     DESCRIPTION
             "The total number of packets (including bad
             packets) transmitted that were between
             128 and 255 octets in length inclusive
             (excluding framing bits but including FCS octets)."
     ::= { cienaCesPmExtendedTxRxTotalStatisticsBinEntry 49 }

   cienaCesPmExtendedTxRxTotalStatsBinTx256To511OctsPkts OBJECT-TYPE
     SYNTAX      Counter64
     MAX-ACCESS  read-only
     STATUS      current
     DESCRIPTION
             "The total number of packets (including bad
             packets) transmitted that were between
             256 and 511 octets in length inclusive
             (excluding framing bits but including FCS octets)."
     ::= { cienaCesPmExtendedTxRxTotalStatisticsBinEntry 50 }

   cienaCesPmExtendedTxRxTotalStatsBinTx512To1023OctsPkts OBJECT-TYPE
     SYNTAX      Counter64
     MAX-ACCESS  read-only
     STATUS      current
     DESCRIPTION
             "The total number of packets (including bad
             packets) transmitted that were between
             512 and 1023 octets in length inclusive
             (excluding framing bits but including FCS octets)."
     ::= { cienaCesPmExtendedTxRxTotalStatisticsBinEntry 51 }

   cienaCesPmExtendedTxRxTotalStatsBinTx1024To1518OctsPkts OBJECT-TYPE
     SYNTAX      Counter64
     MAX-ACCESS  read-only
     STATUS      current
     DESCRIPTION
             "The total number of packets (including bad
             packets) transmitted that were between
             1024 and 1518 octets in length inclusive
             (excluding framing bits but including FCS octets)."
     ::= { cienaCesPmExtendedTxRxTotalStatisticsBinEntry 52 }

   cienaCesPmExtendedTxRxTotalStatsBinTx1519To2047OctsPkts OBJECT-TYPE
     SYNTAX      Counter64
     MAX-ACCESS  read-only
     STATUS      current
     DESCRIPTION
             "The total number of packets (including bad
             packets) transmitted that were between
             1519 and 2047 octets in length inclusive
             (excluding framing bits but including FCS octets)."
     ::= { cienaCesPmExtendedTxRxTotalStatisticsBinEntry 53 }

   cienaCesPmExtendedTxRxTotalStatsBinTx2048To4095OctsPkts OBJECT-TYPE
     SYNTAX      Counter64
     MAX-ACCESS  read-only
     STATUS      current
     DESCRIPTION
             "The total number of packets (including bad
             packets) transmitted that were between
             2048 and 4095 octets in length inclusive
             (excluding framing bits but including FCS octets)."
     ::= { cienaCesPmExtendedTxRxTotalStatisticsBinEntry 54 }

   cienaCesPmExtendedTxRxTotalStatsBinTx4096To9216OctsPkts OBJECT-TYPE
     SYNTAX      Counter64
     MAX-ACCESS  read-only
     STATUS      current
     DESCRIPTION
             "The total number of packets (including bad
             packets) transmitted that were between
             4096 and 9216 octets in length inclusive
             (excluding framing bits but including FCS octets)."
     ::= { cienaCesPmExtendedTxRxTotalStatisticsBinEntry 55 }

   cienaCesPmExtendedTxRxTotalStatsBinTxDeferPkts OBJECT-TYPE
     SYNTAX      Counter64
     MAX-ACCESS  read-only
     STATUS      current
     DESCRIPTION
             "The number of defer packets transmitted on the port."
     ::= { cienaCesPmExtendedTxRxTotalStatisticsBinEntry 56 }

  cienaCesPmExtendedTxRxTotalStatsBinLinkUp OBJECT-TYPE
     SYNTAX      Counter64
     MAX-ACCESS  read-only
     STATUS      current
     DESCRIPTION
             "The number of link up events on the port."
     ::= { cienaCesPmExtendedTxRxTotalStatisticsBinEntry 57 }

  cienaCesPmExtendedTxRxTotalStatsBinLinkDown OBJECT-TYPE
     SYNTAX      Counter64
     MAX-ACCESS  read-only
     STATUS      current
     DESCRIPTION
             "The number of link down events on the port."
     ::= { cienaCesPmExtendedTxRxTotalStatisticsBinEntry 58 }

  cienaCesPmExtendedTxRxTotalStatsBinLinkFlap OBJECT-TYPE
     SYNTAX      Counter64
     MAX-ACCESS  read-only
     STATUS      current
     DESCRIPTION
             "The number of link flap events on the port."
     ::= { cienaCesPmExtendedTxRxTotalStatisticsBinEntry 59 }

  --BasicTxRx Profile Stats
  
 cienaCesPmBasicTxRxHistoryBinTable OBJECT-TYPE
     SYNTAX     SEQUENCE OF CienaCesPmBasicTxRxHistoryBinEntry
     MAX-ACCESS not-accessible
     STATUS     current
     DESCRIPTION
            "The (conceptual) read-only table listing the basic TxRx profile statistics."  
     ::= { cienaCesPmBasicTxRxStats 1 }
     
   cienaCesPmBasicTxRxHistoryBinEntry OBJECT-TYPE
     SYNTAX      CienaCesPmBasicTxRxHistoryBinEntry
     MAX-ACCESS  not-accessible
     STATUS      current
     DESCRIPTION
           "An entry (conceptual row) in the cienaCesPmBasicTxRxHistoryBinTable.

           This table lists the statistics for all the history bins of the PM instance, as 
           specified by the bin-count object of the PM instance. History bins are displayed in the order
           so that #1 bin always represents the most recently completed bin and #2 - the bin previous to that
           and so on.
	       The statistics are displayed for only the instances with valid bins (with start time >0), 
	       as indicated by the operational state of the corresponding PM instance."  
     INDEX { cienaCesPmInstanceIndex, cienaCesPmBasicTxRxHistoryBinIndex }
     ::= { cienaCesPmBasicTxRxHistoryBinTable 1 }
        
 CienaCesPmBasicTxRxHistoryBinEntry ::=  SEQUENCE {
 	 cienaCesPmBasicTxRxHistoryBinIndex             			Unsigned32,
     cienaCesPmBasicTxRxHistoryBinStartTime					DisplayString, 
     cienaCesPmBasicTxRxHistoryBinEndTime						DisplayString,
     cienaCesPmBasicTxRxHistoryBinClearTime                    DisplayString,
     cienaCesPmBasicTxRxHistoryBinDuration						Unsigned32,   
     cienaCesPmBasicTxRxHistoryBinState						PmBinState,
     cienaCesPmBasicTxRxHistoryBinRxAcceptedBytes    		Counter64,
     cienaCesPmBasicTxRxHistoryBinRxAcceptedFrames    	Counter64,
     cienaCesPmBasicTxRxHistoryBinRxYellowBytes    		Counter64,
     cienaCesPmBasicTxRxHistoryBinRxYellowFrames    		Counter64,
     cienaCesPmBasicTxRxHistoryBinRxDroppedBytes    		Counter64,
     cienaCesPmBasicTxRxHistoryBinRxDroppedFrames    		Counter64,
     cienaCesPmBasicTxRxHistoryBinTxForwardedBytes    	Counter64,
     cienaCesPmBasicTxRxHistoryBinTxForwardedFrames     	Counter64,
     cienaCesPmBasicTxRxHistoryBinRxBytesPerSec         	Counter64,
     cienaCesPmBasicTxRxHistoryBinRxFramesPerSec        	Counter64,
     cienaCesPmBasicTxRxHistoryBinTxBytesPerSec         	Counter64,
     cienaCesPmBasicTxRxHistoryBinTxFramesPerSec        	Counter64
   	}
	cienaCesPmBasicTxRxHistoryBinIndex OBJECT-TYPE
     SYNTAX      Unsigned32 (1..65535) 
     MAX-ACCESS  not-accessible
     STATUS      current
     DESCRIPTION
             "Bin number associated with the PmBasicTxRxHistoryBin entry."
     ::= { cienaCesPmBasicTxRxHistoryBinEntry 1 }

   cienaCesPmBasicTxRxHistoryBinStartTime   OBJECT-TYPE
     SYNTAX		DisplayString
     MAX-ACCESS	read-only
     STATUS		current
     DESCRIPTION "Collection start time of the bin."
     ::= { cienaCesPmBasicTxRxHistoryBinEntry 2	}
   
   cienaCesPmBasicTxRxHistoryBinEndTime	OBJECT-TYPE
   	 SYNTAX DisplayString
   	 MAX-ACCESS	read-only
   	 STATUS 	current
   	 DESCRIPTION 	"Collection end time of the bin."
   ::= {cienaCesPmBasicTxRxHistoryBinEntry 3 }
   
   cienaCesPmBasicTxRxHistoryBinClearTime	OBJECT-TYPE
     SYNTAX DisplayString
     MAX-ACCESS read-only
     STATUS		current
     DESCRIPTION	"Clear time of the bin."
   ::= {  cienaCesPmBasicTxRxHistoryBinEntry  4 }
   
   
   cienaCesPmBasicTxRxHistoryBinDuration OBJECT-TYPE
     SYNTAX      Unsigned32 (1..65535)  
     UNITS		"minutes"
     MAX-ACCESS  read-only
     STATUS      current
     DESCRIPTION
             "Duration of the bin."
     ::= { cienaCesPmBasicTxRxHistoryBinEntry 5 }
  
  cienaCesPmBasicTxRxHistoryBinState OBJECT-TYPE
     SYNTAX      PmBinState 
     MAX-ACCESS  read-only
     STATUS      current
     DESCRIPTION
             "State of the bin."
     ::= { cienaCesPmBasicTxRxHistoryBinEntry 6 }

  
  cienaCesPmBasicTxRxHistoryBinRxAcceptedBytes OBJECT-TYPE
     SYNTAX      Counter64
     MAX-ACCESS  read-only
     STATUS      current
     DESCRIPTION
             "The number of accepted bytes on this PM instance."
     ::= { cienaCesPmBasicTxRxHistoryBinEntry 7 }

  cienaCesPmBasicTxRxHistoryBinRxAcceptedFrames OBJECT-TYPE
     SYNTAX      Counter64
     MAX-ACCESS  read-only
     STATUS      current
     DESCRIPTION
             "The number of accepted frames on this PM instance."
     ::= { cienaCesPmBasicTxRxHistoryBinEntry 8 }

  cienaCesPmBasicTxRxHistoryBinRxYellowBytes OBJECT-TYPE
     SYNTAX      Counter64
     MAX-ACCESS  read-only
     STATUS      current
     DESCRIPTION
             "The number of remarked bytes received on this PM instance."
     ::= { cienaCesPmBasicTxRxHistoryBinEntry 9 }

  cienaCesPmBasicTxRxHistoryBinRxYellowFrames OBJECT-TYPE
     SYNTAX      Counter64
     MAX-ACCESS  read-only
     STATUS      current
     DESCRIPTION
             "The number of remarked frames received on this PM instance."
     ::= { cienaCesPmBasicTxRxHistoryBinEntry 10 }

  
  cienaCesPmBasicTxRxHistoryBinRxDroppedBytes OBJECT-TYPE
     SYNTAX      Counter64
     MAX-ACCESS  read-only
     STATUS      current
     DESCRIPTION
             "The number of received bytes dropped on this PM instance."
     ::= { cienaCesPmBasicTxRxHistoryBinEntry 11 }

  cienaCesPmBasicTxRxHistoryBinRxDroppedFrames OBJECT-TYPE
     SYNTAX      Counter64
     MAX-ACCESS  read-only
     STATUS      current
     DESCRIPTION
             "The number of received frames dropped on this PM instance."
     ::= { cienaCesPmBasicTxRxHistoryBinEntry 12 }

  cienaCesPmBasicTxRxHistoryBinTxForwardedBytes OBJECT-TYPE
     SYNTAX      Counter64
     MAX-ACCESS  read-only
     STATUS      current
     DESCRIPTION
             "The number of bytes forwarded on this PM instance."
     ::= { cienaCesPmBasicTxRxHistoryBinEntry 13 }

  cienaCesPmBasicTxRxHistoryBinTxForwardedFrames OBJECT-TYPE
     SYNTAX      Counter64
     MAX-ACCESS  read-only
     STATUS      current
     DESCRIPTION
             "The number of frames forwarded on this PM instance."
     ::= { cienaCesPmBasicTxRxHistoryBinEntry 14 }

  cienaCesPmBasicTxRxHistoryBinRxBytesPerSec OBJECT-TYPE
     SYNTAX      Counter64
     MAX-ACCESS  read-only
     STATUS      current
     DESCRIPTION
             "The number of bytes received per second on this PM instance."
     ::= { cienaCesPmBasicTxRxHistoryBinEntry 15 }

  cienaCesPmBasicTxRxHistoryBinRxFramesPerSec OBJECT-TYPE
     SYNTAX      Counter64
     MAX-ACCESS  read-only
     STATUS      current
     DESCRIPTION
             "The number of frames received per second on this PM instance."
     ::= { cienaCesPmBasicTxRxHistoryBinEntry 16 }

  cienaCesPmBasicTxRxHistoryBinTxBytesPerSec OBJECT-TYPE
     SYNTAX      Counter64
     MAX-ACCESS  read-only
     STATUS      current
     DESCRIPTION
             "The number of bytes transmitted per second on this PM instance."
     ::= { cienaCesPmBasicTxRxHistoryBinEntry 17 }

  cienaCesPmBasicTxRxHistoryBinTxFramesPerSec OBJECT-TYPE
     SYNTAX      Counter64
     MAX-ACCESS  read-only
     STATUS      current
     DESCRIPTION
             "The number of frames transmitted per second on this PM instance."
     ::= { cienaCesPmBasicTxRxHistoryBinEntry 18 }
 
 -- BasicTxRx Current Bin Table
  
 cienaCesPmBasicTxRxCurrBinTable OBJECT-TYPE
     SYNTAX     SEQUENCE OF CienaCesPmBasicTxRxCurrBinEntry
     MAX-ACCESS not-accessible
     STATUS     current
     DESCRIPTION
            "The (conceptual) read-only table listing the basic TxRx profile statistics."  
     ::= { cienaCesPmBasicTxRxStats 2 }
     
   cienaCesPmBasicTxRxCurrBinEntry OBJECT-TYPE
     SYNTAX      CienaCesPmBasicTxRxCurrBinEntry
     MAX-ACCESS  not-accessible
     STATUS      current
     DESCRIPTION
           "An entry (conceptual row) in the cienaCesPmBasicTxRxCurrBinTable.
           This table lists the statistics for the current bin of the PM instance." 
     INDEX {cienaCesPmInstanceIndex}
     ::= { cienaCesPmBasicTxRxCurrBinTable 1 }
        
 CienaCesPmBasicTxRxCurrBinEntry ::=  SEQUENCE {
   cienaCesPmBasicTxRxCurrBinStartTime							DisplayString,
   cienaCesPmBasicTxRxCurrBinClearedTime						DisplayString,
   cienaCesPmBasicTxRxCurrBinDuration							Unsigned32,   
   cienaCesPmBasicTxRxCurrBinState								PmBinState,
   cienaCesPmBasicTxRxCurrBinRxAcceptedBytes    			Counter64,
   cienaCesPmBasicTxRxCurrBinRxAcceptedFrames    			Counter64,
   cienaCesPmBasicTxRxCurrBinRxYellowBytes    			Counter64,
   cienaCesPmBasicTxRxCurrBinRxYellowFrames    			Counter64,
   cienaCesPmBasicTxRxCurrBinRxDroppedBytes    			Counter64,
   cienaCesPmBasicTxRxCurrBinRxDroppedFrames    			Counter64,
   cienaCesPmBasicTxRxCurrBinTxForwardedBytes    			Counter64,
   cienaCesPmBasicTxRxCurrBinTxForwardedFrames            Counter64,
   cienaCesPmBasicTxRxCurrBinRxBytesPerSec                Counter64,
   cienaCesPmBasicTxRxCurrBinRxFramesPerSec               Counter64,
   cienaCesPmBasicTxRxCurrBinTxBytesPerSec                Counter64,
   cienaCesPmBasicTxRxCurrBinTxFramesPerSec               Counter64
  }
  cienaCesPmBasicTxRxCurrBinStartTime   OBJECT-TYPE
     SYNTAX		DisplayString
     MAX-ACCESS	read-only
     STATUS		current
     DESCRIPTION "Collection start time of the bin."
     ::= { cienaCesPmBasicTxRxCurrBinEntry 1}
  
  cienaCesPmBasicTxRxCurrBinClearedTime   OBJECT-TYPE
     SYNTAX		DisplayString
     MAX-ACCESS	read-only
     STATUS		current
     DESCRIPTION "Cleared time of the bin."
     ::= { cienaCesPmBasicTxRxCurrBinEntry 2	}
                   
  cienaCesPmBasicTxRxCurrBinDuration OBJECT-TYPE
     SYNTAX      Unsigned32 (1..65535)  
     UNITS		"minutes"
     MAX-ACCESS  read-only
     STATUS      current
     DESCRIPTION
             "Duration of the bin."
     ::= { cienaCesPmBasicTxRxCurrBinEntry 3 }
  
  cienaCesPmBasicTxRxCurrBinState OBJECT-TYPE
     SYNTAX      PmBinState 
     MAX-ACCESS  read-only
     STATUS      current
     DESCRIPTION
             "State of the bin."
     ::= { cienaCesPmBasicTxRxCurrBinEntry 4 }

  
  cienaCesPmBasicTxRxCurrBinRxAcceptedBytes OBJECT-TYPE
     SYNTAX      Counter64
     MAX-ACCESS  read-only
     STATUS      current
     DESCRIPTION
             "The number of accepted bytes on this PM instance."
     ::= { cienaCesPmBasicTxRxCurrBinEntry 5 }

  cienaCesPmBasicTxRxCurrBinRxAcceptedFrames OBJECT-TYPE
     SYNTAX      Counter64
     MAX-ACCESS  read-only
     STATUS      current
     DESCRIPTION
             "The number of accepted frames on this PM instance."
     ::= { cienaCesPmBasicTxRxCurrBinEntry 6 }

  cienaCesPmBasicTxRxCurrBinRxYellowBytes OBJECT-TYPE
     SYNTAX      Counter64
     MAX-ACCESS  read-only
     STATUS      current
     DESCRIPTION
             "The number of remarked bytes received on this PM instance."
     ::= { cienaCesPmBasicTxRxCurrBinEntry 7 }

  cienaCesPmBasicTxRxCurrBinRxYellowFrames OBJECT-TYPE
     SYNTAX      Counter64
     MAX-ACCESS  read-only
     STATUS      current
     DESCRIPTION
             "The number of remarked frames received on this PM instance."
     ::= { cienaCesPmBasicTxRxCurrBinEntry 8 }

  
  cienaCesPmBasicTxRxCurrBinRxDroppedBytes OBJECT-TYPE
     SYNTAX      Counter64
     MAX-ACCESS  read-only
     STATUS      current
     DESCRIPTION
             "The number of received bytes dropped on this PM instance."
     ::= { cienaCesPmBasicTxRxCurrBinEntry 9 }

  cienaCesPmBasicTxRxCurrBinRxDroppedFrames OBJECT-TYPE
     SYNTAX      Counter64
     MAX-ACCESS  read-only
     STATUS      current
     DESCRIPTION
             "The number of received frames dropped on this PM instance."
     ::= { cienaCesPmBasicTxRxCurrBinEntry 10 }

  cienaCesPmBasicTxRxCurrBinTxForwardedBytes OBJECT-TYPE
     SYNTAX      Counter64
     MAX-ACCESS  read-only
     STATUS      current
     DESCRIPTION
             "The number of bytes forwarded on this PM instance."
     ::= { cienaCesPmBasicTxRxCurrBinEntry 11 }

  cienaCesPmBasicTxRxCurrBinTxForwardedFrames OBJECT-TYPE
     SYNTAX      Counter64
     MAX-ACCESS  read-only
     STATUS      current
     DESCRIPTION
             "The number of frames forwarded on this PM instance."
     ::= { cienaCesPmBasicTxRxCurrBinEntry 12 }

  cienaCesPmBasicTxRxCurrBinRxBytesPerSec OBJECT-TYPE
     SYNTAX      Counter64
     MAX-ACCESS  read-only
     STATUS      current
     DESCRIPTION
             "The number of bytes received per second on this PM instance."
     ::= { cienaCesPmBasicTxRxCurrBinEntry 13 }

  cienaCesPmBasicTxRxCurrBinRxFramesPerSec OBJECT-TYPE
     SYNTAX      Counter64
     MAX-ACCESS  read-only
     STATUS      current
     DESCRIPTION
             "The number of frames received per second on this PM instance."
     ::= { cienaCesPmBasicTxRxCurrBinEntry 14 }

  cienaCesPmBasicTxRxCurrBinTxBytesPerSec OBJECT-TYPE
     SYNTAX      Counter64
     MAX-ACCESS  read-only
     STATUS      current
     DESCRIPTION
             "The number of bytes transmitted per second on this PM instance."
     ::= { cienaCesPmBasicTxRxCurrBinEntry 15 }

  cienaCesPmBasicTxRxCurrBinTxFramesPerSec OBJECT-TYPE
     SYNTAX      Counter64
     MAX-ACCESS  read-only
     STATUS      current
     DESCRIPTION
             "The number of frames transmitted per second on this PM instance."
     ::= { cienaCesPmBasicTxRxCurrBinEntry 16 }
 
  
  --BasicTxRx Profile Stats - current 24 hour bin table  
  
 cienaCesPmBasicTxRxCurr24HBinTable OBJECT-TYPE
     SYNTAX     SEQUENCE OF CienaCesPmBasicTxRxCurr24HBinEntry
     MAX-ACCESS not-accessible
     STATUS     current
     DESCRIPTION
            "The (conceptual) read-only Table listing the basic TxRx profile statistics."  
     ::= { cienaCesPmBasicTxRxStats 3 }
     
   cienaCesPmBasicTxRxCurr24HBinEntry OBJECT-TYPE
     SYNTAX      CienaCesPmBasicTxRxCurr24HBinEntry
     MAX-ACCESS  not-accessible
     STATUS      current
     DESCRIPTION
           "An entry (conceptual row) in the cienaCesPmBasicTxRxCurr24HBinTable.

           This table lists the statistics for the current 24 Hours bin." 
     INDEX {cienaCesPmInstanceIndex}
     ::= { cienaCesPmBasicTxRxCurr24HBinTable 1 }
        
 CienaCesPmBasicTxRxCurr24HBinEntry ::=  SEQUENCE {  
   cienaCesPmBasicTxRxCurr24HBinStartTime					DisplayString,
   cienaCesPmBasicTxRxCurr24HBinEndTime					DisplayString,
   cienaCesPmBasicTxRxCurr24HBinClearedTime				DisplayString,
   cienaCesPmBasicTxRxCurr24HBinDuration					Unsigned32,   
   cienaCesPmBasicTxRxCurr24HBinState						PmBinState,
   cienaCesPmBasicTxRxCurr24HBinRxAcceptedBytes  		Counter64,
   cienaCesPmBasicTxRxCurr24HBinRxAcceptedFrames    	Counter64,
   cienaCesPmBasicTxRxCurr24HBinRxYellowBytes    		Counter64,
   cienaCesPmBasicTxRxCurr24HBinRxYellowFrames    	Counter64,
   cienaCesPmBasicTxRxCurr24HBinRxDroppedBytes    	Counter64,
   cienaCesPmBasicTxRxCurr24HBinRxDroppedFrames    	Counter64,
   cienaCesPmBasicTxRxCurr24HBinTxForwardedBytes    	Counter64,
   cienaCesPmBasicTxRxCurr24HBinTxForwardedFrames     Counter64,
   cienaCesPmBasicTxRxCurr24HBinRxBytesPerSec         Counter64,
   cienaCesPmBasicTxRxCurr24HBinRxFramesPerSec        Counter64,
   cienaCesPmBasicTxRxCurr24HBinTxBytesPerSec         Counter64,
   cienaCesPmBasicTxRxCurr24HBinTxFramesPerSec        Counter64
   	}
   cienaCesPmBasicTxRxCurr24HBinStartTime   OBJECT-TYPE
     SYNTAX		DisplayString
     MAX-ACCESS	read-only
     STATUS		current
     DESCRIPTION "Collection start time of the bin."
     ::= { cienaCesPmBasicTxRxCurr24HBinEntry 1	}
   
   cienaCesPmBasicTxRxCurr24HBinEndTime 		OBJECT-TYPE
     SYNTAX		DisplayString
     MAX-ACCESS	read-only
     STATUS		current
     DESCRIPTION "Collection end time for the bin."
     ::= { cienaCesPmBasicTxRxCurr24HBinEntry 2	}

    cienaCesPmBasicTxRxCurr24HBinClearedTime   OBJECT-TYPE
     SYNTAX		DisplayString
     MAX-ACCESS	read-only
     STATUS		current
     DESCRIPTION "Cleared time of the bin."
     ::= { cienaCesPmBasicTxRxCurr24HBinEntry 3	}
                   
   cienaCesPmBasicTxRxCurr24HBinDuration OBJECT-TYPE
     SYNTAX      Unsigned32 (1..65535)  
     UNITS		"minutes"
     MAX-ACCESS  read-only
     STATUS      current
     DESCRIPTION
             "Interval of the bin."
     ::= { cienaCesPmBasicTxRxCurr24HBinEntry 4 }
  
  cienaCesPmBasicTxRxCurr24HBinState OBJECT-TYPE
     SYNTAX      PmBinState 
     MAX-ACCESS  read-only
     STATUS      current
     DESCRIPTION
             "State of the bin."
     ::= { cienaCesPmBasicTxRxCurr24HBinEntry 5 }

  
  cienaCesPmBasicTxRxCurr24HBinRxAcceptedBytes OBJECT-TYPE
     SYNTAX      Counter64
     MAX-ACCESS  read-only
     STATUS      current
     DESCRIPTION
             "The number of accepted bytes on this PM instance."
     ::= { cienaCesPmBasicTxRxCurr24HBinEntry 6 }

  cienaCesPmBasicTxRxCurr24HBinRxAcceptedFrames OBJECT-TYPE
     SYNTAX      Counter64
     MAX-ACCESS  read-only
     STATUS      current
     DESCRIPTION
             "The number of accepted frames on this PM instance."
     ::= { cienaCesPmBasicTxRxCurr24HBinEntry 7 }

  cienaCesPmBasicTxRxCurr24HBinRxYellowBytes OBJECT-TYPE
     SYNTAX      Counter64
     MAX-ACCESS  read-only
     STATUS      current
     DESCRIPTION
             "The number of remarked bytes received on this PM instance."
     ::= { cienaCesPmBasicTxRxCurr24HBinEntry 8 }

  cienaCesPmBasicTxRxCurr24HBinRxYellowFrames OBJECT-TYPE
     SYNTAX      Counter64
     MAX-ACCESS  read-only
     STATUS      current
     DESCRIPTION
             "The number of remarked frames received on this PM instance."
     ::= { cienaCesPmBasicTxRxCurr24HBinEntry 9 }

  
  cienaCesPmBasicTxRxCurr24HBinRxDroppedBytes OBJECT-TYPE
     SYNTAX      Counter64
     MAX-ACCESS  read-only
     STATUS      current
     DESCRIPTION
             "The number of received bytes dropped on this PM instance."
     ::= { cienaCesPmBasicTxRxCurr24HBinEntry 10 }

  cienaCesPmBasicTxRxCurr24HBinRxDroppedFrames OBJECT-TYPE
     SYNTAX      Counter64
     MAX-ACCESS  read-only
     STATUS      current
     DESCRIPTION
             "The number of received frames dropped on this PM instance."
     ::= { cienaCesPmBasicTxRxCurr24HBinEntry 11 }

  cienaCesPmBasicTxRxCurr24HBinTxForwardedBytes OBJECT-TYPE
     SYNTAX      Counter64
     MAX-ACCESS  read-only
     STATUS      current
     DESCRIPTION
             "The number of bytes forwarded on this PM instance."
     ::= { cienaCesPmBasicTxRxCurr24HBinEntry 12 }

  cienaCesPmBasicTxRxCurr24HBinTxForwardedFrames OBJECT-TYPE
     SYNTAX      Counter64
     MAX-ACCESS  read-only
     STATUS      current
     DESCRIPTION
             "The number of frames forwarded on this PM instance."
     ::= { cienaCesPmBasicTxRxCurr24HBinEntry 13 }

  cienaCesPmBasicTxRxCurr24HBinRxBytesPerSec OBJECT-TYPE
     SYNTAX      Counter64
     MAX-ACCESS  read-only
     STATUS      current
     DESCRIPTION
             "The number of bytes received per second on this PM instance."
     ::= { cienaCesPmBasicTxRxCurr24HBinEntry 14 }

  cienaCesPmBasicTxRxCurr24HBinRxFramesPerSec OBJECT-TYPE
     SYNTAX      Counter64
     MAX-ACCESS  read-only
     STATUS      current
     DESCRIPTION
             "The number of frames received per second on this PM instance."
     ::= { cienaCesPmBasicTxRxCurr24HBinEntry 15 }

  cienaCesPmBasicTxRxCurr24HBinTxBytesPerSec OBJECT-TYPE
     SYNTAX      Counter64
     MAX-ACCESS  read-only
     STATUS      current
     DESCRIPTION
             "The number of bytes transmitted per second on this PM instance."
     ::= { cienaCesPmBasicTxRxCurr24HBinEntry 16 }
  
  cienaCesPmBasicTxRxCurr24HBinTxFramesPerSec OBJECT-TYPE
     SYNTAX      Counter64
     MAX-ACCESS  read-only
     STATUS      current
     DESCRIPTION
             "The number of frames transmitted per second on this PM instance."
     ::= { cienaCesPmBasicTxRxCurr24HBinEntry 17 }
  
 
 --BasicTxRx Profile Stats - history 24 hour bin table  
  
 cienaCesPmBasicTxRxHist24HBinTable OBJECT-TYPE
     SYNTAX     SEQUENCE OF CienaCesPmBasicTxRxHist24HBinEntry
     MAX-ACCESS not-accessible
     STATUS     current
     DESCRIPTION
            "The (conceptual) read-only table listing the basic TxRx profile statistics."  
     ::= { cienaCesPmBasicTxRxStats 4 }
     
   cienaCesPmBasicTxRxHist24HBinEntry OBJECT-TYPE
     SYNTAX      CienaCesPmBasicTxRxHist24HBinEntry
     MAX-ACCESS  not-accessible
     STATUS      current
     DESCRIPTION
           "An entry (conceptual row) in the cienaCesPmBasicTxRxHist24HBinTable.

           This table lists the statistics for the history 24 hours bin." 
     INDEX {cienaCesPmInstanceIndex}
     ::= { cienaCesPmBasicTxRxHist24HBinTable 1 }
        
 CienaCesPmBasicTxRxHist24HBinEntry ::=  SEQUENCE { 
   cienaCesPmBasicTxRxHist24HBinStartTime						DisplayString,
   cienaCesPmBasicTxRxHist24HBinDuration							Unsigned32,   
   cienaCesPmBasicTxRxHist24HBinState							PmBinState,
   cienaCesPmBasicTxRxHist24HBinBasicRxAcceptedBytes    		Counter64,
   cienaCesPmBasicTxRxHist24HBinBasicRxAcceptedFrames    		Counter64,
   cienaCesPmBasicTxRxHist24HBinBasicRxYellowBytes    			Counter64,
   cienaCesPmBasicTxRxHist24HBinBasicRxYellowFrames    		Counter64,
   cienaCesPmBasicTxRxHist24HBinBasicRxDroppedBytes    		Counter64,
   cienaCesPmBasicTxRxHist24HBinBasicRxDroppedFrames    		Counter64,
   cienaCesPmBasicTxRxHist24HBinBasicTxForwardedBytes    		Counter64,
   cienaCesPmBasicTxRxHist24HBinBasicTxForwardedFrames        	Counter64,
   cienaCesPmBasicTxRxHist24HBinBasicRxBytesPerSec           	Counter64,
   cienaCesPmBasicTxRxHist24HBinBasicRxFramesPerSec           	Counter64,
   cienaCesPmBasicTxRxHist24HBinBasicTxBytesPerSec            	Counter64,
   cienaCesPmBasicTxRxHist24HBinBasicTxFramesPerSec           	Counter64,
   cienaCesPmBasicTxRxHist24HBinEndTime                                         DisplayString,
   cienaCesPmBasicTxRxHist24HBinClearTime                                       DisplayString
   	}
  cienaCesPmBasicTxRxHist24HBinStartTime   OBJECT-TYPE
     SYNTAX		DisplayString
     MAX-ACCESS	read-only
     STATUS		current
     DESCRIPTION "Collection start time of the bin."
     ::= { cienaCesPmBasicTxRxHist24HBinEntry 1 }
   
 cienaCesPmBasicTxRxHist24HBinDuration OBJECT-TYPE
     SYNTAX      Unsigned32 (1..65535)  
     UNITS		"minutes"
     MAX-ACCESS  read-only
     STATUS      current
     DESCRIPTION
             "Interval of the bin."
     ::= { cienaCesPmBasicTxRxHist24HBinEntry 2 }
  
  cienaCesPmBasicTxRxHist24HBinState OBJECT-TYPE
     SYNTAX      PmBinState 
     MAX-ACCESS  read-only
     STATUS      current
     DESCRIPTION
             "State of the bin."
     ::= { cienaCesPmBasicTxRxHist24HBinEntry 3 }

  
  cienaCesPmBasicTxRxHist24HBinBasicRxAcceptedBytes OBJECT-TYPE
     SYNTAX      Counter64
     MAX-ACCESS  read-only
     STATUS      current
     DESCRIPTION
             "The number of accepted bytes on this PM instance."
     ::= { cienaCesPmBasicTxRxHist24HBinEntry 4 }

  cienaCesPmBasicTxRxHist24HBinBasicRxAcceptedFrames OBJECT-TYPE
     SYNTAX      Counter64
     MAX-ACCESS  read-only
     STATUS      current
     DESCRIPTION
             "The number of accepted frames on this PM instance."
     ::= { cienaCesPmBasicTxRxHist24HBinEntry 5 }

  cienaCesPmBasicTxRxHist24HBinBasicRxYellowBytes OBJECT-TYPE
     SYNTAX      Counter64
     MAX-ACCESS  read-only
     STATUS      current
     DESCRIPTION
             "The number of remarked bytes received on this PM instance."
     ::= { cienaCesPmBasicTxRxHist24HBinEntry 6 }

  cienaCesPmBasicTxRxHist24HBinBasicRxYellowFrames OBJECT-TYPE
     SYNTAX      Counter64
     MAX-ACCESS  read-only
     STATUS      current
     DESCRIPTION
             "The number of remarked frames received on this PM instance."
     ::= { cienaCesPmBasicTxRxHist24HBinEntry 7 }

  
  cienaCesPmBasicTxRxHist24HBinBasicRxDroppedBytes OBJECT-TYPE
     SYNTAX      Counter64
     MAX-ACCESS  read-only
     STATUS      current
     DESCRIPTION
             "The number of received bytes dropped on this PM instance."
     ::= { cienaCesPmBasicTxRxHist24HBinEntry 8 }

  cienaCesPmBasicTxRxHist24HBinBasicRxDroppedFrames OBJECT-TYPE
     SYNTAX      Counter64
     MAX-ACCESS  read-only
     STATUS      current
     DESCRIPTION
             "The number of received frames dropped on this PM instance."
     ::= { cienaCesPmBasicTxRxHist24HBinEntry 9 }

  cienaCesPmBasicTxRxHist24HBinBasicTxForwardedBytes OBJECT-TYPE
     SYNTAX      Counter64
     MAX-ACCESS  read-only
     STATUS      current
     DESCRIPTION
             "The number of bytes forwarded on this PM instance."
     ::= { cienaCesPmBasicTxRxHist24HBinEntry 10 }

  cienaCesPmBasicTxRxHist24HBinBasicTxForwardedFrames OBJECT-TYPE
     SYNTAX      Counter64
     MAX-ACCESS  read-only
     STATUS      current
     DESCRIPTION
             "The number of frames forwarded on this PM instance."
     ::= { cienaCesPmBasicTxRxHist24HBinEntry 11 }

  cienaCesPmBasicTxRxHist24HBinBasicRxBytesPerSec OBJECT-TYPE
     SYNTAX      Counter64
     MAX-ACCESS  read-only
     STATUS      current
     DESCRIPTION
             "The number of bytes received per second on this PM instance."
     ::= { cienaCesPmBasicTxRxHist24HBinEntry 12 }

  cienaCesPmBasicTxRxHist24HBinBasicRxFramesPerSec OBJECT-TYPE
     SYNTAX      Counter64
     MAX-ACCESS  read-only
     STATUS      current
     DESCRIPTION
             "The number of frames received per second on this PM instance."
     ::= { cienaCesPmBasicTxRxHist24HBinEntry 13 }

  cienaCesPmBasicTxRxHist24HBinBasicTxBytesPerSec OBJECT-TYPE
     SYNTAX      Counter64
     MAX-ACCESS  read-only
     STATUS      current
     DESCRIPTION
             "The number of bytes transmitted per second on this PM instance."
     ::= { cienaCesPmBasicTxRxHist24HBinEntry 14 }

  cienaCesPmBasicTxRxHist24HBinBasicTxFramesPerSec OBJECT-TYPE
     SYNTAX      Counter64
     MAX-ACCESS  read-only
     STATUS      current
     DESCRIPTION
             "The number of frames transmitted per second on this PM instance."
     ::= { cienaCesPmBasicTxRxHist24HBinEntry 15 }
 
   cienaCesPmBasicTxRxHist24HBinEndTime OBJECT-TYPE
     SYNTAX      DisplayString
     MAX-ACCESS  read-only
     STATUS      current
     DESCRIPTION "Collection end time of the bin."
     ::= { cienaCesPmBasicTxRxHist24HBinEntry 16 }

   cienaCesPmBasicTxRxHist24HBinClearTime OBJECT-TYPE
     SYNTAX      DisplayString
     MAX-ACCESS  read-only
     STATUS      current
     DESCRIPTION "Collection clear time of the bin."
      ::= { cienaCesPmBasicTxRxHist24HBinEntry 17 }

 
 --BasicTxRx Profile Stats   
  
 cienaCesPmBasicTxRxAllTimeBinTable OBJECT-TYPE
     SYNTAX     SEQUENCE OF CienaCesPmBasicTxRxAllTimeBinEntry
     MAX-ACCESS not-accessible
     STATUS     deprecated                      
     DESCRIPTION
            "The (conceptual) read-only table listing the basic TxRx profile statistics."  
     ::= { cienaCesPmBasicTxRxStats 5 }
     
   cienaCesPmBasicTxRxAllTimeBinEntry OBJECT-TYPE
     SYNTAX      CienaCesPmBasicTxRxAllTimeBinEntry
     MAX-ACCESS  not-accessible
     STATUS      deprecated
     DESCRIPTION
           "An entry (conceptual row) in the cienaCesPmBasicTxRxAllTimeBinTable.

           This table lists the statistics for the All Time bin of the PM instance." 
     INDEX {cienaCesPmInstanceIndex }
     ::= { cienaCesPmBasicTxRxAllTimeBinTable 1 }
        
 CienaCesPmBasicTxRxAllTimeBinEntry ::=  SEQUENCE {
 	cienaCesPmBasicTxRxAllTimeBinBasicRxAcceptedBytes 			Counter64,
	cienaCesPmBasicTxRxAllTimeBinBasicRxAcceptedFrames    		Counter64,
    cienaCesPmBasicTxRxAllTimeBinBasicRxYellowBytes    		Counter64,
    cienaCesPmBasicTxRxAllTimeBinBasicRxYellowFrames    		Counter64,
    cienaCesPmBasicTxRxAllTimeBinBasicRxDroppedBytes    		Counter64,
    cienaCesPmBasicTxRxAllTimeBinBasicRxDroppedFrames    		Counter64,
    cienaCesPmBasicTxRxAllTimeBinBasicTxForwardedBytes    		Counter64,
    cienaCesPmBasicTxRxAllTimeBinBasicTxForwardedFrames     	Counter64,
    cienaCesPmBasicTxRxAllTimeBinBasicRxBytesPerSec         	Counter64,
    cienaCesPmBasicTxRxAllTimeBinBasicRxFramesPerSec        	Counter64,
    cienaCesPmBasicTxRxAllTimeBinBasicTxBytesPerSec         	Counter64,
    cienaCesPmBasicTxRxAllTimeBinBasicTxFramesPerSec        	Counter64
    }
  cienaCesPmBasicTxRxAllTimeBinBasicRxAcceptedBytes OBJECT-TYPE
     SYNTAX      Counter64
     MAX-ACCESS  read-only
     STATUS      deprecated
     DESCRIPTION
             "The number of accepted bytes on this PM instance."
     ::= { cienaCesPmBasicTxRxAllTimeBinEntry 1 }

  cienaCesPmBasicTxRxAllTimeBinBasicRxAcceptedFrames OBJECT-TYPE
     SYNTAX      Counter64
     MAX-ACCESS  read-only
     STATUS      deprecated
     DESCRIPTION
             "The number of accepted frames on this PM instance."
     ::= { cienaCesPmBasicTxRxAllTimeBinEntry 2 }

  cienaCesPmBasicTxRxAllTimeBinBasicRxYellowBytes OBJECT-TYPE
     SYNTAX      Counter64
     MAX-ACCESS  read-only
     STATUS      deprecated
     DESCRIPTION
             "The number of remarked bytes received on this PM instance."
     ::= { cienaCesPmBasicTxRxAllTimeBinEntry 3 }

  cienaCesPmBasicTxRxAllTimeBinBasicRxYellowFrames OBJECT-TYPE
     SYNTAX      Counter64
     MAX-ACCESS  read-only
     STATUS      deprecated
     DESCRIPTION
             "The number of remarked frames received on this PM instance."
     ::= { cienaCesPmBasicTxRxAllTimeBinEntry 4 }

  
  cienaCesPmBasicTxRxAllTimeBinBasicRxDroppedBytes OBJECT-TYPE
     SYNTAX      Counter64
     MAX-ACCESS  read-only
     STATUS      deprecated
     DESCRIPTION
             "The number of received bytes dropped on this PM instance."
     ::= { cienaCesPmBasicTxRxAllTimeBinEntry 5 }

  cienaCesPmBasicTxRxAllTimeBinBasicRxDroppedFrames OBJECT-TYPE
     SYNTAX      Counter64
     MAX-ACCESS  read-only
     STATUS      deprecated
     DESCRIPTION
             "The number of received frames dropped on this PM instance."
     ::= { cienaCesPmBasicTxRxAllTimeBinEntry 6 }

  cienaCesPmBasicTxRxAllTimeBinBasicTxForwardedBytes OBJECT-TYPE
     SYNTAX      Counter64
     MAX-ACCESS  read-only
     STATUS      deprecated
     DESCRIPTION
             "The number of bytes forwarded on this PM instance."
     ::= { cienaCesPmBasicTxRxAllTimeBinEntry 7 }

  cienaCesPmBasicTxRxAllTimeBinBasicTxForwardedFrames OBJECT-TYPE
     SYNTAX      Counter64
     MAX-ACCESS  read-only
     STATUS      deprecated
     DESCRIPTION
             "The number of frames forwarded on this PM instance."
     ::= { cienaCesPmBasicTxRxAllTimeBinEntry 8 }

  cienaCesPmBasicTxRxAllTimeBinBasicRxBytesPerSec OBJECT-TYPE
     SYNTAX      Counter64
     MAX-ACCESS  read-only
     STATUS      deprecated
     DESCRIPTION
             "The number of bytes received per second on this PM instance."
     ::= { cienaCesPmBasicTxRxAllTimeBinEntry 9 }

  cienaCesPmBasicTxRxAllTimeBinBasicRxFramesPerSec OBJECT-TYPE
     SYNTAX      Counter64
     MAX-ACCESS  read-only
     STATUS      deprecated
     DESCRIPTION
             "The number of frames received per second on this PM instance."
     ::= { cienaCesPmBasicTxRxAllTimeBinEntry 10 }

  cienaCesPmBasicTxRxAllTimeBinBasicTxBytesPerSec OBJECT-TYPE
     SYNTAX      Counter64
     MAX-ACCESS  read-only
     STATUS      deprecated
     DESCRIPTION
             "The number of bytes transmitted per second on this PM instance."
     ::= { cienaCesPmBasicTxRxAllTimeBinEntry 11 }

  cienaCesPmBasicTxRxAllTimeBinBasicTxFramesPerSec OBJECT-TYPE
     SYNTAX      Counter64
     MAX-ACCESS  read-only
     STATUS      deprecated
     DESCRIPTION
             "The number of frames transmitted per second on this PM instance."
     ::= { cienaCesPmBasicTxRxAllTimeBinEntry 12 }


   --BasicTxRx Profile Stats, statistics bin
  
   cienaCesPmBasicTxRxStatisticsBinTable OBJECT-TYPE
     SYNTAX     SEQUENCE OF CienaCesPmBasicTxRxStatisticsBinEntry
     MAX-ACCESS not-accessible
     STATUS     current                      
     DESCRIPTION "The (conceptual) read-only table listing the bin statistics."
     ::= { cienaCesPmBasicTxRxStats 6 }
     
   cienaCesPmBasicTxRxStatisticsBinEntry OBJECT-TYPE
     SYNTAX      CienaCesPmBasicTxRxStatisticsBinEntry
     MAX-ACCESS  not-accessible
     STATUS      current
     DESCRIPTION
           "An entry (conceptual row) in the cienaCesPmBasicTxRxStatisticsBinTable.
           This table lists the statistics for the statistics bin of the PM instance." 
     INDEX {cienaCesPmInstanceIndex}
     ::= { cienaCesPmBasicTxRxStatisticsBinTable 1 }
        
   CienaCesPmBasicTxRxStatisticsBinEntry ::=  SEQUENCE {
     cienaCesPmBasicTxRxStatsBinStartTime                           DisplayString,
     cienaCesPmBasicTxRxStatsBinClearTime                           DisplayString,
     cienaCesPmBasicTxRxStatsBinRxAcceptedBytes                     Counter64,
     cienaCesPmBasicTxRxStatsBinRxAcceptedFrames                    Counter64,
     cienaCesPmBasicTxRxStatsBinRxYellowBytes                       Counter64,
     cienaCesPmBasicTxRxStatsBinRxYellowFrames                      Counter64,
     cienaCesPmBasicTxRxStatsBinRxDroppedBytes                      Counter64,
     cienaCesPmBasicTxRxStatsBinRxDroppedFrames                     Counter64,
     cienaCesPmBasicTxRxStatsBinTxForwardedBytes                    Counter64,
     cienaCesPmBasicTxRxStatsBinTxForwardedFrames                   Counter64,
     cienaCesPmBasicTxRxStatsBinRxBytesPerSec                       Counter64,
     cienaCesPmBasicTxRxStatsBinRxFramesPerSec                      Counter64,
     cienaCesPmBasicTxRxStatsBinTxBytesPerSec                       Counter64,
     cienaCesPmBasicTxRxStatsBinTxFramesPerSec                      Counter64
   }

   cienaCesPmBasicTxRxStatsBinStartTime OBJECT-TYPE
     SYNTAX      DisplayString
     MAX-ACCESS  read-only
     STATUS      current
     DESCRIPTION "Collection start time of the bin."
     ::= { cienaCesPmBasicTxRxStatisticsBinEntry 1 }

   cienaCesPmBasicTxRxStatsBinClearTime OBJECT-TYPE
     SYNTAX      DisplayString
     MAX-ACCESS  read-only
     STATUS      current
     DESCRIPTION "Collection clear time of the bin."
     ::= { cienaCesPmBasicTxRxStatisticsBinEntry 2 }

   cienaCesPmBasicTxRxStatsBinRxAcceptedBytes OBJECT-TYPE
     SYNTAX      Counter64
     MAX-ACCESS  read-only
     STATUS      current
     DESCRIPTION
             "The number of accepted bytes on this PM instance."
     ::= { cienaCesPmBasicTxRxStatisticsBinEntry 3 }

   cienaCesPmBasicTxRxStatsBinRxAcceptedFrames OBJECT-TYPE
     SYNTAX      Counter64
     MAX-ACCESS  read-only
     STATUS      current
     DESCRIPTION
             "The number of accepted frames on this PM instance."
     ::= { cienaCesPmBasicTxRxStatisticsBinEntry 4 }

   cienaCesPmBasicTxRxStatsBinRxYellowBytes OBJECT-TYPE
     SYNTAX      Counter64
     MAX-ACCESS  read-only
     STATUS      current
     DESCRIPTION
             "The number of remarked bytes received on this PM instance."
     ::= { cienaCesPmBasicTxRxStatisticsBinEntry 5 }

   cienaCesPmBasicTxRxStatsBinRxYellowFrames OBJECT-TYPE
     SYNTAX      Counter64
     MAX-ACCESS  read-only
     STATUS      current
     DESCRIPTION
             "The number of remarked frames received on this PM instance."
     ::= { cienaCesPmBasicTxRxStatisticsBinEntry 6 }

   cienaCesPmBasicTxRxStatsBinRxDroppedBytes OBJECT-TYPE
     SYNTAX      Counter64
     MAX-ACCESS  read-only
     STATUS      current
     DESCRIPTION
             "The number of received bytes dropped on this PM instance."
     ::= { cienaCesPmBasicTxRxStatisticsBinEntry 7 }

   cienaCesPmBasicTxRxStatsBinRxDroppedFrames OBJECT-TYPE
     SYNTAX      Counter64
     MAX-ACCESS  read-only
     STATUS      current
     DESCRIPTION
             "The number of received frames dropped on this PM instance."
     ::= { cienaCesPmBasicTxRxStatisticsBinEntry 8 }

   cienaCesPmBasicTxRxStatsBinTxForwardedBytes OBJECT-TYPE
     SYNTAX      Counter64
     MAX-ACCESS  read-only
     STATUS      current
     DESCRIPTION
             "The number of bytes forwarded on this PM instance."
     ::= { cienaCesPmBasicTxRxStatisticsBinEntry 9 }

   cienaCesPmBasicTxRxStatsBinTxForwardedFrames OBJECT-TYPE
     SYNTAX      Counter64
     MAX-ACCESS  read-only
     STATUS      current
     DESCRIPTION
             "The number of frames forwarded on this PM instance."
     ::= { cienaCesPmBasicTxRxStatisticsBinEntry 10 }

   cienaCesPmBasicTxRxStatsBinRxBytesPerSec OBJECT-TYPE
     SYNTAX      Counter64
     MAX-ACCESS  read-only
     STATUS      current
     DESCRIPTION
             "The number of bytes received per second on this PM instance."
     ::= { cienaCesPmBasicTxRxStatisticsBinEntry 11 }

   cienaCesPmBasicTxRxStatsBinRxFramesPerSec OBJECT-TYPE
     SYNTAX      Counter64
     MAX-ACCESS  read-only
     STATUS      current
     DESCRIPTION
             "The number of frames received per second on this PM instance."
     ::= { cienaCesPmBasicTxRxStatisticsBinEntry 12 }

   cienaCesPmBasicTxRxStatsBinTxBytesPerSec OBJECT-TYPE
     SYNTAX      Counter64
     MAX-ACCESS  read-only
     STATUS      current
     DESCRIPTION
             "The number of bytes transmitted per second on this PM instance."
     ::= { cienaCesPmBasicTxRxStatisticsBinEntry 13 }

   cienaCesPmBasicTxRxStatsBinTxFramesPerSec OBJECT-TYPE
     SYNTAX      Counter64
     MAX-ACCESS  read-only
     STATUS      current
     DESCRIPTION
             "The number of frames transmitted per second on this PM instance."
     ::= { cienaCesPmBasicTxRxStatisticsBinEntry 14 }


   --BasicTxRx Profile Stats, total statistics bin
  
 cienaCesPmBasicTxRxTotalStatisticsBinTable OBJECT-TYPE
     SYNTAX     SEQUENCE OF CienaCesPmBasicTxRxTotalStatisticsBinEntry
     MAX-ACCESS not-accessible
     STATUS     current                      
     DESCRIPTION "The (conceptual) read-only table listing the bin statistics."
     ::= { cienaCesPmBasicTxRxStats 7 }
     
   cienaCesPmBasicTxRxTotalStatisticsBinEntry OBJECT-TYPE
     SYNTAX      CienaCesPmBasicTxRxTotalStatisticsBinEntry
     MAX-ACCESS  not-accessible
     STATUS      current
     DESCRIPTION
           "An entry (conceptual row) in the cienaCesPmBasicTxRxTotalStatisticsBinTable.
           This table lists the statistics for the total statistics bin of the PM instance." 
     INDEX {cienaCesPmInstanceIndex}
     ::= { cienaCesPmBasicTxRxTotalStatisticsBinTable 1 }
        
   CienaCesPmBasicTxRxTotalStatisticsBinEntry ::=  SEQUENCE {
     cienaCesPmBasicTxRxTotalStatsBinStartTime                      DisplayString,
     cienaCesPmBasicTxRxTotalStatsBinRxAcceptedBytes                Counter64,
     cienaCesPmBasicTxRxTotalStatsBinRxAcceptedFrames               Counter64,
     cienaCesPmBasicTxRxTotalStatsBinRxYellowBytes                  Counter64,
     cienaCesPmBasicTxRxTotalStatsBinRxYellowFrames                 Counter64,
     cienaCesPmBasicTxRxTotalStatsBinRxDroppedBytes                 Counter64,
     cienaCesPmBasicTxRxTotalStatsBinRxDroppedFrames                Counter64,
     cienaCesPmBasicTxRxTotalStatsBinTxForwardedBytes               Counter64,
     cienaCesPmBasicTxRxTotalStatsBinTxForwardedFrames              Counter64,
     cienaCesPmBasicTxRxTotalStatsBinRxBytesPerSec                  Counter64,
     cienaCesPmBasicTxRxTotalStatsBinRxFramesPerSec                 Counter64,
     cienaCesPmBasicTxRxTotalStatsBinTxBytesPerSec                  Counter64,
     cienaCesPmBasicTxRxTotalStatsBinTxFramesPerSec                 Counter64
   }

   cienaCesPmBasicTxRxTotalStatsBinStartTime OBJECT-TYPE
     SYNTAX      DisplayString
     MAX-ACCESS  read-only
     STATUS      current
     DESCRIPTION "Collection start time of the bin."
     ::= { cienaCesPmBasicTxRxTotalStatisticsBinEntry 1 }

   cienaCesPmBasicTxRxTotalStatsBinRxAcceptedBytes OBJECT-TYPE
     SYNTAX      Counter64
     MAX-ACCESS  read-only
     STATUS      current
     DESCRIPTION
             "The number of accepted bytes on this PM instance."
     ::= { cienaCesPmBasicTxRxTotalStatisticsBinEntry 2 }

   cienaCesPmBasicTxRxTotalStatsBinRxAcceptedFrames OBJECT-TYPE
     SYNTAX      Counter64
     MAX-ACCESS  read-only
     STATUS      current
     DESCRIPTION
             "The number of accepted frames on this PM instance."
     ::= { cienaCesPmBasicTxRxTotalStatisticsBinEntry 3 }

   cienaCesPmBasicTxRxTotalStatsBinRxYellowBytes OBJECT-TYPE
     SYNTAX      Counter64
     MAX-ACCESS  read-only
     STATUS      current
     DESCRIPTION
             "The number of remarked bytes received on this PM instance."
     ::= { cienaCesPmBasicTxRxTotalStatisticsBinEntry 4 }

   cienaCesPmBasicTxRxTotalStatsBinRxYellowFrames OBJECT-TYPE
     SYNTAX      Counter64
     MAX-ACCESS  read-only
     STATUS      current
     DESCRIPTION
             "The number of remarked frames received on this PM instance."
     ::= { cienaCesPmBasicTxRxTotalStatisticsBinEntry 5 }

   cienaCesPmBasicTxRxTotalStatsBinRxDroppedBytes OBJECT-TYPE
     SYNTAX      Counter64
     MAX-ACCESS  read-only
     STATUS      current
     DESCRIPTION
             "The number of received bytes dropped on this PM instance."
     ::= { cienaCesPmBasicTxRxTotalStatisticsBinEntry 6 }

   cienaCesPmBasicTxRxTotalStatsBinRxDroppedFrames OBJECT-TYPE
     SYNTAX      Counter64
     MAX-ACCESS  read-only
     STATUS      current
     DESCRIPTION
             "The number of received frames dropped on this PM instance."
     ::= { cienaCesPmBasicTxRxTotalStatisticsBinEntry 7 }

   cienaCesPmBasicTxRxTotalStatsBinTxForwardedBytes OBJECT-TYPE
     SYNTAX      Counter64
     MAX-ACCESS  read-only
     STATUS      current
     DESCRIPTION
             "The number of bytes forwarded on this PM instance."
     ::= { cienaCesPmBasicTxRxTotalStatisticsBinEntry 8 }

   cienaCesPmBasicTxRxTotalStatsBinTxForwardedFrames OBJECT-TYPE
     SYNTAX      Counter64
     MAX-ACCESS  read-only
     STATUS      current
     DESCRIPTION
             "The number of frames forwarded on this PM instance."
     ::= { cienaCesPmBasicTxRxTotalStatisticsBinEntry 9 }

   cienaCesPmBasicTxRxTotalStatsBinRxBytesPerSec OBJECT-TYPE
     SYNTAX      Counter64
     MAX-ACCESS  read-only
     STATUS      current
     DESCRIPTION
             "The number of bytes received per second on this PM instance."
     ::= { cienaCesPmBasicTxRxTotalStatisticsBinEntry 10 }

   cienaCesPmBasicTxRxTotalStatsBinRxFramesPerSec OBJECT-TYPE
     SYNTAX      Counter64
     MAX-ACCESS  read-only
     STATUS      current
     DESCRIPTION
             "The number of frames received per second on this PM instance."
     ::= { cienaCesPmBasicTxRxTotalStatisticsBinEntry 11 }

   cienaCesPmBasicTxRxTotalStatsBinTxBytesPerSec OBJECT-TYPE
     SYNTAX      Counter64
     MAX-ACCESS  read-only
     STATUS      current
     DESCRIPTION
             "The number of bytes transmitted per second on this PM instance."
     ::= { cienaCesPmBasicTxRxTotalStatisticsBinEntry 12 }

   cienaCesPmBasicTxRxTotalStatsBinTxFramesPerSec OBJECT-TYPE
     SYNTAX      Counter64
     MAX-ACCESS  read-only
     STATUS      current
     DESCRIPTION
             "The number of frames transmitted per second on this PM instance."
     ::= { cienaCesPmBasicTxRxTotalStatisticsBinEntry 13 }

  
    --IGMP Profile Stats  
  
  cienaCesPmIGMPHistoryBinTable OBJECT-TYPE
     SYNTAX     SEQUENCE OF CienaCesPmIGMPHistoryBinEntry
     MAX-ACCESS not-accessible
     STATUS     current
     DESCRIPTION
            "The (conceptual) read-only table listing the bin statistics."  
     ::= { cienaCesPmIgmpStats 1 }
     
   cienaCesPmIGMPHistoryBinEntry OBJECT-TYPE
     SYNTAX      CienaCesPmIGMPHistoryBinEntry
     MAX-ACCESS  not-accessible
     STATUS      current
     DESCRIPTION
           "An entry (conceptual row) in the cienaPortPmIGMPHistoryBinTable.

           This table lists the statistics for all the history bins of the PM instance, as 
           specified by the bin-count object of the PM instance.  History bins are displayed in the order
           so that #1 bin always represents the most recently completed bin and #2 - the bin previous to that
           and so on.
	       The statistics are displayed for only the instances with valid bins (with start time >0), 
	       as indicated by the operational state of the corresponding PM instance."  
     INDEX { cienaCesPmInstanceIndex, cienaCesPmIGMPHistoryBinIndex }
     ::= { cienaCesPmIGMPHistoryBinTable 1 }
        
 CienaCesPmIGMPHistoryBinEntry ::=  SEQUENCE { 
 	 cienaCesPmIGMPHistoryBinIndex                           			Unsigned32,
     cienaCesPmIGMPHistoryBinStartTime									DisplayString,
     cienaCesPmIGMPHistoryBinEndTime									DisplayString,
     cienaCesPmIGMPHistoryBinClearTime									DisplayString,
     cienaCesPmIGMPHistoryBinDuration									Unsigned32,   
     cienaCesPmIGMPHistoryBinState										PmBinState,  
     cienaCesPmIGMPHistoryBinIgmpnumJoins                    			Counter64,
     cienaCesPmIGMPHistoryBinIgmpnumLeaves                   			Counter64,
     cienaCesPmIGMPHistoryBinIgmpnumQueries                  			Counter64,
     cienaCesPmIGMPHistoryBinIgmpnumQueryDiscards            			Counter64,
     cienaCesPmIGMPHistoryBinIgmpnumQueryDiscardsQueryCameTooSoon   	Counter64,   
     cienaCesPmIGMPHistoryBinIgmpnumQueryDiscardsPortDown    			Counter64,
     cienaCesPmIGMPHistoryBinIgmpnumQueryDiscardsPortBlock   			Counter64,
     cienaCesPmIGMPHistoryBinIgmpnumQueryDiscardsLiNoServerLI 			Counter64,
     cienaCesPmIGMPHistoryBinIgmpnumQueryTimeouts             			Counter64,
     cienaCesPmIGMPHistoryBinIgmpnumReplyTimeouts             			Counter64,
     cienaCesPmIGMPHistoryBinIgmpnumRouterDiscards            			Counter64,
     cienaCesPmIGMPHistoryBinIgmpnumHostDiscards              			Counter64,
     cienaCesPmIGMPHistoryBinIgmpnumBadChecksum               			Counter64,
     cienaCesPmIGMPHistoryBinIgmpnumL2L3Mismatch              			Counter64,
     cienaCesPmIGMPHistoryBinIgmpnumUnknownPktType            			Counter64,
     cienaCesPmIGMPHistoryBinIgmpnumResourceExceed		 				Counter64,   
     cienaCesPmIGMPHistoryBinIgmpnumQueryDiscardsSrcIpZero	 			Counter64   
   	}          
   cienaCesPmIGMPHistoryBinIndex OBJECT-TYPE
     SYNTAX      Unsigned32 (1..65535) 
     MAX-ACCESS  not-accessible
     STATUS      current
     DESCRIPTION
             "Bin number associated with the PmIGMPHistoryBin entry."
     ::= { cienaCesPmIGMPHistoryBinEntry 1 }

   cienaCesPmIGMPHistoryBinStartTime   OBJECT-TYPE
     SYNTAX		DisplayString
     MAX-ACCESS	read-only
     STATUS		current
     DESCRIPTION "Collection start time of the bin."
     ::= { cienaCesPmIGMPHistoryBinEntry 2	}
   
   cienaCesPmIGMPHistoryBinEndTime		OBJECT-TYPE
   	 SYNTAX	DisplayString
     MAX-ACCESS	read-only
     STATUS		current
     DESCRIPTION "Collection end time of the bin."
     ::= { cienaCesPmIGMPHistoryBinEntry 3	}
   
   cienaCesPmIGMPHistoryBinClearTime		OBJECT-TYPE
   	 SYNTAX	DisplayString
     MAX-ACCESS	read-only
     STATUS		current
     DESCRIPTION "Collection clear time of the bin."
     ::= { cienaCesPmIGMPHistoryBinEntry 4	}

   cienaCesPmIGMPHistoryBinDuration OBJECT-TYPE
     SYNTAX      Unsigned32 (1..65535)        
     UNITS		 "minutes"
     MAX-ACCESS  read-only
     STATUS      current
     DESCRIPTION
             "Duration of the bin."
     ::= { cienaCesPmIGMPHistoryBinEntry 5 }
  
  cienaCesPmIGMPHistoryBinState OBJECT-TYPE
     SYNTAX      PmBinState 
     MAX-ACCESS  read-only
     STATUS      current
     DESCRIPTION
             "State of the bin."
     ::= { cienaCesPmIGMPHistoryBinEntry 6 }
  
  cienaCesPmIGMPHistoryBinIgmpnumJoins OBJECT-TYPE
     SYNTAX      Counter64 
     MAX-ACCESS  read-only
     STATUS      current
     DESCRIPTION
             "The total number of join messages received."
     ::= { cienaCesPmIGMPHistoryBinEntry 7 }
 
 cienaCesPmIGMPHistoryBinIgmpnumLeaves OBJECT-TYPE
     SYNTAX      Counter64 
     MAX-ACCESS  read-only
     STATUS      current
     DESCRIPTION
             "The total number of leave messages received."
     ::= { cienaCesPmIGMPHistoryBinEntry 8 }
     
 cienaCesPmIGMPHistoryBinIgmpnumQueries OBJECT-TYPE
     SYNTAX      Counter64 
     MAX-ACCESS  read-only
     STATUS      current
     DESCRIPTION
             "The total number of queries received."
     ::= { cienaCesPmIGMPHistoryBinEntry 9 }

 cienaCesPmIGMPHistoryBinIgmpnumQueryDiscards OBJECT-TYPE
     SYNTAX      Counter64 
     MAX-ACCESS  read-only
     STATUS      current
     DESCRIPTION
             "The total number of queries discarded."
     ::= { cienaCesPmIGMPHistoryBinEntry 10 }

 cienaCesPmIGMPHistoryBinIgmpnumQueryDiscardsQueryCameTooSoon OBJECT-TYPE
     SYNTAX      Counter64 
     MAX-ACCESS  read-only
     STATUS      current
     DESCRIPTION
             "The total number of queries discarded because the queries came too soon."
     ::= { cienaCesPmIGMPHistoryBinEntry 11 }
 
  cienaCesPmIGMPHistoryBinIgmpnumQueryDiscardsPortDown OBJECT-TYPE
     SYNTAX      Counter64 
     MAX-ACCESS  read-only
     STATUS      current
     DESCRIPTION
             "The total number queries discarded because the port was down."
     ::= { cienaCesPmIGMPHistoryBinEntry 12 }

  cienaCesPmIGMPHistoryBinIgmpnumQueryDiscardsPortBlock OBJECT-TYPE
     SYNTAX      Counter64 
     MAX-ACCESS  read-only
     STATUS      current
     DESCRIPTION
             "The total number of queries discarded because the port was blocked."
     ::= { cienaCesPmIGMPHistoryBinEntry 13 }

   cienaCesPmIGMPHistoryBinIgmpnumQueryDiscardsLiNoServerLI OBJECT-TYPE
     SYNTAX      Counter64 
     MAX-ACCESS  read-only
     STATUS      current
     DESCRIPTION
             "The total number of queries discarded because of no server logical interfaces."
     ::= { cienaCesPmIGMPHistoryBinEntry 14 }

   cienaCesPmIGMPHistoryBinIgmpnumQueryTimeouts OBJECT-TYPE
     SYNTAX      Counter64 
     MAX-ACCESS  read-only
     STATUS      current
     DESCRIPTION
             "The total number of timeouts waiting for the
	      router to send query."
     ::= { cienaCesPmIGMPHistoryBinEntry 15 }
	
   cienaCesPmIGMPHistoryBinIgmpnumReplyTimeouts OBJECT-TYPE
     SYNTAX      Counter64 
     MAX-ACCESS  read-only
     STATUS      current
     DESCRIPTION
             "The total number of timeouts waiting for the
	      membership reports."
     ::= { cienaCesPmIGMPHistoryBinEntry 16 }
   
   cienaCesPmIGMPHistoryBinIgmpnumRouterDiscards OBJECT-TYPE
     SYNTAX      Counter64 
     MAX-ACCESS  read-only
     STATUS      current
     DESCRIPTION
             "The total number of messages discarded by the
	      router. This happens when a join comes in from 
	      a router port."
     ::= { cienaCesPmIGMPHistoryBinEntry 17 }
 
   cienaCesPmIGMPHistoryBinIgmpnumHostDiscards OBJECT-TYPE
     SYNTAX      Counter64 
     MAX-ACCESS  read-only
     STATUS      current
     DESCRIPTION
             "The total number of messages discarded by the
	      host. This happens when a join or leave comes 
	      in a port, but no router port is established."
     ::= { cienaCesPmIGMPHistoryBinEntry 18 }
 
   cienaCesPmIGMPHistoryBinIgmpnumBadChecksum OBJECT-TYPE
     SYNTAX      Counter64 
     MAX-ACCESS  read-only
     STATUS      current
     DESCRIPTION
             "The total number of packets received with bad 
	      IP checksum."
     ::= { cienaCesPmIGMPHistoryBinEntry 19 }

   cienaCesPmIGMPHistoryBinIgmpnumL2L3Mismatch OBJECT-TYPE
     SYNTAX      Counter64 
     MAX-ACCESS  read-only
     STATUS      current
     DESCRIPTION
             "The total number of IGMP Layer 2 and Layer 3 mismatch packets
	      received."
     ::= { cienaCesPmIGMPHistoryBinEntry 20 }
    
   cienaCesPmIGMPHistoryBinIgmpnumUnknownPktType OBJECT-TYPE
     SYNTAX      Counter64 
     MAX-ACCESS  read-only
     STATUS      current
     DESCRIPTION
             "The total number of unknown type IGMP 
	      packets received."
     ::= { cienaCesPmIGMPHistoryBinEntry 21 }
    
   cienaCesPmIGMPHistoryBinIgmpnumResourceExceed OBJECT-TYPE
     SYNTAX      Counter64 
     MAX-ACCESS  read-only
     STATUS      current
     DESCRIPTION
             "The total number of IGMP packets discarded because there were not enough resources
             to process these messages. This could happen when the rate of the incoming IGMP messages
             is very high."
     ::= { cienaCesPmIGMPHistoryBinEntry 22 }
 
   cienaCesPmIGMPHistoryBinIgmpnumQueryDiscardsSrcIpZero OBJECT-TYPE
     SYNTAX      Counter64 
     MAX-ACCESS  read-only
     STATUS      current
     DESCRIPTION
             "The total number of queries discarded because they had zero source IP."
     ::= { cienaCesPmIGMPHistoryBinEntry 23 }
   
   --IGMP Profile Stats     
 
  cienaCesPmIGMPCurrBinTable OBJECT-TYPE
     SYNTAX     SEQUENCE OF CienaCesPmIGMPCurrBinEntry
     MAX-ACCESS not-accessible
     STATUS     current
     DESCRIPTION
            "The (conceptual) read-only table listing the bin statistics."  
     ::= { cienaCesPmIgmpStats 2 }
     
   cienaCesPmIGMPCurrBinEntry OBJECT-TYPE
     SYNTAX      CienaCesPmIGMPCurrBinEntry
     MAX-ACCESS  not-accessible
     STATUS      current
     DESCRIPTION
           "An entry (conceptual row) in the cienaPortPmIGMPCurrBinTable.

           This table lists the statistics for the current bin of the PM instance." 
     INDEX {cienaCesPmInstanceIndex}
     ::= { cienaCesPmIGMPCurrBinTable 1 }
        
 CienaCesPmIGMPCurrBinEntry ::=  SEQUENCE {
 	 cienaCesPmIGMPCurrBinStartTime								DisplayString,
     cienaCesPmIGMPCurrBinClearedTime								DisplayString,
     cienaCesPmIGMPCurrBinDuration									Unsigned32,   
     cienaCesPmIGMPCurrBinState									PmBinState,  
     cienaCesPmIGMPCurrBinIgmpnumJoins                				Counter64,
     cienaCesPmIGMPCurrBinIgmpnumLeaves               				Counter64,
     cienaCesPmIGMPCurrBinIgmpnumQueries              				Counter64,
     cienaCesPmIGMPCurrBinIgmpnumQueryDiscards        				Counter64,
     cienaCesPmIGMPCurrBinIgmpnumQueryDiscardsQueryCameTooSoon   	Counter64,   
     cienaCesPmIGMPCurrBinIgmpnumQueryDiscardsPortDown    			Counter64,           
     cienaCesPmIGMPCurrBinIgmpnumQueryDiscardsPortBlock   			Counter64,          
     cienaCesPmIGMPCurrBinIgmpnumQueryDiscardsLiNoServerLI 		Counter64,       
     cienaCesPmIGMPCurrBinIgmpnumQueryTimeouts             		Counter64,                   
     cienaCesPmIGMPCurrBinIgmpnumReplyTimeouts             		Counter64,		                   
     cienaCesPmIGMPCurrBinIgmpnumRouterDiscards            		Counter64,                  
     cienaCesPmIGMPCurrBinIgmpnumHostDiscards              		Counter64,                    
     cienaCesPmIGMPCurrBinIgmpnumBadChecksum               		Counter64,                     
     cienaCesPmIGMPCurrBinIgmpnumL2L3Mismatch              		Counter64,                    
     cienaCesPmIGMPCurrBinIgmpnumUnknownPktType            		Counter64,                  
     cienaCesPmIGMPCurrBinIgmpnumResourceExceed		 			Counter64,   
     cienaCesPmIGMPCurrBinIgmpnumQueryDiscardsSrcIpZero	 		Counter64   
   	}          
  
    cienaCesPmIGMPCurrBinStartTime   OBJECT-TYPE
     SYNTAX		DisplayString
     MAX-ACCESS	read-only
     STATUS		current
     DESCRIPTION "Collection start time of the bin."
     ::= { cienaCesPmIGMPCurrBinEntry 1 }
   
   cienaCesPmIGMPCurrBinClearedTime   OBJECT-TYPE
     SYNTAX		DisplayString
     MAX-ACCESS	read-only
     STATUS		current
     DESCRIPTION "Cleared time of the bin."
     ::= { cienaCesPmIGMPCurrBinEntry 2	}
                   
   cienaCesPmIGMPCurrBinDuration OBJECT-TYPE
     SYNTAX      Unsigned32 (1..65535)        
     UNITS		"minutes"
     MAX-ACCESS  read-only
     STATUS      current
     DESCRIPTION
             "Interval of the bin."
     ::= { cienaCesPmIGMPCurrBinEntry 3 }
  
  cienaCesPmIGMPCurrBinState OBJECT-TYPE
     SYNTAX      PmBinState 
     MAX-ACCESS  read-only
     STATUS      current
     DESCRIPTION
             "State of the bin."
     ::= { cienaCesPmIGMPCurrBinEntry 4 }
  
  cienaCesPmIGMPCurrBinIgmpnumJoins OBJECT-TYPE
     SYNTAX      Counter64 
     MAX-ACCESS  read-only
     STATUS      current
     DESCRIPTION
             "The total number of join messages received."
     ::= { cienaCesPmIGMPCurrBinEntry 5 }
 
 cienaCesPmIGMPCurrBinIgmpnumLeaves OBJECT-TYPE
     SYNTAX      Counter64 
     MAX-ACCESS  read-only
     STATUS      current
     DESCRIPTION
             "The total number of leave messages received."
     ::= { cienaCesPmIGMPCurrBinEntry 6 }
     
 cienaCesPmIGMPCurrBinIgmpnumQueries OBJECT-TYPE
     SYNTAX      Counter64 
     MAX-ACCESS  read-only
     STATUS      current
     DESCRIPTION
             "The total number of queries received."
     ::= { cienaCesPmIGMPCurrBinEntry 7 }

 cienaCesPmIGMPCurrBinIgmpnumQueryDiscards OBJECT-TYPE
     SYNTAX      Counter64 
     MAX-ACCESS  read-only
     STATUS      current
     DESCRIPTION
             "The total number of queries discarded."
     ::= { cienaCesPmIGMPCurrBinEntry 8 }

 cienaCesPmIGMPCurrBinIgmpnumQueryDiscardsQueryCameTooSoon OBJECT-TYPE
     SYNTAX      Counter64 
     MAX-ACCESS  read-only
     STATUS      current
     DESCRIPTION
             "The total number of queries discarded because the queries came too soon."
     ::= { cienaCesPmIGMPCurrBinEntry 9 }
 
  cienaCesPmIGMPCurrBinIgmpnumQueryDiscardsPortDown OBJECT-TYPE
     SYNTAX      Counter64 
     MAX-ACCESS  read-only
     STATUS      current
     DESCRIPTION
             "The total number queries discarded because the port was down."
     ::= { cienaCesPmIGMPCurrBinEntry 10 }

  cienaCesPmIGMPCurrBinIgmpnumQueryDiscardsPortBlock OBJECT-TYPE
     SYNTAX      Counter64 
     MAX-ACCESS  read-only
     STATUS      current
     DESCRIPTION
             "The total number of queries discarded because the port was blocked."
     ::= { cienaCesPmIGMPCurrBinEntry 11 }

   cienaCesPmIGMPCurrBinIgmpnumQueryDiscardsLiNoServerLI OBJECT-TYPE
     SYNTAX      Counter64 
     MAX-ACCESS  read-only
     STATUS      current
     DESCRIPTION
             "The total query discarded because of no server logical interfaces."
     ::= { cienaCesPmIGMPCurrBinEntry 12 }

   cienaCesPmIGMPCurrBinIgmpnumQueryTimeouts OBJECT-TYPE
     SYNTAX      Counter64 
     MAX-ACCESS  read-only
     STATUS      current
     DESCRIPTION
             "The total number of timeouts waiting for the
	      router to send query."
     ::= { cienaCesPmIGMPCurrBinEntry 13 }
	
   cienaCesPmIGMPCurrBinIgmpnumReplyTimeouts OBJECT-TYPE
     SYNTAX      Counter64 
     MAX-ACCESS  read-only
     STATUS      current
     DESCRIPTION
             "The total number of timeouts waiting for the
	      membership reports."
     ::= { cienaCesPmIGMPCurrBinEntry 14 }
   
   cienaCesPmIGMPCurrBinIgmpnumRouterDiscards OBJECT-TYPE
     SYNTAX      Counter64 
     MAX-ACCESS  read-only
     STATUS      current
     DESCRIPTION
             "The total number of messages discarded by the
	      router. This happens when a join comes in from 
	      a router port."
     ::= { cienaCesPmIGMPCurrBinEntry 15 }
 
   cienaCesPmIGMPCurrBinIgmpnumHostDiscards OBJECT-TYPE
     SYNTAX      Counter64 
     MAX-ACCESS  read-only
     STATUS      current
     DESCRIPTION
             "The total number of messages discarded by the
	      host. This happens when a join or leave comes 
	      in a port, but no router port is established."
     ::= { cienaCesPmIGMPCurrBinEntry 16 }
 
   cienaCesPmIGMPCurrBinIgmpnumBadChecksum OBJECT-TYPE
     SYNTAX      Counter64 
     MAX-ACCESS  read-only
     STATUS      current
     DESCRIPTION
             "The total number of packets received with bad 
	      IP checksum."
     ::= { cienaCesPmIGMPCurrBinEntry 17 }

   cienaCesPmIGMPCurrBinIgmpnumL2L3Mismatch OBJECT-TYPE
     SYNTAX      Counter64 
     MAX-ACCESS  read-only
     STATUS      current
     DESCRIPTION
             "The total number of IGMP Layer 2 and Layer 3 mismatch packets
	      received."
     ::= { cienaCesPmIGMPCurrBinEntry 18 }
    
   cienaCesPmIGMPCurrBinIgmpnumUnknownPktType OBJECT-TYPE
     SYNTAX      Counter64 
     MAX-ACCESS  read-only
     STATUS      current
     DESCRIPTION
             "The total number of unknown type IGMP 
	      packets received."
     ::= { cienaCesPmIGMPCurrBinEntry 19 }
    
   cienaCesPmIGMPCurrBinIgmpnumResourceExceed OBJECT-TYPE
     SYNTAX      Counter64 
     MAX-ACCESS  read-only
     STATUS      current
     DESCRIPTION
             "The total number of IGMP packets discarded because there were not enough resources
             to process these messages. This could happen when the rate of the incoming IGMP messages
             is very high."
     ::= { cienaCesPmIGMPCurrBinEntry 20 }
 
   cienaCesPmIGMPCurrBinIgmpnumQueryDiscardsSrcIpZero OBJECT-TYPE
     SYNTAX      Counter64 
     MAX-ACCESS  read-only
     STATUS      current
     DESCRIPTION
             "The total number of queries discarded because they had zero source IP."
     ::= { cienaCesPmIGMPCurrBinEntry 21 }

 
 --IGMP Profile Stats  for current 24 hour bin.
  
  cienaCesPmIGMPCurr24HBinTable OBJECT-TYPE
     SYNTAX     SEQUENCE OF CienaCesPmIGMPCurr24HBinEntry
     MAX-ACCESS not-accessible
     STATUS     current
     DESCRIPTION
            "The (conceptual) read-only table listing the bin statistics."  
     ::= { cienaCesPmIgmpStats 3 }
     
   cienaCesPmIGMPCurr24HBinEntry OBJECT-TYPE
     SYNTAX      CienaCesPmIGMPCurr24HBinEntry
     MAX-ACCESS  not-accessible
     STATUS      current
     DESCRIPTION
           "An entry (conceptual row) in the cienaPortPmIGMPCurr24HBinTable.

           This table lists the statistics for the current 24 hours bin." 
     INDEX {cienaCesPmInstanceIndex }
     ::= { cienaCesPmIGMPCurr24HBinTable 1 }
        
 CienaCesPmIGMPCurr24HBinEntry ::=  SEQUENCE {
 	 cienaCesPmIGMPCurr24HBinStartTime									DisplayString,
     cienaCesPmIGMPCurr24HBinEndTime									DisplayString,
     cienaCesPmIGMPCurr24HBinClearedTime								DisplayString,
     cienaCesPmIGMPCurr24HBinDuration									Unsigned32,   
     cienaCesPmIGMPCurr24HBinState										PmBinState,  
     cienaCesPmIGMPCurr24HBinIgmpnumJoins             					Counter64,
     cienaCesPmIGMPCurr24HBinIgmpnumLeaves            					Counter64,
     cienaCesPmIGMPCurr24HBinIgmpnumQueries           					Counter64,
     cienaCesPmIGMPCurr24HBinIgmpnumQueryDiscards     					Counter64,
     cienaCesPmIGMPCurr24HBinIgmpnumQueryDiscardsQueryCameTooSoon   	Counter64,
     cienaCesPmIGMPCurr24HBinIgmpnumQueryDiscardsPortDown    			Counter64,
     cienaCesPmIGMPCurr24HBinIgmpnumQueryDiscardsPortBlock   			Counter64,
     cienaCesPmIGMPCurr24HBinIgmpnumQueryDiscardsLiNoServerLI 			Counter64,
     cienaCesPmIGMPCurr24HBinIgmpnumQueryTimeouts             			Counter64,
     cienaCesPmIGMPCurr24HBinIgmpnumReplyTimeouts             			Counter64,
     cienaCesPmIGMPCurr24HBinIgmpnumRouterDiscards            			Counter64,
     cienaCesPmIGMPCurr24HBinIgmpnumHostDiscards              			Counter64,
     cienaCesPmIGMPCurr24HBinIgmpnumBadChecksum               			Counter64,
     cienaCesPmIGMPCurr24HBinIgmpnumL2L3Mismatch              			Counter64,
     cienaCesPmIGMPCurr24HBinIgmpnumUnknownPktType            			Counter64,
     cienaCesPmIGMPCurr24HBinIgmpnumResourceExceed		 				Counter64,
     cienaCesPmIGMPCurr24HBinIgmpnumQueryDiscardsSrcIpZero	 			Counter64   
   	} 
   
  cienaCesPmIGMPCurr24HBinStartTime   OBJECT-TYPE
     SYNTAX		DisplayString
     MAX-ACCESS	read-only
     STATUS		current
     DESCRIPTION "Collection start time of the bin."
     ::= { cienaCesPmIGMPCurr24HBinEntry 1 }
   
   cienaCesPmIGMPCurr24HBinEndTime 		OBJECT-TYPE
     SYNTAX		DisplayString
     MAX-ACCESS	read-only
     STATUS		current
     DESCRIPTION "Collection end time for the bin."
     ::= { cienaCesPmIGMPCurr24HBinEntry 2	}

    cienaCesPmIGMPCurr24HBinClearedTime   OBJECT-TYPE
     SYNTAX		DisplayString
     MAX-ACCESS	read-only
     STATUS		current
     DESCRIPTION "Cleared time of the bin."
     ::= { cienaCesPmIGMPCurr24HBinEntry 3	}
                   
   cienaCesPmIGMPCurr24HBinDuration OBJECT-TYPE
     SYNTAX      Unsigned32 (1..65535)        
     UNITS		"minutes"
     MAX-ACCESS  read-only
     STATUS      current
     DESCRIPTION
             "Duration of the bin."
     ::= { cienaCesPmIGMPCurr24HBinEntry 4 }
  
  cienaCesPmIGMPCurr24HBinState OBJECT-TYPE
     SYNTAX      PmBinState 
     MAX-ACCESS  read-only
     STATUS      current
     DESCRIPTION
             "State of the bin."
     ::= { cienaCesPmIGMPCurr24HBinEntry 5 }
  
  cienaCesPmIGMPCurr24HBinIgmpnumJoins OBJECT-TYPE
     SYNTAX      Counter64 
     MAX-ACCESS  read-only
     STATUS      current
     DESCRIPTION
             "The total number of join messages received."
     ::= { cienaCesPmIGMPCurr24HBinEntry 6 }
 
 cienaCesPmIGMPCurr24HBinIgmpnumLeaves OBJECT-TYPE
     SYNTAX      Counter64 
     MAX-ACCESS  read-only
     STATUS      current
     DESCRIPTION
             "The total number of leave messages received."
     ::= { cienaCesPmIGMPCurr24HBinEntry 7 }
     
 cienaCesPmIGMPCurr24HBinIgmpnumQueries OBJECT-TYPE
     SYNTAX      Counter64 
     MAX-ACCESS  read-only
     STATUS      current
     DESCRIPTION
             "The total number of queries received."
     ::= { cienaCesPmIGMPCurr24HBinEntry 8 }

 cienaCesPmIGMPCurr24HBinIgmpnumQueryDiscards OBJECT-TYPE
     SYNTAX      Counter64 
     MAX-ACCESS  read-only
     STATUS      current
     DESCRIPTION
             "The total number of queries discarded."
     ::= { cienaCesPmIGMPCurr24HBinEntry 9 }

 cienaCesPmIGMPCurr24HBinIgmpnumQueryDiscardsQueryCameTooSoon OBJECT-TYPE
     SYNTAX      Counter64 
     MAX-ACCESS  read-only
     STATUS      current
     DESCRIPTION
             "The total number of queries discarded because the queries came too soon."
     ::= { cienaCesPmIGMPCurr24HBinEntry 10 }
 
  cienaCesPmIGMPCurr24HBinIgmpnumQueryDiscardsPortDown OBJECT-TYPE
     SYNTAX      Counter64 
     MAX-ACCESS  read-only
     STATUS      current
     DESCRIPTION
             "The total number queries discarded because the port was down."
     ::= { cienaCesPmIGMPCurr24HBinEntry 11 }

  cienaCesPmIGMPCurr24HBinIgmpnumQueryDiscardsPortBlock OBJECT-TYPE
     SYNTAX      Counter64 
     MAX-ACCESS  read-only
     STATUS      current
     DESCRIPTION
             "The total number of queries discarded because the port was blocked."
     ::= { cienaCesPmIGMPCurr24HBinEntry 12 }

   cienaCesPmIGMPCurr24HBinIgmpnumQueryDiscardsLiNoServerLI OBJECT-TYPE
     SYNTAX      Counter64 
     MAX-ACCESS  read-only
     STATUS      current
     DESCRIPTION
             "The total number of queries discarded because of no server logical interfaces."
     ::= { cienaCesPmIGMPCurr24HBinEntry 13 }

   cienaCesPmIGMPCurr24HBinIgmpnumQueryTimeouts OBJECT-TYPE
     SYNTAX      Counter64 
     MAX-ACCESS  read-only
     STATUS      current
     DESCRIPTION
             "The total number of timeouts waiting for the
	      router to send query."
     ::= { cienaCesPmIGMPCurr24HBinEntry 14 }
	
   cienaCesPmIGMPCurr24HBinIgmpnumReplyTimeouts OBJECT-TYPE
     SYNTAX      Counter64 
     MAX-ACCESS  read-only
     STATUS      current
     DESCRIPTION
             "The total number of timeouts waiting for the
	      membership reports."
     ::= { cienaCesPmIGMPCurr24HBinEntry 15 }
   
   cienaCesPmIGMPCurr24HBinIgmpnumRouterDiscards OBJECT-TYPE
     SYNTAX      Counter64 
     MAX-ACCESS  read-only
     STATUS      current
     DESCRIPTION
             "The total number of messages discarded by the
	      router. This happens when a join comes in from 
	      a router port."
     ::= { cienaCesPmIGMPCurr24HBinEntry 16 }
 
   cienaCesPmIGMPCurr24HBinIgmpnumHostDiscards OBJECT-TYPE
     SYNTAX      Counter64 
     MAX-ACCESS  read-only
     STATUS      current
     DESCRIPTION
             "The total number of messages discarded by the
	      host. This happens when a join or leave comes 
	      in a port, but no router port is established."
     ::= { cienaCesPmIGMPCurr24HBinEntry 17 }
 
   cienaCesPmIGMPCurr24HBinIgmpnumBadChecksum OBJECT-TYPE
     SYNTAX      Counter64 
     MAX-ACCESS  read-only
     STATUS      current
     DESCRIPTION
             "The total number of packets received with bad 
	      IP checksum."
     ::= { cienaCesPmIGMPCurr24HBinEntry 18 }

   cienaCesPmIGMPCurr24HBinIgmpnumL2L3Mismatch OBJECT-TYPE
     SYNTAX      Counter64 
     MAX-ACCESS  read-only
     STATUS      current
     DESCRIPTION
             "The total number of IGMP Layer 2 and Layer 3 mismatch packets
	      received."
     ::= { cienaCesPmIGMPCurr24HBinEntry 19 }
    
   cienaCesPmIGMPCurr24HBinIgmpnumUnknownPktType OBJECT-TYPE
     SYNTAX      Counter64 
     MAX-ACCESS  read-only
     STATUS      current
     DESCRIPTION
             "The total number of unknown type IGMP 
	      packets received."
     ::= { cienaCesPmIGMPCurr24HBinEntry 20 }
    
   cienaCesPmIGMPCurr24HBinIgmpnumResourceExceed OBJECT-TYPE
     SYNTAX      Counter64 
     MAX-ACCESS  read-only
     STATUS      current
     DESCRIPTION
             "The total number of IGMP packets discarded because there were not enough resources
             to process these messages. This could happen when the rate of the incoming IGMP messages
             is very high."
     ::= { cienaCesPmIGMPCurr24HBinEntry 21 }
 
   cienaCesPmIGMPCurr24HBinIgmpnumQueryDiscardsSrcIpZero OBJECT-TYPE
     SYNTAX      Counter64 
     MAX-ACCESS  read-only
     STATUS      current
     DESCRIPTION
             "The total number of queries discarded because they had zero source IP."
     ::= { cienaCesPmIGMPCurr24HBinEntry 22 }

 --IGMP Profile Stats  for history 24 hour bin.
  
  cienaCesPmIGMPHist24HBinTable OBJECT-TYPE
     SYNTAX     SEQUENCE OF CienaCesPmIGMPHist24HBinEntry
     MAX-ACCESS not-accessible
     STATUS     current
     DESCRIPTION
            "The (conceptual) read-only Table listing the Bin Statistics"  
     ::= { cienaCesPmIgmpStats 4}
     
   cienaCesPmIGMPHist24HBinEntry OBJECT-TYPE
     SYNTAX      CienaCesPmIGMPHist24HBinEntry
     MAX-ACCESS  not-accessible
     STATUS      current
     DESCRIPTION
           "An entry (conceptual row) in the cienaPortPmIGMPHist24HBinTable.

           This table lists the statistics for the history 24 hours bin." 
     INDEX {cienaCesPmInstanceIndex}
     ::= { cienaCesPmIGMPHist24HBinTable 1 }
        
 CienaCesPmIGMPHist24HBinEntry ::=  SEQUENCE {
 	 cienaCesPmIGMPHist24HBinStartTime			DisplayString,
     cienaCesPmIGMPHist24HBinEndTime			DisplayString,
     cienaCesPmIGMPHist24HBinDuration			Unsigned32,   
     cienaCesPmIGMPHist24HBinState				PmBinState,  
     cienaCesPmIGMPHist24HBinIgmpnumJoins             Counter64,
     cienaCesPmIGMPHist24HBinIgmpnumLeaves            Counter64,
     cienaCesPmIGMPHist24HBinIgmpnumQueries           Counter64,
     cienaCesPmIGMPHist24HBinIgmpnumQueryDiscards     Counter64,
     cienaCesPmIGMPHist24HBinIgmpnumQueryDiscardsQueryCameTooSoon   Counter64,
     cienaCesPmIGMPHist24HBinIgmpnumQueryDiscardsPortDown    Counter64,
     cienaCesPmIGMPHist24HBinIgmpnumQueryDiscardsPortBlock   Counter64,
     cienaCesPmIGMPHist24HBinIgmpnumQueryDiscardsLiNoServerLI Counter64,
     cienaCesPmIGMPHist24HBinIgmpnumQueryTimeouts             Counter64,
     cienaCesPmIGMPHist24HBinIgmpnumReplyTimeouts             Counter64,
     cienaCesPmIGMPHist24HBinIgmpnumRouterDiscards            Counter64,
     cienaCesPmIGMPHist24HBinIgmpnumHostDiscards              Counter64,
     cienaCesPmIGMPHist24HBinIgmpnumBadChecksum               Counter64,
     cienaCesPmIGMPHist24HBinIgmpnumL2L3Mismatch              Counter64,
     cienaCesPmIGMPHist24HBinIgmpnumUnknownPktType            Counter64,
     cienaCesPmIGMPHist24HBinIgmpnumResourceExceed		 Counter64,
     cienaCesPmIGMPHist24HBinIgmpnumQueryDiscardsSrcIpZero	 Counter64,   
     cienaCesPmIGMPHist24HBinClearTime                       DisplayString
   	}          

   cienaCesPmIGMPHist24HBinStartTime   OBJECT-TYPE
     SYNTAX		DisplayString
     MAX-ACCESS	read-only
     STATUS		current
     DESCRIPTION "Collection start time of the bin."
     ::= { cienaCesPmIGMPHist24HBinEntry 1}
   
   cienaCesPmIGMPHist24HBinEndTime 		OBJECT-TYPE
     SYNTAX		DisplayString
     MAX-ACCESS	read-only
     STATUS		current
     DESCRIPTION "Collection end time for the bin."
     ::= { cienaCesPmIGMPHist24HBinEntry 2	}

   cienaCesPmIGMPHist24HBinDuration OBJECT-TYPE
     SYNTAX      Unsigned32 (1..65535)        
     UNITS		"minutes"
     MAX-ACCESS  read-only
     STATUS      current
     DESCRIPTION
             "Duration of the bin."
     ::= { cienaCesPmIGMPHist24HBinEntry 3 }
  
  cienaCesPmIGMPHist24HBinState OBJECT-TYPE
     SYNTAX      PmBinState 
     MAX-ACCESS  read-only
     STATUS      current
     DESCRIPTION
             "State of the bin."
     ::= { cienaCesPmIGMPHist24HBinEntry 4 }
  
  cienaCesPmIGMPHist24HBinIgmpnumJoins OBJECT-TYPE
     SYNTAX      Counter64 
     MAX-ACCESS  read-only
     STATUS      current
     DESCRIPTION
             "The total number of join messages received."
     ::= { cienaCesPmIGMPHist24HBinEntry 5 }
 
 cienaCesPmIGMPHist24HBinIgmpnumLeaves OBJECT-TYPE
     SYNTAX      Counter64 
     MAX-ACCESS  read-only
     STATUS      current
     DESCRIPTION
             "The total number of leave messages received."
     ::= { cienaCesPmIGMPHist24HBinEntry 6 }
     
 cienaCesPmIGMPHist24HBinIgmpnumQueries OBJECT-TYPE
     SYNTAX      Counter64 
     MAX-ACCESS  read-only
     STATUS      current
     DESCRIPTION
             "The total number of queries received."
     ::= { cienaCesPmIGMPHist24HBinEntry 7 }

 cienaCesPmIGMPHist24HBinIgmpnumQueryDiscards OBJECT-TYPE
     SYNTAX      Counter64 
     MAX-ACCESS  read-only
     STATUS      current
     DESCRIPTION
             "The total number of queries discarded."
     ::= { cienaCesPmIGMPHist24HBinEntry 8 }

 cienaCesPmIGMPHist24HBinIgmpnumQueryDiscardsQueryCameTooSoon OBJECT-TYPE
     SYNTAX      Counter64 
     MAX-ACCESS  read-only
     STATUS      current
     DESCRIPTION
             "The total number of queries discarded because the queries came too soon."
     ::= { cienaCesPmIGMPHist24HBinEntry 9 }
 
  cienaCesPmIGMPHist24HBinIgmpnumQueryDiscardsPortDown OBJECT-TYPE
     SYNTAX      Counter64 
     MAX-ACCESS  read-only
     STATUS      current
     DESCRIPTION
             "The total number queries discarded because the port was down."
     ::= { cienaCesPmIGMPHist24HBinEntry 10 }

  cienaCesPmIGMPHist24HBinIgmpnumQueryDiscardsPortBlock OBJECT-TYPE
     SYNTAX      Counter64 
     MAX-ACCESS  read-only
     STATUS      current
     DESCRIPTION
             "The total number of queries discarded because the port was blocked."
     ::= { cienaCesPmIGMPHist24HBinEntry 11 }

   cienaCesPmIGMPHist24HBinIgmpnumQueryDiscardsLiNoServerLI OBJECT-TYPE
     SYNTAX      Counter64 
     MAX-ACCESS  read-only
     STATUS      current
     DESCRIPTION
             "The total number of queries discarded because of no server logical interfaces."
     ::= { cienaCesPmIGMPHist24HBinEntry 12 }

   cienaCesPmIGMPHist24HBinIgmpnumQueryTimeouts OBJECT-TYPE
     SYNTAX      Counter64 
     MAX-ACCESS  read-only
     STATUS      current
     DESCRIPTION
             "The total number of timeouts waiting for the
	      router to send query."
     ::= { cienaCesPmIGMPHist24HBinEntry 13 }
	
   cienaCesPmIGMPHist24HBinIgmpnumReplyTimeouts OBJECT-TYPE
     SYNTAX      Counter64 
     MAX-ACCESS  read-only
     STATUS      current
     DESCRIPTION
             "The total number of timeouts waiting for the
	      membership reports."
     ::= { cienaCesPmIGMPHist24HBinEntry 14 }
   
   cienaCesPmIGMPHist24HBinIgmpnumRouterDiscards OBJECT-TYPE
     SYNTAX      Counter64 
     MAX-ACCESS  read-only
     STATUS      current
     DESCRIPTION
             "The total number of messages discarded by the
	      router. This happens when a join comes in from 
	      a router port."
     ::= { cienaCesPmIGMPHist24HBinEntry 15 }
 
   cienaCesPmIGMPHist24HBinIgmpnumHostDiscards OBJECT-TYPE
     SYNTAX      Counter64 
     MAX-ACCESS  read-only
     STATUS      current
     DESCRIPTION
             "The total number of messages discarded by the
	      host. This happens when a join or leave comes 
	      in a port, but no router port is established."
     ::= { cienaCesPmIGMPHist24HBinEntry 16 }
 
   cienaCesPmIGMPHist24HBinIgmpnumBadChecksum OBJECT-TYPE
     SYNTAX      Counter64 
     MAX-ACCESS  read-only
     STATUS      current
     DESCRIPTION
             "The total number of packets received with bad 
	      IP checksum."
     ::= { cienaCesPmIGMPHist24HBinEntry 17 }

   cienaCesPmIGMPHist24HBinIgmpnumL2L3Mismatch OBJECT-TYPE
     SYNTAX      Counter64 
     MAX-ACCESS  read-only
     STATUS      current
     DESCRIPTION
             "The total number of IGMP Layer 2 and Layer 3 mismatch packets
	      received."
     ::= { cienaCesPmIGMPHist24HBinEntry 18 }
    
   cienaCesPmIGMPHist24HBinIgmpnumUnknownPktType OBJECT-TYPE
     SYNTAX      Counter64 
     MAX-ACCESS  read-only
     STATUS      current
     DESCRIPTION
             "The total number of unknown type IGMP 
	      packets received."
     ::= { cienaCesPmIGMPHist24HBinEntry 19 }
    
   cienaCesPmIGMPHist24HBinIgmpnumResourceExceed OBJECT-TYPE
     SYNTAX      Counter64 
     MAX-ACCESS  read-only
     STATUS      current
     DESCRIPTION
             "The total number of IGMP packets discarded because there were not enough resources
             to process these messages. This could happen when the rate of the incoming IGMP messages
             is very high."
     ::= { cienaCesPmIGMPHist24HBinEntry 20 }
 
   cienaCesPmIGMPHist24HBinIgmpnumQueryDiscardsSrcIpZero OBJECT-TYPE
     SYNTAX      Counter64 
     MAX-ACCESS  read-only
     STATUS      current
     DESCRIPTION
             "The total number of queries discarded because they had zero source IP."
     ::= { cienaCesPmIGMPHist24HBinEntry 21 }

   cienaCesPmIGMPHist24HBinClearTime OBJECT-TYPE
     SYNTAX      DisplayString
     MAX-ACCESS  read-only
     STATUS      current
     DESCRIPTION "Collection clear time of the bin."
     ::= { cienaCesPmIGMPHist24HBinEntry 22 }

 
 --IGMP Profile Stats  
  
  cienaCesPmIGMPAllTimeBinTable OBJECT-TYPE
     SYNTAX     SEQUENCE OF CienaCesPmIGMPAllTimeBinEntry
     MAX-ACCESS not-accessible
     STATUS     deprecated
     DESCRIPTION
            "The (conceptual) read-only table listing the bin statistics."  
     ::= { cienaCesPmIgmpStats 5 }
     
   cienaCesPmIGMPAllTimeBinEntry OBJECT-TYPE
     SYNTAX      CienaCesPmIGMPAllTimeBinEntry
     MAX-ACCESS  not-accessible
     STATUS      deprecated
     DESCRIPTION
           "An entry (conceptual row) in the cienaPortPmIGMPAllTimeBinTable.

           This table lists the statistics for the All Time bin of the PM instance." 
     INDEX {cienaCesPmInstanceIndex}
     ::= { cienaCesPmIGMPAllTimeBinTable 1 }
        
 CienaCesPmIGMPAllTimeBinEntry ::=  SEQUENCE {
 	 cienaCesPmIGMPAllTimeBinIgmpnumJoins             	Counter64,
     cienaCesPmIGMPAllTimeBinIgmpnumLeaves            	Counter64,
     cienaCesPmIGMPAllTimeBinIgmpnumQueries           	Counter64,
     cienaCesPmIGMPAllTimeBinIgmpnumQueryDiscards     				Counter64,
     cienaCesPmIGMPAllTimeBinIgmpnumQueryDiscardsQueryCameTooSoon   Counter64,   
     cienaCesPmIGMPAllTimeBinIgmpnumQueryDiscardsPortDown    			Counter64,
     cienaCesPmIGMPAllTimeBinIgmpnumQueryDiscardsPortBlock   			Counter64, 
     cienaCesPmIGMPAllTimeBinIgmpnumQueryDiscardsLiNoServerLI Counter64,
     cienaCesPmIGMPAllTimeBinIgmpnumQueryTimeouts             Counter64,
     cienaCesPmIGMPAllTimeBinIgmpnumReplyTimeouts             Counter64,
     cienaCesPmIGMPAllTimeBinIgmpnumRouterDiscards            Counter64,   
     cienaCesPmIGMPAllTimeBinIgmpnumHostDiscards              Counter64,
     cienaCesPmIGMPAllTimeBinIgmpnumBadChecksum               Counter64,
     cienaCesPmIGMPAllTimeBinIgmpnumL2L3Mismatch              Counter64,
     cienaCesPmIGMPAllTimeBinIgmpnumUnknownPktType            Counter64,
     cienaCesPmIGMPAllTimeBinIgmpnumResourceExceed		 Counter64,   
     cienaCesPmIGMPAllTimeBinIgmpnumQueryDiscardsSrcIpZero	 Counter64   
   	}          
   
   cienaCesPmIGMPAllTimeBinIgmpnumJoins OBJECT-TYPE
     SYNTAX      Counter64 
     MAX-ACCESS  read-only
     STATUS      deprecated
     DESCRIPTION
             "The total number of join messages received."
     ::= { cienaCesPmIGMPAllTimeBinEntry 1 }
 
 cienaCesPmIGMPAllTimeBinIgmpnumLeaves OBJECT-TYPE
     SYNTAX      Counter64 
     MAX-ACCESS  read-only
     STATUS      deprecated
     DESCRIPTION
             "The total number of leave messages received."
     ::= { cienaCesPmIGMPAllTimeBinEntry 2 }
     
 cienaCesPmIGMPAllTimeBinIgmpnumQueries OBJECT-TYPE
     SYNTAX      Counter64 
     MAX-ACCESS  read-only
     STATUS      deprecated
     DESCRIPTION
             "The total number of queries received."
     ::= { cienaCesPmIGMPAllTimeBinEntry 3 }

 cienaCesPmIGMPAllTimeBinIgmpnumQueryDiscards OBJECT-TYPE
     SYNTAX      Counter64 
     MAX-ACCESS  read-only
     STATUS      deprecated
     DESCRIPTION
             "The total number of queries discarded."
     ::= { cienaCesPmIGMPAllTimeBinEntry 4 }

 cienaCesPmIGMPAllTimeBinIgmpnumQueryDiscardsQueryCameTooSoon OBJECT-TYPE
     SYNTAX      Counter64 
     MAX-ACCESS  read-only
     STATUS      deprecated
     DESCRIPTION
             "The total number of queries discarded because the queries came too soon."
     ::= { cienaCesPmIGMPAllTimeBinEntry 5 }
 
  cienaCesPmIGMPAllTimeBinIgmpnumQueryDiscardsPortDown OBJECT-TYPE
     SYNTAX      Counter64 
     MAX-ACCESS  read-only
     STATUS      deprecated
     DESCRIPTION
             "The total number queries discarded because the port was down."
     ::= { cienaCesPmIGMPAllTimeBinEntry 6 }

  cienaCesPmIGMPAllTimeBinIgmpnumQueryDiscardsPortBlock OBJECT-TYPE
     SYNTAX      Counter64 
     MAX-ACCESS  read-only
     STATUS      deprecated
     DESCRIPTION
             "The total number of queries discarded because the port was blocked."
     ::= { cienaCesPmIGMPAllTimeBinEntry 7 }

   cienaCesPmIGMPAllTimeBinIgmpnumQueryDiscardsLiNoServerLI OBJECT-TYPE
     SYNTAX      Counter64 
     MAX-ACCESS  read-only
     STATUS      deprecated
     DESCRIPTION
             "The total number of queries discarded because of no server logical interfaces."
     ::= { cienaCesPmIGMPAllTimeBinEntry 8 }

   cienaCesPmIGMPAllTimeBinIgmpnumQueryTimeouts OBJECT-TYPE
     SYNTAX      Counter64 
     MAX-ACCESS  read-only
     STATUS      deprecated
     DESCRIPTION
             "The total number of timeouts waiting for the
	      router to send query."
     ::= { cienaCesPmIGMPAllTimeBinEntry 9 }
	
   cienaCesPmIGMPAllTimeBinIgmpnumReplyTimeouts OBJECT-TYPE
     SYNTAX      Counter64 
     MAX-ACCESS  read-only
     STATUS      deprecated
     DESCRIPTION
             "The total number of timeouts waiting for the
	      membership reports."
     ::= { cienaCesPmIGMPAllTimeBinEntry 10 }
   
   cienaCesPmIGMPAllTimeBinIgmpnumRouterDiscards OBJECT-TYPE
     SYNTAX      Counter64 
     MAX-ACCESS  read-only
     STATUS      deprecated
     DESCRIPTION
             "The total number of messages discarded by the
	      router. This happens when a join comes in from 
	      a router port."
     ::= { cienaCesPmIGMPAllTimeBinEntry 11 }
 
   cienaCesPmIGMPAllTimeBinIgmpnumHostDiscards OBJECT-TYPE
     SYNTAX      Counter64 
     MAX-ACCESS  read-only
     STATUS      deprecated
     DESCRIPTION
             "The total number of messages discarded by the
	      host. This happens when a join or leave comes 
	      in a port, but no router port is established."
     ::= { cienaCesPmIGMPAllTimeBinEntry 12 }
 
   cienaCesPmIGMPAllTimeBinIgmpnumBadChecksum OBJECT-TYPE
     SYNTAX      Counter64 
     MAX-ACCESS  read-only
     STATUS      deprecated
     DESCRIPTION
             "The total number of packets received with bad 
	      IP checksum."
     ::= { cienaCesPmIGMPAllTimeBinEntry 13 }

   cienaCesPmIGMPAllTimeBinIgmpnumL2L3Mismatch OBJECT-TYPE
     SYNTAX      Counter64 
     MAX-ACCESS  read-only
     STATUS      deprecated
     DESCRIPTION
             "The total number of IGMP Layer 2 and Layer 3 mismatch packets
	      received."
     ::= { cienaCesPmIGMPAllTimeBinEntry 14 }
    
   cienaCesPmIGMPAllTimeBinIgmpnumUnknownPktType OBJECT-TYPE
     SYNTAX      Counter64 
     MAX-ACCESS  read-only
     STATUS      deprecated
     DESCRIPTION
             "The total number of unknown type IGMP 
	      packets received."
     ::= { cienaCesPmIGMPAllTimeBinEntry 15 }
    
   cienaCesPmIGMPAllTimeBinIgmpnumResourceExceed OBJECT-TYPE
     SYNTAX      Counter64 
     MAX-ACCESS  read-only
     STATUS      deprecated
     DESCRIPTION
             "The total number of IGMP packets discarded because there were not enough resources
             to process these messages. This could happen when the rate of the incoming IGMP messages
             is very high."
     ::= { cienaCesPmIGMPAllTimeBinEntry 16 }
 
   cienaCesPmIGMPAllTimeBinIgmpnumQueryDiscardsSrcIpZero OBJECT-TYPE
     SYNTAX      Counter64 
     MAX-ACCESS  read-only
     STATUS      deprecated
     DESCRIPTION
             "The total number of queries discarded because they had zero source IP."
     ::= { cienaCesPmIGMPAllTimeBinEntry 17 }


   --IGMP Profile Stats, statistics bin
  
  cienaCesPmIGMPStatisticsBinTable OBJECT-TYPE
     SYNTAX     SEQUENCE OF CienaCesPmIGMPStatisticsBinEntry
     MAX-ACCESS not-accessible
     STATUS     current
     DESCRIPTION "The (conceptual) read-only table listing the bin statistics."
     ::= { cienaCesPmIgmpStats 6 }
     
   cienaCesPmIGMPStatisticsBinEntry OBJECT-TYPE
     SYNTAX      CienaCesPmIGMPStatisticsBinEntry
     MAX-ACCESS  not-accessible
     STATUS      current
     DESCRIPTION
           "An entry (conceptual row) in the cienaCesPmIGMPStatisticsBinTable.
           This table lists the statistics for the statistics bin of the PM instance." 
     INDEX {cienaCesPmInstanceIndex}
     ::= { cienaCesPmIGMPStatisticsBinTable 1 }
        
   CienaCesPmIGMPStatisticsBinEntry ::=  SEQUENCE {
     cienaCesPmIGMPStatsBinStartTime                                DisplayString,
     cienaCesPmIGMPStatsBinClearTime                                DisplayString,
     cienaCesPmIGMPStatsBinIgmpnumJoins                             Counter64,
     cienaCesPmIGMPStatsBinIgmpnumLeaves                            Counter64,
     cienaCesPmIGMPStatsBinIgmpnumQueries                           Counter64,
     cienaCesPmIGMPStatsBinIgmpnumQueryDiscards                     Counter64,
     cienaCesPmIGMPStatsBinIgmpnumQueryDiscardsQueryCameTooSoon     Counter64,   
     cienaCesPmIGMPStatsBinIgmpnumQueryDiscardsPortDown             Counter64,
     cienaCesPmIGMPStatsBinIgmpnumQueryDiscardsPortBlock            Counter64, 
     cienaCesPmIGMPStatsBinIgmpnumQueryDiscardsLiNoServerLI         Counter64,
     cienaCesPmIGMPStatsBinIgmpnumQueryTimeouts                     Counter64,
     cienaCesPmIGMPStatsBinIgmpnumReplyTimeouts                     Counter64,
     cienaCesPmIGMPStatsBinIgmpnumRouterDiscards                    Counter64,   
     cienaCesPmIGMPStatsBinIgmpnumHostDiscards                      Counter64,
     cienaCesPmIGMPStatsBinIgmpnumBadChecksum                       Counter64,
     cienaCesPmIGMPStatsBinIgmpnumL2L3Mismatch                      Counter64,
     cienaCesPmIGMPStatsBinIgmpnumUnknownPktType                    Counter64,
     cienaCesPmIGMPStatsBinIgmpnumResourceExceed                    Counter64,   
     cienaCesPmIGMPStatsBinIgmpnumQueryDiscardsSrcIpZero            Counter64   
   }          
   
   cienaCesPmIGMPStatsBinStartTime OBJECT-TYPE
     SYNTAX      DisplayString
     MAX-ACCESS  read-only
     STATUS      current
     DESCRIPTION "Collection start time of the bin."
     ::= { cienaCesPmIGMPStatisticsBinEntry 1 }

   cienaCesPmIGMPStatsBinClearTime OBJECT-TYPE
     SYNTAX      DisplayString
     MAX-ACCESS  read-only
     STATUS      current
     DESCRIPTION "Collection clear time of the bin."
     ::= { cienaCesPmIGMPStatisticsBinEntry 2 }

   cienaCesPmIGMPStatsBinIgmpnumJoins OBJECT-TYPE
     SYNTAX      Counter64 
     MAX-ACCESS  read-only
     STATUS      current
     DESCRIPTION
             "The total number of join messages received."
     ::= { cienaCesPmIGMPStatisticsBinEntry 3 }
 
   cienaCesPmIGMPStatsBinIgmpnumLeaves OBJECT-TYPE
     SYNTAX      Counter64 
     MAX-ACCESS  read-only
     STATUS      current
     DESCRIPTION
             "The total number of leave messages received."
     ::= { cienaCesPmIGMPStatisticsBinEntry 4 }
     
   cienaCesPmIGMPStatsBinIgmpnumQueries OBJECT-TYPE
     SYNTAX      Counter64 
     MAX-ACCESS  read-only
     STATUS      current
     DESCRIPTION
             "The total number of queries received."
     ::= { cienaCesPmIGMPStatisticsBinEntry 5 }

   cienaCesPmIGMPStatsBinIgmpnumQueryDiscards OBJECT-TYPE
     SYNTAX      Counter64 
     MAX-ACCESS  read-only
     STATUS      current
     DESCRIPTION
             "The total number of queries discarded."
     ::= { cienaCesPmIGMPStatisticsBinEntry 6 }

   cienaCesPmIGMPStatsBinIgmpnumQueryDiscardsQueryCameTooSoon OBJECT-TYPE
     SYNTAX      Counter64 
     MAX-ACCESS  read-only
     STATUS      current
     DESCRIPTION
             "The total number of queries discarded because the queries came too soon."
     ::= { cienaCesPmIGMPStatisticsBinEntry 7 }
 
   cienaCesPmIGMPStatsBinIgmpnumQueryDiscardsPortDown OBJECT-TYPE
     SYNTAX      Counter64 
     MAX-ACCESS  read-only
     STATUS      current
     DESCRIPTION
             "The total number queries discarded because the port was down."
     ::= { cienaCesPmIGMPStatisticsBinEntry 8 }

   cienaCesPmIGMPStatsBinIgmpnumQueryDiscardsPortBlock OBJECT-TYPE
     SYNTAX      Counter64 
     MAX-ACCESS  read-only
     STATUS      current
     DESCRIPTION
             "The total number of queries discarded because the port was blocked."
     ::= { cienaCesPmIGMPStatisticsBinEntry 9 }

   cienaCesPmIGMPStatsBinIgmpnumQueryDiscardsLiNoServerLI OBJECT-TYPE
     SYNTAX      Counter64 
     MAX-ACCESS  read-only
     STATUS      current
     DESCRIPTION
             "The total number of queries discarded because of no server logical interfaces."
     ::= { cienaCesPmIGMPStatisticsBinEntry 10 }

   cienaCesPmIGMPStatsBinIgmpnumQueryTimeouts OBJECT-TYPE
     SYNTAX      Counter64 
     MAX-ACCESS  read-only
     STATUS      current
     DESCRIPTION
             "The total number of timeouts waiting for the
             router to send query."
     ::= { cienaCesPmIGMPStatisticsBinEntry 11 }
	
   cienaCesPmIGMPStatsBinIgmpnumReplyTimeouts OBJECT-TYPE
     SYNTAX      Counter64 
     MAX-ACCESS  read-only
     STATUS      current
     DESCRIPTION
             "The total number of timeouts waiting for the
             membership reports."
     ::= { cienaCesPmIGMPStatisticsBinEntry 12 }
   
   cienaCesPmIGMPStatsBinIgmpnumRouterDiscards OBJECT-TYPE
     SYNTAX      Counter64 
     MAX-ACCESS  read-only
     STATUS      current
     DESCRIPTION
             "The total number of messages discarded by the
             router. This happens when a join comes in from 
             a router port."
     ::= { cienaCesPmIGMPStatisticsBinEntry 13 }
 
   cienaCesPmIGMPStatsBinIgmpnumHostDiscards OBJECT-TYPE
     SYNTAX      Counter64 
     MAX-ACCESS  read-only
     STATUS      current
     DESCRIPTION
             "The total number of messages discarded by the
             host. This happens when a join or leave comes 
             in a port, but no router port is established."
     ::= { cienaCesPmIGMPStatisticsBinEntry 14 }
 
   cienaCesPmIGMPStatsBinIgmpnumBadChecksum OBJECT-TYPE
     SYNTAX      Counter64 
     MAX-ACCESS  read-only
     STATUS      current
     DESCRIPTION
             "The total number of packets received with bad 
             IP checksum."
     ::= { cienaCesPmIGMPStatisticsBinEntry 15 }

   cienaCesPmIGMPStatsBinIgmpnumL2L3Mismatch OBJECT-TYPE
     SYNTAX      Counter64 
     MAX-ACCESS  read-only
     STATUS      current
     DESCRIPTION
             "The total number of IGMP Layer 2 and Layer 3 mismatch packets
             received."
     ::= { cienaCesPmIGMPStatisticsBinEntry 16 }
    
   cienaCesPmIGMPStatsBinIgmpnumUnknownPktType OBJECT-TYPE
     SYNTAX      Counter64 
     MAX-ACCESS  read-only
     STATUS      current
     DESCRIPTION
             "The total number of unknown type IGMP 
             packets received."
     ::= { cienaCesPmIGMPStatisticsBinEntry 17 }
    
   cienaCesPmIGMPStatsBinIgmpnumResourceExceed OBJECT-TYPE
     SYNTAX      Counter64 
     MAX-ACCESS  read-only
     STATUS      current
     DESCRIPTION
             "The total number of IGMP packets discarded because there were not enough resources
             to process these messages. This could happen when the rate of the incoming IGMP messages
             is very high."
     ::= { cienaCesPmIGMPStatisticsBinEntry 18 }
 
   cienaCesPmIGMPStatsBinIgmpnumQueryDiscardsSrcIpZero OBJECT-TYPE
     SYNTAX      Counter64 
     MAX-ACCESS  read-only
     STATUS      current
     DESCRIPTION
             "The total number of queries discarded because they had zero source IP."
     ::= { cienaCesPmIGMPStatisticsBinEntry 19 }


   --IGMP Profile Stats, total statistics bin
  
  cienaCesPmIGMPTotalStatisticsBinTable OBJECT-TYPE
     SYNTAX     SEQUENCE OF CienaCesPmIGMPTotalStatisticsBinEntry
     MAX-ACCESS not-accessible
     STATUS     current
     DESCRIPTION "The (conceptual) read-only table listing the bin statistics."
     ::= { cienaCesPmIgmpStats 7 }
     
   cienaCesPmIGMPTotalStatisticsBinEntry OBJECT-TYPE
     SYNTAX      CienaCesPmIGMPTotalStatisticsBinEntry
     MAX-ACCESS  not-accessible
     STATUS      current
     DESCRIPTION
           "An entry (conceptual row) in the cienaCesPmIGMPTotalStatisticsBinTable.
           This table lists the statistics for the total statistics bin of the PM instance." 
     INDEX {cienaCesPmInstanceIndex}
     ::= { cienaCesPmIGMPTotalStatisticsBinTable 1 }
        
   CienaCesPmIGMPTotalStatisticsBinEntry ::=  SEQUENCE {
     cienaCesPmIGMPTotalStatsBinStartTime                             DisplayString,
     cienaCesPmIGMPTotalStatsBinIgmpnumJoins                          Counter64,
     cienaCesPmIGMPTotalStatsBinIgmpnumLeaves                         Counter64,
     cienaCesPmIGMPTotalStatsBinIgmpnumQueries                        Counter64,
     cienaCesPmIGMPTotalStatsBinIgmpnumQueryDiscards                  Counter64,
     cienaCesPmIGMPTotalStatsBinIgmpnumQueryDiscardsQueryCameTooSoon  Counter64,   
     cienaCesPmIGMPTotalStatsBinIgmpnumQueryDiscardsPortDown          Counter64,
     cienaCesPmIGMPTotalStatsBinIgmpnumQueryDiscardsPortBlock         Counter64, 
     cienaCesPmIGMPTotalStatsBinIgmpnumQueryDiscardsLiNoServerLI      Counter64,
     cienaCesPmIGMPTotalStatsBinIgmpnumQueryTimeouts                  Counter64,
     cienaCesPmIGMPTotalStatsBinIgmpnumReplyTimeouts                  Counter64,
     cienaCesPmIGMPTotalStatsBinIgmpnumRouterDiscards                 Counter64,   
     cienaCesPmIGMPTotalStatsBinIgmpnumHostDiscards                   Counter64,
     cienaCesPmIGMPTotalStatsBinIgmpnumBadChecksum                    Counter64,
     cienaCesPmIGMPTotalStatsBinIgmpnumL2L3Mismatch                   Counter64,
     cienaCesPmIGMPTotalStatsBinIgmpnumUnknownPktType                 Counter64,
     cienaCesPmIGMPTotalStatsBinIgmpnumResourceExceed                 Counter64,   
     cienaCesPmIGMPTotalStatsBinIgmpnumQueryDiscardsSrcIpZero         Counter64   
   }          
   
   cienaCesPmIGMPTotalStatsBinStartTime OBJECT-TYPE
     SYNTAX      DisplayString
     MAX-ACCESS  read-only
     STATUS      current
     DESCRIPTION "Collection start time of the bin."
     ::= { cienaCesPmIGMPTotalStatisticsBinEntry 1 }

   cienaCesPmIGMPTotalStatsBinIgmpnumJoins OBJECT-TYPE
     SYNTAX      Counter64 
     MAX-ACCESS  read-only
     STATUS      current
     DESCRIPTION
             "The total number of join messages received."
     ::= { cienaCesPmIGMPTotalStatisticsBinEntry 2 }
 
   cienaCesPmIGMPTotalStatsBinIgmpnumLeaves OBJECT-TYPE
     SYNTAX      Counter64 
     MAX-ACCESS  read-only
     STATUS      current
     DESCRIPTION
             "The total number of leave messages received."
     ::= { cienaCesPmIGMPTotalStatisticsBinEntry 3 }
     
   cienaCesPmIGMPTotalStatsBinIgmpnumQueries OBJECT-TYPE
     SYNTAX      Counter64 
     MAX-ACCESS  read-only
     STATUS      current
     DESCRIPTION
             "The total number of queries received."
     ::= { cienaCesPmIGMPTotalStatisticsBinEntry 4 }

   cienaCesPmIGMPTotalStatsBinIgmpnumQueryDiscards OBJECT-TYPE
     SYNTAX      Counter64 
     MAX-ACCESS  read-only
     STATUS      current
     DESCRIPTION
             "The total number of queries discarded."
     ::= { cienaCesPmIGMPTotalStatisticsBinEntry 5 }

   cienaCesPmIGMPTotalStatsBinIgmpnumQueryDiscardsQueryCameTooSoon OBJECT-TYPE
     SYNTAX      Counter64 
     MAX-ACCESS  read-only
     STATUS      current
     DESCRIPTION
             "The total number of queries discarded because the queries came too soon."
     ::= { cienaCesPmIGMPTotalStatisticsBinEntry 6 }
 
   cienaCesPmIGMPTotalStatsBinIgmpnumQueryDiscardsPortDown OBJECT-TYPE
     SYNTAX      Counter64 
     MAX-ACCESS  read-only
     STATUS      current
     DESCRIPTION
             "The total number queries discarded because the port was down."
     ::= { cienaCesPmIGMPTotalStatisticsBinEntry 7 }

   cienaCesPmIGMPTotalStatsBinIgmpnumQueryDiscardsPortBlock OBJECT-TYPE
     SYNTAX      Counter64 
     MAX-ACCESS  read-only
     STATUS      current
     DESCRIPTION
             "The total number of queries discarded because the port was blocked."
     ::= { cienaCesPmIGMPTotalStatisticsBinEntry 8 }

   cienaCesPmIGMPTotalStatsBinIgmpnumQueryDiscardsLiNoServerLI OBJECT-TYPE
     SYNTAX      Counter64 
     MAX-ACCESS  read-only
     STATUS      current
     DESCRIPTION
             "The total number of queries discarded because of no server logical interfaces."
     ::= { cienaCesPmIGMPTotalStatisticsBinEntry 9 }

   cienaCesPmIGMPTotalStatsBinIgmpnumQueryTimeouts OBJECT-TYPE
     SYNTAX      Counter64 
     MAX-ACCESS  read-only
     STATUS      current
     DESCRIPTION
             "The total number of timeouts waiting for the
             router to send query."
     ::= { cienaCesPmIGMPTotalStatisticsBinEntry 10 }
	
   cienaCesPmIGMPTotalStatsBinIgmpnumReplyTimeouts OBJECT-TYPE
     SYNTAX      Counter64 
     MAX-ACCESS  read-only
     STATUS      current
     DESCRIPTION
             "The total number of timeouts waiting for the
             membership reports."
     ::= { cienaCesPmIGMPTotalStatisticsBinEntry 11 }
   
   cienaCesPmIGMPTotalStatsBinIgmpnumRouterDiscards OBJECT-TYPE
     SYNTAX      Counter64 
     MAX-ACCESS  read-only
     STATUS      current
     DESCRIPTION
             "The total number of messages discarded by the
             router. This happens when a join comes in from 
             a router port."
     ::= { cienaCesPmIGMPTotalStatisticsBinEntry 12 }
 
   cienaCesPmIGMPTotalStatsBinIgmpnumHostDiscards OBJECT-TYPE
     SYNTAX      Counter64 
     MAX-ACCESS  read-only
     STATUS      current
     DESCRIPTION
             "The total number of messages discarded by the
             host. This happens when a join or leave comes 
             in a port, but no router port is established."
     ::= { cienaCesPmIGMPTotalStatisticsBinEntry 13 }
 
   cienaCesPmIGMPTotalStatsBinIgmpnumBadChecksum OBJECT-TYPE
     SYNTAX      Counter64 
     MAX-ACCESS  read-only
     STATUS      current
     DESCRIPTION
             "The total number of packets received with bad 
             IP checksum."
     ::= { cienaCesPmIGMPTotalStatisticsBinEntry 14 }

   cienaCesPmIGMPTotalStatsBinIgmpnumL2L3Mismatch OBJECT-TYPE
     SYNTAX      Counter64 
     MAX-ACCESS  read-only
     STATUS      current
     DESCRIPTION
             "The total number of IGMP Layer 2 and Layer 3 mismatch packets
             received."
     ::= { cienaCesPmIGMPTotalStatisticsBinEntry 15 }
    
   cienaCesPmIGMPTotalStatsBinIgmpnumUnknownPktType OBJECT-TYPE
     SYNTAX      Counter64 
     MAX-ACCESS  read-only
     STATUS      current
     DESCRIPTION
             "The total number of unknown type IGMP 
             packets received."
     ::= { cienaCesPmIGMPTotalStatisticsBinEntry 16 }
    
   cienaCesPmIGMPTotalStatsBinIgmpnumResourceExceed OBJECT-TYPE
     SYNTAX      Counter64 
     MAX-ACCESS  read-only
     STATUS      current
     DESCRIPTION
             "The total number of IGMP packets discarded because there were not enough resources
             to process these messages. This could happen when the rate of the incoming IGMP messages
             is very high."
     ::= { cienaCesPmIGMPTotalStatisticsBinEntry 17 }
 
   cienaCesPmIGMPTotalStatsBinIgmpnumQueryDiscardsSrcIpZero OBJECT-TYPE
     SYNTAX      Counter64 
     MAX-ACCESS  read-only
     STATUS      current
     DESCRIPTION
             "The total number of queries discarded because they had zero source IP."
     ::= { cienaCesPmIGMPTotalStatisticsBinEntry 18 }

  
   --Access profile stats
  
  cienaCesPmAccessHistoryBinTable OBJECT-TYPE
     SYNTAX     SEQUENCE OF CienaCesPmAccessHistoryBinEntry
     MAX-ACCESS not-accessible
     STATUS     current
     DESCRIPTION
            "The (conceptual) read-only table listing the bin statistics."  
     ::= { cienaCesPmAccessStats 1 }       
     
   cienaCesPmAccessHistoryBinEntry OBJECT-TYPE
     SYNTAX      CienaCesPmAccessHistoryBinEntry
     MAX-ACCESS  not-accessible
     STATUS      current
     DESCRIPTION
           "An entry (conceptual row) in the cienaPortPmAccessHistoryBinTable.

           This table lists the statistics for all the history bins of the PM instance, as 
           specified by the bin-count object of the PM instance.  History bins are displayed in the order
           so that #1 bin always represents the most recently completed bin and #2 - the bin previous to that
           and so on.
	       The statistics are displayed for only the instances with valid bins (with start time >0), 
	       as indicated by the operational state of the corresponding PM instance."  
     INDEX { cienaCesPmInstanceIndex, cienaCesPmAccessHistoryBinIndex }
     ::= { cienaCesPmAccessHistoryBinTable 1 }
        
 CienaCesPmAccessHistoryBinEntry ::=  SEQUENCE {
 	 cienaCesPmAccessHistoryBinIndex                         	Unsigned32,
     cienaCesPmAccessHistoryBinStartTime						DisplayString,
     cienaCesPmAccessHistoryBinEndTime							DisplayString,
     cienaCesPmAccessHistoryBinClearTime						DisplayString,
     cienaCesPmAccessHistoryBinDuration						Unsigned32,   
     cienaCesPmAccessHistoryBinState							PmBinState,  
     cienaCesPmAccessHistoryBinAccessHitBytes                	Counter64,
     cienaCesPmAccessHistoryBinAccessHitFrames               	Counter64   
  }
  cienaCesPmAccessHistoryBinIndex OBJECT-TYPE
     SYNTAX      Unsigned32 (1..65535) 
     MAX-ACCESS  not-accessible
     STATUS      current
     DESCRIPTION
             "Bin number associated with the PmAccessHistoryBin entry."
     ::= { cienaCesPmAccessHistoryBinEntry 1}
	
   cienaCesPmAccessHistoryBinStartTime   OBJECT-TYPE
     SYNTAX		DisplayString
     MAX-ACCESS	read-only
     STATUS		current
     DESCRIPTION "Collection start time of the bin."
     ::= { cienaCesPmAccessHistoryBinEntry 2	}
  
   cienaCesPmAccessHistoryBinEndTime	OBJECT-TYPE
     SYNTAX		DisplayString
     MAX-ACCESS	read-only
     STATUS		current
     DESCRIPTION "Collection end time of the bin."
     ::= { cienaCesPmAccessHistoryBinEntry 3	} 
     
   cienaCesPmAccessHistoryBinClearTime	OBJECT-TYPE
     SYNTAX		DisplayString
     MAX-ACCESS	read-only
     STATUS		current
     DESCRIPTION "Collection clear time of the bin."
     ::= { cienaCesPmAccessHistoryBinEntry 4	} 
   
   cienaCesPmAccessHistoryBinDuration OBJECT-TYPE
     SYNTAX      Unsigned32 (1..65535) 
     UNITS		"minutes"
     MAX-ACCESS  read-only
     STATUS      current
     DESCRIPTION
             "Duration of the bin."
     ::= { cienaCesPmAccessHistoryBinEntry 5 }
  
  cienaCesPmAccessHistoryBinState OBJECT-TYPE
     SYNTAX      PmBinState 
     MAX-ACCESS  read-only
     STATUS      current
     DESCRIPTION
             "State of the bin."
     ::= { cienaCesPmAccessHistoryBinEntry 6 }
 
 cienaCesPmAccessHistoryBinAccessHitBytes OBJECT-TYPE
     SYNTAX      Counter64 
     MAX-ACCESS  read-only
     STATUS      current
     DESCRIPTION
             "The total number of access hit bytes for the history bin."
     ::= { cienaCesPmAccessHistoryBinEntry 7 }
 
 cienaCesPmAccessHistoryBinAccessHitFrames OBJECT-TYPE
     SYNTAX      Counter64 
     MAX-ACCESS  read-only
     STATUS      current
     DESCRIPTION
             "The total number of access hit frames for the history bin."
     ::= { cienaCesPmAccessHistoryBinEntry 8 }

-- Pm Access Curr Bin Table

    cienaCesPmAccessCurrBinTable OBJECT-TYPE
     SYNTAX     SEQUENCE OF CienaCesPmAccessCurrBinEntry
     MAX-ACCESS not-accessible
     STATUS     current
     DESCRIPTION
            "The (conceptual) read-only table listing the bin statistics."  
     ::= { cienaCesPmAccessStats 2}
     
   cienaCesPmAccessCurrBinEntry OBJECT-TYPE
     SYNTAX      CienaCesPmAccessCurrBinEntry
     MAX-ACCESS  not-accessible
     STATUS      current
     DESCRIPTION
           "An entry (conceptual row) in the cienaPortPmAccessCurrBinTable.

           This table lists the statistics for the current bin of the PM instance." 
     INDEX {cienaCesPmInstanceIndex}
     ::= { cienaCesPmAccessCurrBinTable 1 }
        
 CienaCesPmAccessCurrBinEntry ::=  SEQUENCE {
 	 cienaCesPmAccessCurrBinStartTime				DisplayString,
     cienaCesPmAccessCurrBinClearedTime			DisplayString,
     cienaCesPmAccessCurrBinDuration					Unsigned32,   
     cienaCesPmAccessCurrBinState					PmBinState,  
     cienaCesPmAccessCurrBinAccessHitBytes         Counter64,
     cienaCesPmAccessCurrBinAccessHitFrames        Counter64   
   	}
  
   cienaCesPmAccessCurrBinStartTime   OBJECT-TYPE
     SYNTAX		DisplayString
     MAX-ACCESS	read-only
     STATUS		current
     DESCRIPTION "Collection start time of the bin."
     ::= { cienaCesPmAccessCurrBinEntry 1	}
   
   cienaCesPmAccessCurrBinClearedTime   OBJECT-TYPE
     SYNTAX		DisplayString
     MAX-ACCESS	read-only
     STATUS		current
     DESCRIPTION "Cleared time of the bin."
     ::= { cienaCesPmAccessCurrBinEntry 2	}
                   
   cienaCesPmAccessCurrBinDuration OBJECT-TYPE
     SYNTAX      Unsigned32 (1..65535) 
     UNITS		"minutes"
     MAX-ACCESS  read-only
     STATUS      current
     DESCRIPTION
             "Duration of the bin."
     ::= { cienaCesPmAccessCurrBinEntry 3 }
  
  cienaCesPmAccessCurrBinState OBJECT-TYPE
     SYNTAX      PmBinState 
     MAX-ACCESS  read-only
     STATUS      current
     DESCRIPTION
             "State of the bin."
     ::= { cienaCesPmAccessCurrBinEntry 4 }
 
 cienaCesPmAccessCurrBinAccessHitBytes OBJECT-TYPE
     SYNTAX      Counter64 
     MAX-ACCESS  read-only
     STATUS      current
     DESCRIPTION
             "The total number of access hit bytes for the current bin."
     ::= { cienaCesPmAccessCurrBinEntry 5 }
 
 cienaCesPmAccessCurrBinAccessHitFrames OBJECT-TYPE
     SYNTAX      Counter64 
     MAX-ACCESS  read-only
     STATUS      current
     DESCRIPTION
             "The total number of access hit frames for the current bin."
     ::= { cienaCesPmAccessCurrBinEntry 6 }
 
 
 --Access profile stats - current 24 Hour bin stats.
  
  cienaCesPmAccessCurr24HBinTable OBJECT-TYPE
     SYNTAX     SEQUENCE OF CienaCesPmAccessCurr24HBinEntry
     MAX-ACCESS not-accessible
     STATUS     current
     DESCRIPTION
            "The (conceptual) read-only table listing the bin statistics."  
     ::= { cienaCesPmAccessStats 3 }
     
   cienaCesPmAccessCurr24HBinEntry OBJECT-TYPE
     SYNTAX      CienaCesPmAccessCurr24HBinEntry
     MAX-ACCESS  not-accessible
     STATUS      current
     DESCRIPTION
           "An entry (conceptual row) in the cienaPortPmAccessCurr24HBinTable.

           This table lists the statistics for the current 24 hours." 
     INDEX {cienaCesPmInstanceIndex}
     ::= { cienaCesPmAccessCurr24HBinTable 1 }
        
 CienaCesPmAccessCurr24HBinEntry ::=  SEQUENCE {  
 	 cienaCesPmAccessCurr24HBinStartTime				DisplayString,
     cienaCesPmAccessCurr24HBinEndTime					DisplayString,
     cienaCesPmAccessCurr24HBinClearedTime				DisplayString,
     cienaCesPmAccessCurr24HBinDuration					Unsigned32,   
     cienaCesPmAccessCurr24HBinState					PmBinState,  
     cienaCesPmAccessCurr24HBinAccessHitBytes         	Counter64,
     cienaCesPmAccessCurr24HBinAccessHitFrames        	Counter64   
   	}
   
   cienaCesPmAccessCurr24HBinStartTime   OBJECT-TYPE
     SYNTAX		DisplayString
     MAX-ACCESS	read-only
     STATUS		current
     DESCRIPTION "Collection start time of the bin."
     ::= { cienaCesPmAccessCurr24HBinEntry 1	}
   
   cienaCesPmAccessCurr24HBinEndTime 		OBJECT-TYPE
     SYNTAX		DisplayString
     MAX-ACCESS	read-only
     STATUS		current
     DESCRIPTION "Collection end time for the bin."
     ::= { cienaCesPmAccessCurr24HBinEntry 2	}

    cienaCesPmAccessCurr24HBinClearedTime   OBJECT-TYPE
     SYNTAX		DisplayString
     MAX-ACCESS	read-only
     STATUS		current
     DESCRIPTION "Cleared time of the bin."
     ::= { cienaCesPmAccessCurr24HBinEntry 3	}
                   
   cienaCesPmAccessCurr24HBinDuration OBJECT-TYPE
     SYNTAX      Unsigned32 (1..65535) 
     UNITS		"minutes"
     MAX-ACCESS  read-only
     STATUS      current
     DESCRIPTION
             "Interval of the bin."
     ::= { cienaCesPmAccessCurr24HBinEntry 4 }
  
  cienaCesPmAccessCurr24HBinState OBJECT-TYPE
     SYNTAX      PmBinState 
     MAX-ACCESS  read-only
     STATUS      current
     DESCRIPTION
             "State of the bin."
     ::= { cienaCesPmAccessCurr24HBinEntry 5 }
 
 cienaCesPmAccessCurr24HBinAccessHitBytes OBJECT-TYPE
     SYNTAX      Counter64 
     MAX-ACCESS  read-only
     STATUS      current
     DESCRIPTION
             "The total number of access hit bytes for the 24 hours bin."
     ::= { cienaCesPmAccessCurr24HBinEntry 6 }
 
 cienaCesPmAccessCurr24HBinAccessHitFrames OBJECT-TYPE
     SYNTAX      Counter64 
     MAX-ACCESS  read-only
     STATUS      current
     DESCRIPTION
             "The total number of access hit frames for the 24 hours bin."
     ::= { cienaCesPmAccessCurr24HBinEntry 7 }


 
 --Access profile stats - history 24 Hour bin stats.
  
  cienaCesPmAccessHist24HBinTable OBJECT-TYPE
     SYNTAX     SEQUENCE OF CienaCesPmAccessHist24HBinEntry
     MAX-ACCESS not-accessible
     STATUS     current
     DESCRIPTION
            "The (conceptual) read-only table listing the bin statistics."  
     ::= { cienaCesPmAccessStats 4 }
     
   cienaCesPmAccessHist24HBinEntry OBJECT-TYPE
     SYNTAX      CienaCesPmAccessHist24HBinEntry
     MAX-ACCESS  not-accessible
     STATUS      current
     DESCRIPTION
           "An entry (conceptual row) in the cienaPortPmAccessHist24HBinTable.
           This table lists the statistics for the history 24 hours bin." 
     INDEX {cienaCesPmInstanceIndex }
     ::= { cienaCesPmAccessHist24HBinTable 1 }
        
 CienaCesPmAccessHist24HBinEntry ::=  SEQUENCE {                     
 	 cienaCesPmAccessHist24HBinStartTime				DisplayString,
     cienaCesPmAccessHist24HBinDuration					Unsigned32,   
     cienaCesPmAccessHist24HBinState					PmBinState,  
     cienaCesPmAccessHist24HBinAccessHitBytes         	Counter64,
     cienaCesPmAccessHist24HBinAccessHitFrames        	Counter64,   
     cienaCesPmAccessHist24HBinEndTime                  DisplayString,
     cienaCesPmAccessHist24HBinClearTime                DisplayString
   	}
   cienaCesPmAccessHist24HBinStartTime   OBJECT-TYPE
     SYNTAX		DisplayString
     MAX-ACCESS	read-only
     STATUS		current
     DESCRIPTION "Collection start time of the bin."
     ::= { cienaCesPmAccessHist24HBinEntry 1	}
   
   cienaCesPmAccessHist24HBinDuration OBJECT-TYPE
     SYNTAX      Unsigned32 (1..65535) 
     UNITS		"minutes"
     MAX-ACCESS  read-only
     STATUS      current
     DESCRIPTION
             "Duration of the bin."
     ::= { cienaCesPmAccessHist24HBinEntry 2 }
  
  cienaCesPmAccessHist24HBinState OBJECT-TYPE
     SYNTAX      PmBinState 
     MAX-ACCESS  read-only
     STATUS      current
     DESCRIPTION
             "State of the bin."
     ::= { cienaCesPmAccessHist24HBinEntry 3 }
 
 cienaCesPmAccessHist24HBinAccessHitBytes OBJECT-TYPE
     SYNTAX      Counter64 
     MAX-ACCESS  read-only
     STATUS      current
     DESCRIPTION
             "The total number of access hit bytes for the history 24 hours bin."
     ::= { cienaCesPmAccessHist24HBinEntry 4 }
 
 cienaCesPmAccessHist24HBinAccessHitFrames OBJECT-TYPE
     SYNTAX      Counter64 
     MAX-ACCESS  read-only
     STATUS      current
     DESCRIPTION
             "The total number of access hit frames for the history 24 hours bin."
     ::= { cienaCesPmAccessHist24HBinEntry 5 }

   cienaCesPmAccessHist24HBinEndTime OBJECT-TYPE
     SYNTAX      DisplayString
     MAX-ACCESS  read-only
     STATUS      current
     DESCRIPTION "Collection end time of the bin."
     ::= { cienaCesPmAccessHist24HBinEntry 6 }

   cienaCesPmAccessHist24HBinClearTime OBJECT-TYPE
     SYNTAX      DisplayString
     MAX-ACCESS  read-only
     STATUS      current
     DESCRIPTION "Collection clear time of the bin."
     ::= { cienaCesPmAccessHist24HBinEntry 7 }

 
 --Access profile stats
  
 cienaCesPmAccessAllTimeBinTable OBJECT-TYPE
     SYNTAX     SEQUENCE OF CienaCesPmAccessAllTimeBinEntry
     MAX-ACCESS not-accessible
     STATUS     deprecated
     DESCRIPTION
            "The (conceptual) read-only table listing the bin statistics."  
     ::= { cienaCesPmAccessStats 5 }
     
   cienaCesPmAccessAllTimeBinEntry OBJECT-TYPE
     SYNTAX      CienaCesPmAccessAllTimeBinEntry
     MAX-ACCESS  not-accessible
     STATUS      deprecated
     DESCRIPTION
           "An entry (conceptual row) in the cienaPortPmAccessAllTimeBinTable.

           This table lists the statistics for the All Time bin of the PM instance." 
     INDEX {cienaCesPmInstanceIndex}
     ::= { cienaCesPmAccessAllTimeBinTable 1 }
        
 CienaCesPmAccessAllTimeBinEntry ::=  SEQUENCE {
 	 cienaCesPmAccessAllTimeBinDuration				Unsigned32,   
     cienaCesPmAccessAllTimeBinState				PmBinState,  
     cienaCesPmAccessAllTimeBinAccessHitBytes 		Counter64,
     cienaCesPmAccessAllTimeBinAccessHitFrames    	Counter64   
   	}
   cienaCesPmAccessAllTimeBinDuration OBJECT-TYPE
     SYNTAX      Unsigned32 (1..65535) 
     UNITS		"minutes"
     MAX-ACCESS  read-only
     STATUS      deprecated
     DESCRIPTION
             "Duration of the bin."
     ::= { cienaCesPmAccessAllTimeBinEntry 1 }
  
  cienaCesPmAccessAllTimeBinState OBJECT-TYPE
     SYNTAX      PmBinState 
     MAX-ACCESS  read-only
     STATUS      deprecated
     DESCRIPTION
             "State of the bin."
     ::= { cienaCesPmAccessAllTimeBinEntry 2 }
 
 cienaCesPmAccessAllTimeBinAccessHitBytes OBJECT-TYPE
     SYNTAX      Counter64 
     MAX-ACCESS  read-only
     STATUS      deprecated
     DESCRIPTION
             "The total number of access hit bytes for the All Time bin."
     ::= { cienaCesPmAccessAllTimeBinEntry 3 }
 
 cienaCesPmAccessAllTimeBinAccessHitFrames OBJECT-TYPE
     SYNTAX      Counter64 
     MAX-ACCESS  read-only
     STATUS      deprecated
     DESCRIPTION
             "The total number of access hit frames for the All Time bin."
     ::= { cienaCesPmAccessAllTimeBinEntry 4 }


   --Access Profile Stats, statistics bin
  
   cienaCesPmAccessStatisticsBinTable OBJECT-TYPE
     SYNTAX     SEQUENCE OF CienaCesPmAccessStatisticsBinEntry
     MAX-ACCESS not-accessible
     STATUS     current
     DESCRIPTION "The (conceptual) read-only table listing the bin statistics."
     ::= { cienaCesPmAccessStats 6 }
     
   cienaCesPmAccessStatisticsBinEntry OBJECT-TYPE
     SYNTAX      CienaCesPmAccessStatisticsBinEntry
     MAX-ACCESS  not-accessible
     STATUS      current
     DESCRIPTION
           "An entry (conceptual row) in the cienaCesPmAccessStatisticsBinTable.
           This table lists the statistics for the statistics bin of the PM instance." 
     INDEX {cienaCesPmInstanceIndex}
     ::= { cienaCesPmAccessStatisticsBinTable 1 }
        
   CienaCesPmAccessStatisticsBinEntry ::=  SEQUENCE {
     cienaCesPmAccessStatsBinStartTime                              DisplayString,
     cienaCesPmAccessStatsBinClearTime                              DisplayString,
     cienaCesPmAccessStatsBinAccessHitBytes                         Counter64,
     cienaCesPmAccessStatsBinAccessHitFrames                        Counter64   
   }

   cienaCesPmAccessStatsBinStartTime OBJECT-TYPE
     SYNTAX      DisplayString
     MAX-ACCESS  read-only
     STATUS      current
     DESCRIPTION "Collection start time of the bin."
     ::= { cienaCesPmAccessStatisticsBinEntry 1 }

   cienaCesPmAccessStatsBinClearTime OBJECT-TYPE
     SYNTAX      DisplayString
     MAX-ACCESS  read-only
     STATUS      current
     DESCRIPTION "Collection clear time of the bin."
     ::= { cienaCesPmAccessStatisticsBinEntry 2 }
 
   cienaCesPmAccessStatsBinAccessHitBytes OBJECT-TYPE
     SYNTAX      Counter64 
     MAX-ACCESS  read-only
     STATUS      current
     DESCRIPTION
             "The total number of access hit bytes for the All Time bin."
     ::= { cienaCesPmAccessStatisticsBinEntry 3 }
 
   cienaCesPmAccessStatsBinAccessHitFrames OBJECT-TYPE
     SYNTAX      Counter64 
     MAX-ACCESS  read-only
     STATUS      current
     DESCRIPTION
             "The total number of access hit frames for the All Time bin."
     ::= { cienaCesPmAccessStatisticsBinEntry 4 }


   --Access Profile Stats, total statistics bin
  
 cienaCesPmAccessTotalStatisticsBinTable OBJECT-TYPE
     SYNTAX     SEQUENCE OF CienaCesPmAccessTotalStatisticsBinEntry
     MAX-ACCESS not-accessible
     STATUS     current
     DESCRIPTION "The (conceptual) read-only table listing the bin statistics."
     ::= { cienaCesPmAccessStats 7 }
     
   cienaCesPmAccessTotalStatisticsBinEntry OBJECT-TYPE
     SYNTAX      CienaCesPmAccessTotalStatisticsBinEntry
     MAX-ACCESS  not-accessible
     STATUS      current
     DESCRIPTION
           "An entry (conceptual row) in the cienaCesPmAccessTotalStatisticsBinTable.
           This table lists the statistics for the total statistics bin of the PM instance." 
     INDEX {cienaCesPmInstanceIndex}
     ::= { cienaCesPmAccessTotalStatisticsBinTable 1 }
        
   CienaCesPmAccessTotalStatisticsBinEntry ::=  SEQUENCE {
     cienaCesPmAccessTotalStatsBinStartTime                         DisplayString,
     cienaCesPmAccessTotalStatsBinAccessHitBytes                    Counter64,
     cienaCesPmAccessTotalStatsBinAccessHitFrames                   Counter64   
   }

   cienaCesPmAccessTotalStatsBinStartTime OBJECT-TYPE
     SYNTAX      DisplayString
     MAX-ACCESS  read-only
     STATUS      current
     DESCRIPTION "Collection start time of the bin."
     ::= { cienaCesPmAccessTotalStatisticsBinEntry 1 }

   cienaCesPmAccessTotalStatsBinAccessHitBytes OBJECT-TYPE
     SYNTAX      Counter64 
     MAX-ACCESS  read-only
     STATUS      current
     DESCRIPTION
             "The total number of access hit bytes for the All Time bin."
     ::= { cienaCesPmAccessTotalStatisticsBinEntry 2 }
 
   cienaCesPmAccessTotalStatsBinAccessHitFrames OBJECT-TYPE
     SYNTAX      Counter64 
     MAX-ACCESS  read-only
     STATUS      current
     DESCRIPTION
             "The total number of access hit frames for the All Time bin."
     ::= { cienaCesPmAccessTotalStatisticsBinEntry 3 }
  

     --FloodContainer Profile Stats  
  
  cienaCesPmFloodContainerHistoryBinTable OBJECT-TYPE
     SYNTAX     SEQUENCE OF CienaCesPmFloodContainerHistoryBinEntry
     MAX-ACCESS not-accessible
     STATUS     current
     DESCRIPTION
            "The (conceptual) read-only table listing the bin statistics."  
     ::= { cienaCesPmFloodContainerStats 1 }
     
   cienaCesPmFloodContainerHistoryBinEntry OBJECT-TYPE
     SYNTAX      CienaCesPmFloodContainerHistoryBinEntry
     MAX-ACCESS  not-accessible
     STATUS      current
     DESCRIPTION
           "An entry (conceptual row) in the cienaPortPmIGMPBinTable.

           This table lists the statistics for all the history bins of the PM instance, as 
           specified by the bin-count object of the PM instance.  History bins are displayed in the order
           so that #1 bin always represents the most recently completed bin and #2 - the bin previous to that
           and so on.
	       The statistics are displayed for only the instances with valid bins (with start time >0), 
	       as indicated by the operational state of the corresponding PM instance."  
     INDEX { cienaCesPmInstanceIndex, cienaCesPmFloodContainerHistoryBinIndex }
     ::= { cienaCesPmFloodContainerHistoryBinTable 1 }
        
 CienaCesPmFloodContainerHistoryBinEntry ::=  SEQUENCE { 
 	 cienaCesPmFloodContainerHistoryBinIndex                       Unsigned32,
     cienaCesPmFloodContainerHistoryBinStartTime			 		DisplayString,
     cienaCesPmFloodContainerHistoryBinEndTime                     DisplayString,
     cienaCesPmFloodContainerHistoryBinClearTime					DisplayString,
     cienaCesPmFloodContainerHistoryBinDuration			 		Unsigned32,   
     cienaCesPmFloodContainerHistoryBinState			 			PmBinState,  
     cienaCesPmFloodContainerHistoryBinBcastDroppedBytes           Counter64,
     cienaCesPmFloodContainerHistoryBinBcastDroppedFrames          Counter64,
     cienaCesPmFloodContainerHistoryBinL2McastDroppedBytes           Counter64,
     cienaCesPmFloodContainerHistoryBinL2McastDroppedFrames          Counter64,
     cienaCesPmFloodContainerHistoryBinUnknownUnicastDroppedBytes           Counter64,
     cienaCesPmFloodContainerHistoryBinUnknownUnicastDroppedFrames          Counter64
     } 
  
   cienaCesPmFloodContainerHistoryBinIndex OBJECT-TYPE
     SYNTAX      Unsigned32 (1..65535) 
     MAX-ACCESS  not-accessible
     STATUS      current
     DESCRIPTION
             "Bin number associated with the PmFloodContainerHistoryBin entry."
     ::= { cienaCesPmFloodContainerHistoryBinEntry 1 }
      
   cienaCesPmFloodContainerHistoryBinStartTime   OBJECT-TYPE
     SYNTAX		DisplayString
     MAX-ACCESS	read-only
     STATUS		current
     DESCRIPTION "Collection start time of the bin."
     ::= { cienaCesPmFloodContainerHistoryBinEntry 2	}
   
   cienaCesPmFloodContainerHistoryBinEndTime	OBJECT-TYPE
   	 SYNTAX		DisplayString
     MAX-ACCESS	read-only
     STATUS		current
     DESCRIPTION "Collection end time of the bin."
     ::= { cienaCesPmFloodContainerHistoryBinEntry 3	}
   
   cienaCesPmFloodContainerHistoryBinClearTime	OBJECT-TYPE
   	 SYNTAX		DisplayString
     MAX-ACCESS	read-only
     STATUS		current
     DESCRIPTION "Collection clear time of the bin."
     ::= { cienaCesPmFloodContainerHistoryBinEntry 4	}


   cienaCesPmFloodContainerHistoryBinDuration OBJECT-TYPE
     SYNTAX      Unsigned32 (1..65535)        
     UNITS		"minutes"
     MAX-ACCESS  read-only
     STATUS      current
     DESCRIPTION
             "Duration of the bin."
     ::= { cienaCesPmFloodContainerHistoryBinEntry 5 }
  
  cienaCesPmFloodContainerHistoryBinState OBJECT-TYPE
     SYNTAX      PmBinState 
     MAX-ACCESS  read-only
     STATUS      current
     DESCRIPTION
             "State of the bin."
     ::= { cienaCesPmFloodContainerHistoryBinEntry 6 }

  cienaCesPmFloodContainerHistoryBinBcastDroppedBytes  OBJECT-TYPE
     SYNTAX      Counter64 
     MAX-ACCESS  read-only
     STATUS      current
     DESCRIPTION
             "Dropped broadcast bytes."
     ::= { cienaCesPmFloodContainerHistoryBinEntry 7 }
     
   cienaCesPmFloodContainerHistoryBinBcastDroppedFrames OBJECT-TYPE
      SYNTAX Counter64
      MAX-ACCESS read-only
      STATUS current
      DESCRIPTION 
      		"Broadcast dropped frames."
      ::= { cienaCesPmFloodContainerHistoryBinEntry 8 }

   cienaCesPmFloodContainerHistoryBinL2McastDroppedBytes  OBJECT-TYPE
     SYNTAX Counter64
     MAX-ACCESS read-only
     STATUS current
     DESCRIPTION 
      		"Multicast dropped bytes."
      ::= { cienaCesPmFloodContainerHistoryBinEntry 9 }
     
   cienaCesPmFloodContainerHistoryBinL2McastDroppedFrames  OBJECT-TYPE
     SYNTAX Counter64
     MAX-ACCESS read-only
     STATUS current
     DESCRIPTION 
      		"Multicast dropped frames."
      ::= { cienaCesPmFloodContainerHistoryBinEntry 10 }

   cienaCesPmFloodContainerHistoryBinUnknownUnicastDroppedBytes OBJECT-TYPE
       SYNTAX Counter64
       MAX-ACCESS read-only
       STATUS current
       DESCRIPTION
       		"Unicast dropped bytes." 
       ::= { cienaCesPmFloodContainerHistoryBinEntry 11 }
       
   cienaCesPmFloodContainerHistoryBinUnknownUnicastDroppedFrames OBJECT-TYPE
        SYNTAX Counter64
        MAX-ACCESS read-only
        STATUS current
        DESCRIPTION
        	"Unicast dropped frames."
        ::= { cienaCesPmFloodContainerHistoryBinEntry 12 }	 
    
 -- Pm Contain Current Bin Table   
    
 cienaCesPmFloodContainerCurrBinTable OBJECT-TYPE
     SYNTAX     SEQUENCE OF CienaCesPmFloodContainerCurrBinEntry
     MAX-ACCESS not-accessible
     STATUS     current
     DESCRIPTION
            "The (conceptual) read-only table listing the bin statistics."  
     ::= { cienaCesPmFloodContainerStats 2 }
     
   cienaCesPmFloodContainerCurrBinEntry OBJECT-TYPE
     SYNTAX      CienaCesPmFloodContainerCurrBinEntry
     MAX-ACCESS  not-accessible
     STATUS      current
     DESCRIPTION
           "An entry (conceptual row) in the cienaPortPmIGMPBinTable.

           This table lists the statistics for the current bin of the PM instance." 
     INDEX {cienaCesPmInstanceIndex}
     ::= { cienaCesPmFloodContainerCurrBinTable 1 }
        
 CienaCesPmFloodContainerCurrBinEntry ::=  SEQUENCE { 
 	 cienaCesPmFloodContainerCurrBinStartTime		 					DisplayString,
     cienaCesPmFloodContainerCurrBinClearedTime		 				DisplayString,
     cienaCesPmFloodContainerCurrBinDuration			 				Unsigned32,   
     cienaCesPmFloodContainerCurrBinState			 					PmBinState,  
     cienaCesPmFloodContainerCurrBinBcastDroppedBytes       			Counter64,
     cienaCesPmFloodContainerCurrBinBcastDroppedFrames      			Counter64,
     cienaCesPmFloodContainerCurrBinL2McastDroppedBytes       			Counter64,
     cienaCesPmFloodContainerCurrBinL2McastDroppedFrames      			Counter64,
     cienaCesPmFloodContainerCurrBinUnknownUnicastDroppedBytes       	Counter64,
     cienaCesPmFloodContainerCurrBinUnknownUnicastDroppedFrames      	Counter64
     } 
  
  cienaCesPmFloodContainerCurrBinStartTime   OBJECT-TYPE
     SYNTAX		DisplayString
     MAX-ACCESS	read-only
     STATUS		current
     DESCRIPTION "Collection start time of the bin."
     ::= { cienaCesPmFloodContainerCurrBinEntry 1	}
   
  cienaCesPmFloodContainerCurrBinClearedTime   OBJECT-TYPE
     SYNTAX		DisplayString
     MAX-ACCESS	read-only
     STATUS		current
     DESCRIPTION "Cleared time of the bin."
     ::= { cienaCesPmFloodContainerCurrBinEntry 2	}
                   
   cienaCesPmFloodContainerCurrBinDuration OBJECT-TYPE
     SYNTAX      Unsigned32 (1..65535)        
     UNITS		"minutes"
     MAX-ACCESS  read-only
     STATUS      current
     DESCRIPTION
             "Duration of the bin."
     ::= { cienaCesPmFloodContainerCurrBinEntry 3 }
  
  cienaCesPmFloodContainerCurrBinState OBJECT-TYPE
     SYNTAX      PmBinState 
     MAX-ACCESS  read-only
     STATUS      current
     DESCRIPTION
             "State of the bin."
     ::= { cienaCesPmFloodContainerCurrBinEntry 4 }

  cienaCesPmFloodContainerCurrBinBcastDroppedBytes  OBJECT-TYPE
     SYNTAX      Counter64 
     MAX-ACCESS  read-only
     STATUS      current
     DESCRIPTION
             "Broadcast dropped bytes."
     ::= { cienaCesPmFloodContainerCurrBinEntry 5 }
     
   cienaCesPmFloodContainerCurrBinBcastDroppedFrames OBJECT-TYPE
      SYNTAX Counter64
      MAX-ACCESS read-only
      STATUS current
      DESCRIPTION 
      		"Broadcast dropped frames."
      ::= { cienaCesPmFloodContainerCurrBinEntry 6 }

   cienaCesPmFloodContainerCurrBinL2McastDroppedBytes  OBJECT-TYPE
     SYNTAX Counter64
     MAX-ACCESS read-only
     STATUS current
     DESCRIPTION 
      		"L2 multicast dropped bytes."
      ::= { cienaCesPmFloodContainerCurrBinEntry 7 }
     
    cienaCesPmFloodContainerCurrBinL2McastDroppedFrames  OBJECT-TYPE
     SYNTAX Counter64
     MAX-ACCESS read-only
     STATUS current
     DESCRIPTION 
      		"L2 multicast dropped frames."
      ::= { cienaCesPmFloodContainerCurrBinEntry 8 }

     cienaCesPmFloodContainerCurrBinUnknownUnicastDroppedBytes OBJECT-TYPE
       SYNTAX Counter64
       MAX-ACCESS read-only
       STATUS current
       DESCRIPTION
       		"Unknown unicast dropped bytes." 
       ::= { cienaCesPmFloodContainerCurrBinEntry 9 }
       
      cienaCesPmFloodContainerCurrBinUnknownUnicastDroppedFrames OBJECT-TYPE
        SYNTAX Counter64
        MAX-ACCESS read-only
        STATUS current
        DESCRIPTION
        	"Unknown unicast dropped frames."
        ::= { cienaCesPmFloodContainerCurrBinEntry 10 }
 
  --FloodContainer bin current 24H bin stats.
  
  cienaCesPmFloodContainerCurr24HBinTable OBJECT-TYPE
     SYNTAX     SEQUENCE OF CienaCesPmFloodContainerCurr24HBinEntry
     MAX-ACCESS not-accessible
     STATUS     current
     DESCRIPTION
            "The (conceptual) read-only table listing the bin statistics."  
     ::= { cienaCesPmFloodContainerStats 3 }
     
   cienaCesPmFloodContainerCurr24HBinEntry OBJECT-TYPE
     SYNTAX      CienaCesPmFloodContainerCurr24HBinEntry
     MAX-ACCESS  not-accessible
     STATUS      current
     DESCRIPTION
           "An entry (conceptual row) in the cienaPortPmIGMPBinTable.

           This table lists the statistics for the current 24 hours bin." 
     INDEX {cienaCesPmInstanceIndex}
     ::= { cienaCesPmFloodContainerCurr24HBinTable 1 }
        
 CienaCesPmFloodContainerCurr24HBinEntry ::=  SEQUENCE {
 	 cienaCesPmFloodContainerCurr24HBinStartTime		 	 DisplayString,
     cienaCesPmFloodContainerCurr24HBinEndTime		 		 DisplayString,
     cienaCesPmFloodContainerCurr24HBinClearedTime		 	 DisplayString,
     cienaCesPmFloodContainerCurr24HBinDuration		 		 Unsigned32,   
     cienaCesPmFloodContainerCurr24HBinState		 		 PmBinState,  
     cienaCesPmFloodContainerCurr24HBinBcastDroppedBytes     Counter64,
     cienaCesPmFloodContainerCurr24HBinBcastDroppedFrames    Counter64,
     cienaCesPmFloodContainerCurr24HBinL2McastDroppedBytes     Counter64,
     cienaCesPmFloodContainerCurr24HBinL2McastDroppedFrames    Counter64,
     cienaCesPmFloodContainerCurr24HBinUnknownUnicastDroppedBytes     Counter64,
     cienaCesPmFloodContainerCurr24HBinUnknownUnicastDroppedFrames    Counter64
     } 
   cienaCesPmFloodContainerCurr24HBinStartTime   OBJECT-TYPE
     SYNTAX		DisplayString
     MAX-ACCESS	read-only
     STATUS		current
     DESCRIPTION "Collection start time of the bin."
     ::= { cienaCesPmFloodContainerCurr24HBinEntry 1 }
   
   cienaCesPmFloodContainerCurr24HBinEndTime 		OBJECT-TYPE
     SYNTAX		DisplayString
     MAX-ACCESS	read-only
     STATUS		current
     DESCRIPTION "Collection end time for the bin."
     ::= { cienaCesPmFloodContainerCurr24HBinEntry 2 }

    cienaCesPmFloodContainerCurr24HBinClearedTime   OBJECT-TYPE
     SYNTAX		DisplayString
     MAX-ACCESS	read-only
     STATUS		current
     DESCRIPTION "Cleared time of the bin."
     ::= { cienaCesPmFloodContainerCurr24HBinEntry 3 }
                   
   cienaCesPmFloodContainerCurr24HBinDuration OBJECT-TYPE
     SYNTAX      Unsigned32 (1..65535)        
     UNITS		"minutes"
     MAX-ACCESS  read-only
     STATUS      current
     DESCRIPTION
             "Duration of the bin."
     ::= { cienaCesPmFloodContainerCurr24HBinEntry 4 }
  
  cienaCesPmFloodContainerCurr24HBinState OBJECT-TYPE
     SYNTAX      PmBinState 
     MAX-ACCESS  read-only
     STATUS      current
     DESCRIPTION
             "State of the bin."
     ::= { cienaCesPmFloodContainerCurr24HBinEntry 5 }

  cienaCesPmFloodContainerCurr24HBinBcastDroppedBytes  OBJECT-TYPE
     SYNTAX      Counter64 
     MAX-ACCESS  read-only
     STATUS      current
     DESCRIPTION
             "Broadcast dropped bytes."
     ::= { cienaCesPmFloodContainerCurr24HBinEntry 6 }
     
   cienaCesPmFloodContainerCurr24HBinBcastDroppedFrames OBJECT-TYPE
      SYNTAX Counter64
      MAX-ACCESS read-only
      STATUS current
      DESCRIPTION 
      		"Broadcast dropped frames."
      ::= { cienaCesPmFloodContainerCurr24HBinEntry 7 }

   cienaCesPmFloodContainerCurr24HBinL2McastDroppedBytes  OBJECT-TYPE
     SYNTAX Counter64
     MAX-ACCESS read-only
     STATUS current
     DESCRIPTION 
      		"L2 multicast dropped bytes."
      ::= { cienaCesPmFloodContainerCurr24HBinEntry 8 }
     
    cienaCesPmFloodContainerCurr24HBinL2McastDroppedFrames  OBJECT-TYPE
     SYNTAX Counter64
     MAX-ACCESS read-only
     STATUS current
     DESCRIPTION 
      		"L2 multicast dropped frames."
      ::= { cienaCesPmFloodContainerCurr24HBinEntry 9 }

     cienaCesPmFloodContainerCurr24HBinUnknownUnicastDroppedBytes OBJECT-TYPE
       SYNTAX Counter64
       MAX-ACCESS read-only
       STATUS current
       DESCRIPTION
       		"Unknown unicast dropped bytes." 
       ::= { cienaCesPmFloodContainerCurr24HBinEntry 10 }
       
      cienaCesPmFloodContainerCurr24HBinUnknownUnicastDroppedFrames OBJECT-TYPE
        SYNTAX Counter64
        MAX-ACCESS read-only
        STATUS current
        DESCRIPTION
        	"Unknown unicast dropped frames."
        ::= { cienaCesPmFloodContainerCurr24HBinEntry 11 }
 

  --FloodContainer bin history 24H bin stats.
  
  cienaCesPmFloodContainerHist24HBinTable OBJECT-TYPE
     SYNTAX     SEQUENCE OF CienaCesPmFloodContainerHist24HBinEntry
     MAX-ACCESS not-accessible
     STATUS     current
     DESCRIPTION
            "The (conceptual) read-only table listing the bin statistics."  
     ::= { cienaCesPmFloodContainerStats 4 }
     
   cienaCesPmFloodContainerHist24HBinEntry OBJECT-TYPE
     SYNTAX      CienaCesPmFloodContainerHist24HBinEntry
     MAX-ACCESS  not-accessible
     STATUS      current
     DESCRIPTION
           "An entry (conceptual row) in the cienaPortPmIGMPBinTable.

           This table lists the statistics for the history 24 hours bin." 
     INDEX {cienaCesPmInstanceIndex}
     ::= { cienaCesPmFloodContainerHist24HBinTable 1 }
        
 CienaCesPmFloodContainerHist24HBinEntry ::=  SEQUENCE {
 	 cienaCesPmFloodContainerHist24HBinStartTime		 	DisplayString,
     cienaCesPmFloodContainerHist24HBinDuration		 		Unsigned32,   
     cienaCesPmFloodContainerHist24HBinState		 		PmBinState,  
     cienaCesPmFloodContainerHist24HBinBcastDroppedBytes    Counter64,
     cienaCesPmFloodContainerHist24HBinBcastDroppedFrames   Counter64,
     cienaCesPmFloodContainerHist24HBinL2McastDroppedBytes    Counter64,
     cienaCesPmFloodContainerHist24HBinL2McastDroppedFrames   Counter64,
     cienaCesPmFloodContainerHist24HBinUnknownUnicastDroppedBytes    Counter64,
     cienaCesPmFloodContainerHist24HBinUnknownUnicastDroppedFrames   Counter64,
     cienaCesPmFloodContainerHist24HBinEndTime                  DisplayString,
     cienaCesPmFloodContainerHist24HBinClearTime                DisplayString
     } 
  
   cienaCesPmFloodContainerHist24HBinStartTime   OBJECT-TYPE
     SYNTAX		DisplayString
     MAX-ACCESS	read-only
     STATUS		current
     DESCRIPTION "Collection start time of the bin."
     ::= { cienaCesPmFloodContainerHist24HBinEntry 1	}
   
   cienaCesPmFloodContainerHist24HBinDuration OBJECT-TYPE
     SYNTAX      Unsigned32 (1..65535)        
     UNITS		"minutes"
     MAX-ACCESS  read-only
     STATUS      current
     DESCRIPTION
             "Duration of the bin."
     ::= { cienaCesPmFloodContainerHist24HBinEntry 2 }
  
  cienaCesPmFloodContainerHist24HBinState OBJECT-TYPE
     SYNTAX      PmBinState 
     MAX-ACCESS  read-only
     STATUS      current
     DESCRIPTION
             "State of the bin."
     ::= { cienaCesPmFloodContainerHist24HBinEntry 3 }

  cienaCesPmFloodContainerHist24HBinBcastDroppedBytes  OBJECT-TYPE
     SYNTAX      Counter64 
     MAX-ACCESS  read-only
     STATUS      current
     DESCRIPTION
             "Broadcast dropped bytes."
     ::= { cienaCesPmFloodContainerHist24HBinEntry 4 }
     
   cienaCesPmFloodContainerHist24HBinBcastDroppedFrames OBJECT-TYPE
      SYNTAX Counter64
      MAX-ACCESS read-only
      STATUS current
      DESCRIPTION 
      		"Broadcast dropped frames."
      ::= { cienaCesPmFloodContainerHist24HBinEntry 5 }

   cienaCesPmFloodContainerHist24HBinL2McastDroppedBytes  OBJECT-TYPE
     SYNTAX Counter64
     MAX-ACCESS read-only
     STATUS current
     DESCRIPTION 
      		"L2 multicast dropped bytes."
      ::= { cienaCesPmFloodContainerHist24HBinEntry 6 }
     
    cienaCesPmFloodContainerHist24HBinL2McastDroppedFrames  OBJECT-TYPE
     SYNTAX Counter64
     MAX-ACCESS read-only
     STATUS current
     DESCRIPTION 
      		"L2 multicast dropped frames."
      ::= { cienaCesPmFloodContainerHist24HBinEntry 7 }

     cienaCesPmFloodContainerHist24HBinUnknownUnicastDroppedBytes OBJECT-TYPE
       SYNTAX Counter64
       MAX-ACCESS read-only
       STATUS current
       DESCRIPTION
       		"Unicast dropped bytes." 
       ::= { cienaCesPmFloodContainerHist24HBinEntry 8 }
       
      cienaCesPmFloodContainerHist24HBinUnknownUnicastDroppedFrames OBJECT-TYPE
        SYNTAX Counter64
        MAX-ACCESS read-only
        STATUS current
        DESCRIPTION
        	"Unicast dropped frames."
        ::= { cienaCesPmFloodContainerHist24HBinEntry 9 }

   cienaCesPmFloodContainerHist24HBinEndTime OBJECT-TYPE
     SYNTAX      DisplayString
     MAX-ACCESS  read-only
     STATUS      current
     DESCRIPTION "Collection end time of the bin."
     ::= { cienaCesPmFloodContainerHist24HBinEntry 10 }

   cienaCesPmFloodContainerHist24HBinClearTime OBJECT-TYPE
     SYNTAX      DisplayString
     MAX-ACCESS  read-only
     STATUS      current
     DESCRIPTION "Collection clear time of the bin."
     ::= { cienaCesPmFloodContainerHist24HBinEntry 11 }

             
 -- FloodContainer All time bin Table.             
 cienaCesPmFloodContainerAllTimeBinTable OBJECT-TYPE
     SYNTAX     SEQUENCE OF CienaCesPmFloodContainerAllTimeBinEntry
     MAX-ACCESS not-accessible
     STATUS     deprecated
     DESCRIPTION
            "The (conceptual) read-only table listing the bin statistics."  
     ::= { cienaCesPmFloodContainerStats 5 }
     
   cienaCesPmFloodContainerAllTimeBinEntry OBJECT-TYPE
     SYNTAX      CienaCesPmFloodContainerAllTimeBinEntry
     MAX-ACCESS  not-accessible
     STATUS      deprecated
     DESCRIPTION
           "An entry (conceptual row) in the cienaPortPmIGMPBinTable.

           This table lists the statistics for the All Time bin of the PM instance." 
     INDEX {cienaCesPmInstanceIndex}
     ::= { cienaCesPmFloodContainerAllTimeBinTable 1 }
        
 CienaCesPmFloodContainerAllTimeBinEntry ::=  SEQUENCE { 
 	 cienaCesPmFloodContainerAllTimeBinBcastDroppedBytes    Counter64,            
     cienaCesPmFloodContainerAllTimeBinBcastDroppedFrames   Counter64,             
     cienaCesPmFloodContainerAllTimeBinL2McastDroppedBytes    Counter64,
     cienaCesPmFloodContainerAllTimeBinL2McastDroppedFrames   Counter64,
     cienaCesPmFloodContainerAllTimeBinUnknownUnicastDroppedBytes    Counter64,
     cienaCesPmFloodContainerAllTimeBinUnknownUnicastDroppedFrames   Counter64
     } 
   cienaCesPmFloodContainerAllTimeBinBcastDroppedBytes  OBJECT-TYPE
     SYNTAX      Counter64 
     MAX-ACCESS  read-only
     STATUS      deprecated
     DESCRIPTION
             "Broadcast dropped bytes."
     ::= { cienaCesPmFloodContainerAllTimeBinEntry 1 }
     
   cienaCesPmFloodContainerAllTimeBinBcastDroppedFrames OBJECT-TYPE
      SYNTAX Counter64
      MAX-ACCESS read-only
      STATUS deprecated
      DESCRIPTION 
      		"Broadcast dropped frames."
      ::= { cienaCesPmFloodContainerAllTimeBinEntry 2 }

   cienaCesPmFloodContainerAllTimeBinL2McastDroppedBytes  OBJECT-TYPE
     SYNTAX Counter64
     MAX-ACCESS read-only
     STATUS deprecated
     DESCRIPTION 
      		"L2 multicast dropped bytes."
      ::= { cienaCesPmFloodContainerAllTimeBinEntry 3 }
     
    cienaCesPmFloodContainerAllTimeBinL2McastDroppedFrames  OBJECT-TYPE
     SYNTAX Counter64
     MAX-ACCESS read-only
     STATUS deprecated
     DESCRIPTION 
      		"L2 multicast dropped frames."
      ::= { cienaCesPmFloodContainerAllTimeBinEntry 4 }

     cienaCesPmFloodContainerAllTimeBinUnknownUnicastDroppedBytes OBJECT-TYPE
       SYNTAX Counter64
       MAX-ACCESS read-only
       STATUS deprecated
       DESCRIPTION
       		"Unknown unicast dropped bytes." 
       ::= { cienaCesPmFloodContainerAllTimeBinEntry 5 }
                    
      cienaCesPmFloodContainerAllTimeBinUnknownUnicastDroppedFrames OBJECT-TYPE
        SYNTAX Counter64
        MAX-ACCESS read-only
        STATUS deprecated
        DESCRIPTION
        	"Unknown unicast dropped frames."
        ::= { cienaCesPmFloodContainerAllTimeBinEntry 6 } 


   --FloodContainer Profile Stats, statistics bin

   cienaCesPmFloodContainerStatisticsBinTable OBJECT-TYPE
     SYNTAX     SEQUENCE OF CienaCesPmFloodContainerStatisticsBinEntry
     MAX-ACCESS not-accessible
     STATUS     current
     DESCRIPTION "The (conceptual) read-only table listing the bin statistics."
     ::= { cienaCesPmFloodContainerStats 6 }
     
   cienaCesPmFloodContainerStatisticsBinEntry OBJECT-TYPE
     SYNTAX      CienaCesPmFloodContainerStatisticsBinEntry
     MAX-ACCESS  not-accessible
     STATUS      current
     DESCRIPTION
           "An entry (conceptual row) in the cienaCesPmFloodContainerStatisticsBinTable.
           This table lists the statistics for the statistics bin of the PM instance." 
     INDEX {cienaCesPmInstanceIndex}
     ::= { cienaCesPmFloodContainerStatisticsBinTable 1 }
        
   CienaCesPmFloodContainerStatisticsBinEntry ::=  SEQUENCE { 
     cienaCesPmFloodContainerStatsBinStartTime                      DisplayString,
     cienaCesPmFloodContainerStatsBinClearTime                      DisplayString,
     cienaCesPmFloodContainerStatsBinBcastDroppedBytes              Counter64,            
     cienaCesPmFloodContainerStatsBinBcastDroppedFrames             Counter64,             
     cienaCesPmFloodContainerStatsBinL2McastDroppedBytes            Counter64,
     cienaCesPmFloodContainerStatsBinL2McastDroppedFrames           Counter64,
     cienaCesPmFloodContainerStatsBinUnknownUnicastDroppedBytes     Counter64,
     cienaCesPmFloodContainerStatsBinUnknownUnicastDroppedFrames    Counter64
   } 

   cienaCesPmFloodContainerStatsBinStartTime OBJECT-TYPE
     SYNTAX      DisplayString
     MAX-ACCESS  read-only
     STATUS      current
     DESCRIPTION "Collection start time of the bin."
     ::= { cienaCesPmFloodContainerStatisticsBinEntry 1 }

   cienaCesPmFloodContainerStatsBinClearTime OBJECT-TYPE
     SYNTAX      DisplayString
     MAX-ACCESS  read-only
     STATUS      current
     DESCRIPTION "Collection clear time of the bin."
     ::= { cienaCesPmFloodContainerStatisticsBinEntry 2 }

   cienaCesPmFloodContainerStatsBinBcastDroppedBytes  OBJECT-TYPE
     SYNTAX      Counter64 
     MAX-ACCESS  read-only
     STATUS      current
     DESCRIPTION "Broadcast dropped bytes."
     ::= { cienaCesPmFloodContainerStatisticsBinEntry 3 }
     
   cienaCesPmFloodContainerStatsBinBcastDroppedFrames OBJECT-TYPE
     SYNTAX      Counter64
     MAX-ACCESS  read-only
     STATUS      current
     DESCRIPTION "Broadcast dropped frames."
     ::= { cienaCesPmFloodContainerStatisticsBinEntry 4 }

   cienaCesPmFloodContainerStatsBinL2McastDroppedBytes  OBJECT-TYPE
     SYNTAX      Counter64
     MAX-ACCESS  read-only
     STATUS      current
     DESCRIPTION "L2 multicast dropped bytes."
     ::= { cienaCesPmFloodContainerStatisticsBinEntry 5 }

   cienaCesPmFloodContainerStatsBinL2McastDroppedFrames  OBJECT-TYPE
     SYNTAX      Counter64
     MAX-ACCESS  read-only
     STATUS      current
     DESCRIPTION "L2 multicast dropped frames."
     ::= { cienaCesPmFloodContainerStatisticsBinEntry 6 }

   cienaCesPmFloodContainerStatsBinUnknownUnicastDroppedBytes OBJECT-TYPE
     SYNTAX      Counter64
     MAX-ACCESS  read-only
     STATUS      current
     DESCRIPTION "Unknown unicast dropped bytes." 
     ::= { cienaCesPmFloodContainerStatisticsBinEntry 7 }
                    
   cienaCesPmFloodContainerStatsBinUnknownUnicastDroppedFrames OBJECT-TYPE
     SYNTAX      Counter64
     MAX-ACCESS  read-only
     STATUS      current
     DESCRIPTION "Unknown unicast dropped frames."
     ::= { cienaCesPmFloodContainerStatisticsBinEntry 8 } 


   --FloodContainer Profile Stats, total statistics bin

   cienaCesPmFloodContainerTotalStatisticsBinTable OBJECT-TYPE
     SYNTAX     SEQUENCE OF CienaCesPmFloodContainerTotalStatisticsBinEntry
     MAX-ACCESS not-accessible
     STATUS     current
     DESCRIPTION "The (conceptual) read-only table listing the bin statistics."
     ::= { cienaCesPmFloodContainerStats 7 }
     
   cienaCesPmFloodContainerTotalStatisticsBinEntry OBJECT-TYPE
     SYNTAX      CienaCesPmFloodContainerTotalStatisticsBinEntry
     MAX-ACCESS  not-accessible
     STATUS      current
     DESCRIPTION
           "An entry (conceptual row) in the cienaCesPmFloodContainerTotalStatisticsBinTable.
           This table lists the statistics for the total statistics bin of the PM instance." 
     INDEX {cienaCesPmInstanceIndex}
     ::= { cienaCesPmFloodContainerTotalStatisticsBinTable 1 }
        
   CienaCesPmFloodContainerTotalStatisticsBinEntry ::=  SEQUENCE { 
     cienaCesPmFloodContainerTotalStatsBinStartTime                      DisplayString,
     cienaCesPmFloodContainerTotalStatsBinBcastDroppedBytes              Counter64,            
     cienaCesPmFloodContainerTotalStatsBinBcastDroppedFrames             Counter64,             
     cienaCesPmFloodContainerTotalStatsBinL2McastDroppedBytes            Counter64,
     cienaCesPmFloodContainerTotalStatsBinL2McastDroppedFrames           Counter64,
     cienaCesPmFloodContainerTotalStatsBinUnknownUnicastDroppedBytes     Counter64,
     cienaCesPmFloodContainerTotalStatsBinUnknownUnicastDroppedFrames    Counter64
   } 

   cienaCesPmFloodContainerTotalStatsBinStartTime OBJECT-TYPE
     SYNTAX      DisplayString
     MAX-ACCESS  read-only
     STATUS      current
     DESCRIPTION "Collection start time of the bin."
     ::= { cienaCesPmFloodContainerTotalStatisticsBinEntry 1 }

   cienaCesPmFloodContainerTotalStatsBinBcastDroppedBytes  OBJECT-TYPE
     SYNTAX      Counter64 
     MAX-ACCESS  read-only
     STATUS      current
     DESCRIPTION "Broadcast dropped bytes."
     ::= { cienaCesPmFloodContainerTotalStatisticsBinEntry 2 }
     
   cienaCesPmFloodContainerTotalStatsBinBcastDroppedFrames OBJECT-TYPE
     SYNTAX      Counter64
     MAX-ACCESS  read-only
     STATUS      current
     DESCRIPTION "Broadcast dropped frames."
     ::= { cienaCesPmFloodContainerTotalStatisticsBinEntry 3 }

   cienaCesPmFloodContainerTotalStatsBinL2McastDroppedBytes  OBJECT-TYPE
     SYNTAX      Counter64
     MAX-ACCESS  read-only
     STATUS      current
     DESCRIPTION "L2 multicast dropped bytes."
     ::= { cienaCesPmFloodContainerTotalStatisticsBinEntry 4 }

   cienaCesPmFloodContainerTotalStatsBinL2McastDroppedFrames  OBJECT-TYPE
     SYNTAX      Counter64
     MAX-ACCESS  read-only
     STATUS      current
     DESCRIPTION "L2 multicast dropped frames."
     ::= { cienaCesPmFloodContainerTotalStatisticsBinEntry 5 }

   cienaCesPmFloodContainerTotalStatsBinUnknownUnicastDroppedBytes OBJECT-TYPE
     SYNTAX      Counter64
     MAX-ACCESS  read-only
     STATUS      current
     DESCRIPTION "Unknown unicast dropped bytes." 
     ::= { cienaCesPmFloodContainerTotalStatisticsBinEntry 6 }
                    
   cienaCesPmFloodContainerTotalStatsBinUnknownUnicastDroppedFrames OBJECT-TYPE
     SYNTAX      Counter64
     MAX-ACCESS  read-only
     STATUS      current
     DESCRIPTION "Unknown unicast dropped frames."
     ::= { cienaCesPmFloodContainerTotalStatisticsBinEntry 7 } 

 
 --
 -- BASIC Rx Bin
 --
  --BasicRx Profile Stats
  
 cienaCesPmBasicRxHistoryBinTable OBJECT-TYPE
     SYNTAX     SEQUENCE OF CienaCesPmBasicRxHistoryBinEntry
     MAX-ACCESS not-accessible
     STATUS     current
     DESCRIPTION
            "The (conceptual) read-only table listing the basic TxRx profile statistics."  
     ::= { cienaCesPmBasicRxStats 1 }
     
   cienaCesPmBasicRxHistoryBinEntry OBJECT-TYPE
     SYNTAX      CienaCesPmBasicRxHistoryBinEntry
     MAX-ACCESS  not-accessible
     STATUS      current
     DESCRIPTION
           "An entry (conceptual row) in the cienaCesPmBasicRxHistoryBinTable.

           This table lists the statistics for all the history bins of the PM instance, as 
           specified by the bin-count object of the PM instance.  History bins are displayed in the order
           so that #1 bin always represents the most recently completed bin and #2 - the bin previous to that
           and so on.
	       The statistics are displayed for only the instances with valid bins (with start time >0), 
	       as indicated by the operational state of the corresponding PM instance."  
     INDEX { cienaCesPmInstanceIndex, cienaCesPmBasicRxHistoryBinIndex }
     ::= { cienaCesPmBasicRxHistoryBinTable 1 }
        
 CienaCesPmBasicRxHistoryBinEntry ::=  SEQUENCE {
 	 cienaCesPmBasicRxHistoryBinIndex     	                Unsigned32,
     cienaCesPmBasicRxHistoryBinStartTime					DisplayString,
     cienaCesPmBasicRxHistoryBinEndTime					DisplayString,
     cienaCesPmBasicRxHistoryBinClearTime					DisplayString,
     cienaCesPmBasicRxHistoryBinDuration					Unsigned32,   
     cienaCesPmBasicRxHistoryBinState						PmBinState,
     cienaCesPmBasicRxHistoryBinBasicRxAcceptedBytes    	Counter64,
     cienaCesPmBasicRxHistoryBinBasicRxAcceptedFrames    	Counter64,
     cienaCesPmBasicRxHistoryBinBasicRxYellowBytes    		Counter64,
     cienaCesPmBasicRxHistoryBinBasicRxYellowFrames    	Counter64,
     cienaCesPmBasicRxHistoryBinBasicRxDroppedBytes    	Counter64,
     cienaCesPmBasicRxHistoryBinBasicRxDroppedFrames    	Counter64,
     cienaCesPmBasicRxHistoryBinBasicRxBytesPerSec         Counter64,
     cienaCesPmBasicRxHistoryBinBasicRxFramesPerSec        Counter64
   	}
  
   cienaCesPmBasicRxHistoryBinIndex OBJECT-TYPE
     SYNTAX      Unsigned32 (1..65535) 
     MAX-ACCESS  not-accessible
     STATUS      current
     DESCRIPTION
             "Bin number associated with the PmBasicTxRxBin entry."
     ::= { cienaCesPmBasicRxHistoryBinEntry 1 }

   cienaCesPmBasicRxHistoryBinStartTime   OBJECT-TYPE
     SYNTAX		DisplayString
     MAX-ACCESS	read-only
     STATUS		current
     DESCRIPTION "Collection start time of the bin."
     ::= { cienaCesPmBasicRxHistoryBinEntry 2	}
   
   cienaCesPmBasicRxHistoryBinEndTime	OBJECT-TYPE
   	SYNTAX	DisplayString
   	MAX-ACCESS read-only
   	STATUS 		current
   	DESCRIPTION	"Collection end time of the bin."
   	::= {cienaCesPmBasicRxHistoryBinEntry 3 }
   
   cienaCesPmBasicRxHistoryBinClearTime	OBJECT-TYPE
   	SYNTAX	DisplayString
   	MAX-ACCESS read-only
   	STATUS 		current
   	DESCRIPTION	"Collection clear time of the bin."
   	::= {cienaCesPmBasicRxHistoryBinEntry 4 }
   
   cienaCesPmBasicRxHistoryBinDuration OBJECT-TYPE
     SYNTAX      Unsigned32 (1..65535)  
     UNITS		"minutes"
     MAX-ACCESS  read-only
     STATUS      current
     DESCRIPTION
             "Duration of the bin."
     ::= { cienaCesPmBasicRxHistoryBinEntry 5 }
  
  cienaCesPmBasicRxHistoryBinState OBJECT-TYPE
     SYNTAX      PmBinState 
     MAX-ACCESS  read-only
     STATUS      current
     DESCRIPTION
             "State of the bin."
     ::= { cienaCesPmBasicRxHistoryBinEntry 6 }

  
  cienaCesPmBasicRxHistoryBinBasicRxAcceptedBytes OBJECT-TYPE
     SYNTAX      Counter64
     MAX-ACCESS  read-only
     STATUS      current
     DESCRIPTION
             "The number of accepted bytes on this PM instance."
     ::= { cienaCesPmBasicRxHistoryBinEntry 7 }

  cienaCesPmBasicRxHistoryBinBasicRxAcceptedFrames OBJECT-TYPE
     SYNTAX      Counter64
     MAX-ACCESS  read-only
     STATUS      current
     DESCRIPTION
             "The number of accepted frames on this PM instance."
     ::= { cienaCesPmBasicRxHistoryBinEntry 8 }

  cienaCesPmBasicRxHistoryBinBasicRxYellowBytes OBJECT-TYPE
     SYNTAX      Counter64
     MAX-ACCESS  read-only
     STATUS      current
     DESCRIPTION
             "The number of remarked bytes received on this PM instance."
     ::= { cienaCesPmBasicRxHistoryBinEntry 9 }

  cienaCesPmBasicRxHistoryBinBasicRxYellowFrames OBJECT-TYPE
     SYNTAX      Counter64
     MAX-ACCESS  read-only
     STATUS      current
     DESCRIPTION
             "The number of remarked frames received on this PM instance."
     ::= { cienaCesPmBasicRxHistoryBinEntry 10 }

  
  cienaCesPmBasicRxHistoryBinBasicRxDroppedBytes OBJECT-TYPE
     SYNTAX      Counter64
     MAX-ACCESS  read-only
     STATUS      current
     DESCRIPTION
             "The number of received bytes dropped on this PM instance."
     ::= { cienaCesPmBasicRxHistoryBinEntry 11 }

  cienaCesPmBasicRxHistoryBinBasicRxDroppedFrames OBJECT-TYPE
     SYNTAX      Counter64
     MAX-ACCESS  read-only
     STATUS      current
     DESCRIPTION
             "The number of received frames dropped on this PM instance."
     ::= { cienaCesPmBasicRxHistoryBinEntry 12 }

  cienaCesPmBasicRxHistoryBinBasicRxBytesPerSec OBJECT-TYPE
     SYNTAX      Counter64
     MAX-ACCESS  read-only
     STATUS      current
     DESCRIPTION
             "The number of bytes received per second on this PM instance."
     ::= { cienaCesPmBasicRxHistoryBinEntry 13 }

  cienaCesPmBasicRxHistoryBinBasicRxFramesPerSec OBJECT-TYPE
     SYNTAX      Counter64
     MAX-ACCESS  read-only
     STATUS      current
     DESCRIPTION
             "The number of frames received per second on this PM instance."
     ::= { cienaCesPmBasicRxHistoryBinEntry 14 }
   
 --BasicRx Profile Stats for interface
 
 cienaCesPmBasicRxCurrBinTable OBJECT-TYPE
     SYNTAX     SEQUENCE OF CienaCesPmBasicRxCurrBinEntry
     MAX-ACCESS not-accessible
     STATUS     current
     DESCRIPTION
            "The (conceptual) read-only table listing the basic Rx profile statistics."  
     ::= { cienaCesPmBasicRxStats 2 }
     
   cienaCesPmBasicRxCurrBinEntry OBJECT-TYPE
     SYNTAX      CienaCesPmBasicRxCurrBinEntry
     MAX-ACCESS  not-accessible
     STATUS      current
     DESCRIPTION
           "An entry (conceptual row) in the cienaCesPmBasicRxCurrBinTable.

           This table lists the statistics for the current bin of the PM instance." 
     INDEX {cienaCesPmInstanceIndex}
     ::= { cienaCesPmBasicRxCurrBinTable 1 }
        
 CienaCesPmBasicRxCurrBinEntry ::=  SEQUENCE {
   cienaCesPmBasicRxCurrBinStartTime					DisplayString,
   cienaCesPmBasicRxCurrBinClearedTime					DisplayString,
   cienaCesPmBasicRxCurrBinDuration					Unsigned32,   
   cienaCesPmBasicRxCurrBinState						PmBinState,
   cienaCesPmBasicRxCurrBinBasicRxAcceptedBytes    	Counter64,
   cienaCesPmBasicRxCurrBinBasicRxAcceptedFrames    	Counter64,
   cienaCesPmBasicRxCurrBinBasicRxYellowBytes    		Counter64,
   cienaCesPmBasicRxCurrBinBasicRxYellowFrames    		Counter64,
   cienaCesPmBasicRxCurrBinBasicRxDroppedBytes    		Counter64,
   cienaCesPmBasicRxCurrBinBasicRxDroppedFrames    	Counter64,
   cienaCesPmBasicRxCurrBinBasicRxBytesPerSec         	Counter64,
   cienaCesPmBasicRxCurrBinBasicRxFramesPerSec        	Counter64
  }
  cienaCesPmBasicRxCurrBinStartTime   OBJECT-TYPE
     SYNTAX		DisplayString
     MAX-ACCESS	read-only
     STATUS		current
     DESCRIPTION "Collection start time of the bin."
     ::= { cienaCesPmBasicRxCurrBinEntry 1	}

  cienaCesPmBasicRxCurrBinClearedTime   OBJECT-TYPE
     SYNTAX		DisplayString
     MAX-ACCESS	read-only
     STATUS		current
     DESCRIPTION "Cleared time of the bin."
     ::= { cienaCesPmBasicRxCurrBinEntry 2	}
                   
  cienaCesPmBasicRxCurrBinDuration OBJECT-TYPE
     SYNTAX      Unsigned32 (1..65535)  
     UNITS		"minutes"
     MAX-ACCESS  read-only
     STATUS      current
     DESCRIPTION
             "Duration of the bin."
     ::= { cienaCesPmBasicRxCurrBinEntry 3 }
  
  cienaCesPmBasicRxCurrBinState OBJECT-TYPE
     SYNTAX      PmBinState 
     MAX-ACCESS  read-only
     STATUS      current
     DESCRIPTION
             "State of the bin."
     ::= { cienaCesPmBasicRxCurrBinEntry 4 }

  
  cienaCesPmBasicRxCurrBinBasicRxAcceptedBytes OBJECT-TYPE
     SYNTAX      Counter64
     MAX-ACCESS  read-only
     STATUS      current
     DESCRIPTION
             "The number of accepted bytes on this PM instance."
     ::= { cienaCesPmBasicRxCurrBinEntry 5 }

  cienaCesPmBasicRxCurrBinBasicRxAcceptedFrames OBJECT-TYPE
     SYNTAX      Counter64
     MAX-ACCESS  read-only
     STATUS      current
     DESCRIPTION
             "The number of accepted frames on this PM instance."
     ::= { cienaCesPmBasicRxCurrBinEntry 6 }

  cienaCesPmBasicRxCurrBinBasicRxYellowBytes OBJECT-TYPE
     SYNTAX      Counter64
     MAX-ACCESS  read-only
     STATUS      current
     DESCRIPTION
             "The number of remarked bytes received on this PM instance."
     ::= { cienaCesPmBasicRxCurrBinEntry 7 }

  cienaCesPmBasicRxCurrBinBasicRxYellowFrames OBJECT-TYPE
     SYNTAX      Counter64
     MAX-ACCESS  read-only
     STATUS      current
     DESCRIPTION
             "The number of remarked frames received on this PM instance."
     ::= { cienaCesPmBasicRxCurrBinEntry 8 }

  
  cienaCesPmBasicRxCurrBinBasicRxDroppedBytes OBJECT-TYPE
     SYNTAX      Counter64
     MAX-ACCESS  read-only
     STATUS      current
     DESCRIPTION
             "The number of received bytes dropped on this PM instance."
     ::= { cienaCesPmBasicRxCurrBinEntry 9 }

  cienaCesPmBasicRxCurrBinBasicRxDroppedFrames OBJECT-TYPE
     SYNTAX      Counter64
     MAX-ACCESS  read-only
     STATUS      current
     DESCRIPTION
             "The number of received frames dropped on this PM instance."
     ::= { cienaCesPmBasicRxCurrBinEntry 10 }

  cienaCesPmBasicRxCurrBinBasicRxBytesPerSec OBJECT-TYPE
     SYNTAX      Counter64
     MAX-ACCESS  read-only
     STATUS      current
     DESCRIPTION
             "The number of bytes received per second on this PM instance."
     ::= { cienaCesPmBasicRxCurrBinEntry 11 }

  cienaCesPmBasicRxCurrBinBasicRxFramesPerSec OBJECT-TYPE
     SYNTAX      Counter64
     MAX-ACCESS  read-only
     STATUS      current
     DESCRIPTION
             "The number of frames received per second on this PM instance."
     ::= { cienaCesPmBasicRxCurrBinEntry 12 }

    
  --BasicRx Profile Stats - current 24 hour bin table  
  
 cienaCesPmBasicRxCurr24HBinTable OBJECT-TYPE
     SYNTAX     SEQUENCE OF CienaCesPmBasicRxCurr24HBinEntry
     MAX-ACCESS not-accessible
     STATUS     current
     DESCRIPTION
            "The (conceptual) read-only table listing the basic TxRx profile statistics."  
     ::= { cienaCesPmBasicRxStats 3 }
     
   cienaCesPmBasicRxCurr24HBinEntry OBJECT-TYPE
     SYNTAX      CienaCesPmBasicRxCurr24HBinEntry
     MAX-ACCESS  not-accessible
     STATUS      current
     DESCRIPTION
           "An entry (conceptual row) in the cienaCesPmBasicTxRxCurr24HBinTable.

           This table lists the statistics for the current 24 Hours bin." 
     INDEX {cienaCesPmInstanceIndex }
     ::= { cienaCesPmBasicRxCurr24HBinTable 1 }
        
 CienaCesPmBasicRxCurr24HBinEntry ::=  SEQUENCE {
 	 cienaCesPmBasicRxCurr24HBinStartTime				DisplayString,
     cienaCesPmBasicRxCurr24HBinEndTime				DisplayString,
     cienaCesPmBasicRxCurr24HBinClearedTime			DisplayString,
     cienaCesPmBasicRxCurr24HBinDuration				Unsigned32,   
     cienaCesPmBasicRxCurr24HBinState					PmBinState,
     cienaCesPmBasicRxCurr24HBinBasicRxAcceptedBytes 	Counter64,
     cienaCesPmBasicRxCurr24HBinBasicRxAcceptedFrames	Counter64,
     cienaCesPmBasicRxCurr24HBinBasicRxYellowBytes   	Counter64,
     cienaCesPmBasicRxCurr24HBinBasicRxYellowFrames  	Counter64,
     cienaCesPmBasicRxCurr24HBinBasicRxDroppedBytes  	Counter64,
     cienaCesPmBasicRxCurr24HBinBasicRxDroppedFrames 	Counter64,
     cienaCesPmBasicRxCurr24HBinBasicRxBytesPerSec    	Counter64,
     cienaCesPmBasicRxCurr24HBinBasicRxFramesPerSec   	Counter64
   }
   
   cienaCesPmBasicRxCurr24HBinStartTime   OBJECT-TYPE
     SYNTAX		DisplayString
     MAX-ACCESS	read-only
     STATUS		current
     DESCRIPTION "Collection start time of the bin."
     ::= { cienaCesPmBasicRxCurr24HBinEntry 1	}
   
   cienaCesPmBasicRxCurr24HBinEndTime 		OBJECT-TYPE
     SYNTAX		DisplayString
     MAX-ACCESS	read-only
     STATUS		current
     DESCRIPTION "Collection end time for the bin."
     ::= { cienaCesPmBasicRxCurr24HBinEntry 2	}

    cienaCesPmBasicRxCurr24HBinClearedTime   OBJECT-TYPE
     SYNTAX		DisplayString
     MAX-ACCESS	read-only
     STATUS		current
     DESCRIPTION "Cleared time of the bin."
     ::= { cienaCesPmBasicRxCurr24HBinEntry 3	}
                   
   cienaCesPmBasicRxCurr24HBinDuration OBJECT-TYPE
     SYNTAX      Unsigned32 (1..65535)  
     UNITS		 "minutes"
     MAX-ACCESS  read-only
     STATUS      current
     DESCRIPTION
             "Duration of the bin."
     ::= { cienaCesPmBasicRxCurr24HBinEntry 4 }
  
  cienaCesPmBasicRxCurr24HBinState OBJECT-TYPE
     SYNTAX      PmBinState 
     MAX-ACCESS  read-only
     STATUS      current
     DESCRIPTION
             "State of the bin."
     ::= { cienaCesPmBasicRxCurr24HBinEntry 5 }

  
  cienaCesPmBasicRxCurr24HBinBasicRxAcceptedBytes OBJECT-TYPE
     SYNTAX      Counter64
     MAX-ACCESS  read-only
     STATUS      current
     DESCRIPTION
             "The number of accepted bytes."
     ::= { cienaCesPmBasicRxCurr24HBinEntry 6 }

  cienaCesPmBasicRxCurr24HBinBasicRxAcceptedFrames OBJECT-TYPE
     SYNTAX      Counter64
     MAX-ACCESS  read-only
     STATUS      current
     DESCRIPTION
             "The number of accepted frames."
     ::= { cienaCesPmBasicRxCurr24HBinEntry 7 }

  cienaCesPmBasicRxCurr24HBinBasicRxYellowBytes OBJECT-TYPE
     SYNTAX      Counter64
     MAX-ACCESS  read-only
     STATUS      current
     DESCRIPTION
             "The number of remarked bytes received."
     ::= { cienaCesPmBasicRxCurr24HBinEntry 8 }

  cienaCesPmBasicRxCurr24HBinBasicRxYellowFrames OBJECT-TYPE
     SYNTAX      Counter64
     MAX-ACCESS  read-only
     STATUS      current
     DESCRIPTION
             "The number of remarked frames received."
     ::= { cienaCesPmBasicRxCurr24HBinEntry 9 }

  
  cienaCesPmBasicRxCurr24HBinBasicRxDroppedBytes OBJECT-TYPE
     SYNTAX      Counter64
     MAX-ACCESS  read-only
     STATUS      current
     DESCRIPTION
             "The number of received bytes dropped"
     ::= { cienaCesPmBasicRxCurr24HBinEntry 10 }

  cienaCesPmBasicRxCurr24HBinBasicRxDroppedFrames OBJECT-TYPE
     SYNTAX      Counter64
     MAX-ACCESS  read-only
     STATUS      current
     DESCRIPTION
             "The number of received frames dropped."
     ::= { cienaCesPmBasicRxCurr24HBinEntry 11 }

  cienaCesPmBasicRxCurr24HBinBasicRxBytesPerSec OBJECT-TYPE
     SYNTAX      Counter64
     MAX-ACCESS  read-only
     STATUS      current
     DESCRIPTION
             "The number of bytes received per second."
     ::= { cienaCesPmBasicRxCurr24HBinEntry 12 }

  cienaCesPmBasicRxCurr24HBinBasicRxFramesPerSec OBJECT-TYPE
     SYNTAX      Counter64
     MAX-ACCESS  read-only
     STATUS      current
     DESCRIPTION
             "The number of frames received per second."
     ::= { cienaCesPmBasicRxCurr24HBinEntry 13 }

 --BasicTxRx Profile Stats for PM instance - history 24 hour bin table  
  
 cienaCesPmBasicRxHist24HBinTable OBJECT-TYPE
     SYNTAX     SEQUENCE OF CienaCesPmBasicRxHist24HBinEntry
     MAX-ACCESS not-accessible
     STATUS     current
     DESCRIPTION
            "The (conceptual) read-only table listing the basic TxRx profile statistics."  
     ::= { cienaCesPmBasicRxStats 4 }
     
   cienaCesPmBasicRxHist24HBinEntry OBJECT-TYPE
     SYNTAX      CienaCesPmBasicRxHist24HBinEntry
     MAX-ACCESS  not-accessible
     STATUS      current
     DESCRIPTION
           "An entry (conceptual row) in the cienaCesPmBasicTxRxHist24HBinTable.
           This table lists the statistics for the history 24 hours bin." 
     INDEX {cienaCesPmInstanceIndex }
     ::= { cienaCesPmBasicRxHist24HBinTable 1 }
        
 CienaCesPmBasicRxHist24HBinEntry ::=  SEQUENCE {
 	 cienaCesPmBasicRxHist24HBinStartTime					DisplayString,
     cienaCesPmBasicRxHist24HBinDuration					Unsigned32,   
     cienaCesPmBasicRxHist24HBinState						PmBinState,
     cienaCesPmBasicRxHist24HBinBasicRxAcceptedBytes 		Counter64,
     cienaCesPmBasicRxHist24HBinBasicRxAcceptedFrames		Counter64,
     cienaCesPmBasicRxHist24HBinBasicRxYellowBytes   		Counter64,
     cienaCesPmBasicRxHist24HBinBasicRxYellowFrames  		Counter64,
     cienaCesPmBasicRxHist24HBinBasicRxDroppedBytes  		Counter64,
     cienaCesPmBasicRxHist24HBinBasicRxDroppedFrames 		Counter64,
     cienaCesPmBasicRxHist24HBinBasicRxBytesPerSec         Counter64,
     cienaCesPmBasicRxHist24HBinBasicRxFramesPerSec        Counter64,
     cienaCesPmBasicRxHist24HBinEndTime                    DisplayString,
     cienaCesPmBasicRxHist24HBinClearTime                  DisplayString
   }
   
   cienaCesPmBasicRxHist24HBinStartTime   OBJECT-TYPE
     SYNTAX		DisplayString
     MAX-ACCESS	read-only
     STATUS		current
     DESCRIPTION "Collection start time of the bin."
     ::= { cienaCesPmBasicRxHist24HBinEntry 1	}
   
   cienaCesPmBasicRxHist24HBinDuration OBJECT-TYPE
     SYNTAX      Unsigned32 (1..65535)  
     UNITS		"minutes"
     MAX-ACCESS  read-only
     STATUS      current
     DESCRIPTION
             "Duration of the bin."
     ::= { cienaCesPmBasicRxHist24HBinEntry 2 }
  
  cienaCesPmBasicRxHist24HBinState OBJECT-TYPE
     SYNTAX      PmBinState 
     MAX-ACCESS  read-only
     STATUS      current
     DESCRIPTION
             "State of the bin."
     ::= { cienaCesPmBasicRxHist24HBinEntry 3 }

  
  cienaCesPmBasicRxHist24HBinBasicRxAcceptedBytes OBJECT-TYPE
     SYNTAX      Counter64
     MAX-ACCESS  read-only
     STATUS      current
     DESCRIPTION
             "The number of accepted bytes on this PM instance."
     ::= { cienaCesPmBasicRxHist24HBinEntry 4 }

  cienaCesPmBasicRxHist24HBinBasicRxAcceptedFrames OBJECT-TYPE
     SYNTAX      Counter64
     MAX-ACCESS  read-only
     STATUS      current
     DESCRIPTION
             "The number of accepted frames on this PM instance."
     ::= { cienaCesPmBasicRxHist24HBinEntry 5 }

  cienaCesPmBasicRxHist24HBinBasicRxYellowBytes OBJECT-TYPE
     SYNTAX      Counter64
     MAX-ACCESS  read-only
     STATUS      current
     DESCRIPTION
             "The number of remarked bytes received on this PM instance."
     ::= { cienaCesPmBasicRxHist24HBinEntry 6 }

  cienaCesPmBasicRxHist24HBinBasicRxYellowFrames OBJECT-TYPE
     SYNTAX      Counter64
     MAX-ACCESS  read-only
     STATUS      current
     DESCRIPTION
             "The number of remarked frames received on this PM instance."
     ::= { cienaCesPmBasicRxHist24HBinEntry 7 }

  
  cienaCesPmBasicRxHist24HBinBasicRxDroppedBytes OBJECT-TYPE
     SYNTAX      Counter64
     MAX-ACCESS  read-only
     STATUS      current
     DESCRIPTION
             "The number of dropped bytes on this PM instance."
     ::= { cienaCesPmBasicRxHist24HBinEntry 8 }

  cienaCesPmBasicRxHist24HBinBasicRxDroppedFrames OBJECT-TYPE
     SYNTAX      Counter64
     MAX-ACCESS  read-only
     STATUS      current
     DESCRIPTION
             "The number of received frames dropped on this PM instance."
     ::= { cienaCesPmBasicRxHist24HBinEntry 9 }

  cienaCesPmBasicRxHist24HBinBasicRxBytesPerSec OBJECT-TYPE
     SYNTAX      Counter64
     MAX-ACCESS  read-only
     STATUS      current
     DESCRIPTION
             "The number of bytes received per second on this PM instance."
     ::= { cienaCesPmBasicRxHist24HBinEntry 10 }

  cienaCesPmBasicRxHist24HBinBasicRxFramesPerSec OBJECT-TYPE
     SYNTAX      Counter64
     MAX-ACCESS  read-only
     STATUS      current
     DESCRIPTION
             "The number of frames received per second on this PM instance."
     ::= { cienaCesPmBasicRxHist24HBinEntry 11 }

   cienaCesPmBasicRxHist24HBinEndTime OBJECT-TYPE
     SYNTAX      DisplayString
     MAX-ACCESS  read-only
     STATUS      current
     DESCRIPTION "Collection end time of the bin."
     ::= { cienaCesPmBasicRxHist24HBinEntry 12 }

   cienaCesPmBasicRxHist24HBinClearTime OBJECT-TYPE
     SYNTAX      DisplayString
     MAX-ACCESS  read-only
     STATUS      current
     DESCRIPTION "Collection clear time of the bin."
     ::= { cienaCesPmBasicRxHist24HBinEntry 13 }


 --BasicRx Profile Stats 
  
 cienaCesPmBasicRxAllTimeBinTable OBJECT-TYPE
     SYNTAX     SEQUENCE OF CienaCesPmBasicRxAllTimeBinEntry
     MAX-ACCESS not-accessible
     STATUS     deprecated
     DESCRIPTION
            "The (conceptual) read-only table listing the basic TxRx profile statistics."  
     ::= { cienaCesPmBasicRxStats 5 }
     
   cienaCesPmBasicRxAllTimeBinEntry OBJECT-TYPE
     SYNTAX      CienaCesPmBasicRxAllTimeBinEntry
     MAX-ACCESS  not-accessible
     STATUS      deprecated
     DESCRIPTION
           "An entry (conceptual row) in the cienaCesPmBasicTxRxAllTimeBinTable.

           This table lists the statistics for the All Time bin of the PM instance." 
     INDEX {cienaCesPmInstanceIndex}
     ::= { cienaCesPmBasicRxAllTimeBinTable 1 }
        
 CienaCesPmBasicRxAllTimeBinEntry ::=  SEQUENCE {
 	 cienaCesPmBasicRxAllTimeBinBasicRxAcceptedBytes    	Counter64,
     cienaCesPmBasicRxAllTimeBinBasicRxAcceptedFrames    	Counter64,
     cienaCesPmBasicRxAllTimeBinBasicRxYellowBytes    		Counter64,
     cienaCesPmBasicRxAllTimeBinBasicRxYellowFrames    	Counter64,
     cienaCesPmBasicRxAllTimeBinBasicRxDroppedBytes    	Counter64,
     cienaCesPmBasicRxAllTimeBinBasicRxDroppedFrames    	Counter64,
     cienaCesPmBasicRxAllTimeBinBasicRxBytesPerSec         Counter64,
     cienaCesPmBasicRxAllTimeBinBasicRxFramesPerSec        Counter64
 }
  cienaCesPmBasicRxAllTimeBinBasicRxAcceptedBytes OBJECT-TYPE
     SYNTAX      Counter64
     MAX-ACCESS  read-only
     STATUS      deprecated
     DESCRIPTION
             "The number of accepted bytes on this PM instance."
     ::= { cienaCesPmBasicRxAllTimeBinEntry 1 }

  cienaCesPmBasicRxAllTimeBinBasicRxAcceptedFrames OBJECT-TYPE
     SYNTAX      Counter64
     MAX-ACCESS  read-only
     STATUS      deprecated
     DESCRIPTION
             "The number of accepted frames on this PM instance."
     ::= { cienaCesPmBasicRxAllTimeBinEntry 2 }

  cienaCesPmBasicRxAllTimeBinBasicRxYellowBytes OBJECT-TYPE
     SYNTAX      Counter64
     MAX-ACCESS  read-only
     STATUS      deprecated
     DESCRIPTION
             "The number of remarked bytes received on this PM instance."
     ::= { cienaCesPmBasicRxAllTimeBinEntry 3 }

  cienaCesPmBasicRxAllTimeBinBasicRxYellowFrames OBJECT-TYPE
     SYNTAX      Counter64
     MAX-ACCESS  read-only
     STATUS      deprecated
     DESCRIPTION
             "The number of remarked frames received on this PM instance."
     ::= { cienaCesPmBasicRxAllTimeBinEntry 4 }

  
  cienaCesPmBasicRxAllTimeBinBasicRxDroppedBytes OBJECT-TYPE
     SYNTAX      Counter64
     MAX-ACCESS  read-only
     STATUS      deprecated
     DESCRIPTION
             "The number of received bytes dropped on this PM instance."
     ::= { cienaCesPmBasicRxAllTimeBinEntry 5 }

  cienaCesPmBasicRxAllTimeBinBasicRxDroppedFrames OBJECT-TYPE
     SYNTAX      Counter64
     MAX-ACCESS  read-only
     STATUS      deprecated
     DESCRIPTION
             "The number of received frames dropped on this PM instance."
     ::= { cienaCesPmBasicRxAllTimeBinEntry 6 }

  cienaCesPmBasicRxAllTimeBinBasicRxBytesPerSec OBJECT-TYPE
     SYNTAX      Counter64
     MAX-ACCESS  read-only
     STATUS      deprecated
     DESCRIPTION
             "The number of bytes received per second on this PM instance."
     ::= { cienaCesPmBasicRxAllTimeBinEntry 7 }

  cienaCesPmBasicRxAllTimeBinBasicRxFramesPerSec OBJECT-TYPE
     SYNTAX      Counter64
     MAX-ACCESS  read-only
     STATUS      deprecated
     DESCRIPTION
             "The number of frames received per second on this PM instance."
     ::= { cienaCesPmBasicRxAllTimeBinEntry 8 }


   --BasicRx Profile Stats, statistics bin
  
   cienaCesPmBasicRxStatisticsBinTable OBJECT-TYPE
     SYNTAX     SEQUENCE OF CienaCesPmBasicRxStatisticsBinEntry
     MAX-ACCESS not-accessible
     STATUS     current
     DESCRIPTION "The (conceptual) read-only table listing the bin statistics."
     ::= { cienaCesPmBasicRxStats 6 }
     
   cienaCesPmBasicRxStatisticsBinEntry OBJECT-TYPE
     SYNTAX      CienaCesPmBasicRxStatisticsBinEntry
     MAX-ACCESS  not-accessible
     STATUS      current
     DESCRIPTION
           "An entry (conceptual row) in the cienaCesPmBasicRxStatisticsBinTable.
           This table lists the statistics for the statistics bin of the PM instance." 
     INDEX {cienaCesPmInstanceIndex}
     ::= { cienaCesPmBasicRxStatisticsBinTable 1 }
        
   CienaCesPmBasicRxStatisticsBinEntry ::=  SEQUENCE {
     cienaCesPmBasicRxStatsBinStartTime                             DisplayString,
     cienaCesPmBasicRxStatsBinClearTime                             DisplayString,
     cienaCesPmBasicRxStatsBinBasicRxAcceptedBytes                  Counter64,
     cienaCesPmBasicRxStatsBinBasicRxAcceptedFrames                 Counter64,
     cienaCesPmBasicRxStatsBinBasicRxYellowBytes                    Counter64,
     cienaCesPmBasicRxStatsBinBasicRxYellowFrames                   Counter64,
     cienaCesPmBasicRxStatsBinBasicRxDroppedBytes                   Counter64,
     cienaCesPmBasicRxStatsBinBasicRxDroppedFrames                  Counter64,
     cienaCesPmBasicRxStatsBinBasicRxBytesPerSec                    Counter64,
     cienaCesPmBasicRxStatsBinBasicRxFramesPerSec                   Counter64
   }

   cienaCesPmBasicRxStatsBinStartTime OBJECT-TYPE
     SYNTAX      DisplayString
     MAX-ACCESS  read-only
     STATUS      current
     DESCRIPTION "Collection start time of the bin."
     ::= { cienaCesPmBasicRxStatisticsBinEntry 1 }

   cienaCesPmBasicRxStatsBinClearTime OBJECT-TYPE
     SYNTAX      DisplayString
     MAX-ACCESS  read-only
     STATUS      current
     DESCRIPTION "Collection clear time of the bin."
     ::= { cienaCesPmBasicRxStatisticsBinEntry 2 }

   cienaCesPmBasicRxStatsBinBasicRxAcceptedBytes OBJECT-TYPE
     SYNTAX      Counter64
     MAX-ACCESS  read-only
     STATUS      current
     DESCRIPTION
             "The number of accepted bytes on this PM instance."
     ::= { cienaCesPmBasicRxStatisticsBinEntry 3 }

   cienaCesPmBasicRxStatsBinBasicRxAcceptedFrames OBJECT-TYPE
     SYNTAX      Counter64
     MAX-ACCESS  read-only
     STATUS      current
     DESCRIPTION
             "The number of accepted frames on this PM instance."
     ::= { cienaCesPmBasicRxStatisticsBinEntry 4 }

   cienaCesPmBasicRxStatsBinBasicRxYellowBytes OBJECT-TYPE
     SYNTAX      Counter64
     MAX-ACCESS  read-only
     STATUS      current
     DESCRIPTION
             "The number of remarked bytes received on this PM instance."
     ::= { cienaCesPmBasicRxStatisticsBinEntry 5 }

   cienaCesPmBasicRxStatsBinBasicRxYellowFrames OBJECT-TYPE
     SYNTAX      Counter64
     MAX-ACCESS  read-only
     STATUS      current
     DESCRIPTION
             "The number of remarked frames received on this PM instance."
     ::= { cienaCesPmBasicRxStatisticsBinEntry 6 }
  
   cienaCesPmBasicRxStatsBinBasicRxDroppedBytes OBJECT-TYPE
     SYNTAX      Counter64
     MAX-ACCESS  read-only
     STATUS      current
     DESCRIPTION
             "The number of received bytes dropped on this PM instance."
     ::= { cienaCesPmBasicRxStatisticsBinEntry 7 }

   cienaCesPmBasicRxStatsBinBasicRxDroppedFrames OBJECT-TYPE
     SYNTAX      Counter64
     MAX-ACCESS  read-only
     STATUS      current
     DESCRIPTION
             "The number of received frames dropped on this PM instance."
     ::= { cienaCesPmBasicRxStatisticsBinEntry 8 }

   cienaCesPmBasicRxStatsBinBasicRxBytesPerSec OBJECT-TYPE
     SYNTAX      Counter64
     MAX-ACCESS  read-only
     STATUS      current
     DESCRIPTION
             "The number of bytes received per second on this PM instance."
     ::= { cienaCesPmBasicRxStatisticsBinEntry 9 }

   cienaCesPmBasicRxStatsBinBasicRxFramesPerSec OBJECT-TYPE
     SYNTAX      Counter64
     MAX-ACCESS  read-only
     STATUS      current
     DESCRIPTION
             "The number of frames received per second on this PM instance."
     ::= { cienaCesPmBasicRxStatisticsBinEntry 10 }


   --BasicRx Profile Stats, total statistics bin
  
   cienaCesPmBasicRxTotalStatisticsBinTable OBJECT-TYPE
     SYNTAX     SEQUENCE OF CienaCesPmBasicRxTotalStatisticsBinEntry
     MAX-ACCESS not-accessible
     STATUS     current
     DESCRIPTION "The (conceptual) read-only table listing the bin statistics."
     ::= { cienaCesPmBasicRxStats 7 }
     
   cienaCesPmBasicRxTotalStatisticsBinEntry OBJECT-TYPE
     SYNTAX      CienaCesPmBasicRxTotalStatisticsBinEntry
     MAX-ACCESS  not-accessible
     STATUS      current
     DESCRIPTION
           "An entry (conceptual row) in the cienaCesPmBasicRxTotalStatisticsBinTable.
           This table lists the statistics for the statistics bin of the PM instance." 
     INDEX {cienaCesPmInstanceIndex}
     ::= { cienaCesPmBasicRxTotalStatisticsBinTable 1 }
        
   CienaCesPmBasicRxTotalStatisticsBinEntry ::=  SEQUENCE {
     cienaCesPmBasicRxTotalStatsBinStartTime                        DisplayString,
     cienaCesPmBasicRxTotalStatsBinBasicRxAcceptedBytes             Counter64,
     cienaCesPmBasicRxTotalStatsBinBasicRxAcceptedFrames            Counter64,
     cienaCesPmBasicRxTotalStatsBinBasicRxYellowBytes               Counter64,
     cienaCesPmBasicRxTotalStatsBinBasicRxYellowFrames              Counter64,
     cienaCesPmBasicRxTotalStatsBinBasicRxDroppedBytes              Counter64,
     cienaCesPmBasicRxTotalStatsBinBasicRxDroppedFrames             Counter64,
     cienaCesPmBasicRxTotalStatsBinBasicRxBytesPerSec               Counter64,
     cienaCesPmBasicRxTotalStatsBinBasicRxFramesPerSec              Counter64
   }

   cienaCesPmBasicRxTotalStatsBinStartTime OBJECT-TYPE
     SYNTAX      DisplayString
     MAX-ACCESS  read-only
     STATUS      current
     DESCRIPTION "Collection start time of the bin."
     ::= { cienaCesPmBasicRxTotalStatisticsBinEntry 1 }

   cienaCesPmBasicRxTotalStatsBinBasicRxAcceptedBytes OBJECT-TYPE
     SYNTAX      Counter64
     MAX-ACCESS  read-only
     STATUS      current
     DESCRIPTION
             "The number of accepted bytes on this PM instance."
     ::= { cienaCesPmBasicRxTotalStatisticsBinEntry 2 }

   cienaCesPmBasicRxTotalStatsBinBasicRxAcceptedFrames OBJECT-TYPE
     SYNTAX      Counter64
     MAX-ACCESS  read-only
     STATUS      current
     DESCRIPTION
             "The number of accepted frames on this PM instance."
     ::= { cienaCesPmBasicRxTotalStatisticsBinEntry 3 }

   cienaCesPmBasicRxTotalStatsBinBasicRxYellowBytes OBJECT-TYPE
     SYNTAX      Counter64
     MAX-ACCESS  read-only
     STATUS      current
     DESCRIPTION
             "The number of remarked bytes received on this PM instance."
     ::= { cienaCesPmBasicRxTotalStatisticsBinEntry 4 }

   cienaCesPmBasicRxTotalStatsBinBasicRxYellowFrames OBJECT-TYPE
     SYNTAX      Counter64
     MAX-ACCESS  read-only
     STATUS      current
     DESCRIPTION
             "The number of remarked frames received on this PM instance."
     ::= { cienaCesPmBasicRxTotalStatisticsBinEntry 5 }

   cienaCesPmBasicRxTotalStatsBinBasicRxDroppedBytes OBJECT-TYPE
     SYNTAX      Counter64
     MAX-ACCESS  read-only
     STATUS      current
     DESCRIPTION
             "The number of received bytes dropped on this PM instance."
     ::= { cienaCesPmBasicRxTotalStatisticsBinEntry 6 }

   cienaCesPmBasicRxTotalStatsBinBasicRxDroppedFrames OBJECT-TYPE
     SYNTAX      Counter64
     MAX-ACCESS  read-only
     STATUS      current
     DESCRIPTION
             "The number of received frames dropped on this PM instance."
     ::= { cienaCesPmBasicRxTotalStatisticsBinEntry 7 }

   cienaCesPmBasicRxTotalStatsBinBasicRxBytesPerSec OBJECT-TYPE
     SYNTAX      Counter64
     MAX-ACCESS  read-only
     STATUS      current
     DESCRIPTION
             "The number of bytes received per second on this PM instance."
     ::= { cienaCesPmBasicRxTotalStatisticsBinEntry 8 }

   cienaCesPmBasicRxTotalStatsBinBasicRxFramesPerSec OBJECT-TYPE
     SYNTAX      Counter64
     MAX-ACCESS  read-only
     STATUS      current
     DESCRIPTION
             "The number of frames received per second on this PM instance."
     ::= { cienaCesPmBasicRxTotalStatisticsBinEntry 9 }

 
 --
-- Queue Group Bin
--
  --QueueGroup Profile Stats
  
 cienaCesPmQueueGroupHistoryBinTable OBJECT-TYPE
     SYNTAX     SEQUENCE OF CienaCesPmQueueGroupHistoryBinEntry
     MAX-ACCESS not-accessible
     STATUS     current
     DESCRIPTION
            "The (conceptual) read-only table listing the egress queue profile statistics."  
     ::= { cienaCesPmQueueGroupStats 1 }
     
   cienaCesPmQueueGroupHistoryBinEntry OBJECT-TYPE
     SYNTAX      CienaCesPmQueueGroupHistoryBinEntry
     MAX-ACCESS  not-accessible
     STATUS      current
     DESCRIPTION
           "An entry (conceptual row) in the cienaCesPmQueueGroupHistoryBinTable.

           This table lists the statistics for all the history bins of the PM instance, as 
           specified by the bin-count object of the PM instance.  History bins are displayed in the order
           that #1 bin always represents the most recently completed bin and #2 - the bin previous to that
           and so on.
               The statistics are displayed for only the instances with valid bins (with start time >0), 
               as indicated by the operational state of the corresponding PM instance."  
     INDEX { cienaCesPmInstanceIndex, cienaCesPmQueueGroupHistoryBinIndex,cienaCesPmQueueGroupQueueIndex }
     ::= { cienaCesPmQueueGroupHistoryBinTable 1 }
        
 CienaCesPmQueueGroupHistoryBinEntry ::=  SEQUENCE {
     cienaCesPmQueueGroupHistoryBinIndex                      Unsigned32,
     cienaCesPmQueueGroupQueueIndex                           Integer32,
     cienaCesPmQueueGroupHistoryBinStartTime                  DisplayString,
     cienaCesPmQueueGroupHistoryBinEndTime                    DisplayString,
     cienaCesPmQueueGroupHistoryBinClearTime                  DisplayString,
     cienaCesPmQueueGroupHistoryBinDuration                   Unsigned32,   
     cienaCesPmQueueGroupHistoryBinState                      PmBinState,
     cienaCesPmQueueGroupHistoryBinEnqueuedBytes              Counter64,
     cienaCesPmQueueGroupHistoryBinEnqueuedFrames             Counter64,
     cienaCesPmQueueGroupHistoryBinDroppedBytes              Counter64,
     cienaCesPmQueueGroupHistoryBinDroppedFrames              Counter64
     }

    cienaCesPmQueueGroupHistoryBinIndex OBJECT-TYPE
     SYNTAX      Unsigned32 (1..65535) 
     MAX-ACCESS  not-accessible
     STATUS      current
     DESCRIPTION
             "Bin number associated with the PmEgressQueueBin entry."
     ::= { cienaCesPmQueueGroupHistoryBinEntry 1 }

    cienaCesPmQueueGroupQueueIndex               OBJECT-TYPE
               SYNTAX                                                Integer32(0..65535) 
               MAX-ACCESS                     not-accessible
               STATUS                                                current
               DESCRIPTION
                               "This object indicates a unique index for every queue
                                in the queue group."
               ::= { cienaCesPmQueueGroupHistoryBinEntry 2 }    
 
 cienaCesPmQueueGroupHistoryBinStartTime   OBJECT-TYPE
     SYNTAX             DisplayString
     MAX-ACCESS read-only
    STATUS             current
     DESCRIPTION "Collection start time of the bin."
     ::= { cienaCesPmQueueGroupHistoryBinEntry 3 }
   
   cienaCesPmQueueGroupHistoryBinEndTime        OBJECT-TYPE
        SYNTAX  DisplayString
        MAX-ACCESS read-only
        STATUS          current
        DESCRIPTION     "Collection end time of the bin."
        ::= {cienaCesPmQueueGroupHistoryBinEntry 4 }
   
   cienaCesPmQueueGroupHistoryBinClearTime      OBJECT-TYPE
        SYNTAX  DisplayString
        MAX-ACCESS read-only
        STATUS          current
        DESCRIPTION     "Collection clear time of the bin."
        ::= {cienaCesPmQueueGroupHistoryBinEntry 5 }
   
   cienaCesPmQueueGroupHistoryBinDuration OBJECT-TYPE
     SYNTAX      Unsigned32 (1..65535)  
     UNITS              "minutes"
     MAX-ACCESS  read-only
     STATUS      current
     DESCRIPTION
             "Duration of the bin."
     ::= { cienaCesPmQueueGroupHistoryBinEntry 6 }
  
  cienaCesPmQueueGroupHistoryBinState OBJECT-TYPE
     SYNTAX      PmBinState 
     MAX-ACCESS  read-only
     STATUS      current
     DESCRIPTION
             "State of the bin."
     ::= { cienaCesPmQueueGroupHistoryBinEntry 7 }
   
   cienaCesPmQueueGroupHistoryBinEnqueuedBytes OBJECT-TYPE
     SYNTAX      Counter64
     MAX-ACCESS  read-only
     STATUS      current
     DESCRIPTION
             "The number of enqueued bytes on this PM instance for this cienaCesPmQueueGroupQueueIndex."
     ::= { cienaCesPmQueueGroupHistoryBinEntry 8 }

  cienaCesPmQueueGroupHistoryBinEnqueuedFrames OBJECT-TYPE
     SYNTAX      Counter64
     MAX-ACCESS  read-only
     STATUS      current
     DESCRIPTION
             "The number of enqueued frames on this PM instance for this cienaCesPmQueueGroupQueueIndex."
     ::= { cienaCesPmQueueGroupHistoryBinEntry 9 }

  cienaCesPmQueueGroupHistoryBinDroppedBytes OBJECT-TYPE
     SYNTAX      Counter64
     MAX-ACCESS  read-only
     STATUS      current
     DESCRIPTION
             "The number of received bytes dropped on this PM instance for this cienaCesPmQueueGroupQueueIndex."
     ::= { cienaCesPmQueueGroupHistoryBinEntry 10 }

  cienaCesPmQueueGroupHistoryBinDroppedFrames OBJECT-TYPE
     SYNTAX      Counter64
     MAX-ACCESS  read-only
     STATUS      current
     DESCRIPTION
             "The number of received frames dropped on this PM instance for this cienaCesPmQueueGroupQueueIndex."
     ::= { cienaCesPmQueueGroupHistoryBinEntry 11 }

 --QueueGroup Profile Stats - Current  bin table  
  
 cienaCesPmQueueGroupCurrBinTable OBJECT-TYPE
     SYNTAX     SEQUENCE OF CienaCesPmQueueGroupCurrBinEntry
     MAX-ACCESS not-accessible
     STATUS     current
     DESCRIPTION
            "The (conceptual) read-only table listing the queue group profile statistics."  
     ::= { cienaCesPmQueueGroupStats 2 }
     
   cienaCesPmQueueGroupCurrBinEntry OBJECT-TYPE
     SYNTAX      CienaCesPmQueueGroupCurrBinEntry
     MAX-ACCESS  not-accessible
     STATUS      current
     DESCRIPTION
           "An entry (conceptual row) in the cienaCesPmQueueGroupCurrBinTable.

           This table lists the statistics for the current bin of the PM instance." 
     INDEX {cienaCesPmInstanceIndex ,cienaCesPmQueueGroupQueueIndex}
     ::= { cienaCesPmQueueGroupCurrBinTable 1 }
        
 CienaCesPmQueueGroupCurrBinEntry ::=  SEQUENCE {
     cienaCesPmQueueGroupCurrBinStartTime                   DisplayString,
     cienaCesPmQueueGroupCurrBinClearedTime                 DisplayString,
     cienaCesPmQueueGroupCurrBinDuration                    Unsigned32,   
     cienaCesPmQueueGroupCurrBinState                       PmBinState,
     cienaCesPmQueueGroupCurrBinEnqueuedBytes               Counter64,
     cienaCesPmQueueGroupCurrBinEnqueuedFrames              Counter64,
     cienaCesPmQueueGroupCurrBinDroppedBytes                Counter64,
     cienaCesPmQueueGroupCurrBinDroppedFrames               Counter64
   }
   
   cienaCesPmQueueGroupCurrBinStartTime   OBJECT-TYPE
     SYNTAX             DisplayString
     MAX-ACCESS read-only
     STATUS             current
     DESCRIPTION "Collection start time of the bin."
     ::= { cienaCesPmQueueGroupCurrBinEntry 1        }
   
    cienaCesPmQueueGroupCurrBinClearedTime   OBJECT-TYPE
     SYNTAX             DisplayString
     MAX-ACCESS read-only
     STATUS             current
     DESCRIPTION "Cleared time of the bin."
     ::= { cienaCesPmQueueGroupCurrBinEntry 2        }
                   
   cienaCesPmQueueGroupCurrBinDuration OBJECT-TYPE
     SYNTAX      Unsigned32 (1..65535)  
     UNITS               "minutes"
     MAX-ACCESS  read-only
     STATUS      current
     DESCRIPTION
             "Duration of the bin."
     ::= { cienaCesPmQueueGroupCurrBinEntry 3 }
  
  cienaCesPmQueueGroupCurrBinState OBJECT-TYPE
     SYNTAX      PmBinState 
     MAX-ACCESS  read-only
     STATUS      current
     DESCRIPTION
             "State of the bin."
     ::= { cienaCesPmQueueGroupCurrBinEntry 4 }

  
  cienaCesPmQueueGroupCurrBinEnqueuedBytes OBJECT-TYPE
     SYNTAX      Counter64
     MAX-ACCESS  read-only
     STATUS      current
     DESCRIPTION
             "The number of enqueued bytes for this cienaCesPmQueueGroupQueueIndex"
     ::= { cienaCesPmQueueGroupCurrBinEntry 5 }

  cienaCesPmQueueGroupCurrBinEnqueuedFrames OBJECT-TYPE
     SYNTAX      Counter64
     MAX-ACCESS  read-only
     STATUS      current
     DESCRIPTION
             "The number of enqueued frames for this cienaCesPmQueueGroupQueueIndex"
     ::= { cienaCesPmQueueGroupCurrBinEntry 6 }
  
  cienaCesPmQueueGroupCurrBinDroppedBytes OBJECT-TYPE
     SYNTAX      Counter64
     MAX-ACCESS  read-only
     STATUS      current
     DESCRIPTION
             "The number of received bytes dropped for this cienaCesPmQueueGroupQueueIndex"
     ::= { cienaCesPmQueueGroupCurrBinEntry 7 }

  cienaCesPmQueueGroupCurrBinDroppedFrames OBJECT-TYPE
     SYNTAX      Counter64
     MAX-ACCESS  read-only
     STATUS      current
     DESCRIPTION
             "The number of received frames dropped for this cienaCesPmQueueGroupQueueIndex."
     ::= { cienaCesPmQueueGroupCurrBinEntry 8 }

 --QueueGroup Profile Stats - current 24 hour bin table  
  
 cienaCesPmQueueGroupCurr24HBinTable OBJECT-TYPE
     SYNTAX     SEQUENCE OF CienaCesPmQueueGroupCurr24HBinEntry
     MAX-ACCESS not-accessible
     STATUS     current
     DESCRIPTION
            "The (conceptual) read-only table listing the queue group profile statistics."  
     ::= { cienaCesPmQueueGroupStats 3 }
     
   cienaCesPmQueueGroupCurr24HBinEntry OBJECT-TYPE
     SYNTAX      CienaCesPmQueueGroupCurr24HBinEntry
     MAX-ACCESS  not-accessible
     STATUS      current
     DESCRIPTION
           "An entry (conceptual row) in the cienaCesPmQueueGroupCurr24HBinTable.

           This table lists the statistics for the current 24 hours bin." 
     INDEX {cienaCesPmInstanceIndex ,cienaCesPmQueueGroupQueueIndex}
     ::= { cienaCesPmQueueGroupCurr24HBinTable 1 }
        
 CienaCesPmQueueGroupCurr24HBinEntry ::=  SEQUENCE {
     cienaCesPmQueueGroupCurr24HBinStartTime                                   DisplayString,
     cienaCesPmQueueGroupCurr24HBinEndTime                                     DisplayString,
     cienaCesPmQueueGroupCurr24HBinClearedTime                                 DisplayString,
     cienaCesPmQueueGroupCurr24HBinDuration                                    Unsigned32,   
     cienaCesPmQueueGroupCurr24HBinState                                       PmBinState,
     cienaCesPmQueueGroupCurr24HBinEnqueuedBytes                Counter64,
     cienaCesPmQueueGroupCurr24HBinEnqueuedFrames               Counter64,
     cienaCesPmQueueGroupCurr24HBinDroppedBytes                 Counter64,
     cienaCesPmQueueGroupCurr24HBinDroppedFrames                Counter64
   }
   
   cienaCesPmQueueGroupCurr24HBinStartTime   OBJECT-TYPE
     SYNTAX             DisplayString
     MAX-ACCESS read-only
     STATUS             current
     DESCRIPTION "Collection start time of the bin."
     ::= { cienaCesPmQueueGroupCurr24HBinEntry 1        }
   
   cienaCesPmQueueGroupCurr24HBinEndTime                OBJECT-TYPE
     SYNTAX             DisplayString
     MAX-ACCESS read-only
     STATUS             current
     DESCRIPTION "Collection end time for the bin."
     ::= { cienaCesPmQueueGroupCurr24HBinEntry 2        }

    cienaCesPmQueueGroupCurr24HBinClearedTime   OBJECT-TYPE
     SYNTAX             DisplayString
     MAX-ACCESS read-only
     STATUS             current
     DESCRIPTION "Cleared time of the bin."
     ::= { cienaCesPmQueueGroupCurr24HBinEntry 3        }
                   
   cienaCesPmQueueGroupCurr24HBinDuration OBJECT-TYPE
     SYNTAX      Unsigned32 (1..65535)  
     UNITS               "minutes"
     MAX-ACCESS  read-only
     STATUS      current
     DESCRIPTION
             "Duration of the bin."
     ::= { cienaCesPmQueueGroupCurr24HBinEntry 4 }
  
  cienaCesPmQueueGroupCurr24HBinState OBJECT-TYPE
     SYNTAX      PmBinState 
     MAX-ACCESS  read-only
     STATUS      current
     DESCRIPTION
             "State of the bin."
     ::= { cienaCesPmQueueGroupCurr24HBinEntry 5 }

  
  cienaCesPmQueueGroupCurr24HBinEnqueuedBytes OBJECT-TYPE
     SYNTAX      Counter64
     MAX-ACCESS  read-only
     STATUS      current
     DESCRIPTION
             "The number of enqueued bytes for this cienaCesPmQueueGroupQueueIndex."
     ::= { cienaCesPmQueueGroupCurr24HBinEntry 6 }

  cienaCesPmQueueGroupCurr24HBinEnqueuedFrames OBJECT-TYPE
     SYNTAX      Counter64
     MAX-ACCESS  read-only
     STATUS      current
     DESCRIPTION
             "The number of enqueued frames for this cienaCesPmQueueGroupQueueIndex."
     ::= { cienaCesPmQueueGroupCurr24HBinEntry 7 }
  
  cienaCesPmQueueGroupCurr24HBinDroppedBytes OBJECT-TYPE
     SYNTAX      Counter64
     MAX-ACCESS  read-only
     STATUS      current
     DESCRIPTION
             "The number of received bytes dropped for this cienaCesPmQueueGroupQueueIndex."
     ::= { cienaCesPmQueueGroupCurr24HBinEntry 8 }

  cienaCesPmQueueGroupCurr24HBinDroppedFrames OBJECT-TYPE
     SYNTAX      Counter64
     MAX-ACCESS  read-only
     STATUS      current
     DESCRIPTION
             "The number of received frames dropped for this cienaCesPmQueueGroupQueueIndex."
     ::= { cienaCesPmQueueGroupCurr24HBinEntry 9 }

   
   --QueueGroup Profile Stats for PM instance - history 24 hour bin table  
  
 cienaCesPmQueueGroupHist24HBinTable OBJECT-TYPE
     SYNTAX     SEQUENCE OF CienaCesPmQueueGroupHist24HBinEntry
     MAX-ACCESS not-accessible
     STATUS     current
     DESCRIPTION
            "The (conceptual) read-only table listing the queue group profile statistics."  
     ::= { cienaCesPmQueueGroupStats 4 }
     
   cienaCesPmQueueGroupHist24HBinEntry OBJECT-TYPE
     SYNTAX      CienaCesPmQueueGroupHist24HBinEntry
     MAX-ACCESS  not-accessible
     STATUS      current
     DESCRIPTION
           "An entry (conceptual row) in the cienaCesPmQueueGroupHist24HBinTable.
           This table lists the statistics for the history 24 hours bin." 
     INDEX {cienaCesPmInstanceIndex,cienaCesPmQueueGroupQueueIndex }
     ::= { cienaCesPmQueueGroupHist24HBinTable 1 }
        
 CienaCesPmQueueGroupHist24HBinEntry ::=  SEQUENCE {
     cienaCesPmQueueGroupHist24HBinStartTime                                   DisplayString,
     cienaCesPmQueueGroupHist24HBinDuration                                    Unsigned32,   
     cienaCesPmQueueGroupHist24HBinState                                       PmBinState,
     cienaCesPmQueueGroupHist24HBinEnqueuedBytes                Counter64,
     cienaCesPmQueueGroupHist24HBinEnqueuedFrames               Counter64,
     cienaCesPmQueueGroupHist24HBinDroppedBytes                 Counter64,
     cienaCesPmQueueGroupHist24HBinDroppedFrames                Counter64,
     cienaCesPmQueueGroupHist24HBinEndTime                      DisplayString,
     cienaCesPmQueueGroupHist24HBinClearTime                    DisplayString
   }

 cienaCesPmQueueGroupHist24HBinStartTime   OBJECT-TYPE
     SYNTAX             DisplayString
     MAX-ACCESS read-only
     STATUS             current
     DESCRIPTION "Collection start time of the bin."
     ::= { cienaCesPmQueueGroupHist24HBinEntry 1        }
   
   cienaCesPmQueueGroupHist24HBinDuration OBJECT-TYPE
     SYNTAX      Unsigned32 (1..65535)  
     UNITS              "minutes"
     MAX-ACCESS  read-only
     STATUS      current
     DESCRIPTION
             "Duration of the bin."
     ::= { cienaCesPmQueueGroupHist24HBinEntry 2 }
  
  cienaCesPmQueueGroupHist24HBinState OBJECT-TYPE
     SYNTAX      PmBinState 
     MAX-ACCESS  read-only
     STATUS      current
     DESCRIPTION
             "State of the bin."
     ::= { cienaCesPmQueueGroupHist24HBinEntry 3 }

  cienaCesPmQueueGroupHist24HBinEnqueuedBytes OBJECT-TYPE
     SYNTAX      Counter64
     MAX-ACCESS  read-only
     STATUS      current
     DESCRIPTION
             "The number of enqueued bytes on this PM instance for this cienaCesPmQueueGroupQueueIndex."
     ::= { cienaCesPmQueueGroupHist24HBinEntry 4 }

  cienaCesPmQueueGroupHist24HBinEnqueuedFrames OBJECT-TYPE
     SYNTAX      Counter64
     MAX-ACCESS  read-only
     STATUS      current
     DESCRIPTION
             "The number of enqueued frames on this PM instance for this cienaCesPmQueueGroupQueueIndex."
     ::= { cienaCesPmQueueGroupHist24HBinEntry 5 }
  
    cienaCesPmQueueGroupHist24HBinDroppedBytes OBJECT-TYPE
     SYNTAX      Counter64
     MAX-ACCESS  read-only
     STATUS      current
     DESCRIPTION
             "The number of dropped bytes on this PM instance for this cienaCesPmQueueGroupQueueIndex."
     ::= { cienaCesPmQueueGroupHist24HBinEntry 6 }

  cienaCesPmQueueGroupHist24HBinDroppedFrames OBJECT-TYPE
     SYNTAX      Counter64
     MAX-ACCESS  read-only
     STATUS      current
     DESCRIPTION
             "The number of received frames dropped on this PM instance for this cienaCesPmQueueGroupQueueIndex."
     ::= { cienaCesPmQueueGroupHist24HBinEntry 7 }

   cienaCesPmQueueGroupHist24HBinEndTime OBJECT-TYPE
     SYNTAX      DisplayString
     MAX-ACCESS  read-only
     STATUS      current
     DESCRIPTION "Collection end time of the bin."
     ::= { cienaCesPmQueueGroupHist24HBinEntry 8 }

   cienaCesPmQueueGroupHist24HBinClearTime OBJECT-TYPE
     SYNTAX      DisplayString
     MAX-ACCESS  read-only
     STATUS      current
     DESCRIPTION "Collection clear time of the bin."
     ::= { cienaCesPmQueueGroupHist24HBinEntry 9 }


  --QueueGroup Profile Stats 
  
 cienaCesPmQueueGroupAllTimeBinTable OBJECT-TYPE
     SYNTAX     SEQUENCE OF CienaCesPmQueueGroupAllTimeBinEntry
     MAX-ACCESS not-accessible
     STATUS     deprecated
     DESCRIPTION
            "The (conceptual) read-only table listing the queue group profile statistics."  
     ::= { cienaCesPmQueueGroupStats 5 }
     
   cienaCesPmQueueGroupAllTimeBinEntry OBJECT-TYPE
     SYNTAX      CienaCesPmQueueGroupAllTimeBinEntry
     MAX-ACCESS  not-accessible
     STATUS      deprecated
     DESCRIPTION
           "An entry (conceptual row) in the cienaCesPmQueueGroupAllTimeBinTable.

           This table lists the statistics for the All Time bin of the PM instance." 
     INDEX {cienaCesPmInstanceIndex,cienaCesPmQueueGroupQueueIndex}
     ::= { cienaCesPmQueueGroupAllTimeBinTable 1 }
        
 CienaCesPmQueueGroupAllTimeBinEntry ::=  SEQUENCE {
     cienaCesPmQueueGroupAllTimeBinEnqueuedBytes                Counter64,
     cienaCesPmQueueGroupAllTimeBinEnqueuedFrames               Counter64,
     cienaCesPmQueueGroupAllTimeBinDroppedBytes                 Counter64,
     cienaCesPmQueueGroupAllTimeBinDroppedFrames                Counter64
     }

   cienaCesPmQueueGroupAllTimeBinEnqueuedBytes OBJECT-TYPE
     SYNTAX      Counter64
     MAX-ACCESS  read-only
     STATUS      deprecated
     DESCRIPTION
             "The number of enqueued bytes on this PM instance for this cienaCesPmQueueGroupQueueIndex."
     ::= { cienaCesPmQueueGroupAllTimeBinEntry 1 }

  cienaCesPmQueueGroupAllTimeBinEnqueuedFrames OBJECT-TYPE
     SYNTAX      Counter64
     MAX-ACCESS  read-only
     STATUS      deprecated
     DESCRIPTION
             "The number of enqueued frames on this PM instance for this cienaCesPmQueueGroupQueueIndex."
     ::= { cienaCesPmQueueGroupAllTimeBinEntry 2 }
  
  cienaCesPmQueueGroupAllTimeBinDroppedBytes OBJECT-TYPE
     SYNTAX      Counter64
     MAX-ACCESS  read-only
     STATUS      deprecated
     DESCRIPTION
             "The number of received bytes dropped on this PM instance for this cienaCesPmQueueGroupQueueIndex."
     ::= { cienaCesPmQueueGroupAllTimeBinEntry 3 }

  cienaCesPmQueueGroupAllTimeBinDroppedFrames OBJECT-TYPE
     SYNTAX      Counter64
     MAX-ACCESS  read-only
     STATUS      deprecated
     DESCRIPTION
             "The number of received frames dropped on this PM instance for this cienaCesPmQueueGroupQueueIndex."
     ::= { cienaCesPmQueueGroupAllTimeBinEntry 4 }


   --QueueGroup Profile Stats, statistics bin
  
   cienaCesPmQueueGroupStatisticsBinTable OBJECT-TYPE
     SYNTAX     SEQUENCE OF CienaCesPmQueueGroupStatisticsBinEntry
     MAX-ACCESS not-accessible
     STATUS     current
     DESCRIPTION "The (conceptual) read-only table listing the bin statistics."
     ::= { cienaCesPmQueueGroupStats 6 }
     
   cienaCesPmQueueGroupStatisticsBinEntry OBJECT-TYPE
     SYNTAX      CienaCesPmQueueGroupStatisticsBinEntry
     MAX-ACCESS  not-accessible
     STATUS      current
     DESCRIPTION
           "An entry (conceptual row) in the cienaCesPmQueueGroupStatisticsBinTable.
           This table lists the statistics for the statistics bin of the PM instance." 
     INDEX {cienaCesPmInstanceIndex,cienaCesPmQueueGroupQueueIndex}
     ::= { cienaCesPmQueueGroupStatisticsBinTable 1 }
        
   CienaCesPmQueueGroupStatisticsBinEntry ::=  SEQUENCE {
     cienaCesPmQueueGroupStatsBinStartTime                          DisplayString,
     cienaCesPmQueueGroupStatsBinClearTime                          DisplayString,
     cienaCesPmQueueGroupStatsBinEnqueuedBytes                      Counter64,
     cienaCesPmQueueGroupStatsBinEnqueuedFrames                     Counter64,
     cienaCesPmQueueGroupStatsBinDroppedBytes                       Counter64,
     cienaCesPmQueueGroupStatsBinDroppedFrames                      Counter64
   }

   cienaCesPmQueueGroupStatsBinStartTime OBJECT-TYPE
     SYNTAX      DisplayString
     MAX-ACCESS  read-only
     STATUS      current
     DESCRIPTION "Collection start time of the bin."
     ::= { cienaCesPmQueueGroupStatisticsBinEntry 1 }

   cienaCesPmQueueGroupStatsBinClearTime OBJECT-TYPE
     SYNTAX      DisplayString
     MAX-ACCESS  read-only
     STATUS      current
     DESCRIPTION "Collection clear time of the bin."
     ::= { cienaCesPmQueueGroupStatisticsBinEntry 2 }

   cienaCesPmQueueGroupStatsBinEnqueuedBytes OBJECT-TYPE
     SYNTAX      Counter64
     MAX-ACCESS  read-only
     STATUS      current
     DESCRIPTION
             "The number of enqueued bytes on this PM instance for this cienaCesPmQueueGroupQueueIndex."
     ::= { cienaCesPmQueueGroupStatisticsBinEntry 3 }

   cienaCesPmQueueGroupStatsBinEnqueuedFrames OBJECT-TYPE
     SYNTAX      Counter64
     MAX-ACCESS  read-only
     STATUS      current
     DESCRIPTION
             "The number of enqueued frames on this PM instance for this cienaCesPmQueueGroupQueueIndex."
     ::= { cienaCesPmQueueGroupStatisticsBinEntry 4 }
  
   cienaCesPmQueueGroupStatsBinDroppedBytes OBJECT-TYPE
     SYNTAX      Counter64
     MAX-ACCESS  read-only
     STATUS      current
     DESCRIPTION
             "The number of received bytes dropped on this PM instance for this cienaCesPmQueueGroupQueueIndex."
     ::= { cienaCesPmQueueGroupStatisticsBinEntry 5 }

   cienaCesPmQueueGroupStatsBinDroppedFrames OBJECT-TYPE
     SYNTAX      Counter64
     MAX-ACCESS  read-only
     STATUS      current
     DESCRIPTION
             "The number of received frames dropped on this PM instance for this cienaCesPmQueueGroupQueueIndex."
     ::= { cienaCesPmQueueGroupStatisticsBinEntry 6 }


   --QueueGroup Profile Stats, total statistics bin
  
   cienaCesPmQueueGroupTotalStatisticsBinTable OBJECT-TYPE
     SYNTAX     SEQUENCE OF CienaCesPmQueueGroupTotalStatisticsBinEntry
     MAX-ACCESS not-accessible
     STATUS     current
     DESCRIPTION "The (conceptual) read-only table listing the bin statistics."
     ::= { cienaCesPmQueueGroupStats 7 }
     
   cienaCesPmQueueGroupTotalStatisticsBinEntry OBJECT-TYPE
     SYNTAX      CienaCesPmQueueGroupTotalStatisticsBinEntry
     MAX-ACCESS  not-accessible
     STATUS      current
     DESCRIPTION
           "An entry (conceptual row) in the cienaCesPmQueueGroupTotalStatisticsBinTable.
           This table lists the statistics for the total statistics bin of the PM instance." 
     INDEX {cienaCesPmInstanceIndex,cienaCesPmQueueGroupQueueIndex}
     ::= { cienaCesPmQueueGroupTotalStatisticsBinTable 1 }
        
   CienaCesPmQueueGroupTotalStatisticsBinEntry ::=  SEQUENCE {
     cienaCesPmQueueGroupTotalStatsBinStartTime                     DisplayString,
     cienaCesPmQueueGroupTotalStatsBinEnqueuedBytes                 Counter64,
     cienaCesPmQueueGroupTotalStatsBinEnqueuedFrames                Counter64,
     cienaCesPmQueueGroupTotalStatsBinDroppedBytes                  Counter64,
     cienaCesPmQueueGroupTotalStatsBinDroppedFrames                 Counter64
   }

   cienaCesPmQueueGroupTotalStatsBinStartTime OBJECT-TYPE
     SYNTAX      DisplayString
     MAX-ACCESS  read-only
     STATUS      current
     DESCRIPTION "Collection start time of the bin."
     ::= { cienaCesPmQueueGroupTotalStatisticsBinEntry 1 }

   cienaCesPmQueueGroupTotalStatsBinEnqueuedBytes OBJECT-TYPE
     SYNTAX      Counter64
     MAX-ACCESS  read-only
     STATUS      current
     DESCRIPTION
             "The number of enqueued bytes on this PM instance for this cienaCesPmQueueGroupQueueIndex."
     ::= { cienaCesPmQueueGroupTotalStatisticsBinEntry 2 }

   cienaCesPmQueueGroupTotalStatsBinEnqueuedFrames OBJECT-TYPE
     SYNTAX      Counter64
     MAX-ACCESS  read-only
     STATUS      current
     DESCRIPTION
             "The number of enqueued frames on this PM instance for this cienaCesPmQueueGroupQueueIndex."
     ::= { cienaCesPmQueueGroupTotalStatisticsBinEntry 3 }
  
   cienaCesPmQueueGroupTotalStatsBinDroppedBytes OBJECT-TYPE
     SYNTAX      Counter64
     MAX-ACCESS  read-only
     STATUS      current
     DESCRIPTION
             "The number of received bytes dropped on this PM instance for this cienaCesPmQueueGroupQueueIndex."
     ::= { cienaCesPmQueueGroupTotalStatisticsBinEntry 4 }

   cienaCesPmQueueGroupTotalStatsBinDroppedFrames OBJECT-TYPE
     SYNTAX      Counter64
     MAX-ACCESS  read-only
     STATUS      current
     DESCRIPTION
             "The number of received frames dropped on this PM instance for this cienaCesPmQueueGroupQueueIndex."
     ::= { cienaCesPmQueueGroupTotalStatisticsBinEntry 5 }


  --
-- Egress Queue Bin
--
  --EgressQueue Profile Stats
  
 cienaCesPmEgressQueueHistoryBinTable OBJECT-TYPE
     SYNTAX     SEQUENCE OF CienaCesPmEgressQueueHistoryBinEntry
     MAX-ACCESS not-accessible
     STATUS     current
     DESCRIPTION
            "The (conceptual) read-only table listing the egress queue profile statistics."  
     ::= { cienaCesPmEgressQueueStats 1 }
     
   cienaCesPmEgressQueueHistoryBinEntry OBJECT-TYPE
     SYNTAX      CienaCesPmEgressQueueHistoryBinEntry
     MAX-ACCESS  not-accessible
     STATUS      current
     DESCRIPTION
           "An entry (conceptual row) in the cienaCesPmEgressQueueHistoryBinTable.

           This table lists the statistics for all the history bins of the PM instance, as 
           specified by the bin-count object of the PM instance.  History bins are displayed in the order
           so that #1 bin always represents the most recently completed bin and #2 - the bin previous to that
           and so on.
               The statistics are displayed for only the instances with valid bins (with start time >0), 
               as indicated by the operational state of the corresponding PM instance."  
     INDEX { cienaCesPmInstanceIndex, cienaCesPmEgressQueueHistoryBinIndex }
     ::= { cienaCesPmEgressQueueHistoryBinTable 1 }
        
 CienaCesPmEgressQueueHistoryBinEntry ::=  SEQUENCE {
     cienaCesPmEgressQueueHistoryBinIndex                            Unsigned32,
     cienaCesPmEgressQueueHistoryBinStartTime                        DisplayString,
     cienaCesPmEgressQueueHistoryBinEndTime                          DisplayString,
     cienaCesPmEgressQueueHistoryBinClearTime                        DisplayString,
     cienaCesPmEgressQueueHistoryBinDuration                         Unsigned32,   
     cienaCesPmEgressQueueHistoryBinState                            PmBinState,
     cienaCesPmEgressQueueHistoryBinUnicastDroppedBytes                 Counter64,
     cienaCesPmEgressQueueHistoryBinUnicastDroppedFrames                Counter64,
     cienaCesPmEgressQueueHistoryBinMulticastEnqueuedBytes           Counter64,
     cienaCesPmEgressQueueHistoryBinMulticastEnqueuedFrames          Counter64,
     cienaCesPmEgressQueueHistoryBinMulticastDroppedBytes            Counter64,
     cienaCesPmEgressQueueHistoryBinMulticastDroppedFrames           Counter64
        }
  cienaCesPmEgressQueueHistoryBinIndex OBJECT-TYPE
     SYNTAX      Unsigned32 (1..65535) 
     MAX-ACCESS  not-accessible
     STATUS      current
     DESCRIPTION
             "Bin number associated with the PmEgressQueueBin entry."
     ::= { cienaCesPmEgressQueueHistoryBinEntry 1 }

   cienaCesPmEgressQueueHistoryBinStartTime   OBJECT-TYPE
     SYNTAX             DisplayString
     MAX-ACCESS read-only
     STATUS             current
     DESCRIPTION "Collection start time of the bin."
     ::= { cienaCesPmEgressQueueHistoryBinEntry 2       }
   
   cienaCesPmEgressQueueHistoryBinEndTime       OBJECT-TYPE
        SYNTAX  DisplayString
        MAX-ACCESS read-only
        STATUS          current
        DESCRIPTION     "Collection end time of the bin."
        ::= {cienaCesPmEgressQueueHistoryBinEntry 3 }
   
   cienaCesPmEgressQueueHistoryBinClearTime     OBJECT-TYPE
        SYNTAX  DisplayString
        MAX-ACCESS read-only
        STATUS          current
        DESCRIPTION     "Collection clear time of the bin."
        ::= {cienaCesPmEgressQueueHistoryBinEntry 4 }
   
   cienaCesPmEgressQueueHistoryBinDuration OBJECT-TYPE
     SYNTAX      Unsigned32 (1..65535)  
     UNITS              "minutes"
     MAX-ACCESS  read-only
     STATUS      current
     DESCRIPTION
             "Duration of the bin."
     ::= { cienaCesPmEgressQueueHistoryBinEntry 5 }
  
  cienaCesPmEgressQueueHistoryBinState OBJECT-TYPE
     SYNTAX      PmBinState 
     MAX-ACCESS  read-only
     STATUS      current
     DESCRIPTION
             "State of the bin."
     ::= { cienaCesPmEgressQueueHistoryBinEntry 6 }
  
  cienaCesPmEgressQueueHistoryBinUnicastDroppedBytes OBJECT-TYPE
     SYNTAX      Counter64
     MAX-ACCESS  read-only
     STATUS      current
     DESCRIPTION
             "The number of received unicast bytes that were dropped at egress on this PM instance."
     ::= { cienaCesPmEgressQueueHistoryBinEntry 7 }
     
    cienaCesPmEgressQueueHistoryBinUnicastDroppedFrames OBJECT-TYPE
     SYNTAX      Counter64
     MAX-ACCESS  read-only
     STATUS      current
     DESCRIPTION
             "The number of received unicast frames that were dropped at egress on this PM instance."
     ::= { cienaCesPmEgressQueueHistoryBinEntry 8}
   
     cienaCesPmEgressQueueHistoryBinMulticastEnqueuedBytes OBJECT-TYPE
     SYNTAX      Counter64
     MAX-ACCESS  read-only
     STATUS      current
     DESCRIPTION
             "The number of multicast bytes that were enqueued at egress on this PM instance."
     ::= { cienaCesPmEgressQueueHistoryBinEntry 9}  
     
   cienaCesPmEgressQueueHistoryBinMulticastEnqueuedFrames OBJECT-TYPE
     SYNTAX      Counter64
     MAX-ACCESS  read-only
     STATUS      current
     DESCRIPTION
             "The number of multicast frames that were enqueued at egress on this PM instance."
     ::= { cienaCesPmEgressQueueHistoryBinEntry 10}  
   
     cienaCesPmEgressQueueHistoryBinMulticastDroppedBytes OBJECT-TYPE
     SYNTAX      Counter64
     MAX-ACCESS  read-only
     STATUS      current
     DESCRIPTION
             "The number of multicast bytes that were dropped before being enqueued on this PM instance."
     ::= { cienaCesPmEgressQueueHistoryBinEntry 11}  
     
   cienaCesPmEgressQueueHistoryBinMulticastDroppedFrames OBJECT-TYPE
     SYNTAX      Counter64
     MAX-ACCESS  read-only
     STATUS      current
     DESCRIPTION
             "The number of multicast frames that were dropped before being enqueued on this PM instance."
     ::= { cienaCesPmEgressQueueHistoryBinEntry 12}  
   
   --EgressQueue Profile Stats for interface

 cienaCesPmEgressQueueCurrBinTable OBJECT-TYPE
     SYNTAX     SEQUENCE OF CienaCesPmEgressQueueCurrBinEntry
     MAX-ACCESS not-accessible
     STATUS     current
     DESCRIPTION
            "The (conceptual) read-only table listing the egress queue profile statistics."  
     ::= { cienaCesPmEgressQueueStats 2 }
     
   cienaCesPmEgressQueueCurrBinEntry OBJECT-TYPE
     SYNTAX      CienaCesPmEgressQueueCurrBinEntry
     MAX-ACCESS  not-accessible
     STATUS      current
     DESCRIPTION
           "An entry (conceptual row) in the cienaCesPmEgressQueueCurrBinTable.

           This table lists the statistics for the current bin of the PM instance." 
     INDEX {cienaCesPmInstanceIndex}
     ::= { cienaCesPmEgressQueueCurrBinTable 1 }
        
 CienaCesPmEgressQueueCurrBinEntry ::=  SEQUENCE {
   cienaCesPmEgressQueueCurrBinStartTime                        DisplayString,
   cienaCesPmEgressQueueCurrBinClearedTime                      DisplayString,
   cienaCesPmEgressQueueCurrBinDuration                         Unsigned32,   
   cienaCesPmEgressQueueCurrBinState                            PmBinState,
   cienaCesPmEgressQueueCurrBinUnicastDroppedBytes                 Counter64,
   cienaCesPmEgressQueueCurrBinUnicastDroppedFrames                Counter64,
   cienaCesPmEgressQueueCurrBinMulticastEnqueuedBytes           Counter64,
   cienaCesPmEgressQueueCurrBinMulticastEnqueuedFrames          Counter64,
   cienaCesPmEgressQueueCurrBinMulticastDroppedBytes            Counter64,
   cienaCesPmEgressQueueCurrBinMulticastDroppedFrames           Counter64
     }
     cienaCesPmEgressQueueCurrBinStartTime   OBJECT-TYPE
     SYNTAX             DisplayString
     MAX-ACCESS read-only
     STATUS             current
     DESCRIPTION "Collection start time of the bin."
     ::= { cienaCesPmEgressQueueCurrBinEntry 1  }

  cienaCesPmEgressQueueCurrBinClearedTime   OBJECT-TYPE
     SYNTAX             DisplayString
     MAX-ACCESS read-only
     STATUS             current
     DESCRIPTION "Cleared time of the bin."
     ::= { cienaCesPmEgressQueueCurrBinEntry 2  }
                   
  cienaCesPmEgressQueueCurrBinDuration OBJECT-TYPE
     SYNTAX      Unsigned32 (1..65535)  
     UNITS              "minutes"
     MAX-ACCESS  read-only
     STATUS      current
     DESCRIPTION
             "Duration of the bin."
     ::= { cienaCesPmEgressQueueCurrBinEntry 3 }
  
  cienaCesPmEgressQueueCurrBinState OBJECT-TYPE
     SYNTAX      PmBinState 
     MAX-ACCESS  read-only
     STATUS      current
     DESCRIPTION
             "State of the bin."
     ::= { cienaCesPmEgressQueueCurrBinEntry 4 }

   cienaCesPmEgressQueueCurrBinUnicastDroppedBytes OBJECT-TYPE
     SYNTAX      Counter64
     MAX-ACCESS  read-only
     STATUS      current
     DESCRIPTION
             "The number of received unicast bytes that were dropped at egress on this PM instance."
     ::= { cienaCesPmEgressQueueCurrBinEntry 5 }
     
    cienaCesPmEgressQueueCurrBinUnicastDroppedFrames OBJECT-TYPE
     SYNTAX      Counter64
     MAX-ACCESS  read-only
     STATUS      current
     DESCRIPTION
             "The number of received unicast frames that were dropped at egress on this PM instance."
     ::= { cienaCesPmEgressQueueCurrBinEntry 6}
   
     cienaCesPmEgressQueueCurrBinMulticastEnqueuedBytes OBJECT-TYPE
     SYNTAX      Counter64
     MAX-ACCESS  read-only
     STATUS      current
     DESCRIPTION
             "The number of multicast bytes that were enqueued at egress on this PM instance."
     ::= { cienaCesPmEgressQueueCurrBinEntry 7}  
     
   cienaCesPmEgressQueueCurrBinMulticastEnqueuedFrames OBJECT-TYPE
     SYNTAX      Counter64
     MAX-ACCESS  read-only
     STATUS      current
     DESCRIPTION
             "The number of multicast frames that were enqueued at egress on this PM instance."
     ::= { cienaCesPmEgressQueueCurrBinEntry 8}  
   
     cienaCesPmEgressQueueCurrBinMulticastDroppedBytes OBJECT-TYPE
     SYNTAX      Counter64
     MAX-ACCESS  read-only
     STATUS      current
     DESCRIPTION
             "The number of multicast bytes that were dropped before being enqueued on this PM instance."
     ::= { cienaCesPmEgressQueueCurrBinEntry 9}  
     
   cienaCesPmEgressQueueCurrBinMulticastDroppedFrames OBJECT-TYPE
     SYNTAX      Counter64
     MAX-ACCESS  read-only
     STATUS      current
     DESCRIPTION
             "The number of multicast frames that were dropped before being enqueued on this PM instance."
     ::= { cienaCesPmEgressQueueCurrBinEntry 10}  
     
     --EgressQueue Profile Stats - current 24 hour bin table  
  
 cienaCesPmEgressQueueCurr24HBinTable OBJECT-TYPE
     SYNTAX     SEQUENCE OF CienaCesPmEgressQueueCurr24HBinEntry
     MAX-ACCESS not-accessible
     STATUS     current
     DESCRIPTION
            "The (conceptual) read-only table listing the egress queue profile statistics"  
     ::= { cienaCesPmEgressQueueStats 3 }
     
   cienaCesPmEgressQueueCurr24HBinEntry OBJECT-TYPE
     SYNTAX      CienaCesPmEgressQueueCurr24HBinEntry
     MAX-ACCESS  not-accessible
     STATUS      current
     DESCRIPTION
           "An entry (conceptual row) in the cienaCesPmEgressQueueCurr24HBinTable.

           This table lists the statistics for the current 24 hours bin." 
     INDEX {cienaCesPmInstanceIndex }
     ::= { cienaCesPmEgressQueueCurr24HBinTable 1 }
        
 CienaCesPmEgressQueueCurr24HBinEntry ::=  SEQUENCE {
     cienaCesPmEgressQueueCurr24HBinStartTime                  DisplayString,
     cienaCesPmEgressQueueCurr24HBinEndTime                    DisplayString,
     cienaCesPmEgressQueueCurr24HBinClearedTime                DisplayString,
     cienaCesPmEgressQueueCurr24HBinDuration                   Unsigned32,   
     cienaCesPmEgressQueueCurr24HBinState                      PmBinState,
     cienaCesPmEgressQueueCurr24HBinUnicastDroppedBytes           Counter64,
     cienaCesPmEgressQueueCurr24HBinUnicastDroppedFrames          Counter64,
     cienaCesPmEgressQueueCurr24HBinMulticastEnqueuedBytes     Counter64,
     cienaCesPmEgressQueueCurr24HBinMulticastEnqueuedFrames   Counter64,
     cienaCesPmEgressQueueCurr24HBinMulticastDroppedBytes      Counter64,
     cienaCesPmEgressQueueCurr24HBinMulticastDroppedFrames     Counter64
   }
   
      cienaCesPmEgressQueueCurr24HBinStartTime   OBJECT-TYPE
     SYNTAX             DisplayString
     MAX-ACCESS read-only
     STATUS             current
     DESCRIPTION "Collection start time of the bin."
     ::= { cienaCesPmEgressQueueCurr24HBinEntry 1       }
   
   cienaCesPmEgressQueueCurr24HBinEndTime               OBJECT-TYPE
     SYNTAX             DisplayString
     MAX-ACCESS read-only
     STATUS             current
     DESCRIPTION "Collection end time for the bin."
     ::= { cienaCesPmEgressQueueCurr24HBinEntry 2       }

    cienaCesPmEgressQueueCurr24HBinClearedTime   OBJECT-TYPE
     SYNTAX             DisplayString
     MAX-ACCESS read-only
     STATUS             current
     DESCRIPTION "Cleared time of the bin."
     ::= { cienaCesPmEgressQueueCurr24HBinEntry 3       }
                   
   cienaCesPmEgressQueueCurr24HBinDuration OBJECT-TYPE
     SYNTAX      Unsigned32 (1..65535)  
     UNITS               "minutes"
     MAX-ACCESS  read-only
     STATUS      current
     DESCRIPTION
             "Duration of the bin."
     ::= { cienaCesPmEgressQueueCurr24HBinEntry 4 }
  
  cienaCesPmEgressQueueCurr24HBinState OBJECT-TYPE
     SYNTAX      PmBinState 
     MAX-ACCESS  read-only
     STATUS      current
     DESCRIPTION
             "State of the bin."
     ::= { cienaCesPmEgressQueueCurr24HBinEntry 5 }
  
  cienaCesPmEgressQueueCurr24HBinUnicastDroppedBytes OBJECT-TYPE
     SYNTAX      Counter64
     MAX-ACCESS  read-only
     STATUS      current
     DESCRIPTION
             "The number of received unicast bytes that were dropped on this PM instance."
     ::= { cienaCesPmEgressQueueCurr24HBinEntry 6 }
     
    cienaCesPmEgressQueueCurr24HBinUnicastDroppedFrames OBJECT-TYPE
     SYNTAX      Counter64
     MAX-ACCESS  read-only
     STATUS      current
     DESCRIPTION
             "The number of received unicast frames that were dropped on this PM instance."
     ::= { cienaCesPmEgressQueueCurr24HBinEntry 7}
   
     cienaCesPmEgressQueueCurr24HBinMulticastEnqueuedBytes OBJECT-TYPE
     SYNTAX      Counter64
     MAX-ACCESS  read-only
     STATUS      current
     DESCRIPTION
             "The number of multicast bytes that were enqueued at egress on this PM instance."
     ::= { cienaCesPmEgressQueueCurr24HBinEntry 8}  
     
   cienaCesPmEgressQueueCurr24HBinMulticastEnqueuedFrames OBJECT-TYPE
     SYNTAX      Counter64
     MAX-ACCESS  read-only
     STATUS      current
     DESCRIPTION
             "The number of multicast frames that were enqueued at egress on this PM instance."
     ::= { cienaCesPmEgressQueueCurr24HBinEntry 9}  
   
     cienaCesPmEgressQueueCurr24HBinMulticastDroppedBytes OBJECT-TYPE
     SYNTAX      Counter64
    MAX-ACCESS  read-only
     STATUS      current
     DESCRIPTION
             "The number of multicast bytes that were enqueued at egress on this PM instance."
     ::= { cienaCesPmEgressQueueCurr24HBinEntry 10}  
     
   cienaCesPmEgressQueueCurr24HBinMulticastDroppedFrames OBJECT-TYPE
     SYNTAX      Counter64
     MAX-ACCESS  read-only
     STATUS      current
     DESCRIPTION
             "The number of multicast frames that were enqueued at egress on this PM instance."
     ::= { cienaCesPmEgressQueueCurr24HBinEntry 11}  
     
      
     --EgressQueue Profile Stats for PM instance - history 24 hour bin table  
  
 cienaCesPmEgressQueueHist24HBinTable OBJECT-TYPE
     SYNTAX     SEQUENCE OF CienaCesPmEgressQueueHist24HBinEntry
     MAX-ACCESS not-accessible
     STATUS     current
     DESCRIPTION
            "The (conceptual) read-only table listing the egress queue profile statistics."  
     ::= { cienaCesPmEgressQueueStats 4 }
     
   cienaCesPmEgressQueueHist24HBinEntry OBJECT-TYPE
     SYNTAX      CienaCesPmEgressQueueHist24HBinEntry
     MAX-ACCESS  not-accessible
     STATUS      current
     DESCRIPTION
           "An entry (conceptual row) in the cienaCesPmEgressQueueHist24HBinTable.
           This table lists the statistics for the history 24 hours bin." 
     INDEX {cienaCesPmInstanceIndex }
     ::= { cienaCesPmEgressQueueHist24HBinTable 1 }
        
 CienaCesPmEgressQueueHist24HBinEntry ::=  SEQUENCE {
     cienaCesPmEgressQueueHist24HBinStartTime                 DisplayString,
     cienaCesPmEgressQueueHist24HBinDuration                  Unsigned32,   
     cienaCesPmEgressQueueHist24HBinState                     PmBinState,
     cienaCesPmEgressQueueHist24HBinUnicastDroppedBytes       Counter64,
     cienaCesPmEgressQueueHist24HBinUnicastDroppedFrames      Counter64,
     cienaCesPmEgressQueueHist24HBinMulticastEnqueuedBytes    Counter64,
     cienaCesPmEgressQueueHist24HBinMulticastEnqueuedFrames   Counter64,
     cienaCesPmEgressQueueHist24HBinMulticastDroppedBytes     Counter64,
     cienaCesPmEgressQueueHist24HBinMulticastDroppedFrames    Counter64,
     cienaCesPmEgressQueueHist24HBinEndTime                   DisplayString,
     cienaCesPmEgressQueueHist24HBinClearTime                 DisplayString
   }
   
      cienaCesPmEgressQueueHist24HBinStartTime   OBJECT-TYPE
     SYNTAX             DisplayString
     MAX-ACCESS read-only
     STATUS             current
    DESCRIPTION "Collection start time of the bin."
     ::= { cienaCesPmEgressQueueHist24HBinEntry 1       }
   
   cienaCesPmEgressQueueHist24HBinDuration OBJECT-TYPE
     SYNTAX      Unsigned32 (1..65535)  
     UNITS              "minutes"
     MAX-ACCESS  read-only
     STATUS      current
     DESCRIPTION
             "Duration of the bin."
     ::= { cienaCesPmEgressQueueHist24HBinEntry 2 }
  
  cienaCesPmEgressQueueHist24HBinState OBJECT-TYPE
     SYNTAX      PmBinState 
     MAX-ACCESS  read-only
     STATUS      current
     DESCRIPTION
             "State of the bin."
     ::= { cienaCesPmEgressQueueHist24HBinEntry 3 }
   
  cienaCesPmEgressQueueHist24HBinUnicastDroppedBytes OBJECT-TYPE
     SYNTAX      Counter64
     MAX-ACCESS  read-only
     STATUS      current
     DESCRIPTION
             "The number of unicast bytes that were dropped at egress on this PM instance."
     ::= { cienaCesPmEgressQueueHist24HBinEntry 4 }

  cienaCesPmEgressQueueHist24HBinUnicastDroppedFrames OBJECT-TYPE
     SYNTAX      Counter64
     MAX-ACCESS  read-only
     STATUS      current
     DESCRIPTION
             "The number of unicast frames that were dropped at egress on this PM instance."
     ::= { cienaCesPmEgressQueueHist24HBinEntry 5 }
  
    cienaCesPmEgressQueueHist24HBinMulticastEnqueuedBytes OBJECT-TYPE
     SYNTAX      Counter64
     MAX-ACCESS  read-only
     STATUS      current
     DESCRIPTION
             "The number of multicast bytes that were enqueued at egress on this PM instance."
     ::= { cienaCesPmEgressQueueHist24HBinEntry 6}  
     
   cienaCesPmEgressQueueHist24HBinMulticastEnqueuedFrames OBJECT-TYPE
     SYNTAX      Counter64
     MAX-ACCESS  read-only
     STATUS      current
     DESCRIPTION
             "The number of multicast frames that were enqueued at egress on this PM instance."
     ::= { cienaCesPmEgressQueueHist24HBinEntry 7}  
   
    cienaCesPmEgressQueueHist24HBinMulticastDroppedBytes OBJECT-TYPE
     SYNTAX      Counter64
     MAX-ACCESS  read-only
     STATUS      current
     DESCRIPTION
             "The number of multicast bytes that were dropped before being enqueued at egress on this PM instance."
     ::= { cienaCesPmEgressQueueHist24HBinEntry 8}  
     
   cienaCesPmEgressQueueHist24HBinMulticastDroppedFrames OBJECT-TYPE
     SYNTAX      Counter64
     MAX-ACCESS  read-only
     STATUS      current
     DESCRIPTION
             "The number of multicast frames that were dropped before being enqueued at egress on this PM instance."
     ::= { cienaCesPmEgressQueueHist24HBinEntry 9}    
     
   cienaCesPmEgressQueueHist24HBinEndTime OBJECT-TYPE
     SYNTAX      DisplayString
     MAX-ACCESS  read-only
     STATUS      current
     DESCRIPTION "Collection end time of the bin."
     ::= { cienaCesPmEgressQueueHist24HBinEntry 10 }

   cienaCesPmEgressQueueHist24HBinClearTime OBJECT-TYPE
     SYNTAX      DisplayString
     MAX-ACCESS  read-only
     STATUS      current
     DESCRIPTION "Collection clear time of the bin."
     ::= { cienaCesPmEgressQueueHist24HBinEntry 11 }


     --EgressQueue Profile Stats 
  
 cienaCesPmEgressQueueAllTimeBinTable OBJECT-TYPE
     SYNTAX     SEQUENCE OF CienaCesPmEgressQueueAllTimeBinEntry
     MAX-ACCESS not-accessible
     STATUS     deprecated
     DESCRIPTION
            "The (conceptual) read-only table listing the egress queue profile statistics."  
     ::= { cienaCesPmEgressQueueStats 5 }
     
   cienaCesPmEgressQueueAllTimeBinEntry OBJECT-TYPE
     SYNTAX      CienaCesPmEgressQueueAllTimeBinEntry
     MAX-ACCESS  not-accessible
     STATUS      deprecated
     DESCRIPTION
           "An entry (conceptual row) in the cienaCesPmEgressQueueAllTimeBinTable.

           This table lists the statistics for the All Time bin of the PM instance." 
     INDEX {cienaCesPmInstanceIndex}
     ::= { cienaCesPmEgressQueueAllTimeBinTable 1 }
        
 CienaCesPmEgressQueueAllTimeBinEntry ::=  SEQUENCE {
     cienaCesPmEgressQueueAllTimeBinUnicastDroppedBytes        Counter64,
     cienaCesPmEgressQueueAllTimeBinUnicastDroppedFrames       Counter64,
     cienaCesPmEgressQueueAllTimeBinMulticastEnqueuedBytes     Counter64,
     cienaCesPmEgressQueueAllTimeBinMulticastEnqueuedFrames    Counter64,
     cienaCesPmEgressQueueAllTimeBinMulticastDroppedBytes      Counter64,
     cienaCesPmEgressQueueAllTimeBinMulticastDroppedFrames     Counter64
}
  cienaCesPmEgressQueueAllTimeBinUnicastDroppedBytes OBJECT-TYPE
     SYNTAX      Counter64
     MAX-ACCESS  read-only
     STATUS      deprecated
     DESCRIPTION
             "The number of unicast bytes that were dropped at egress on this PM instance."
     ::= { cienaCesPmEgressQueueAllTimeBinEntry 1 }

  cienaCesPmEgressQueueAllTimeBinUnicastDroppedFrames OBJECT-TYPE
     SYNTAX      Counter64
     MAX-ACCESS  read-only
     STATUS      deprecated
     DESCRIPTION
            "The number of unicast frames that were dropped at egress on this PM instance."
     ::= { cienaCesPmEgressQueueAllTimeBinEntry 2 }
  
    cienaCesPmEgressQueueAllTimeBinMulticastEnqueuedBytes OBJECT-TYPE
     SYNTAX      Counter64
     MAX-ACCESS  read-only
     STATUS      deprecated
     DESCRIPTION
             "The number of multicast bytes that were enqueued at egress on this PM instance."
     ::= { cienaCesPmEgressQueueAllTimeBinEntry 3}  
     
   cienaCesPmEgressQueueAllTimeBinMulticastEnqueuedFrames OBJECT-TYPE
     SYNTAX      Counter64
     MAX-ACCESS  read-only
     STATUS      deprecated
     DESCRIPTION
             "The number of multicast frames that were enqueued at egress on this PM instance."
     ::= { cienaCesPmEgressQueueAllTimeBinEntry 4}  
   
    cienaCesPmEgressQueueAllTimeBinMulticastDroppedBytes OBJECT-TYPE
     SYNTAX      Counter64
     MAX-ACCESS  read-only
     STATUS      deprecated
     DESCRIPTION
             "The number of multicast bytes that were dropped at egress on this PM instance."
     ::= { cienaCesPmEgressQueueAllTimeBinEntry 5}  
     
   cienaCesPmEgressQueueAllTimeBinMulticastDroppedFrames OBJECT-TYPE
     SYNTAX      Counter64
     MAX-ACCESS  read-only
     STATUS      deprecated
     DESCRIPTION
             "The number of multicast frames that were dropped at egress on this PM instance."
     ::= { cienaCesPmEgressQueueAllTimeBinEntry 6}  


   --EgressQueue Profile Stats, statistics bin
  
   cienaCesPmEgressQueueStatisticsBinTable OBJECT-TYPE
     SYNTAX     SEQUENCE OF CienaCesPmEgressQueueStatisticsBinEntry
     MAX-ACCESS not-accessible
     STATUS     current
     DESCRIPTION "The (conceptual) read-only table listing the bin statistics."
     ::= { cienaCesPmEgressQueueStats 6 }
     
   cienaCesPmEgressQueueStatisticsBinEntry OBJECT-TYPE
     SYNTAX      CienaCesPmEgressQueueStatisticsBinEntry
     MAX-ACCESS  not-accessible
     STATUS      current
     DESCRIPTION
           "An entry (conceptual row) in the cienaCesPmEgressQueueStatisticsBinTable.
           This table lists the statistics for the statistics bin of the PM instance." 
     INDEX {cienaCesPmInstanceIndex}
     ::= { cienaCesPmEgressQueueStatisticsBinTable 1 }
        
   CienaCesPmEgressQueueStatisticsBinEntry ::=  SEQUENCE {
     cienaCesPmEgressQueueStatsBinStartTime                         DisplayString,
     cienaCesPmEgressQueueStatsBinClearTime                         DisplayString,
     cienaCesPmEgressQueueStatsBinUnicastDroppedBytes               Counter64,
     cienaCesPmEgressQueueStatsBinUnicastDroppedFrames              Counter64,
     cienaCesPmEgressQueueStatsBinMulticastEnqueuedBytes            Counter64,
     cienaCesPmEgressQueueStatsBinMulticastEnqueuedFrames           Counter64,
     cienaCesPmEgressQueueStatsBinMulticastDroppedBytes             Counter64,
     cienaCesPmEgressQueueStatsBinMulticastDroppedFrames            Counter64
   }

   cienaCesPmEgressQueueStatsBinStartTime OBJECT-TYPE
     SYNTAX      DisplayString
     MAX-ACCESS  read-only
     STATUS      current
     DESCRIPTION "Collection start time of the bin."
     ::= { cienaCesPmEgressQueueStatisticsBinEntry 1 }

   cienaCesPmEgressQueueStatsBinClearTime OBJECT-TYPE
     SYNTAX      DisplayString
     MAX-ACCESS  read-only
     STATUS      current
     DESCRIPTION "Collection clear time of the bin."
     ::= { cienaCesPmEgressQueueStatisticsBinEntry 2 }

   cienaCesPmEgressQueueStatsBinUnicastDroppedBytes OBJECT-TYPE
     SYNTAX      Counter64
     MAX-ACCESS  read-only
     STATUS      current
     DESCRIPTION
             "The number of unicast bytes that were dropped at egress on this PM instance."
     ::= { cienaCesPmEgressQueueStatisticsBinEntry 3 }

   cienaCesPmEgressQueueStatsBinUnicastDroppedFrames OBJECT-TYPE
     SYNTAX      Counter64
     MAX-ACCESS  read-only
     STATUS      current
     DESCRIPTION
            "The number of unicast frames that were dropped at egress on this PM instance."
     ::= { cienaCesPmEgressQueueStatisticsBinEntry 4 }
  
   cienaCesPmEgressQueueStatsBinMulticastEnqueuedBytes OBJECT-TYPE
     SYNTAX      Counter64
     MAX-ACCESS  read-only
     STATUS      current
     DESCRIPTION
             "The number of multicast bytes that were enqueued at egress on this PM instance."
     ::= { cienaCesPmEgressQueueStatisticsBinEntry 5 }  
     
   cienaCesPmEgressQueueStatsBinMulticastEnqueuedFrames OBJECT-TYPE
     SYNTAX      Counter64
     MAX-ACCESS  read-only
     STATUS      current
     DESCRIPTION
             "The number of multicast frames that were enqueued at egress on this PM instance."
     ::= { cienaCesPmEgressQueueStatisticsBinEntry 6 }  
   
   cienaCesPmEgressQueueStatsBinMulticastDroppedBytes OBJECT-TYPE
     SYNTAX      Counter64
     MAX-ACCESS  read-only
     STATUS      current
     DESCRIPTION
             "The number of multicast bytes that were dropped at egress on this PM instance."
     ::= { cienaCesPmEgressQueueStatisticsBinEntry 7 }  
     
   cienaCesPmEgressQueueStatsBinMulticastDroppedFrames OBJECT-TYPE
     SYNTAX      Counter64
     MAX-ACCESS  read-only
     STATUS      current
     DESCRIPTION
             "The number of multicast frames that were dropped at egress on this PM instance."
     ::= { cienaCesPmEgressQueueStatisticsBinEntry 8 }  


   --EgressQueue Profile Stats, total statistics bin
  
   cienaCesPmEgressQueueTotalStatisticsBinTable OBJECT-TYPE
     SYNTAX     SEQUENCE OF CienaCesPmEgressQueueTotalStatisticsBinEntry
     MAX-ACCESS not-accessible
     STATUS     current
     DESCRIPTION "The (conceptual) read-only table listing the bin statistics."
     ::= { cienaCesPmEgressQueueStats 7 }
     
   cienaCesPmEgressQueueTotalStatisticsBinEntry OBJECT-TYPE
     SYNTAX      CienaCesPmEgressQueueTotalStatisticsBinEntry
     MAX-ACCESS  not-accessible
     STATUS      current
     DESCRIPTION
           "An entry (conceptual row) in the cienaCesPmEgressQueueTotalStatisticsBinTable.
           This table lists the statistics for the total statistics bin of the PM instance." 
     INDEX {cienaCesPmInstanceIndex}
     ::= { cienaCesPmEgressQueueTotalStatisticsBinTable 1 }
        
   CienaCesPmEgressQueueTotalStatisticsBinEntry ::=  SEQUENCE {
     cienaCesPmEgressQueueTotalStatsBinStartTime                    DisplayString,
     cienaCesPmEgressQueueTotalStatsBinUnicastDroppedBytes          Counter64,
     cienaCesPmEgressQueueTotalStatsBinUnicastDroppedFrames         Counter64,
     cienaCesPmEgressQueueTotalStatsBinMulticastEnqueuedBytes       Counter64,
     cienaCesPmEgressQueueTotalStatsBinMulticastEnqueuedFrames      Counter64,
     cienaCesPmEgressQueueTotalStatsBinMulticastDroppedBytes        Counter64,
     cienaCesPmEgressQueueTotalStatsBinMulticastDroppedFrames       Counter64
   }

   cienaCesPmEgressQueueTotalStatsBinStartTime OBJECT-TYPE
     SYNTAX      DisplayString
     MAX-ACCESS  read-only
     STATUS      current
     DESCRIPTION "Collection start time of the bin."
     ::= { cienaCesPmEgressQueueTotalStatisticsBinEntry 1 }

   cienaCesPmEgressQueueTotalStatsBinUnicastDroppedBytes OBJECT-TYPE
     SYNTAX      Counter64
     MAX-ACCESS  read-only
     STATUS      current
     DESCRIPTION
             "The number of unicast bytes that were dropped at egress on this PM instance."
     ::= { cienaCesPmEgressQueueTotalStatisticsBinEntry 2 }

   cienaCesPmEgressQueueTotalStatsBinUnicastDroppedFrames OBJECT-TYPE
     SYNTAX      Counter64
     MAX-ACCESS  read-only
     STATUS      current
     DESCRIPTION
            "The number of unicast frames that were dropped at egress on this PM instance."
     ::= { cienaCesPmEgressQueueTotalStatisticsBinEntry 3 }
  
   cienaCesPmEgressQueueTotalStatsBinMulticastEnqueuedBytes OBJECT-TYPE
     SYNTAX      Counter64
     MAX-ACCESS  read-only
     STATUS      current
     DESCRIPTION
             "The number of multicast bytes that were enqueued at egress on this PM instance."
     ::= { cienaCesPmEgressQueueTotalStatisticsBinEntry 4 }  
     
   cienaCesPmEgressQueueTotalStatsBinMulticastEnqueuedFrames OBJECT-TYPE
     SYNTAX      Counter64
     MAX-ACCESS  read-only
     STATUS      current
     DESCRIPTION
             "The number of multicast frames that were enqueued at egress on this PM instance."
     ::= { cienaCesPmEgressQueueTotalStatisticsBinEntry 5 }  
   
   cienaCesPmEgressQueueTotalStatsBinMulticastDroppedBytes OBJECT-TYPE
     SYNTAX      Counter64
     MAX-ACCESS  read-only
     STATUS      current
     DESCRIPTION
             "The number of multicast bytes that were dropped at egress on this PM instance."
     ::= { cienaCesPmEgressQueueTotalStatisticsBinEntry 6 }  
     
   cienaCesPmEgressQueueTotalStatsBinMulticastDroppedFrames OBJECT-TYPE
     SYNTAX      Counter64
     MAX-ACCESS  read-only
     STATUS      current
     DESCRIPTION
             "The number of multicast frames that were dropped at egress on this PM instance."
     ::= { cienaCesPmEgressQueueTotalStatisticsBinEntry 7 }  


   --TdmT1Port Profile Stats, history bins

   cienaCesPmTdmT1PortHistoryBinTable OBJECT-TYPE
     SYNTAX      SEQUENCE OF CienaCesPmTdmT1PortHistoryBinEntry
     MAX-ACCESS  not-accessible
     STATUS      current
     DESCRIPTION
           "The (conceptual) read-only table listing the bin statistics."
     ::= { cienaCesPmTdmT1PortStats 1 }

   cienaCesPmTdmT1PortHistoryBinEntry OBJECT-TYPE
     SYNTAX      CienaCesPmTdmT1PortHistoryBinEntry
     MAX-ACCESS  not-accessible
     STATUS      current
     DESCRIPTION
           "An entry (conceptual row) in the cienaPortPmTdmT1PortHistoryBinTable.

           This table lists the statistics for all the history bins of the PM instance, as 
           specified by the bin-count object of the PM instance.  History bins are displayed in the order
           so that #1 bin always represents the most recently completed bin and #2 - the bin previous to that
           and so on.

           The statistics are displayed for only the instances with valid bins (with start time >0), 
           as indicated by the operational state of the corresponding PM instance."
     INDEX { cienaCesPmInstanceIndex, cienaCesPmTdmT1PortHistoryBinIndex }
     ::= { cienaCesPmTdmT1PortHistoryBinTable 1 }

   CienaCesPmTdmT1PortHistoryBinEntry ::=  SEQUENCE {
     cienaCesPmTdmT1PortHistoryBinIndex                             Unsigned32,
     cienaCesPmTdmT1PortHistoryBinStartTime                         DisplayString,
     cienaCesPmTdmT1PortHistoryBinEndTime                           DisplayString,
     cienaCesPmTdmT1PortHistoryBinClearTime                         DisplayString,
     cienaCesPmTdmT1PortHistoryBinDuration                          Unsigned32,
     cienaCesPmTdmT1PortHistoryBinState                             PmBinState,
     cienaCesPmTdmT1PortHistoryBinCvl                               Counter64,
     cienaCesPmTdmT1PortHistoryBinEsl                               Counter64,
     cienaCesPmTdmT1PortHistoryBinSesl                              Counter64,
     cienaCesPmTdmT1PortHistoryBinLossl                             Counter64,
     cienaCesPmTdmT1PortHistoryBinCvp                               Counter64,
     cienaCesPmTdmT1PortHistoryBinEsp                               Counter64,
     cienaCesPmTdmT1PortHistoryBinSesp                              Counter64,
     cienaCesPmTdmT1PortHistoryBinUasp                              Counter64,
     cienaCesPmTdmT1PortHistoryBinSasp                              Counter64,
     cienaCesPmTdmT1PortHistoryBinFcp                               Counter64,
     cienaCesPmTdmT1PortHistoryBinAsp                               Counter64,
     cienaCesPmTdmT1PortHistoryBinTtp                               Counter64
   }
   cienaCesPmTdmT1PortHistoryBinIndex OBJECT-TYPE
     SYNTAX      Unsigned32 (1..65535)
     MAX-ACCESS  not-accessible
     STATUS      current
     DESCRIPTION "Bin number associated with the PmTdmT1PortHistoryBin entry."
     ::= { cienaCesPmTdmT1PortHistoryBinEntry 1 }

   cienaCesPmTdmT1PortHistoryBinStartTime OBJECT-TYPE
     SYNTAX      DisplayString
     MAX-ACCESS  read-only
     STATUS      current
     DESCRIPTION "Collection start time of the bin."
     ::= { cienaCesPmTdmT1PortHistoryBinEntry 2 }

   cienaCesPmTdmT1PortHistoryBinEndTime OBJECT-TYPE
     SYNTAX      DisplayString
     MAX-ACCESS  read-only
     STATUS      current
     DESCRIPTION "Collection end time of the bin."
     ::= { cienaCesPmTdmT1PortHistoryBinEntry 3 }

   cienaCesPmTdmT1PortHistoryBinClearTime OBJECT-TYPE
     SYNTAX      DisplayString
     MAX-ACCESS  read-only
     STATUS      current
     DESCRIPTION "Collection clear time of the bin."
     ::= { cienaCesPmTdmT1PortHistoryBinEntry 4 }

   cienaCesPmTdmT1PortHistoryBinDuration OBJECT-TYPE
     SYNTAX      Unsigned32 (1..65535)
     UNITS       "minutes"
     MAX-ACCESS  read-only
     STATUS      current
     DESCRIPTION "Duration of the bin."
     ::= { cienaCesPmTdmT1PortHistoryBinEntry 5 }

   cienaCesPmTdmT1PortHistoryBinState OBJECT-TYPE
     SYNTAX      PmBinState
     MAX-ACCESS  read-only
     STATUS      current
     DESCRIPTION "State of the bin."
     ::= { cienaCesPmTdmT1PortHistoryBinEntry 6 }

   cienaCesPmTdmT1PortHistoryBinCvl OBJECT-TYPE
     SYNTAX      Counter64
     MAX-ACCESS  read-only
     STATUS      current
     DESCRIPTION "Line, Code violations."
     ::= { cienaCesPmTdmT1PortHistoryBinEntry 7 }

   cienaCesPmTdmT1PortHistoryBinEsl OBJECT-TYPE
     SYNTAX      Counter64
     MAX-ACCESS  read-only
     STATUS      current
     DESCRIPTION "Line, Errored seconds."
     ::= { cienaCesPmTdmT1PortHistoryBinEntry 8 }

   cienaCesPmTdmT1PortHistoryBinSesl OBJECT-TYPE
     SYNTAX      Counter64
     MAX-ACCESS  read-only
     STATUS      current
     DESCRIPTION "Line, Severely errored seconds."
     ::= { cienaCesPmTdmT1PortHistoryBinEntry 9 }

   cienaCesPmTdmT1PortHistoryBinLossl OBJECT-TYPE
     SYNTAX      Counter64
     MAX-ACCESS  read-only
     STATUS      current
     DESCRIPTION "Line, Loss of signal seconds."
     ::= { cienaCesPmTdmT1PortHistoryBinEntry 10 }

   cienaCesPmTdmT1PortHistoryBinCvp OBJECT-TYPE
     SYNTAX      Counter64
     MAX-ACCESS  read-only
     STATUS      current
     DESCRIPTION "Path, Code violations."
     ::= { cienaCesPmTdmT1PortHistoryBinEntry 11 }

   cienaCesPmTdmT1PortHistoryBinEsp OBJECT-TYPE
     SYNTAX      Counter64
     MAX-ACCESS  read-only
     STATUS      current
     DESCRIPTION "Path, Errored seconds."
     ::= { cienaCesPmTdmT1PortHistoryBinEntry 12 }

   cienaCesPmTdmT1PortHistoryBinSesp OBJECT-TYPE
     SYNTAX      Counter64
     MAX-ACCESS  read-only
     STATUS      current
     DESCRIPTION "Path, Severely errored seconds."
     ::= { cienaCesPmTdmT1PortHistoryBinEntry 13 }

   cienaCesPmTdmT1PortHistoryBinUasp OBJECT-TYPE
     SYNTAX      Counter64
     MAX-ACCESS  read-only
     STATUS      current
     DESCRIPTION "Path, Unavailable seconds."
     ::= { cienaCesPmTdmT1PortHistoryBinEntry 14 }

   cienaCesPmTdmT1PortHistoryBinSasp OBJECT-TYPE
     SYNTAX      Counter64
     MAX-ACCESS  read-only
     STATUS      current
     DESCRIPTION "Path, SEF/AIS seconds."
     ::= { cienaCesPmTdmT1PortHistoryBinEntry 15 }

   cienaCesPmTdmT1PortHistoryBinFcp OBJECT-TYPE
     SYNTAX      Counter64
     MAX-ACCESS  read-only
     STATUS      current
     DESCRIPTION "Path, Failure count."
     ::= { cienaCesPmTdmT1PortHistoryBinEntry 16 }

   cienaCesPmTdmT1PortHistoryBinAsp OBJECT-TYPE
     SYNTAX      Counter64
     MAX-ACCESS  read-only
     STATUS      current
     DESCRIPTION "Path, Available seconds."
     ::= { cienaCesPmTdmT1PortHistoryBinEntry 17 }

   cienaCesPmTdmT1PortHistoryBinTtp OBJECT-TYPE
     SYNTAX      Counter64
     MAX-ACCESS  read-only
     STATUS      current
     DESCRIPTION "Path, Total time seconds."
     ::= { cienaCesPmTdmT1PortHistoryBinEntry 18 }


   --TdmT1Port Profile Stats, current bin

   cienaCesPmTdmT1PortCurrBinTable OBJECT-TYPE
     SYNTAX      SEQUENCE OF CienaCesPmTdmT1PortCurrBinEntry
     MAX-ACCESS  not-accessible
     STATUS      current
     DESCRIPTION "The (conceptual) read-only table listing the bin statistics."
     ::= { cienaCesPmTdmT1PortStats 2 }

   cienaCesPmTdmT1PortCurrBinEntry OBJECT-TYPE
     SYNTAX      CienaCesPmTdmT1PortCurrBinEntry
     MAX-ACCESS  not-accessible
     STATUS      current
     DESCRIPTION
           "An entry (conceptual row) in the cienaPortPmTdmT1PortCurrBinTable.
           This table lists the statistics for the current bin of the PM instance."
     INDEX {cienaCesPmInstanceIndex}
     ::= { cienaCesPmTdmT1PortCurrBinTable 1 }

   CienaCesPmTdmT1PortCurrBinEntry ::=  SEQUENCE {
     cienaCesPmTdmT1PortCurrBinStartTime                            DisplayString,
     cienaCesPmTdmT1PortCurrBinClearTime                            DisplayString,
     cienaCesPmTdmT1PortCurrBinDuration                             Unsigned32,
     cienaCesPmTdmT1PortCurrBinState                                PmBinState,
     cienaCesPmTdmT1PortCurrBinCvl                                  Counter64,
     cienaCesPmTdmT1PortCurrBinEsl                                  Counter64,
     cienaCesPmTdmT1PortCurrBinSesl                                 Counter64,
     cienaCesPmTdmT1PortCurrBinLossl                                Counter64,
     cienaCesPmTdmT1PortCurrBinCvp                                  Counter64,
     cienaCesPmTdmT1PortCurrBinEsp                                  Counter64,
     cienaCesPmTdmT1PortCurrBinSesp                                 Counter64,
     cienaCesPmTdmT1PortCurrBinUasp                                 Counter64,
     cienaCesPmTdmT1PortCurrBinSasp                                 Counter64,
     cienaCesPmTdmT1PortCurrBinFcp                                  Counter64,
     cienaCesPmTdmT1PortCurrBinAsp                                  Counter64,
     cienaCesPmTdmT1PortCurrBinTtp                                  Counter64
   }

   cienaCesPmTdmT1PortCurrBinStartTime OBJECT-TYPE
     SYNTAX      DisplayString
     MAX-ACCESS  read-only
     STATUS      current
     DESCRIPTION "Collection start time of the bin."
     ::= { cienaCesPmTdmT1PortCurrBinEntry 1 }

   cienaCesPmTdmT1PortCurrBinClearTime OBJECT-TYPE
     SYNTAX      DisplayString
     MAX-ACCESS  read-only
     STATUS      current
     DESCRIPTION "Cleared time of the bin."
     ::= { cienaCesPmTdmT1PortCurrBinEntry 2 }

   cienaCesPmTdmT1PortCurrBinDuration OBJECT-TYPE
     SYNTAX      Unsigned32 (1..65535)
     UNITS       "minutes"
     MAX-ACCESS  read-only
     STATUS      current
     DESCRIPTION "Interval of the bin."
     ::= { cienaCesPmTdmT1PortCurrBinEntry 3 }

   cienaCesPmTdmT1PortCurrBinState OBJECT-TYPE
     SYNTAX      PmBinState
     MAX-ACCESS  read-only
     STATUS      current
     DESCRIPTION "State of the bin."
     ::= { cienaCesPmTdmT1PortCurrBinEntry 4 }

   cienaCesPmTdmT1PortCurrBinCvl OBJECT-TYPE
     SYNTAX      Counter64
     MAX-ACCESS  read-only
     STATUS      current
     DESCRIPTION "Line, Code violations."
     ::= { cienaCesPmTdmT1PortCurrBinEntry 5 }

  cienaCesPmTdmT1PortCurrBinEsl OBJECT-TYPE
     SYNTAX      Counter64
     MAX-ACCESS  read-only
     STATUS      current
     DESCRIPTION "Line, Errored seconds."
     ::= { cienaCesPmTdmT1PortCurrBinEntry 6 }

   cienaCesPmTdmT1PortCurrBinSesl OBJECT-TYPE
     SYNTAX      Counter64
     MAX-ACCESS  read-only
     STATUS      current
     DESCRIPTION "Line, Severely errored seconds."
     ::= { cienaCesPmTdmT1PortCurrBinEntry 7 }

   cienaCesPmTdmT1PortCurrBinLossl OBJECT-TYPE
     SYNTAX      Counter64
     MAX-ACCESS  read-only
     STATUS      current
     DESCRIPTION "Line, Loss of signal seconds."
     ::= { cienaCesPmTdmT1PortCurrBinEntry 8 }

   cienaCesPmTdmT1PortCurrBinCvp OBJECT-TYPE
     SYNTAX      Counter64
     MAX-ACCESS  read-only
     STATUS      current
     DESCRIPTION "Path, Code violations."
     ::= { cienaCesPmTdmT1PortCurrBinEntry 9 }

   cienaCesPmTdmT1PortCurrBinEsp OBJECT-TYPE
     SYNTAX      Counter64
     MAX-ACCESS  read-only
     STATUS      current
     DESCRIPTION "Path, Errored seconds."
     ::= { cienaCesPmTdmT1PortCurrBinEntry 10 }

   cienaCesPmTdmT1PortCurrBinSesp OBJECT-TYPE
     SYNTAX      Counter64
     MAX-ACCESS  read-only
     STATUS      current
     DESCRIPTION "Path, Severely errored seconds."
     ::= { cienaCesPmTdmT1PortCurrBinEntry 11 }

   cienaCesPmTdmT1PortCurrBinUasp OBJECT-TYPE
     SYNTAX      Counter64
     MAX-ACCESS  read-only
     STATUS      current
     DESCRIPTION "Path, Unavailable seconds."
     ::= { cienaCesPmTdmT1PortCurrBinEntry 12 }

   cienaCesPmTdmT1PortCurrBinSasp OBJECT-TYPE
     SYNTAX      Counter64
     MAX-ACCESS  read-only
     STATUS      current
     DESCRIPTION "Path, SEF/AIS seconds."
     ::= { cienaCesPmTdmT1PortCurrBinEntry 13 }

   cienaCesPmTdmT1PortCurrBinFcp OBJECT-TYPE
     SYNTAX      Counter64
     MAX-ACCESS  read-only
     STATUS      current
     DESCRIPTION "Path, Failure count."
     ::= { cienaCesPmTdmT1PortCurrBinEntry 14 }

   cienaCesPmTdmT1PortCurrBinAsp OBJECT-TYPE
     SYNTAX      Counter64
     MAX-ACCESS  read-only
     STATUS      current
     DESCRIPTION "Path, Available seconds."
     ::= { cienaCesPmTdmT1PortCurrBinEntry 15 }

   cienaCesPmTdmT1PortCurrBinTtp OBJECT-TYPE
     SYNTAX      Counter64
     MAX-ACCESS  read-only
     STATUS      current
     DESCRIPTION "Path, Total time seconds."
     ::= { cienaCesPmTdmT1PortCurrBinEntry 16 }


   --TdmT1Port Profile Stats, current 24 hour bin
  
   cienaCesPmTdmT1PortCurr24HBinTable OBJECT-TYPE
     SYNTAX      SEQUENCE OF CienaCesPmTdmT1PortCurr24HBinEntry
     MAX-ACCESS  not-accessible
     STATUS      current
     DESCRIPTION "The (conceptual) read-only table listing the bin statistics."
     ::= { cienaCesPmTdmT1PortStats 3 }

   cienaCesPmTdmT1PortCurr24HBinEntry OBJECT-TYPE
     SYNTAX      CienaCesPmTdmT1PortCurr24HBinEntry
     MAX-ACCESS  not-accessible
     STATUS      current
     DESCRIPTION
           "An entry (conceptual row) in the cienaPortPmTdmT1PortCurr24HBinTable.
           This table lists the statistics for the current 24 hours bin."
     INDEX {cienaCesPmInstanceIndex }
     ::= { cienaCesPmTdmT1PortCurr24HBinTable 1 }

   CienaCesPmTdmT1PortCurr24HBinEntry ::=  SEQUENCE {
     cienaCesPmTdmT1PortCurr24HBinStartTime                         DisplayString,
     cienaCesPmTdmT1PortCurr24HBinClearTime                         DisplayString,
     cienaCesPmTdmT1PortCurr24HBinDuration                          Unsigned32,
     cienaCesPmTdmT1PortCurr24HBinState                             PmBinState,
     cienaCesPmTdmT1PortCurr24HBinCvl                               Counter64,
     cienaCesPmTdmT1PortCurr24HBinEsl                               Counter64,
     cienaCesPmTdmT1PortCurr24HBinSesl                              Counter64,
     cienaCesPmTdmT1PortCurr24HBinLossl                             Counter64,
     cienaCesPmTdmT1PortCurr24HBinCvp                               Counter64,
     cienaCesPmTdmT1PortCurr24HBinEsp                               Counter64,
     cienaCesPmTdmT1PortCurr24HBinSesp                              Counter64,
     cienaCesPmTdmT1PortCurr24HBinUasp                              Counter64,
     cienaCesPmTdmT1PortCurr24HBinSasp                              Counter64,
     cienaCesPmTdmT1PortCurr24HBinFcp                               Counter64,
     cienaCesPmTdmT1PortCurr24HBinAsp                               Counter64,
     cienaCesPmTdmT1PortCurr24HBinTtp                               Counter64
   } 

   cienaCesPmTdmT1PortCurr24HBinStartTime OBJECT-TYPE
     SYNTAX      DisplayString
     MAX-ACCESS  read-only
     STATUS      current
     DESCRIPTION "Collection start time of the bin."
     ::= { cienaCesPmTdmT1PortCurr24HBinEntry 1 }

   cienaCesPmTdmT1PortCurr24HBinClearTime OBJECT-TYPE
     SYNTAX      DisplayString
     MAX-ACCESS  read-only
     STATUS      current
     DESCRIPTION "Cleared time of the bin."
     ::= { cienaCesPmTdmT1PortCurr24HBinEntry 2 }

   cienaCesPmTdmT1PortCurr24HBinDuration OBJECT-TYPE
     SYNTAX      Unsigned32 (1..65535)
     UNITS       "minutes"
     MAX-ACCESS  read-only
     STATUS      current
     DESCRIPTION "Duration of the bin."
     ::= { cienaCesPmTdmT1PortCurr24HBinEntry 3 }

   cienaCesPmTdmT1PortCurr24HBinState OBJECT-TYPE
     SYNTAX      PmBinState
     MAX-ACCESS  read-only
     STATUS      current
     DESCRIPTION "State of the bin."
     ::= { cienaCesPmTdmT1PortCurr24HBinEntry 4 }

   cienaCesPmTdmT1PortCurr24HBinCvl OBJECT-TYPE
     SYNTAX      Counter64
     MAX-ACCESS  read-only
     STATUS      current
     DESCRIPTION "Line, Code violations."
     ::= { cienaCesPmTdmT1PortCurr24HBinEntry 5 }

   cienaCesPmTdmT1PortCurr24HBinEsl OBJECT-TYPE
     SYNTAX      Counter64
     MAX-ACCESS  read-only
     STATUS      current
     DESCRIPTION "Line, Errored seconds."
     ::= { cienaCesPmTdmT1PortCurr24HBinEntry 6 }

   cienaCesPmTdmT1PortCurr24HBinSesl OBJECT-TYPE
     SYNTAX      Counter64
     MAX-ACCESS  read-only
     STATUS      current
     DESCRIPTION "Line, Severely errored seconds."
     ::= { cienaCesPmTdmT1PortCurr24HBinEntry 7 }

   cienaCesPmTdmT1PortCurr24HBinLossl OBJECT-TYPE
     SYNTAX      Counter64
     MAX-ACCESS  read-only
     STATUS      current
     DESCRIPTION "Line, Loss of signal seconds."
     ::= { cienaCesPmTdmT1PortCurr24HBinEntry 8 }

   cienaCesPmTdmT1PortCurr24HBinCvp OBJECT-TYPE
     SYNTAX      Counter64
     MAX-ACCESS  read-only
     STATUS      current
     DESCRIPTION "Path, Code violations."
     ::= { cienaCesPmTdmT1PortCurr24HBinEntry 9 }

   cienaCesPmTdmT1PortCurr24HBinEsp OBJECT-TYPE
     SYNTAX      Counter64
     MAX-ACCESS  read-only
     STATUS      current
     DESCRIPTION "Path, Errored seconds."
     ::= { cienaCesPmTdmT1PortCurr24HBinEntry 10 }

   cienaCesPmTdmT1PortCurr24HBinSesp OBJECT-TYPE
     SYNTAX      Counter64
     MAX-ACCESS  read-only
     STATUS      current
     DESCRIPTION "Path, Severely errored seconds."
     ::= { cienaCesPmTdmT1PortCurr24HBinEntry 11 }

   cienaCesPmTdmT1PortCurr24HBinUasp OBJECT-TYPE
     SYNTAX      Counter64
     MAX-ACCESS  read-only
     STATUS      current
     DESCRIPTION "Path, Unavailable seconds."
     ::= { cienaCesPmTdmT1PortCurr24HBinEntry 12 }

   cienaCesPmTdmT1PortCurr24HBinSasp OBJECT-TYPE
     SYNTAX      Counter64
     MAX-ACCESS  read-only
     STATUS      current
     DESCRIPTION "Path, SEF/AIS seconds."
     ::= { cienaCesPmTdmT1PortCurr24HBinEntry 13 }

   cienaCesPmTdmT1PortCurr24HBinFcp OBJECT-TYPE
     SYNTAX      Counter64
     MAX-ACCESS  read-only
     STATUS      current
     DESCRIPTION "Path, Failure count."
     ::= { cienaCesPmTdmT1PortCurr24HBinEntry 14 }

   cienaCesPmTdmT1PortCurr24HBinAsp OBJECT-TYPE
     SYNTAX      Counter64
     MAX-ACCESS  read-only
     STATUS      current
     DESCRIPTION "Path, Available seconds."
     ::= { cienaCesPmTdmT1PortCurr24HBinEntry 15 }

   cienaCesPmTdmT1PortCurr24HBinTtp OBJECT-TYPE
     SYNTAX      Counter64
     MAX-ACCESS  read-only
     STATUS      current
     DESCRIPTION "Path, Total time seconds."
     ::= { cienaCesPmTdmT1PortCurr24HBinEntry 16 }

                            
   --TdmT1Port Profile Stats, history 24 hour bin
  
   cienaCesPmTdmT1PortHist24HBinTable OBJECT-TYPE
     SYNTAX      SEQUENCE OF CienaCesPmTdmT1PortHist24HBinEntry
     MAX-ACCESS  not-accessible
     STATUS      current
     DESCRIPTION "The (conceptual) read-only Table listing the Bin Statistics."
     ::= { cienaCesPmTdmT1PortStats 4 }

   cienaCesPmTdmT1PortHist24HBinEntry OBJECT-TYPE
     SYNTAX      CienaCesPmTdmT1PortHist24HBinEntry
     MAX-ACCESS  not-accessible
     STATUS      current
     DESCRIPTION
           "An entry (conceptual row) in the cienaPortPmTdmT1PortHist24HBinTable.
           This table lists the statistics for the history 24 hours bin."
     INDEX {cienaCesPmInstanceIndex}
     ::= { cienaCesPmTdmT1PortHist24HBinTable 1 }

   CienaCesPmTdmT1PortHist24HBinEntry ::=  SEQUENCE {
     cienaCesPmTdmT1PortHist24HBinStartTime                         DisplayString,
     cienaCesPmTdmT1PortHist24HBinEndTime                           DisplayString,
     cienaCesPmTdmT1PortHist24HBinClearTime                         DisplayString,
     cienaCesPmTdmT1PortHist24HBinDuration                          Unsigned32,
     cienaCesPmTdmT1PortHist24HBinState                             PmBinState,
     cienaCesPmTdmT1PortHist24HBinCvl                               Counter64,
     cienaCesPmTdmT1PortHist24HBinEsl                               Counter64,
     cienaCesPmTdmT1PortHist24HBinSesl                              Counter64,
     cienaCesPmTdmT1PortHist24HBinLossl                             Counter64,
     cienaCesPmTdmT1PortHist24HBinCvp                               Counter64,
     cienaCesPmTdmT1PortHist24HBinEsp                               Counter64,
     cienaCesPmTdmT1PortHist24HBinSesp                              Counter64,
     cienaCesPmTdmT1PortHist24HBinUasp                              Counter64,
     cienaCesPmTdmT1PortHist24HBinSasp                              Counter64,
     cienaCesPmTdmT1PortHist24HBinFcp                               Counter64,
     cienaCesPmTdmT1PortHist24HBinAsp                               Counter64,
     cienaCesPmTdmT1PortHist24HBinTtp                               Counter64
   }

   cienaCesPmTdmT1PortHist24HBinStartTime OBJECT-TYPE
     SYNTAX      DisplayString
     MAX-ACCESS  read-only
     STATUS      current
     DESCRIPTION "Collection start time of the bin."
     ::= { cienaCesPmTdmT1PortHist24HBinEntry 1 }

   cienaCesPmTdmT1PortHist24HBinEndTime OBJECT-TYPE
     SYNTAX      DisplayString
     MAX-ACCESS  read-only
     STATUS      current
     DESCRIPTION "Collection end time for the bin."
     ::= { cienaCesPmTdmT1PortHist24HBinEntry 2 }

   cienaCesPmTdmT1PortHist24HBinClearTime OBJECT-TYPE
     SYNTAX      DisplayString
     MAX-ACCESS  read-only
     STATUS      current
     DESCRIPTION "Cleared time of the bin."
     ::= { cienaCesPmTdmT1PortHist24HBinEntry 3 }

   cienaCesPmTdmT1PortHist24HBinDuration OBJECT-TYPE
     SYNTAX      Unsigned32 (1..65535)
     UNITS       "minutes"
     MAX-ACCESS  read-only
     STATUS      current
     DESCRIPTION "Duration of the bin."
     ::= { cienaCesPmTdmT1PortHist24HBinEntry 4 }

   cienaCesPmTdmT1PortHist24HBinState OBJECT-TYPE
     SYNTAX      PmBinState
     MAX-ACCESS  read-only
     STATUS      current
     DESCRIPTION "State of the bin."
     ::= { cienaCesPmTdmT1PortHist24HBinEntry 5 }

   cienaCesPmTdmT1PortHist24HBinCvl OBJECT-TYPE
     SYNTAX      Counter64
     MAX-ACCESS  read-only
     STATUS      current
     DESCRIPTION "Line, Code violations."
     ::= { cienaCesPmTdmT1PortHist24HBinEntry 6 }

   cienaCesPmTdmT1PortHist24HBinEsl OBJECT-TYPE
     SYNTAX      Counter64
     MAX-ACCESS  read-only
     STATUS      current
     DESCRIPTION "Line, Errored seconds."
     ::= { cienaCesPmTdmT1PortHist24HBinEntry 7 }

   cienaCesPmTdmT1PortHist24HBinSesl OBJECT-TYPE
     SYNTAX      Counter64
     MAX-ACCESS  read-only
     STATUS      current
     DESCRIPTION "Line, Severely errored seconds."
     ::= { cienaCesPmTdmT1PortHist24HBinEntry 8 }

   cienaCesPmTdmT1PortHist24HBinLossl OBJECT-TYPE
     SYNTAX      Counter64
     MAX-ACCESS  read-only
     STATUS      current
     DESCRIPTION "Line, Loss of signal seconds."
     ::= { cienaCesPmTdmT1PortHist24HBinEntry 9 }

   cienaCesPmTdmT1PortHist24HBinCvp OBJECT-TYPE
     SYNTAX      Counter64
     MAX-ACCESS  read-only
     STATUS      current
     DESCRIPTION "Path, Code violations."
     ::= { cienaCesPmTdmT1PortHist24HBinEntry 10 }

   cienaCesPmTdmT1PortHist24HBinEsp OBJECT-TYPE
     SYNTAX      Counter64
     MAX-ACCESS  read-only
     STATUS      current
     DESCRIPTION "Path, Errored seconds."
     ::= { cienaCesPmTdmT1PortHist24HBinEntry 11 }

   cienaCesPmTdmT1PortHist24HBinSesp OBJECT-TYPE
     SYNTAX      Counter64
     MAX-ACCESS  read-only
     STATUS      current
     DESCRIPTION "Path, Severely errored seconds."
     ::= { cienaCesPmTdmT1PortHist24HBinEntry 12 }

   cienaCesPmTdmT1PortHist24HBinUasp OBJECT-TYPE
     SYNTAX      Counter64
     MAX-ACCESS  read-only
     STATUS      current
     DESCRIPTION "Path, Unavailable seconds."
     ::= { cienaCesPmTdmT1PortHist24HBinEntry 13 }

   cienaCesPmTdmT1PortHist24HBinSasp OBJECT-TYPE
     SYNTAX      Counter64
     MAX-ACCESS  read-only
     STATUS      current
     DESCRIPTION "Path, SEF/AIS seconds."
     ::= { cienaCesPmTdmT1PortHist24HBinEntry 14 }

   cienaCesPmTdmT1PortHist24HBinFcp OBJECT-TYPE
     SYNTAX      Counter64
     MAX-ACCESS  read-only
     STATUS      current
     DESCRIPTION "Path, Failure count."
     ::= { cienaCesPmTdmT1PortHist24HBinEntry 15 }

   cienaCesPmTdmT1PortHist24HBinAsp OBJECT-TYPE
     SYNTAX      Counter64
     MAX-ACCESS  read-only
     STATUS      current
     DESCRIPTION "Path, Available seconds."
     ::= { cienaCesPmTdmT1PortHist24HBinEntry 16 }

   cienaCesPmTdmT1PortHist24HBinTtp OBJECT-TYPE
     SYNTAX      Counter64
     MAX-ACCESS  read-only
     STATUS      current
     DESCRIPTION "Path, Total time seconds."
     ::= { cienaCesPmTdmT1PortHist24HBinEntry 17 }

 
   --TdmT1Port Profile Stats, statistics bin

   cienaCesPmTdmT1PortStatisticsBinTable OBJECT-TYPE
     SYNTAX      SEQUENCE OF CienaCesPmTdmT1PortStatisticsBinEntry
     MAX-ACCESS  not-accessible
     STATUS      current
     DESCRIPTION "The (conceptual) read-only table listing the bin statistics."
     ::= { cienaCesPmTdmT1PortStats 5 }

   cienaCesPmTdmT1PortStatisticsBinEntry OBJECT-TYPE
     SYNTAX      CienaCesPmTdmT1PortStatisticsBinEntry
     MAX-ACCESS  not-accessible
     STATUS      current
     DESCRIPTION
           "An entry (conceptual row) in the cienaPortPmTdmT1PortStatisticsBinTable.
           This table lists the statistics for the statistics bin of the PM instance."
     INDEX {cienaCesPmInstanceIndex}
     ::= { cienaCesPmTdmT1PortStatisticsBinTable 1 }

   CienaCesPmTdmT1PortStatisticsBinEntry ::=  SEQUENCE {
     cienaCesPmTdmT1PortStatisticsBinStartTime                      DisplayString,
     cienaCesPmTdmT1PortStatisticsBinClearTime                      DisplayString,
     cienaCesPmTdmT1PortStatisticsBinCvl                            Counter64,
     cienaCesPmTdmT1PortStatisticsBinEsl                            Counter64,
     cienaCesPmTdmT1PortStatisticsBinSesl                           Counter64,
     cienaCesPmTdmT1PortStatisticsBinLossl                          Counter64,
     cienaCesPmTdmT1PortStatisticsBinCvp                            Counter64,   
     cienaCesPmTdmT1PortStatisticsBinEsp                            Counter64,
     cienaCesPmTdmT1PortStatisticsBinSesp                           Counter64, 
     cienaCesPmTdmT1PortStatisticsBinUasp                           Counter64,
     cienaCesPmTdmT1PortStatisticsBinSasp                           Counter64,
     cienaCesPmTdmT1PortStatisticsBinFcp                            Counter64,
     cienaCesPmTdmT1PortStatisticsBinAsp                            Counter64,   
     cienaCesPmTdmT1PortStatisticsBinTtp                            Counter64
   }          

   cienaCesPmTdmT1PortStatisticsBinStartTime OBJECT-TYPE
     SYNTAX      DisplayString
     MAX-ACCESS  read-only
     STATUS      current
     DESCRIPTION "Collection start time of the bin."
     ::= { cienaCesPmTdmT1PortStatisticsBinEntry 1 }

   cienaCesPmTdmT1PortStatisticsBinClearTime OBJECT-TYPE
     SYNTAX      DisplayString
     MAX-ACCESS  read-only
     STATUS      current
     DESCRIPTION "Cleared time of the bin."
     ::= { cienaCesPmTdmT1PortStatisticsBinEntry 2 }

   cienaCesPmTdmT1PortStatisticsBinCvl OBJECT-TYPE
     SYNTAX      Counter64
     MAX-ACCESS  read-only
     STATUS      current
     DESCRIPTION "Line, Code violations."
     ::= { cienaCesPmTdmT1PortStatisticsBinEntry 3 }

   cienaCesPmTdmT1PortStatisticsBinEsl OBJECT-TYPE
     SYNTAX      Counter64
     MAX-ACCESS  read-only
     STATUS      current
     DESCRIPTION "Line, Errored seconds."
     ::= { cienaCesPmTdmT1PortStatisticsBinEntry 4 }

   cienaCesPmTdmT1PortStatisticsBinSesl OBJECT-TYPE
     SYNTAX      Counter64
     MAX-ACCESS  read-only
     STATUS      current
     DESCRIPTION "Line, Severely errored seconds."
     ::= { cienaCesPmTdmT1PortStatisticsBinEntry 5 }

   cienaCesPmTdmT1PortStatisticsBinLossl OBJECT-TYPE
     SYNTAX      Counter64
     MAX-ACCESS  read-only
     STATUS      current
     DESCRIPTION "Line, Loss of signal seconds."
     ::= { cienaCesPmTdmT1PortStatisticsBinEntry 6 }

   cienaCesPmTdmT1PortStatisticsBinCvp OBJECT-TYPE
     SYNTAX      Counter64
     MAX-ACCESS  read-only
     STATUS      current
     DESCRIPTION "Path, Code violations."
     ::= { cienaCesPmTdmT1PortStatisticsBinEntry 7 }

  cienaCesPmTdmT1PortStatisticsBinEsp OBJECT-TYPE
     SYNTAX      Counter64
     MAX-ACCESS  read-only
     STATUS      current
     DESCRIPTION "Path, Errored seconds."
     ::= { cienaCesPmTdmT1PortStatisticsBinEntry 8 }

   cienaCesPmTdmT1PortStatisticsBinSesp OBJECT-TYPE
     SYNTAX      Counter64
     MAX-ACCESS  read-only
     STATUS      current
     DESCRIPTION "Path, Severely errored seconds."
     ::= { cienaCesPmTdmT1PortStatisticsBinEntry 9 }

   cienaCesPmTdmT1PortStatisticsBinUasp OBJECT-TYPE
     SYNTAX      Counter64
     MAX-ACCESS  read-only
     STATUS      current
     DESCRIPTION "Path, Unavailable seconds."
     ::= { cienaCesPmTdmT1PortStatisticsBinEntry 10 }

   cienaCesPmTdmT1PortStatisticsBinSasp OBJECT-TYPE
     SYNTAX      Counter64
     MAX-ACCESS  read-only
     STATUS      current
     DESCRIPTION "Path, SEF/AIS seconds."
     ::= { cienaCesPmTdmT1PortStatisticsBinEntry 11 }

   cienaCesPmTdmT1PortStatisticsBinFcp OBJECT-TYPE
     SYNTAX      Counter64
     MAX-ACCESS  read-only
     STATUS      current
     DESCRIPTION "Path, Failure count."
     ::= { cienaCesPmTdmT1PortStatisticsBinEntry 12 }

   cienaCesPmTdmT1PortStatisticsBinAsp OBJECT-TYPE
     SYNTAX      Counter64
     MAX-ACCESS  read-only
     STATUS      current
     DESCRIPTION "Path, Available seconds."
     ::= { cienaCesPmTdmT1PortStatisticsBinEntry 13 }

   cienaCesPmTdmT1PortStatisticsBinTtp OBJECT-TYPE
     SYNTAX      Counter64
     MAX-ACCESS  read-only
     STATUS      current
     DESCRIPTION "Path, Total time seconds."
     ::= { cienaCesPmTdmT1PortStatisticsBinEntry 14 }


   --TdmT1Port Profile Stats, total statistics bin

   cienaCesPmTdmT1PortTotalStatisticsBinTable OBJECT-TYPE
     SYNTAX      SEQUENCE OF CienaCesPmTdmT1PortTotalStatisticsBinEntry
     MAX-ACCESS  not-accessible
     STATUS      current
     DESCRIPTION "The (conceptual) read-only table listing the bin statistics."
     ::= { cienaCesPmTdmT1PortStats 6 }

   cienaCesPmTdmT1PortTotalStatisticsBinEntry OBJECT-TYPE
     SYNTAX      CienaCesPmTdmT1PortTotalStatisticsBinEntry
     MAX-ACCESS  not-accessible
     STATUS      current
     DESCRIPTION
           "An entry (conceptual row) in the cienaPortPmTdmT1PortTotalStatisticsBinTable.
           This table lists the statistics for the total statistics bin of the PM instance."
     INDEX {cienaCesPmInstanceIndex}
     ::= { cienaCesPmTdmT1PortTotalStatisticsBinTable 1 }

   CienaCesPmTdmT1PortTotalStatisticsBinEntry ::=  SEQUENCE {
     cienaCesPmTdmT1PortTotalStatisticsBinStartTime                 DisplayString,
     cienaCesPmTdmT1PortTotalStatisticsBinCvl                       Counter64,
     cienaCesPmTdmT1PortTotalStatisticsBinEsl                       Counter64,
     cienaCesPmTdmT1PortTotalStatisticsBinSesl                      Counter64,
     cienaCesPmTdmT1PortTotalStatisticsBinLossl                     Counter64,
     cienaCesPmTdmT1PortTotalStatisticsBinCvp                       Counter64,   
     cienaCesPmTdmT1PortTotalStatisticsBinEsp                       Counter64,
     cienaCesPmTdmT1PortTotalStatisticsBinSesp                      Counter64, 
     cienaCesPmTdmT1PortTotalStatisticsBinUasp                      Counter64,
     cienaCesPmTdmT1PortTotalStatisticsBinSasp                      Counter64,
     cienaCesPmTdmT1PortTotalStatisticsBinFcp                       Counter64,
     cienaCesPmTdmT1PortTotalStatisticsBinAsp                       Counter64,   
     cienaCesPmTdmT1PortTotalStatisticsBinTtp                       Counter64
   }          

   cienaCesPmTdmT1PortTotalStatisticsBinStartTime OBJECT-TYPE
     SYNTAX      DisplayString
     MAX-ACCESS  read-only
     STATUS      current
     DESCRIPTION "Collection start time of the bin."
     ::= { cienaCesPmTdmT1PortTotalStatisticsBinEntry 1 }

   cienaCesPmTdmT1PortTotalStatisticsBinCvl OBJECT-TYPE
     SYNTAX      Counter64
     MAX-ACCESS  read-only
     STATUS      current
     DESCRIPTION "Line, Code violations."
     ::= { cienaCesPmTdmT1PortTotalStatisticsBinEntry 2 }

   cienaCesPmTdmT1PortTotalStatisticsBinEsl OBJECT-TYPE
     SYNTAX      Counter64
     MAX-ACCESS  read-only
     STATUS      current
     DESCRIPTION "Line, Errored seconds."
     ::= { cienaCesPmTdmT1PortTotalStatisticsBinEntry 3 }

   cienaCesPmTdmT1PortTotalStatisticsBinSesl OBJECT-TYPE
     SYNTAX      Counter64
     MAX-ACCESS  read-only
     STATUS      current
     DESCRIPTION "Line, Severely errored seconds."
     ::= { cienaCesPmTdmT1PortTotalStatisticsBinEntry 4 }

   cienaCesPmTdmT1PortTotalStatisticsBinLossl OBJECT-TYPE
     SYNTAX      Counter64
     MAX-ACCESS  read-only
     STATUS      current
     DESCRIPTION "Line, Loss of signal seconds."
     ::= { cienaCesPmTdmT1PortTotalStatisticsBinEntry 5 }

   cienaCesPmTdmT1PortTotalStatisticsBinCvp OBJECT-TYPE
     SYNTAX      Counter64
     MAX-ACCESS  read-only
     STATUS      current
     DESCRIPTION "Path, Code violations."
     ::= { cienaCesPmTdmT1PortTotalStatisticsBinEntry 6 }

  cienaCesPmTdmT1PortTotalStatisticsBinEsp OBJECT-TYPE
     SYNTAX      Counter64
     MAX-ACCESS  read-only
     STATUS      current
     DESCRIPTION "Path, Errored seconds."
     ::= { cienaCesPmTdmT1PortTotalStatisticsBinEntry 7 }

   cienaCesPmTdmT1PortTotalStatisticsBinSesp OBJECT-TYPE
     SYNTAX      Counter64
     MAX-ACCESS  read-only
     STATUS      current
     DESCRIPTION "Path, Severely errored seconds."
     ::= { cienaCesPmTdmT1PortTotalStatisticsBinEntry 8 }

   cienaCesPmTdmT1PortTotalStatisticsBinUasp OBJECT-TYPE
     SYNTAX      Counter64
     MAX-ACCESS  read-only
     STATUS      current
     DESCRIPTION "Path, Unavailable seconds."
     ::= { cienaCesPmTdmT1PortTotalStatisticsBinEntry 9 }

   cienaCesPmTdmT1PortTotalStatisticsBinSasp OBJECT-TYPE
     SYNTAX      Counter64
     MAX-ACCESS  read-only
     STATUS      current
     DESCRIPTION "Path, SEF/AIS seconds."
     ::= { cienaCesPmTdmT1PortTotalStatisticsBinEntry 10 }

   cienaCesPmTdmT1PortTotalStatisticsBinFcp OBJECT-TYPE
     SYNTAX      Counter64
     MAX-ACCESS  read-only
     STATUS      current
     DESCRIPTION "Path, Failure count."
     ::= { cienaCesPmTdmT1PortTotalStatisticsBinEntry 11 }

   cienaCesPmTdmT1PortTotalStatisticsBinAsp OBJECT-TYPE
     SYNTAX      Counter64
     MAX-ACCESS  read-only
     STATUS      current
     DESCRIPTION "Path, Available seconds."
     ::= { cienaCesPmTdmT1PortTotalStatisticsBinEntry 12 }

   cienaCesPmTdmT1PortTotalStatisticsBinTtp OBJECT-TYPE
     SYNTAX      Counter64
     MAX-ACCESS  read-only
     STATUS      current
     DESCRIPTION "Path, Total time seconds."
     ::= { cienaCesPmTdmT1PortTotalStatisticsBinEntry 13 }


   --TdmE1Port Profile Stats, history bins

   cienaCesPmTdmE1PortHistoryBinTable OBJECT-TYPE
     SYNTAX      SEQUENCE OF CienaCesPmTdmE1PortHistoryBinEntry
     MAX-ACCESS  not-accessible
     STATUS      current
     DESCRIPTION
           "The (conceptual) read-only table listing the bin statistics."
     ::= { cienaCesPmTdmE1PortStats 1 }

   cienaCesPmTdmE1PortHistoryBinEntry OBJECT-TYPE
     SYNTAX      CienaCesPmTdmE1PortHistoryBinEntry
     MAX-ACCESS  not-accessible
     STATUS      current
     DESCRIPTION
           "An entry (conceptual row) in the cienaPortPmTdmE1PortHistoryBinTable.

           This table lists the statistics for all the history bins of the PM instance, as 
           specified by the bin-count object of the PM instance.  History bins are displayed in the order
           so that #1 bin always represents the most recently completed bin and #2 - the bin previous to that
           and so on.

           The statistics are displayed for only the instances with valid bins (with start time >0), 
           as indicated by the operational state of the corresponding PM instance."
     INDEX { cienaCesPmInstanceIndex, cienaCesPmTdmE1PortHistoryBinIndex }
     ::= { cienaCesPmTdmE1PortHistoryBinTable 1 }

   CienaCesPmTdmE1PortHistoryBinEntry ::=  SEQUENCE {
     cienaCesPmTdmE1PortHistoryBinIndex                             Unsigned32,
     cienaCesPmTdmE1PortHistoryBinStartTime                         DisplayString,
     cienaCesPmTdmE1PortHistoryBinEndTime                           DisplayString,
     cienaCesPmTdmE1PortHistoryBinClearTime                         DisplayString,
     cienaCesPmTdmE1PortHistoryBinDuration                          Unsigned32,
     cienaCesPmTdmE1PortHistoryBinState                             PmBinState,
     cienaCesPmTdmE1PortHistoryBinEb                                Counter64,
     cienaCesPmTdmE1PortHistoryBinBbe                               Counter64,
     cienaCesPmTdmE1PortHistoryBinEs                                Counter64,
     cienaCesPmTdmE1PortHistoryBinSes                               Counter64,
     cienaCesPmTdmE1PortHistoryBinUas                               Counter64,
     cienaCesPmTdmE1PortHistoryBinAs                                Counter64,
     cienaCesPmTdmE1PortHistoryBinTt                                Counter64
   }
   cienaCesPmTdmE1PortHistoryBinIndex OBJECT-TYPE
     SYNTAX      Unsigned32 (1..65535)
     MAX-ACCESS  not-accessible
     STATUS      current
     DESCRIPTION "Bin number associated with the PmTdmE1PortHistoryBin entry."
     ::= { cienaCesPmTdmE1PortHistoryBinEntry 1 }

   cienaCesPmTdmE1PortHistoryBinStartTime OBJECT-TYPE
     SYNTAX      DisplayString
     MAX-ACCESS  read-only
     STATUS      current
     DESCRIPTION "Collection start time of the bin."
     ::= { cienaCesPmTdmE1PortHistoryBinEntry 2 }

   cienaCesPmTdmE1PortHistoryBinEndTime OBJECT-TYPE
     SYNTAX      DisplayString
     MAX-ACCESS  read-only
     STATUS      current
     DESCRIPTION "Collection end time of the bin."
     ::= { cienaCesPmTdmE1PortHistoryBinEntry 3 }

   cienaCesPmTdmE1PortHistoryBinClearTime OBJECT-TYPE
     SYNTAX      DisplayString
     MAX-ACCESS  read-only
     STATUS      current
     DESCRIPTION "Collection clear time of the bin."
     ::= { cienaCesPmTdmE1PortHistoryBinEntry 4 }

   cienaCesPmTdmE1PortHistoryBinDuration OBJECT-TYPE
     SYNTAX      Unsigned32 (1..65535)
     UNITS       "minutes"
     MAX-ACCESS  read-only
     STATUS      current
     DESCRIPTION "Duration of the bin."
     ::= { cienaCesPmTdmE1PortHistoryBinEntry 5 }

   cienaCesPmTdmE1PortHistoryBinState OBJECT-TYPE
     SYNTAX      PmBinState
     MAX-ACCESS  read-only
     STATUS      current
     DESCRIPTION "State of the bin."
     ::= { cienaCesPmTdmE1PortHistoryBinEntry 6 }

   cienaCesPmTdmE1PortHistoryBinEb OBJECT-TYPE
     SYNTAX      Counter64
     MAX-ACCESS  read-only
     STATUS      current
     DESCRIPTION "Errored blocks."
     ::= { cienaCesPmTdmE1PortHistoryBinEntry 7 }

   cienaCesPmTdmE1PortHistoryBinBbe OBJECT-TYPE
     SYNTAX      Counter64
     MAX-ACCESS  read-only
     STATUS      current
     DESCRIPTION "Background block errors."
     ::= { cienaCesPmTdmE1PortHistoryBinEntry 8 }

   cienaCesPmTdmE1PortHistoryBinEs OBJECT-TYPE
     SYNTAX      Counter64
     MAX-ACCESS  read-only
     STATUS      current
     DESCRIPTION "Errored seconds."
     ::= { cienaCesPmTdmE1PortHistoryBinEntry 9 }

   cienaCesPmTdmE1PortHistoryBinSes OBJECT-TYPE
     SYNTAX      Counter64
     MAX-ACCESS  read-only
     STATUS      current
     DESCRIPTION "Severely errored seconds."
     ::= { cienaCesPmTdmE1PortHistoryBinEntry 10 }

   cienaCesPmTdmE1PortHistoryBinUas OBJECT-TYPE
     SYNTAX      Counter64
     MAX-ACCESS  read-only
     STATUS      current
     DESCRIPTION "Unavailable seconds."
     ::= { cienaCesPmTdmE1PortHistoryBinEntry 11 }

   cienaCesPmTdmE1PortHistoryBinAs OBJECT-TYPE
     SYNTAX      Counter64
     MAX-ACCESS  read-only
     STATUS      current
     DESCRIPTION "Available seconds."
     ::= { cienaCesPmTdmE1PortHistoryBinEntry 12 }

   cienaCesPmTdmE1PortHistoryBinTt OBJECT-TYPE
     SYNTAX      Counter64
     MAX-ACCESS  read-only
     STATUS      current
     DESCRIPTION "Total time seconds."
     ::= { cienaCesPmTdmE1PortHistoryBinEntry 13 }


   --TdmE1Port Profile Stats, current bin

   cienaCesPmTdmE1PortCurrBinTable OBJECT-TYPE
     SYNTAX      SEQUENCE OF CienaCesPmTdmE1PortCurrBinEntry
     MAX-ACCESS  not-accessible
     STATUS      current
     DESCRIPTION "The (conceptual) read-only table listing the bin statistics."
     ::= { cienaCesPmTdmE1PortStats 2 }

   cienaCesPmTdmE1PortCurrBinEntry OBJECT-TYPE
     SYNTAX      CienaCesPmTdmE1PortCurrBinEntry
     MAX-ACCESS  not-accessible
     STATUS      current
     DESCRIPTION
           "An entry (conceptual row) in the cienaPortPmTdmE1PortCurrBinTable.
           This table lists the statistics for the current bin of the PM instance."
     INDEX {cienaCesPmInstanceIndex}
     ::= { cienaCesPmTdmE1PortCurrBinTable 1 }

   CienaCesPmTdmE1PortCurrBinEntry ::=  SEQUENCE {
     cienaCesPmTdmE1PortCurrBinStartTime                            DisplayString,
     cienaCesPmTdmE1PortCurrBinClearTime                            DisplayString,
     cienaCesPmTdmE1PortCurrBinDuration                             Unsigned32,
     cienaCesPmTdmE1PortCurrBinState                                PmBinState,
     cienaCesPmTdmE1PortCurrBinEb                                   Counter64,
     cienaCesPmTdmE1PortCurrBinBbe                                  Counter64,
     cienaCesPmTdmE1PortCurrBinEs                                   Counter64,
     cienaCesPmTdmE1PortCurrBinSes                                  Counter64,
     cienaCesPmTdmE1PortCurrBinUas                                  Counter64,
     cienaCesPmTdmE1PortCurrBinAs                                   Counter64,
     cienaCesPmTdmE1PortCurrBinTt                                   Counter64
   }

   cienaCesPmTdmE1PortCurrBinStartTime OBJECT-TYPE
     SYNTAX      DisplayString
     MAX-ACCESS  read-only
     STATUS      current
     DESCRIPTION "Collection start time of the bin."
     ::= { cienaCesPmTdmE1PortCurrBinEntry 1 }

   cienaCesPmTdmE1PortCurrBinClearTime OBJECT-TYPE
     SYNTAX      DisplayString
     MAX-ACCESS  read-only
     STATUS      current
     DESCRIPTION "Cleared time of the bin."
     ::= { cienaCesPmTdmE1PortCurrBinEntry 2 }

   cienaCesPmTdmE1PortCurrBinDuration OBJECT-TYPE
     SYNTAX      Unsigned32 (1..65535)
     UNITS       "minutes"
     MAX-ACCESS  read-only
     STATUS      current
     DESCRIPTION "Interval of the bin."
     ::= { cienaCesPmTdmE1PortCurrBinEntry 3 }

   cienaCesPmTdmE1PortCurrBinState OBJECT-TYPE
     SYNTAX      PmBinState
     MAX-ACCESS  read-only
     STATUS      current
     DESCRIPTION "State of the bin."
     ::= { cienaCesPmTdmE1PortCurrBinEntry 4 }

   cienaCesPmTdmE1PortCurrBinEb OBJECT-TYPE
     SYNTAX      Counter64
     MAX-ACCESS  read-only
     STATUS      current
     DESCRIPTION "Errored blocks."
     ::= { cienaCesPmTdmE1PortCurrBinEntry 5 }

  cienaCesPmTdmE1PortCurrBinBbe OBJECT-TYPE
     SYNTAX      Counter64
     MAX-ACCESS  read-only
     STATUS      current
     DESCRIPTION "Background block errors."
     ::= { cienaCesPmTdmE1PortCurrBinEntry 6 }

   cienaCesPmTdmE1PortCurrBinEs OBJECT-TYPE
     SYNTAX      Counter64
     MAX-ACCESS  read-only
     STATUS      current
     DESCRIPTION "Errored seconds."
     ::= { cienaCesPmTdmE1PortCurrBinEntry 7 }

   cienaCesPmTdmE1PortCurrBinSes OBJECT-TYPE
     SYNTAX      Counter64
     MAX-ACCESS  read-only
     STATUS      current
     DESCRIPTION "Severely errored seconds."
     ::= { cienaCesPmTdmE1PortCurrBinEntry 8 }

   cienaCesPmTdmE1PortCurrBinUas OBJECT-TYPE
     SYNTAX      Counter64
     MAX-ACCESS  read-only
     STATUS      current
     DESCRIPTION "Unavailable seconds."
     ::= { cienaCesPmTdmE1PortCurrBinEntry 9 }

   cienaCesPmTdmE1PortCurrBinAs OBJECT-TYPE
     SYNTAX      Counter64
     MAX-ACCESS  read-only
     STATUS      current
     DESCRIPTION "Available seconds."
     ::= { cienaCesPmTdmE1PortCurrBinEntry 10 }

   cienaCesPmTdmE1PortCurrBinTt OBJECT-TYPE
     SYNTAX      Counter64
     MAX-ACCESS  read-only
     STATUS      current
     DESCRIPTION "Total time seconds."
     ::= { cienaCesPmTdmE1PortCurrBinEntry 11 }


   --TdmE1Port Profile Stats, current 24 hour bin
  
   cienaCesPmTdmE1PortCurr24HBinTable OBJECT-TYPE
     SYNTAX      SEQUENCE OF CienaCesPmTdmE1PortCurr24HBinEntry
     MAX-ACCESS  not-accessible
     STATUS      current
     DESCRIPTION "The (conceptual) read-only table listing the bin statistics."
     ::= { cienaCesPmTdmE1PortStats 3 }

   cienaCesPmTdmE1PortCurr24HBinEntry OBJECT-TYPE
     SYNTAX      CienaCesPmTdmE1PortCurr24HBinEntry
     MAX-ACCESS  not-accessible
     STATUS      current
     DESCRIPTION
           "An entry (conceptual row) in the cienaPortPmTdmE1PortCurr24HBinTable.
           This table lists the statistics for the current 24 hours bin."
     INDEX {cienaCesPmInstanceIndex }
     ::= { cienaCesPmTdmE1PortCurr24HBinTable 1 }

   CienaCesPmTdmE1PortCurr24HBinEntry ::=  SEQUENCE {
     cienaCesPmTdmE1PortCurr24HBinStartTime                         DisplayString,
     cienaCesPmTdmE1PortCurr24HBinClearTime                         DisplayString,
     cienaCesPmTdmE1PortCurr24HBinDuration                          Unsigned32,
     cienaCesPmTdmE1PortCurr24HBinState                             PmBinState,
     cienaCesPmTdmE1PortCurr24HBinEb                                Counter64,
     cienaCesPmTdmE1PortCurr24HBinBbe                               Counter64,
     cienaCesPmTdmE1PortCurr24HBinEs                                Counter64,
     cienaCesPmTdmE1PortCurr24HBinSes                               Counter64,
     cienaCesPmTdmE1PortCurr24HBinUas                               Counter64,
     cienaCesPmTdmE1PortCurr24HBinAs                                Counter64,
     cienaCesPmTdmE1PortCurr24HBinTt                                Counter64
   } 

   cienaCesPmTdmE1PortCurr24HBinStartTime OBJECT-TYPE
     SYNTAX      DisplayString
     MAX-ACCESS  read-only
     STATUS      current
     DESCRIPTION "Collection start time of the bin."
     ::= { cienaCesPmTdmE1PortCurr24HBinEntry 1 }

   cienaCesPmTdmE1PortCurr24HBinClearTime OBJECT-TYPE
     SYNTAX      DisplayString
     MAX-ACCESS  read-only
     STATUS      current
     DESCRIPTION "Cleared time of the bin."
     ::= { cienaCesPmTdmE1PortCurr24HBinEntry 2 }

   cienaCesPmTdmE1PortCurr24HBinDuration OBJECT-TYPE
     SYNTAX      Unsigned32 (1..65535)
     UNITS       "minutes"
     MAX-ACCESS  read-only
     STATUS      current
     DESCRIPTION "Duration of the bin."
     ::= { cienaCesPmTdmE1PortCurr24HBinEntry 3 }

   cienaCesPmTdmE1PortCurr24HBinState OBJECT-TYPE
     SYNTAX      PmBinState
     MAX-ACCESS  read-only
     STATUS      current
     DESCRIPTION "State of the bin."
     ::= { cienaCesPmTdmE1PortCurr24HBinEntry 4 }

   cienaCesPmTdmE1PortCurr24HBinEb OBJECT-TYPE
     SYNTAX      Counter64
     MAX-ACCESS  read-only
     STATUS      current
     DESCRIPTION "Errored blocks."
     ::= { cienaCesPmTdmE1PortCurr24HBinEntry 5 }

   cienaCesPmTdmE1PortCurr24HBinBbe OBJECT-TYPE
     SYNTAX      Counter64
     MAX-ACCESS  read-only
     STATUS      current
     DESCRIPTION "Background block errors."
     ::= { cienaCesPmTdmE1PortCurr24HBinEntry 6 }

   cienaCesPmTdmE1PortCurr24HBinEs OBJECT-TYPE
     SYNTAX      Counter64
     MAX-ACCESS  read-only
     STATUS      current
     DESCRIPTION "Errored seconds."
     ::= { cienaCesPmTdmE1PortCurr24HBinEntry 7 }

   cienaCesPmTdmE1PortCurr24HBinSes OBJECT-TYPE
     SYNTAX      Counter64
     MAX-ACCESS  read-only
     STATUS      current
     DESCRIPTION "Severely errored seconds."
     ::= { cienaCesPmTdmE1PortCurr24HBinEntry 8 }

   cienaCesPmTdmE1PortCurr24HBinUas OBJECT-TYPE
     SYNTAX      Counter64
     MAX-ACCESS  read-only
     STATUS      current
     DESCRIPTION "Unavailable seconds."
     ::= { cienaCesPmTdmE1PortCurr24HBinEntry 9 }

   cienaCesPmTdmE1PortCurr24HBinAs OBJECT-TYPE
     SYNTAX      Counter64
     MAX-ACCESS  read-only
     STATUS      current
     DESCRIPTION "Available seconds."
     ::= { cienaCesPmTdmE1PortCurr24HBinEntry 10 }

   cienaCesPmTdmE1PortCurr24HBinTt OBJECT-TYPE
     SYNTAX      Counter64
     MAX-ACCESS  read-only
     STATUS      current
     DESCRIPTION "Total time seconds."
     ::= { cienaCesPmTdmE1PortCurr24HBinEntry 11 }


   --TdmE1Port Profile Stats, history 24 hour bin
  
   cienaCesPmTdmE1PortHist24HBinTable OBJECT-TYPE
     SYNTAX      SEQUENCE OF CienaCesPmTdmE1PortHist24HBinEntry
     MAX-ACCESS  not-accessible
     STATUS      current
     DESCRIPTION "The (conceptual) read-only Table listing the Bin Statistics."
     ::= { cienaCesPmTdmE1PortStats 4 }

   cienaCesPmTdmE1PortHist24HBinEntry OBJECT-TYPE
     SYNTAX      CienaCesPmTdmE1PortHist24HBinEntry
     MAX-ACCESS  not-accessible
     STATUS      current
     DESCRIPTION
           "An entry (conceptual row) in the cienaPortPmTdmE1PortHist24HBinTable.
           This table lists the statistics for the history 24 hours bin."
     INDEX {cienaCesPmInstanceIndex}
     ::= { cienaCesPmTdmE1PortHist24HBinTable 1 }

   CienaCesPmTdmE1PortHist24HBinEntry ::=  SEQUENCE {
     cienaCesPmTdmE1PortHist24HBinStartTime                         DisplayString,
     cienaCesPmTdmE1PortHist24HBinEndTime                           DisplayString,
     cienaCesPmTdmE1PortHist24HBinClearTime                         DisplayString,
     cienaCesPmTdmE1PortHist24HBinDuration                          Unsigned32,
     cienaCesPmTdmE1PortHist24HBinState                             PmBinState,
     cienaCesPmTdmE1PortHist24HBinEb                                Counter64,
     cienaCesPmTdmE1PortHist24HBinBbe                               Counter64,
     cienaCesPmTdmE1PortHist24HBinEs                                Counter64,
     cienaCesPmTdmE1PortHist24HBinSes                               Counter64,
     cienaCesPmTdmE1PortHist24HBinUas                               Counter64,
     cienaCesPmTdmE1PortHist24HBinAs                                Counter64,
     cienaCesPmTdmE1PortHist24HBinTt                                Counter64
   }

   cienaCesPmTdmE1PortHist24HBinStartTime OBJECT-TYPE
     SYNTAX      DisplayString
     MAX-ACCESS  read-only
     STATUS      current
     DESCRIPTION "Collection start time of the bin."
     ::= { cienaCesPmTdmE1PortHist24HBinEntry 1 }

   cienaCesPmTdmE1PortHist24HBinEndTime OBJECT-TYPE
     SYNTAX      DisplayString
     MAX-ACCESS  read-only
     STATUS      current
     DESCRIPTION "Collection end time for the bin."
     ::= { cienaCesPmTdmE1PortHist24HBinEntry 2 }

   cienaCesPmTdmE1PortHist24HBinClearTime OBJECT-TYPE
     SYNTAX      DisplayString
     MAX-ACCESS  read-only
     STATUS      current
     DESCRIPTION "Cleared time of the bin."
     ::= { cienaCesPmTdmE1PortHist24HBinEntry 3 }

   cienaCesPmTdmE1PortHist24HBinDuration OBJECT-TYPE
     SYNTAX      Unsigned32 (1..65535)
     UNITS       "minutes"
     MAX-ACCESS  read-only
     STATUS      current
     DESCRIPTION "Duration of the bin."
     ::= { cienaCesPmTdmE1PortHist24HBinEntry 4 }

   cienaCesPmTdmE1PortHist24HBinState OBJECT-TYPE
     SYNTAX      PmBinState
     MAX-ACCESS  read-only
     STATUS      current
     DESCRIPTION "State of the bin."
     ::= { cienaCesPmTdmE1PortHist24HBinEntry 5 }

   cienaCesPmTdmE1PortHist24HBinEb OBJECT-TYPE
     SYNTAX      Counter64
     MAX-ACCESS  read-only
     STATUS      current
     DESCRIPTION "Errored blocks."
     ::= { cienaCesPmTdmE1PortHist24HBinEntry 6 }

   cienaCesPmTdmE1PortHist24HBinBbe OBJECT-TYPE
     SYNTAX      Counter64
     MAX-ACCESS  read-only
     STATUS      current
     DESCRIPTION "Background block errors."
     ::= { cienaCesPmTdmE1PortHist24HBinEntry 7 }

   cienaCesPmTdmE1PortHist24HBinEs OBJECT-TYPE
     SYNTAX      Counter64
     MAX-ACCESS  read-only
     STATUS      current
     DESCRIPTION "Errored seconds."
     ::= { cienaCesPmTdmE1PortHist24HBinEntry 8 }

   cienaCesPmTdmE1PortHist24HBinSes OBJECT-TYPE
     SYNTAX      Counter64
     MAX-ACCESS  read-only
     STATUS      current
     DESCRIPTION "Severely errored seconds."
     ::= { cienaCesPmTdmE1PortHist24HBinEntry 9 }

   cienaCesPmTdmE1PortHist24HBinUas OBJECT-TYPE
     SYNTAX      Counter64
     MAX-ACCESS  read-only
     STATUS      current
     DESCRIPTION "Unavailable seconds."
     ::= { cienaCesPmTdmE1PortHist24HBinEntry 10 }

   cienaCesPmTdmE1PortHist24HBinAs OBJECT-TYPE
     SYNTAX      Counter64
     MAX-ACCESS  read-only
     STATUS      current
     DESCRIPTION "Available seconds."
     ::= { cienaCesPmTdmE1PortHist24HBinEntry 11 }

   cienaCesPmTdmE1PortHist24HBinTt OBJECT-TYPE
     SYNTAX      Counter64
     MAX-ACCESS  read-only
     STATUS      current
     DESCRIPTION "Total time seconds."
     ::= { cienaCesPmTdmE1PortHist24HBinEntry 12 }

 
   --TdmE1Port Profile Stats, statistics bin

   cienaCesPmTdmE1PortStatisticsBinTable OBJECT-TYPE
     SYNTAX      SEQUENCE OF CienaCesPmTdmE1PortStatisticsBinEntry
     MAX-ACCESS  not-accessible
     STATUS      current
     DESCRIPTION "The (conceptual) read-only table listing the bin statistics."
     ::= { cienaCesPmTdmE1PortStats 5 }

   cienaCesPmTdmE1PortStatisticsBinEntry OBJECT-TYPE
     SYNTAX      CienaCesPmTdmE1PortStatisticsBinEntry
     MAX-ACCESS  not-accessible
     STATUS      current
     DESCRIPTION
           "An entry (conceptual row) in the cienaPortPmTdmE1PortStatisticsBinTable.
           This table lists the statistics for the statistics bin of the PM instance."
     INDEX {cienaCesPmInstanceIndex}
     ::= { cienaCesPmTdmE1PortStatisticsBinTable 1 }

   CienaCesPmTdmE1PortStatisticsBinEntry ::=  SEQUENCE {
     cienaCesPmTdmE1PortStatisticsBinStartTime                      DisplayString,
     cienaCesPmTdmE1PortStatisticsBinClearTime                      DisplayString,
     cienaCesPmTdmE1PortStatisticsBinEb                             Counter64,
     cienaCesPmTdmE1PortStatisticsBinBbe                            Counter64,
     cienaCesPmTdmE1PortStatisticsBinEs                             Counter64,
     cienaCesPmTdmE1PortStatisticsBinSes                            Counter64,
     cienaCesPmTdmE1PortStatisticsBinUas                            Counter64,
     cienaCesPmTdmE1PortStatisticsBinAs                             Counter64,
     cienaCesPmTdmE1PortStatisticsBinTt                             Counter64
   }          

   cienaCesPmTdmE1PortStatisticsBinStartTime OBJECT-TYPE
     SYNTAX      DisplayString
     MAX-ACCESS  read-only
     STATUS      current
     DESCRIPTION "Collection start time of the bin."
     ::= { cienaCesPmTdmE1PortStatisticsBinEntry 1 }

   cienaCesPmTdmE1PortStatisticsBinClearTime OBJECT-TYPE
     SYNTAX      DisplayString
     MAX-ACCESS  read-only
     STATUS      current
     DESCRIPTION "Cleared time of the bin."
     ::= { cienaCesPmTdmE1PortStatisticsBinEntry 2 }

   cienaCesPmTdmE1PortStatisticsBinEb OBJECT-TYPE
     SYNTAX      Counter64
     MAX-ACCESS  read-only
     STATUS      current
     DESCRIPTION "Errored blocks."
     ::= { cienaCesPmTdmE1PortStatisticsBinEntry 3 }

   cienaCesPmTdmE1PortStatisticsBinBbe OBJECT-TYPE
     SYNTAX      Counter64
     MAX-ACCESS  read-only
     STATUS      current
     DESCRIPTION "Background block errors."
     ::= { cienaCesPmTdmE1PortStatisticsBinEntry 4 }

   cienaCesPmTdmE1PortStatisticsBinEs OBJECT-TYPE
     SYNTAX      Counter64
     MAX-ACCESS  read-only
     STATUS      current
     DESCRIPTION "Errored seconds."
     ::= { cienaCesPmTdmE1PortStatisticsBinEntry 5 }

   cienaCesPmTdmE1PortStatisticsBinSes OBJECT-TYPE
     SYNTAX      Counter64
     MAX-ACCESS  read-only
     STATUS      current
     DESCRIPTION "Severely errored seconds."
     ::= { cienaCesPmTdmE1PortStatisticsBinEntry 6 }

   cienaCesPmTdmE1PortStatisticsBinUas OBJECT-TYPE
     SYNTAX      Counter64
     MAX-ACCESS  read-only
     STATUS      current
     DESCRIPTION "Unavailable seconds."
     ::= { cienaCesPmTdmE1PortStatisticsBinEntry 7 }

  cienaCesPmTdmE1PortStatisticsBinAs OBJECT-TYPE
     SYNTAX      Counter64
     MAX-ACCESS  read-only
     STATUS      current
     DESCRIPTION "Available seconds."
     ::= { cienaCesPmTdmE1PortStatisticsBinEntry 8 }

   cienaCesPmTdmE1PortStatisticsBinTt OBJECT-TYPE
     SYNTAX      Counter64
     MAX-ACCESS  read-only
     STATUS      current
     DESCRIPTION "Total time seconds."
     ::= { cienaCesPmTdmE1PortStatisticsBinEntry 9 }


   --TdmE1Port Profile Stats, total statistics bin

   cienaCesPmTdmE1PortTotalStatisticsBinTable OBJECT-TYPE
     SYNTAX      SEQUENCE OF CienaCesPmTdmE1PortTotalStatisticsBinEntry
     MAX-ACCESS  not-accessible
     STATUS      current
     DESCRIPTION "The (conceptual) read-only table listing the bin statistics."
     ::= { cienaCesPmTdmE1PortStats 6 }

   cienaCesPmTdmE1PortTotalStatisticsBinEntry OBJECT-TYPE
     SYNTAX      CienaCesPmTdmE1PortTotalStatisticsBinEntry
     MAX-ACCESS  not-accessible
     STATUS      current
     DESCRIPTION
           "An entry (conceptual row) in the cienaPortPmTdmE1PortTotalStatisticsBinTable.
           This table lists the statistics for the total statistics bin of the PM instance."
     INDEX {cienaCesPmInstanceIndex}
     ::= { cienaCesPmTdmE1PortTotalStatisticsBinTable 1 }

   CienaCesPmTdmE1PortTotalStatisticsBinEntry ::=  SEQUENCE {
     cienaCesPmTdmE1PortTotalStatisticsBinStartTime                 DisplayString,
     cienaCesPmTdmE1PortTotalStatisticsBinEb                        Counter64,
     cienaCesPmTdmE1PortTotalStatisticsBinBbe                       Counter64,
     cienaCesPmTdmE1PortTotalStatisticsBinEs                        Counter64,
     cienaCesPmTdmE1PortTotalStatisticsBinSes                       Counter64,
     cienaCesPmTdmE1PortTotalStatisticsBinUas                       Counter64,
     cienaCesPmTdmE1PortTotalStatisticsBinAs                        Counter64,
     cienaCesPmTdmE1PortTotalStatisticsBinTt                        Counter64
   }          

   cienaCesPmTdmE1PortTotalStatisticsBinStartTime OBJECT-TYPE
     SYNTAX      DisplayString
     MAX-ACCESS  read-only
     STATUS      current
     DESCRIPTION "Collection start time of the bin."
     ::= { cienaCesPmTdmE1PortTotalStatisticsBinEntry 1 }

   cienaCesPmTdmE1PortTotalStatisticsBinEb OBJECT-TYPE
     SYNTAX      Counter64
     MAX-ACCESS  read-only
     STATUS      current
     DESCRIPTION "Errored blocks."
     ::= { cienaCesPmTdmE1PortTotalStatisticsBinEntry 2 }

   cienaCesPmTdmE1PortTotalStatisticsBinBbe OBJECT-TYPE
     SYNTAX      Counter64
     MAX-ACCESS  read-only
     STATUS      current
     DESCRIPTION "Background block errors."
     ::= { cienaCesPmTdmE1PortTotalStatisticsBinEntry 3 }

   cienaCesPmTdmE1PortTotalStatisticsBinEs OBJECT-TYPE
     SYNTAX      Counter64
     MAX-ACCESS  read-only
     STATUS      current
     DESCRIPTION "Errored seconds."
     ::= { cienaCesPmTdmE1PortTotalStatisticsBinEntry 4 }

   cienaCesPmTdmE1PortTotalStatisticsBinSes OBJECT-TYPE
     SYNTAX      Counter64
     MAX-ACCESS  read-only
     STATUS      current
     DESCRIPTION "Severely errored seconds."
     ::= { cienaCesPmTdmE1PortTotalStatisticsBinEntry 5 }

   cienaCesPmTdmE1PortTotalStatisticsBinUas OBJECT-TYPE
     SYNTAX      Counter64
     MAX-ACCESS  read-only
     STATUS      current
     DESCRIPTION "Unavailable seconds."
     ::= { cienaCesPmTdmE1PortTotalStatisticsBinEntry 6 }

  cienaCesPmTdmE1PortTotalStatisticsBinAs OBJECT-TYPE
     SYNTAX      Counter64
     MAX-ACCESS  read-only
     STATUS      current
     DESCRIPTION "Available seconds."
     ::= { cienaCesPmTdmE1PortTotalStatisticsBinEntry 7 }

   cienaCesPmTdmE1PortTotalStatisticsBinTt OBJECT-TYPE
     SYNTAX      Counter64
     MAX-ACCESS  read-only
     STATUS      current
     DESCRIPTION "Total time seconds."
     ::= { cienaCesPmTdmE1PortTotalStatisticsBinEntry 8 }


   --TdmPw Profile Stats, history bins

   cienaCesPmTdmPwHistoryBinTable OBJECT-TYPE
     SYNTAX      SEQUENCE OF CienaCesPmTdmPwHistoryBinEntry
     MAX-ACCESS  not-accessible
     STATUS      current
     DESCRIPTION
           "The (conceptual) read-only table listing the bin statistics."
     ::= { cienaCesPmTdmPwStats 1 }

   cienaCesPmTdmPwHistoryBinEntry OBJECT-TYPE
     SYNTAX      CienaCesPmTdmPwHistoryBinEntry
     MAX-ACCESS  not-accessible
     STATUS      current
     DESCRIPTION
           "An entry (conceptual row) in the cienaPortPmTdmPwHistoryBinTable.

           This table lists the statistics for all the history bins of the PM instance, as 
           specified by the bin-count object of the PM instance.  History bins are displayed in the order
           so that #1 bin always represents the most recently completed bin and #2 - the bin previous to that
           and so on.

           The statistics are displayed for only the instances with valid bins (with start time >0), 
           as indicated by the operational state of the corresponding PM instance."
     INDEX { cienaCesPmInstanceIndex, cienaCesPmTdmPwHistoryBinIndex }
     ::= { cienaCesPmTdmPwHistoryBinTable 1 }

   CienaCesPmTdmPwHistoryBinEntry ::=  SEQUENCE {
     cienaCesPmTdmPwHistoryBinIndex                             Unsigned32,
     cienaCesPmTdmPwHistoryBinStartTime                         DisplayString,
     cienaCesPmTdmPwHistoryBinEndTime                           DisplayString,
     cienaCesPmTdmPwHistoryBinClearTime                         DisplayString,
     cienaCesPmTdmPwHistoryBinDuration                          Unsigned32,
     cienaCesPmTdmPwHistoryBinState                             PmBinState,
     cienaCesPmTdmPwHistoryBinMiss                              Counter64,
     cienaCesPmTdmPwHistoryBinReorder                           Counter64,
     cienaCesPmTdmPwHistoryBinMissorder                         Counter64,
     cienaCesPmTdmPwHistoryBinMalformed                         Counter64,
     cienaCesPmTdmPwHistoryBinUnderrun                          Counter64,
     cienaCesPmTdmPwHistoryBinOverrun                           Counter64,
     cienaCesPmTdmPwHistoryBinEs                                Counter64,
     cienaCesPmTdmPwHistoryBinSes                               Counter64,
     cienaCesPmTdmPwHistoryBinUas                               Counter64,
     cienaCesPmTdmPwHistoryBinLops                              Counter64,
     cienaCesPmTdmPwHistoryBinLbit                              Counter64,
     cienaCesPmTdmPwHistoryBinRbit                              Counter64,
     cienaCesPmTdmPwHistoryBinMbit                              Counter64,
     cienaCesPmTdmPwHistoryBinRxPkt                             Counter64,
     cienaCesPmTdmPwHistoryBinTxPkt                             Counter64,
     cienaCesPmTdmPwHistoryBinEsp                               Counter64,
     cienaCesPmTdmPwHistoryBinSesp                              Counter64,
     cienaCesPmTdmPwHistoryBinUasp                              Counter64,
     cienaCesPmTdmPwHistoryBinCvp                               Counter64,
     cienaCesPmTdmPwHistoryBinFcp                               Counter64,
     cienaCesPmTdmPwHistoryBinAsp                               Counter64,
     cienaCesPmTdmPwHistoryBinTtp                               Counter64
   }
   cienaCesPmTdmPwHistoryBinIndex OBJECT-TYPE
     SYNTAX      Unsigned32 (1..65535)
     MAX-ACCESS  not-accessible
     STATUS      current
     DESCRIPTION "Bin number associated with the PmTdmPwHistoryBin entry."
     ::= { cienaCesPmTdmPwHistoryBinEntry 1 }

   cienaCesPmTdmPwHistoryBinStartTime OBJECT-TYPE
     SYNTAX      DisplayString
     MAX-ACCESS  read-only
     STATUS      current
     DESCRIPTION "Collection start time of the bin."
     ::= { cienaCesPmTdmPwHistoryBinEntry 2 }

   cienaCesPmTdmPwHistoryBinEndTime OBJECT-TYPE
     SYNTAX      DisplayString
     MAX-ACCESS  read-only
     STATUS      current
     DESCRIPTION "Collection end time of the bin."
     ::= { cienaCesPmTdmPwHistoryBinEntry 3 }

   cienaCesPmTdmPwHistoryBinClearTime OBJECT-TYPE
     SYNTAX      DisplayString
     MAX-ACCESS  read-only
     STATUS      current
     DESCRIPTION "Collection clear time of the bin."
     ::= { cienaCesPmTdmPwHistoryBinEntry 4 }

   cienaCesPmTdmPwHistoryBinDuration OBJECT-TYPE
     SYNTAX      Unsigned32 (1..65535)
     UNITS       "minutes"
     MAX-ACCESS  read-only
     STATUS      current
     DESCRIPTION "Duration of the bin."
     ::= { cienaCesPmTdmPwHistoryBinEntry 5 }

   cienaCesPmTdmPwHistoryBinState OBJECT-TYPE
     SYNTAX      PmBinState
     MAX-ACCESS  read-only
     STATUS      current
     DESCRIPTION "State of the bin."
     ::= { cienaCesPmTdmPwHistoryBinEntry 6 }

   cienaCesPmTdmPwHistoryBinMiss OBJECT-TYPE
     SYNTAX      Counter64
     MAX-ACCESS  read-only
     STATUS      current
     DESCRIPTION "Number of missing PWE packets."
     ::= { cienaCesPmTdmPwHistoryBinEntry 7 }

   cienaCesPmTdmPwHistoryBinReorder OBJECT-TYPE
     SYNTAX      Counter64
     MAX-ACCESS  read-only
     STATUS      current
     DESCRIPTION "Number of successfully reordered packets."
     ::= { cienaCesPmTdmPwHistoryBinEntry 8 }

   cienaCesPmTdmPwHistoryBinMissorder OBJECT-TYPE
     SYNTAX      Counter64
     MAX-ACCESS  read-only
     STATUS      current
     DESCRIPTION "Number of packets that cannot be reordered or dropped."
     ::= { cienaCesPmTdmPwHistoryBinEntry 9 }

   cienaCesPmTdmPwHistoryBinMalformed OBJECT-TYPE
     SYNTAX      Counter64
     MAX-ACCESS  read-only
     STATUS      current
     DESCRIPTION "Number of packets with invalid payload size of header."
     ::= { cienaCesPmTdmPwHistoryBinEntry 10 }

   cienaCesPmTdmPwHistoryBinUnderrun OBJECT-TYPE
     SYNTAX      Counter64
     MAX-ACCESS  read-only
     STATUS      current
     DESCRIPTION "Number of PDV buffer empty events."
     ::= { cienaCesPmTdmPwHistoryBinEntry 11 }

   cienaCesPmTdmPwHistoryBinOverrun OBJECT-TYPE
     SYNTAX      Counter64
     MAX-ACCESS  read-only
     STATUS      current
     DESCRIPTION "Number of PDV buffer full events."
     ::= { cienaCesPmTdmPwHistoryBinEntry 12 }

   cienaCesPmTdmPwHistoryBinEs OBJECT-TYPE
     SYNTAX      Counter64
     MAX-ACCESS  read-only
     STATUS      current
     DESCRIPTION "Errored seconds."
     ::= { cienaCesPmTdmPwHistoryBinEntry 13 }

   cienaCesPmTdmPwHistoryBinSes OBJECT-TYPE
     SYNTAX      Counter64
     MAX-ACCESS  read-only
     STATUS      current
     DESCRIPTION "Severely errored seconds."
     ::= { cienaCesPmTdmPwHistoryBinEntry 14 }

   cienaCesPmTdmPwHistoryBinUas OBJECT-TYPE
     SYNTAX      Counter64
     MAX-ACCESS  read-only
     STATUS      current
     DESCRIPTION "Unavailable seconds."
     ::= { cienaCesPmTdmPwHistoryBinEntry 15 }

   cienaCesPmTdmPwHistoryBinLops OBJECT-TYPE
     SYNTAX      Counter64
     MAX-ACCESS  read-only
     STATUS      current
     DESCRIPTION "Number of LOPS events."
     ::= { cienaCesPmTdmPwHistoryBinEntry 16 }

   cienaCesPmTdmPwHistoryBinLbit OBJECT-TYPE
     SYNTAX      Counter64
     MAX-ACCESS  read-only
     STATUS      current
     DESCRIPTION "Number of L-bit set events."
     ::= { cienaCesPmTdmPwHistoryBinEntry 17 }

   cienaCesPmTdmPwHistoryBinRbit OBJECT-TYPE
     SYNTAX      Counter64
     MAX-ACCESS  read-only
     STATUS      current
     DESCRIPTION "Number of R-bit set events."
     ::= { cienaCesPmTdmPwHistoryBinEntry 18 }

   cienaCesPmTdmPwHistoryBinMbit OBJECT-TYPE
     SYNTAX      Counter64
     MAX-ACCESS  read-only
     STATUS      current
     DESCRIPTION "Number of M-bit set events (CESoP specific counter)."
     ::= { cienaCesPmTdmPwHistoryBinEntry 19 }

   cienaCesPmTdmPwHistoryBinRxPkt OBJECT-TYPE
     SYNTAX      Counter64
     MAX-ACCESS  read-only
     STATUS      current
     DESCRIPTION "Number of valid received packet over a service instance (i.e. PW)."
     ::= { cienaCesPmTdmPwHistoryBinEntry 20 }

   cienaCesPmTdmPwHistoryBinTxPkt OBJECT-TYPE
     SYNTAX      Counter64
     MAX-ACCESS  read-only
     STATUS      current
     DESCRIPTION "Number of valid transmit packet over a service instance (i.e. PW)."
     ::= { cienaCesPmTdmPwHistoryBinEntry 21 }

   cienaCesPmTdmPwHistoryBinEsp OBJECT-TYPE
     SYNTAX      Counter64
     MAX-ACCESS  read-only
     STATUS      current
     DESCRIPTION "Path errored seconds."

     ::= { cienaCesPmTdmPwHistoryBinEntry 22 }

   cienaCesPmTdmPwHistoryBinSesp OBJECT-TYPE
     SYNTAX      Counter64
     MAX-ACCESS  read-only
     STATUS      current
     DESCRIPTION "Path severely errored seconds."
     ::= { cienaCesPmTdmPwHistoryBinEntry 23 }

   cienaCesPmTdmPwHistoryBinUasp OBJECT-TYPE
     SYNTAX      Counter64
     MAX-ACCESS  read-only
     STATUS      current
     DESCRIPTION "Path unavailable seconds."
     ::= { cienaCesPmTdmPwHistoryBinEntry 24 }

   cienaCesPmTdmPwHistoryBinCvp OBJECT-TYPE
     SYNTAX      Counter64
     MAX-ACCESS  read-only
     STATUS      current
     DESCRIPTION "Number of path code violations."
     ::= { cienaCesPmTdmPwHistoryBinEntry 25 }

   cienaCesPmTdmPwHistoryBinFcp OBJECT-TYPE
     SYNTAX      Counter64
     MAX-ACCESS  read-only
     STATUS      current
     DESCRIPTION "Number of path fault events."
     ::= { cienaCesPmTdmPwHistoryBinEntry 26 }

   cienaCesPmTdmPwHistoryBinAsp OBJECT-TYPE
     SYNTAX      Counter64
     MAX-ACCESS  read-only
     STATUS      current
     DESCRIPTION "Path available seconds."
     ::= { cienaCesPmTdmPwHistoryBinEntry 27 }

   cienaCesPmTdmPwHistoryBinTtp OBJECT-TYPE
     SYNTAX      Counter64
     MAX-ACCESS  read-only
     STATUS      current
     DESCRIPTION "Path total times seconds."
     ::= { cienaCesPmTdmPwHistoryBinEntry 28 }


   --TdmPw Profile Stats, current bin

   cienaCesPmTdmPwCurrBinTable OBJECT-TYPE
     SYNTAX      SEQUENCE OF CienaCesPmTdmPwCurrBinEntry
     MAX-ACCESS  not-accessible
     STATUS      current
     DESCRIPTION "The (conceptual) read-only table listing the bin statistics."
     ::= { cienaCesPmTdmPwStats 2 }

   cienaCesPmTdmPwCurrBinEntry OBJECT-TYPE
     SYNTAX      CienaCesPmTdmPwCurrBinEntry
     MAX-ACCESS  not-accessible
     STATUS      current
     DESCRIPTION
           "An entry (conceptual row) in the cienaPortPmTdmPwCurrBinTable.
           This table lists the statistics for the current bin of the PM instance."
     INDEX {cienaCesPmInstanceIndex}
     ::= { cienaCesPmTdmPwCurrBinTable 1 }

   CienaCesPmTdmPwCurrBinEntry ::=  SEQUENCE {
     cienaCesPmTdmPwCurrBinStartTime                            DisplayString,
     cienaCesPmTdmPwCurrBinClearTime                            DisplayString,
     cienaCesPmTdmPwCurrBinDuration                             Unsigned32,
     cienaCesPmTdmPwCurrBinState                                PmBinState,
     cienaCesPmTdmPwCurrBinMiss                                 Counter64,
     cienaCesPmTdmPwCurrBinReorder                              Counter64,
     cienaCesPmTdmPwCurrBinMissorder                            Counter64,
     cienaCesPmTdmPwCurrBinMalformed                            Counter64,
     cienaCesPmTdmPwCurrBinUnderrun                             Counter64,
     cienaCesPmTdmPwCurrBinOverrun                              Counter64,
     cienaCesPmTdmPwCurrBinEs                                   Counter64,
     cienaCesPmTdmPwCurrBinSes                                  Counter64,
     cienaCesPmTdmPwCurrBinUas                                  Counter64,
     cienaCesPmTdmPwCurrBinLops                                 Counter64,
     cienaCesPmTdmPwCurrBinLbit                                 Counter64,
     cienaCesPmTdmPwCurrBinRbit                                 Counter64,
     cienaCesPmTdmPwCurrBinMbit                                 Counter64,
     cienaCesPmTdmPwCurrBinRxPkt                                Counter64,
     cienaCesPmTdmPwCurrBinTxPkt                                Counter64,
     cienaCesPmTdmPwCurrBinEsp                                  Counter64,
     cienaCesPmTdmPwCurrBinSesp                                 Counter64,
     cienaCesPmTdmPwCurrBinUasp                                 Counter64,
     cienaCesPmTdmPwCurrBinCvp                                  Counter64,
     cienaCesPmTdmPwCurrBinFcp                                  Counter64,
     cienaCesPmTdmPwCurrBinAsp                                  Counter64,
     cienaCesPmTdmPwCurrBinTtp                                  Counter64
   }

   cienaCesPmTdmPwCurrBinStartTime OBJECT-TYPE
     SYNTAX      DisplayString
     MAX-ACCESS  read-only
     STATUS      current
     DESCRIPTION "Collection start time of the bin."
     ::= { cienaCesPmTdmPwCurrBinEntry 1 }

   cienaCesPmTdmPwCurrBinClearTime OBJECT-TYPE
     SYNTAX      DisplayString
     MAX-ACCESS  read-only
     STATUS      current
     DESCRIPTION "Cleared time of the bin."
     ::= { cienaCesPmTdmPwCurrBinEntry 2 }

   cienaCesPmTdmPwCurrBinDuration OBJECT-TYPE
     SYNTAX      Unsigned32 (1..65535)
     UNITS       "minutes"
     MAX-ACCESS  read-only
     STATUS      current
     DESCRIPTION "Interval of the bin."
     ::= { cienaCesPmTdmPwCurrBinEntry 3 }

   cienaCesPmTdmPwCurrBinState OBJECT-TYPE
     SYNTAX      PmBinState
     MAX-ACCESS  read-only
     STATUS      current
     DESCRIPTION "State of the bin."
     ::= { cienaCesPmTdmPwCurrBinEntry 4 }

   cienaCesPmTdmPwCurrBinMiss OBJECT-TYPE
     SYNTAX      Counter64
     MAX-ACCESS  read-only
     STATUS      current
     DESCRIPTION "Number of missing PWE packets."
     ::= { cienaCesPmTdmPwCurrBinEntry 5 }

  cienaCesPmTdmPwCurrBinReorder OBJECT-TYPE
     SYNTAX      Counter64
     MAX-ACCESS  read-only
     STATUS      current
     DESCRIPTION "Number of successfully reordered packets."
     ::= { cienaCesPmTdmPwCurrBinEntry 6 }

   cienaCesPmTdmPwCurrBinMissorder OBJECT-TYPE
     SYNTAX      Counter64
     MAX-ACCESS  read-only
     STATUS      current
     DESCRIPTION "Number of packets that cannot be reordered or dropped."
     ::= { cienaCesPmTdmPwCurrBinEntry 7 }

   cienaCesPmTdmPwCurrBinMalformed OBJECT-TYPE
     SYNTAX      Counter64
     MAX-ACCESS  read-only
     STATUS      current
     DESCRIPTION "Number of packets with invalid payload size of header."
     ::= { cienaCesPmTdmPwCurrBinEntry 8 }

   cienaCesPmTdmPwCurrBinUnderrun OBJECT-TYPE
     SYNTAX      Counter64
     MAX-ACCESS  read-only
     STATUS      current
     DESCRIPTION "Number of PDV buffer empty events."
     ::= { cienaCesPmTdmPwCurrBinEntry 9 }

   cienaCesPmTdmPwCurrBinOverrun OBJECT-TYPE
     SYNTAX      Counter64
     MAX-ACCESS  read-only
     STATUS      current
     DESCRIPTION "Number of PDV buffer full events."
     ::= { cienaCesPmTdmPwCurrBinEntry 10 }

   cienaCesPmTdmPwCurrBinEs OBJECT-TYPE
     SYNTAX      Counter64
     MAX-ACCESS  read-only
     STATUS      current
     DESCRIPTION "Errored seconds."
     ::= { cienaCesPmTdmPwCurrBinEntry 11 }

   cienaCesPmTdmPwCurrBinSes OBJECT-TYPE
     SYNTAX      Counter64
     MAX-ACCESS  read-only
     STATUS      current
     DESCRIPTION "Severely errored seconds."
     ::= { cienaCesPmTdmPwCurrBinEntry 12 }

   cienaCesPmTdmPwCurrBinUas OBJECT-TYPE
     SYNTAX      Counter64
     MAX-ACCESS  read-only
     STATUS      current
     DESCRIPTION "Unavailable seconds."
     ::= { cienaCesPmTdmPwCurrBinEntry 13 }

   cienaCesPmTdmPwCurrBinLops OBJECT-TYPE
     SYNTAX      Counter64
     MAX-ACCESS  read-only
     STATUS      current
     DESCRIPTION "Number of LOPS events."
     ::= { cienaCesPmTdmPwCurrBinEntry 14 }

   cienaCesPmTdmPwCurrBinLbit OBJECT-TYPE
     SYNTAX      Counter64
     MAX-ACCESS  read-only
     STATUS      current
     DESCRIPTION "Number of L-bit set events."
     ::= { cienaCesPmTdmPwCurrBinEntry 15 }

   cienaCesPmTdmPwCurrBinRbit OBJECT-TYPE
     SYNTAX      Counter64
     MAX-ACCESS  read-only
     STATUS      current
     DESCRIPTION "Number of R-bit set events."
     ::= { cienaCesPmTdmPwCurrBinEntry 16 }

   cienaCesPmTdmPwCurrBinMbit OBJECT-TYPE
     SYNTAX      Counter64
     MAX-ACCESS  read-only
     STATUS      current
     DESCRIPTION "Number of M-bit set events (CESoP specific counter)."
     ::= { cienaCesPmTdmPwCurrBinEntry 17 }

   cienaCesPmTdmPwCurrBinRxPkt OBJECT-TYPE
     SYNTAX      Counter64
     MAX-ACCESS  read-only
     STATUS      current
     DESCRIPTION "Number of valid received packet over a service instance (i.e. PW)."
     ::= { cienaCesPmTdmPwCurrBinEntry 18 }

   cienaCesPmTdmPwCurrBinTxPkt OBJECT-TYPE
     SYNTAX      Counter64
     MAX-ACCESS  read-only
     STATUS      current
     DESCRIPTION "Number of valid transmit packet over a service instance (i.e. PW)."
     ::= { cienaCesPmTdmPwCurrBinEntry 19 }

   cienaCesPmTdmPwCurrBinEsp OBJECT-TYPE
     SYNTAX      Counter64
     MAX-ACCESS  read-only
     STATUS      current
     DESCRIPTION "Path errored seconds."
     ::= { cienaCesPmTdmPwCurrBinEntry 20 }

   cienaCesPmTdmPwCurrBinSesp OBJECT-TYPE
     SYNTAX      Counter64
     MAX-ACCESS  read-only
     STATUS      current
     DESCRIPTION "Path severely errored seconds."
     ::= { cienaCesPmTdmPwCurrBinEntry 21 }

   cienaCesPmTdmPwCurrBinUasp OBJECT-TYPE
     SYNTAX      Counter64
     MAX-ACCESS  read-only
     STATUS      current
     DESCRIPTION "Path unavailable seconds."
     ::= { cienaCesPmTdmPwCurrBinEntry 22 }

   cienaCesPmTdmPwCurrBinCvp OBJECT-TYPE
     SYNTAX      Counter64
     MAX-ACCESS  read-only
     STATUS      current
     DESCRIPTION "Number of path code violations."
     ::= { cienaCesPmTdmPwCurrBinEntry 23 }

   cienaCesPmTdmPwCurrBinFcp OBJECT-TYPE
     SYNTAX      Counter64
     MAX-ACCESS  read-only
     STATUS      current
     DESCRIPTION "Number of path fault events."
     ::= { cienaCesPmTdmPwCurrBinEntry 24 }

   cienaCesPmTdmPwCurrBinAsp OBJECT-TYPE
     SYNTAX      Counter64
     MAX-ACCESS  read-only
     STATUS      current
     DESCRIPTION "Path available seconds."
     ::= { cienaCesPmTdmPwCurrBinEntry 25 }

   cienaCesPmTdmPwCurrBinTtp OBJECT-TYPE
     SYNTAX      Counter64
     MAX-ACCESS  read-only
     STATUS      current
     DESCRIPTION "Path total time seconds."
     ::= { cienaCesPmTdmPwCurrBinEntry 26 }


   --TdmPw Profile Stats, current 24 hour bin
  
   cienaCesPmTdmPwCurr24HBinTable OBJECT-TYPE
     SYNTAX      SEQUENCE OF CienaCesPmTdmPwCurr24HBinEntry
     MAX-ACCESS  not-accessible
     STATUS      current
     DESCRIPTION "The (conceptual) read-only table listing the bin statistics."
     ::= { cienaCesPmTdmPwStats 3 }

   cienaCesPmTdmPwCurr24HBinEntry OBJECT-TYPE
     SYNTAX      CienaCesPmTdmPwCurr24HBinEntry
     MAX-ACCESS  not-accessible
     STATUS      current
     DESCRIPTION
           "An entry (conceptual row) in the cienaPortPmTdmPwCurr24HBinTable.
           This table lists the statistics for the current 24 hours bin."
     INDEX {cienaCesPmInstanceIndex }
     ::= { cienaCesPmTdmPwCurr24HBinTable 1 }

   CienaCesPmTdmPwCurr24HBinEntry ::=  SEQUENCE {
     cienaCesPmTdmPwCurr24HBinStartTime                         DisplayString,
     cienaCesPmTdmPwCurr24HBinClearTime                         DisplayString,
     cienaCesPmTdmPwCurr24HBinDuration                          Unsigned32,
     cienaCesPmTdmPwCurr24HBinState                             PmBinState,
     cienaCesPmTdmPwCurr24HBinMiss                              Counter64,
     cienaCesPmTdmPwCurr24HBinReorder                           Counter64,
     cienaCesPmTdmPwCurr24HBinMissorder                         Counter64,
     cienaCesPmTdmPwCurr24HBinMalformed                         Counter64,
     cienaCesPmTdmPwCurr24HBinUnderrun                          Counter64,
     cienaCesPmTdmPwCurr24HBinOverrun                           Counter64,
     cienaCesPmTdmPwCurr24HBinEs                                Counter64,
     cienaCesPmTdmPwCurr24HBinSes                               Counter64,
     cienaCesPmTdmPwCurr24HBinUas                               Counter64,
     cienaCesPmTdmPwCurr24HBinLops                              Counter64,
     cienaCesPmTdmPwCurr24HBinLbit                              Counter64,
     cienaCesPmTdmPwCurr24HBinRbit                              Counter64,
     cienaCesPmTdmPwCurr24HBinMbit                              Counter64,
     cienaCesPmTdmPwCurr24HBinRxPkt                             Counter64,
     cienaCesPmTdmPwCurr24HBinTxPkt                             Counter64,
     cienaCesPmTdmPwCurr24HBinEsp                               Counter64,
     cienaCesPmTdmPwCurr24HBinSesp                              Counter64,
     cienaCesPmTdmPwCurr24HBinUasp                              Counter64,
     cienaCesPmTdmPwCurr24HBinCvp                               Counter64,
     cienaCesPmTdmPwCurr24HBinFcp                               Counter64,
     cienaCesPmTdmPwCurr24HBinAsp                               Counter64,
     cienaCesPmTdmPwCurr24HBinTtp                               Counter64
   } 

   cienaCesPmTdmPwCurr24HBinStartTime OBJECT-TYPE
     SYNTAX      DisplayString
     MAX-ACCESS  read-only
     STATUS      current
     DESCRIPTION "Collection start time of the bin."
     ::= { cienaCesPmTdmPwCurr24HBinEntry 1 }

   cienaCesPmTdmPwCurr24HBinClearTime OBJECT-TYPE
     SYNTAX      DisplayString
     MAX-ACCESS  read-only
     STATUS      current
     DESCRIPTION "Cleared time of the bin."
     ::= { cienaCesPmTdmPwCurr24HBinEntry 2 }

   cienaCesPmTdmPwCurr24HBinDuration OBJECT-TYPE
     SYNTAX      Unsigned32 (1..65535)
     UNITS       "minutes"
     MAX-ACCESS  read-only
     STATUS      current
     DESCRIPTION "Duration of the bin."
     ::= { cienaCesPmTdmPwCurr24HBinEntry 3 }

   cienaCesPmTdmPwCurr24HBinState OBJECT-TYPE
     SYNTAX      PmBinState
     MAX-ACCESS  read-only
     STATUS      current
     DESCRIPTION "State of the bin."
     ::= { cienaCesPmTdmPwCurr24HBinEntry 4 }

   cienaCesPmTdmPwCurr24HBinMiss OBJECT-TYPE
     SYNTAX      Counter64
     MAX-ACCESS  read-only
     STATUS      current
     DESCRIPTION "Number of missing PWE packets."
     ::= { cienaCesPmTdmPwCurr24HBinEntry 5 }

   cienaCesPmTdmPwCurr24HBinReorder OBJECT-TYPE
     SYNTAX      Counter64
     MAX-ACCESS  read-only
     STATUS      current
     DESCRIPTION "Number of successfully reordered packets."
     ::= { cienaCesPmTdmPwCurr24HBinEntry 6 }

   cienaCesPmTdmPwCurr24HBinMissorder OBJECT-TYPE
     SYNTAX      Counter64
     MAX-ACCESS  read-only
     STATUS      current
     DESCRIPTION "Number of packets that cannot be reordered or dropped."
     ::= { cienaCesPmTdmPwCurr24HBinEntry 7 }

   cienaCesPmTdmPwCurr24HBinMalformed OBJECT-TYPE
     SYNTAX      Counter64
     MAX-ACCESS  read-only
     STATUS      current
     DESCRIPTION "Number of packets with invalid payload size of header."
     ::= { cienaCesPmTdmPwCurr24HBinEntry 8 }

   cienaCesPmTdmPwCurr24HBinUnderrun OBJECT-TYPE
     SYNTAX      Counter64
     MAX-ACCESS  read-only
     STATUS      current
     DESCRIPTION "Number of PDV buffer empty events."
     ::= { cienaCesPmTdmPwCurr24HBinEntry 9 }

   cienaCesPmTdmPwCurr24HBinOverrun OBJECT-TYPE
     SYNTAX      Counter64
     MAX-ACCESS  read-only
     STATUS      current
     DESCRIPTION "Number of PDV buffer full events."
     ::= { cienaCesPmTdmPwCurr24HBinEntry 10 }

   cienaCesPmTdmPwCurr24HBinEs OBJECT-TYPE
     SYNTAX      Counter64
     MAX-ACCESS  read-only
     STATUS      current
     DESCRIPTION "Errored seconds."
     ::= { cienaCesPmTdmPwCurr24HBinEntry 11 }

   cienaCesPmTdmPwCurr24HBinSes OBJECT-TYPE
     SYNTAX      Counter64
     MAX-ACCESS  read-only
     STATUS      current
     DESCRIPTION "Severely errored seconds."
     ::= { cienaCesPmTdmPwCurr24HBinEntry 12 }

   cienaCesPmTdmPwCurr24HBinUas OBJECT-TYPE
     SYNTAX      Counter64
     MAX-ACCESS  read-only
     STATUS      current
     DESCRIPTION "Unavailable seconds."
     ::= { cienaCesPmTdmPwCurr24HBinEntry 13 }

   cienaCesPmTdmPwCurr24HBinLops OBJECT-TYPE
     SYNTAX      Counter64
     MAX-ACCESS  read-only
     STATUS      current
     DESCRIPTION "Number of LOPS events."
     ::= { cienaCesPmTdmPwCurr24HBinEntry 14 }

   cienaCesPmTdmPwCurr24HBinLbit OBJECT-TYPE
     SYNTAX      Counter64
     MAX-ACCESS  read-only
     STATUS      current
     DESCRIPTION "Number of L-bit set events."
     ::= { cienaCesPmTdmPwCurr24HBinEntry 15 }

   cienaCesPmTdmPwCurr24HBinRbit OBJECT-TYPE
     SYNTAX      Counter64
     MAX-ACCESS  read-only
     STATUS      current
     DESCRIPTION "Number of R-bit set events."
     ::= { cienaCesPmTdmPwCurr24HBinEntry 16 }

   cienaCesPmTdmPwCurr24HBinMbit OBJECT-TYPE
     SYNTAX      Counter64
     MAX-ACCESS  read-only
     STATUS      current
     DESCRIPTION "Number of M-bit set events (CESoP specific counter)."
     ::= { cienaCesPmTdmPwCurr24HBinEntry 17 }

   cienaCesPmTdmPwCurr24HBinRxPkt OBJECT-TYPE
     SYNTAX      Counter64
     MAX-ACCESS  read-only
     STATUS      current
     DESCRIPTION "Number of valid received packet over a service instance (i.e. PW)."
     ::= { cienaCesPmTdmPwCurr24HBinEntry 18 }

   cienaCesPmTdmPwCurr24HBinTxPkt OBJECT-TYPE
     SYNTAX      Counter64
     MAX-ACCESS  read-only
     STATUS      current
     DESCRIPTION "Number of valid transmit packet over a service instance (i.e. PW)."
     ::= { cienaCesPmTdmPwCurr24HBinEntry 19 }

   cienaCesPmTdmPwCurr24HBinEsp OBJECT-TYPE
     SYNTAX      Counter64
     MAX-ACCESS  read-only
     STATUS      current
     DESCRIPTION "Path errored seconds."
     ::= { cienaCesPmTdmPwCurr24HBinEntry 20 }

   cienaCesPmTdmPwCurr24HBinSesp OBJECT-TYPE
     SYNTAX      Counter64
     MAX-ACCESS  read-only
     STATUS      current
     DESCRIPTION "Path severely errored seconds."
     ::= { cienaCesPmTdmPwCurr24HBinEntry 21 }

   cienaCesPmTdmPwCurr24HBinUasp OBJECT-TYPE
     SYNTAX      Counter64
     MAX-ACCESS  read-only
     STATUS      current
     DESCRIPTION "Path unavailable seconds."
     ::= { cienaCesPmTdmPwCurr24HBinEntry 22 }

   cienaCesPmTdmPwCurr24HBinCvp OBJECT-TYPE
     SYNTAX      Counter64
     MAX-ACCESS  read-only
     STATUS      current
     DESCRIPTION "Number of path code violations."
     ::= { cienaCesPmTdmPwCurr24HBinEntry 23 }

   cienaCesPmTdmPwCurr24HBinFcp OBJECT-TYPE
     SYNTAX      Counter64
     MAX-ACCESS  read-only
     STATUS      current
     DESCRIPTION "Number of path fault events."
     ::= { cienaCesPmTdmPwCurr24HBinEntry 24 }

   cienaCesPmTdmPwCurr24HBinAsp OBJECT-TYPE
     SYNTAX      Counter64
     MAX-ACCESS  read-only
     STATUS      current
     DESCRIPTION "Path available seconds."
     ::= { cienaCesPmTdmPwCurr24HBinEntry 25 }

   cienaCesPmTdmPwCurr24HBinTtp OBJECT-TYPE
     SYNTAX      Counter64
     MAX-ACCESS  read-only
     STATUS      current
     DESCRIPTION "Path total time seconds."
     ::= { cienaCesPmTdmPwCurr24HBinEntry 26 }


   --TdmPw Profile Stats, history 24 hour bin
  
   cienaCesPmTdmPwHist24HBinTable OBJECT-TYPE
     SYNTAX      SEQUENCE OF CienaCesPmTdmPwHist24HBinEntry
     MAX-ACCESS  not-accessible
     STATUS      current
     DESCRIPTION "The (conceptual) read-only Table listing the Bin Statistics."
     ::= { cienaCesPmTdmPwStats 4 }

   cienaCesPmTdmPwHist24HBinEntry OBJECT-TYPE
     SYNTAX      CienaCesPmTdmPwHist24HBinEntry
     MAX-ACCESS  not-accessible
     STATUS      current
     DESCRIPTION
           "An entry (conceptual row) in the cienaPortPmTdmPwHist24HBinTable.
           This table lists the statistics for the history 24 hours bin."
     INDEX {cienaCesPmInstanceIndex}
     ::= { cienaCesPmTdmPwHist24HBinTable 1 }

   CienaCesPmTdmPwHist24HBinEntry ::=  SEQUENCE {
     cienaCesPmTdmPwHist24HBinStartTime                         DisplayString,
     cienaCesPmTdmPwHist24HBinEndTime                           DisplayString,
     cienaCesPmTdmPwHist24HBinClearTime                         DisplayString,
     cienaCesPmTdmPwHist24HBinDuration                          Unsigned32,
     cienaCesPmTdmPwHist24HBinState                             PmBinState,
     cienaCesPmTdmPwHist24HBinMiss                              Counter64,
     cienaCesPmTdmPwHist24HBinReorder                           Counter64,
     cienaCesPmTdmPwHist24HBinMissorder                         Counter64,
     cienaCesPmTdmPwHist24HBinMalformed                         Counter64,
     cienaCesPmTdmPwHist24HBinUnderrun                          Counter64,
     cienaCesPmTdmPwHist24HBinOverrun                           Counter64,
     cienaCesPmTdmPwHist24HBinEs                                Counter64,
     cienaCesPmTdmPwHist24HBinSes                               Counter64,
     cienaCesPmTdmPwHist24HBinUas                               Counter64,
     cienaCesPmTdmPwHist24HBinLops                              Counter64,
     cienaCesPmTdmPwHist24HBinLbit                              Counter64,
     cienaCesPmTdmPwHist24HBinRbit                              Counter64,
     cienaCesPmTdmPwHist24HBinMbit                              Counter64,
     cienaCesPmTdmPwHist24HBinRxPkt                             Counter64,
     cienaCesPmTdmPwHist24HBinTxPkt                             Counter64,
     cienaCesPmTdmPwHist24HBinEsp                               Counter64,
     cienaCesPmTdmPwHist24HBinSesp                              Counter64,
     cienaCesPmTdmPwHist24HBinUasp                              Counter64,
     cienaCesPmTdmPwHist24HBinCvp                               Counter64,
     cienaCesPmTdmPwHist24HBinFcp                               Counter64,
     cienaCesPmTdmPwHist24HBinAsp                               Counter64,
     cienaCesPmTdmPwHist24HBinTtp                               Counter64
   }

   cienaCesPmTdmPwHist24HBinStartTime OBJECT-TYPE
     SYNTAX      DisplayString
     MAX-ACCESS  read-only
     STATUS      current
     DESCRIPTION "Collection start time of the bin."
     ::= { cienaCesPmTdmPwHist24HBinEntry 1 }

   cienaCesPmTdmPwHist24HBinEndTime OBJECT-TYPE
     SYNTAX      DisplayString
     MAX-ACCESS  read-only
     STATUS      current
     DESCRIPTION "Collection end time for the bin."
     ::= { cienaCesPmTdmPwHist24HBinEntry 2 }

   cienaCesPmTdmPwHist24HBinClearTime OBJECT-TYPE
     SYNTAX      DisplayString
     MAX-ACCESS  read-only
     STATUS      current
     DESCRIPTION "Cleared time of the bin."
     ::= { cienaCesPmTdmPwHist24HBinEntry 3 }

   cienaCesPmTdmPwHist24HBinDuration OBJECT-TYPE
     SYNTAX      Unsigned32 (1..65535)
     UNITS       "minutes"
     MAX-ACCESS  read-only
     STATUS      current
     DESCRIPTION "Duration of the bin."
     ::= { cienaCesPmTdmPwHist24HBinEntry 4 }

   cienaCesPmTdmPwHist24HBinState OBJECT-TYPE
     SYNTAX      PmBinState
     MAX-ACCESS  read-only
     STATUS      current
     DESCRIPTION "State of the bin."
     ::= { cienaCesPmTdmPwHist24HBinEntry 5 }

   cienaCesPmTdmPwHist24HBinMiss OBJECT-TYPE
     SYNTAX      Counter64
     MAX-ACCESS  read-only
     STATUS      current
     DESCRIPTION "Number of missing PWE packets."
     ::= { cienaCesPmTdmPwHist24HBinEntry 6 }

   cienaCesPmTdmPwHist24HBinReorder OBJECT-TYPE
     SYNTAX      Counter64
     MAX-ACCESS  read-only
     STATUS      current
     DESCRIPTION "Number of successfully reordered packets."
     ::= { cienaCesPmTdmPwHist24HBinEntry 7 }

   cienaCesPmTdmPwHist24HBinMissorder OBJECT-TYPE
     SYNTAX      Counter64
     MAX-ACCESS  read-only
     STATUS      current
     DESCRIPTION "Number of packets that cannot be reordered or dropped."
     ::= { cienaCesPmTdmPwHist24HBinEntry 8 }

   cienaCesPmTdmPwHist24HBinMalformed OBJECT-TYPE
     SYNTAX      Counter64
     MAX-ACCESS  read-only
     STATUS      current
     DESCRIPTION "Number of packets with invalid payload size of header."
     ::= { cienaCesPmTdmPwHist24HBinEntry 9 }

   cienaCesPmTdmPwHist24HBinUnderrun OBJECT-TYPE
     SYNTAX      Counter64
     MAX-ACCESS  read-only
     STATUS      current
     DESCRIPTION "Number of PDV buffer empty events."
     ::= { cienaCesPmTdmPwHist24HBinEntry 10 }

   cienaCesPmTdmPwHist24HBinOverrun OBJECT-TYPE
     SYNTAX      Counter64
     MAX-ACCESS  read-only
     STATUS      current
     DESCRIPTION "Number of PDV buffer full events."
     ::= { cienaCesPmTdmPwHist24HBinEntry 11 }

   cienaCesPmTdmPwHist24HBinEs OBJECT-TYPE
     SYNTAX      Counter64
     MAX-ACCESS  read-only
     STATUS      current
     DESCRIPTION "Errored seconds."
     ::= { cienaCesPmTdmPwHist24HBinEntry 12 }

   cienaCesPmTdmPwHist24HBinSes OBJECT-TYPE
     SYNTAX      Counter64
     MAX-ACCESS  read-only
     STATUS      current
     DESCRIPTION "Severely errored seconds."
     ::= { cienaCesPmTdmPwHist24HBinEntry 13 }

   cienaCesPmTdmPwHist24HBinUas OBJECT-TYPE
     SYNTAX      Counter64
     MAX-ACCESS  read-only
     STATUS      current
     DESCRIPTION "Unavailable seconds."
     ::= { cienaCesPmTdmPwHist24HBinEntry 14 }

   cienaCesPmTdmPwHist24HBinLops OBJECT-TYPE
     SYNTAX      Counter64
     MAX-ACCESS  read-only
     STATUS      current
     DESCRIPTION "Number of LOPS events."
     ::= { cienaCesPmTdmPwHist24HBinEntry 15 }

   cienaCesPmTdmPwHist24HBinLbit OBJECT-TYPE
     SYNTAX      Counter64
     MAX-ACCESS  read-only
     STATUS      current
     DESCRIPTION "Number of L-bit set events."
     ::= { cienaCesPmTdmPwHist24HBinEntry 16 }

   cienaCesPmTdmPwHist24HBinRbit OBJECT-TYPE
     SYNTAX      Counter64
     MAX-ACCESS  read-only
     STATUS      current
     DESCRIPTION "Number of R-bit set events."
     ::= { cienaCesPmTdmPwHist24HBinEntry 17 }

   cienaCesPmTdmPwHist24HBinMbit OBJECT-TYPE
     SYNTAX      Counter64
     MAX-ACCESS  read-only
     STATUS      current
     DESCRIPTION "Number of M-bit set events (CESoP specific counter)."
     ::= { cienaCesPmTdmPwHist24HBinEntry 18 }

   cienaCesPmTdmPwHist24HBinRxPkt OBJECT-TYPE
     SYNTAX      Counter64
     MAX-ACCESS  read-only
     STATUS      current
     DESCRIPTION "Number of valid received packet over a service instance (i.e. PW)."
     ::= { cienaCesPmTdmPwHist24HBinEntry 19 }

   cienaCesPmTdmPwHist24HBinTxPkt OBJECT-TYPE
     SYNTAX      Counter64
     MAX-ACCESS  read-only
     STATUS      current
     DESCRIPTION "Number of valid transmit packet over a service instance (i.e. PW)."
     ::= { cienaCesPmTdmPwHist24HBinEntry 20 }

   cienaCesPmTdmPwHist24HBinEsp OBJECT-TYPE
     SYNTAX      Counter64
     MAX-ACCESS  read-only
     STATUS      current
     DESCRIPTION "Path errored seconds."
     ::= { cienaCesPmTdmPwHist24HBinEntry 21 }

   cienaCesPmTdmPwHist24HBinSesp OBJECT-TYPE
     SYNTAX      Counter64
     MAX-ACCESS  read-only
     STATUS      current
     DESCRIPTION "Path severely errored seconds."
     ::= { cienaCesPmTdmPwHist24HBinEntry 22 }

   cienaCesPmTdmPwHist24HBinUasp OBJECT-TYPE
     SYNTAX      Counter64
     MAX-ACCESS  read-only
     STATUS      current
     DESCRIPTION "Path unavailable seconds."
     ::= { cienaCesPmTdmPwHist24HBinEntry 23 }

   cienaCesPmTdmPwHist24HBinCvp OBJECT-TYPE
     SYNTAX      Counter64
     MAX-ACCESS  read-only
     STATUS      current
     DESCRIPTION "Number of path code violations."
     ::= { cienaCesPmTdmPwHist24HBinEntry 24 }

   cienaCesPmTdmPwHist24HBinFcp OBJECT-TYPE
     SYNTAX      Counter64
     MAX-ACCESS  read-only
     STATUS      current
     DESCRIPTION "Number of path fault events."
     ::= { cienaCesPmTdmPwHist24HBinEntry 25 }

   cienaCesPmTdmPwHist24HBinAsp OBJECT-TYPE
     SYNTAX      Counter64
     MAX-ACCESS  read-only
     STATUS      current
     DESCRIPTION "Path available seconds."
     ::= { cienaCesPmTdmPwHist24HBinEntry 26 }
 
   cienaCesPmTdmPwHist24HBinTtp OBJECT-TYPE
     SYNTAX      Counter64
     MAX-ACCESS  read-only
     STATUS      current
     DESCRIPTION "Path total time seconds."
     ::= { cienaCesPmTdmPwHist24HBinEntry 27 }


   --TdmPw Profile Stats, statistics bin

   cienaCesPmTdmPwStatisticsBinTable OBJECT-TYPE
     SYNTAX      SEQUENCE OF CienaCesPmTdmPwStatisticsBinEntry
     MAX-ACCESS  not-accessible
     STATUS      current
     DESCRIPTION "The (conceptual) read-only table listing the bin statistics."
     ::= { cienaCesPmTdmPwStats 5 }

   cienaCesPmTdmPwStatisticsBinEntry OBJECT-TYPE
     SYNTAX      CienaCesPmTdmPwStatisticsBinEntry
     MAX-ACCESS  not-accessible
     STATUS      current
     DESCRIPTION
           "An entry (conceptual row) in the cienaPortPmTdmPwStatisticsBinTable.
           This table lists the statistics for the statistics bin of the PM instance."
     INDEX {cienaCesPmInstanceIndex}
     ::= { cienaCesPmTdmPwStatisticsBinTable 1 }

   CienaCesPmTdmPwStatisticsBinEntry ::=  SEQUENCE {
     cienaCesPmTdmPwStatisticsBinStartTime                      DisplayString,
     cienaCesPmTdmPwStatisticsBinClearTime                      DisplayString,
     cienaCesPmTdmPwStatisticsBinMiss                           Counter64,
     cienaCesPmTdmPwStatisticsBinReorder                        Counter64,
     cienaCesPmTdmPwStatisticsBinMissorder                      Counter64,
     cienaCesPmTdmPwStatisticsBinMalformed                      Counter64,
     cienaCesPmTdmPwStatisticsBinUnderrun                       Counter64,
     cienaCesPmTdmPwStatisticsBinOverrun                        Counter64,
     cienaCesPmTdmPwStatisticsBinEs                             Counter64,
     cienaCesPmTdmPwStatisticsBinSes                            Counter64,
     cienaCesPmTdmPwStatisticsBinUas                            Counter64,
     cienaCesPmTdmPwStatisticsBinLops                           Counter64,
     cienaCesPmTdmPwStatisticsBinLbit                           Counter64,
     cienaCesPmTdmPwStatisticsBinRbit                           Counter64,
     cienaCesPmTdmPwStatisticsBinMbit                           Counter64,
     cienaCesPmTdmPwStatisticsBinRxPkt                          Counter64,
     cienaCesPmTdmPwStatisticsBinTxPkt                          Counter64,
     cienaCesPmTdmPwStatisticsBinEsp                            Counter64,
     cienaCesPmTdmPwStatisticsBinSesp                           Counter64,
     cienaCesPmTdmPwStatisticsBinUasp                           Counter64,
     cienaCesPmTdmPwStatisticsBinCvp                            Counter64,
     cienaCesPmTdmPwStatisticsBinFcp                            Counter64,
     cienaCesPmTdmPwStatisticsBinAsp                            Counter64,
     cienaCesPmTdmPwStatisticsBinTtp                            Counter64
   }          

   cienaCesPmTdmPwStatisticsBinStartTime OBJECT-TYPE
     SYNTAX      DisplayString
     MAX-ACCESS  read-only
     STATUS      current
     DESCRIPTION "Collection start time of the bin."
     ::= { cienaCesPmTdmPwStatisticsBinEntry 1 }

   cienaCesPmTdmPwStatisticsBinClearTime OBJECT-TYPE
     SYNTAX      DisplayString
     MAX-ACCESS  read-only
     STATUS      current
     DESCRIPTION "Cleared time of the bin."
     ::= { cienaCesPmTdmPwStatisticsBinEntry 2 }

   cienaCesPmTdmPwStatisticsBinMiss OBJECT-TYPE
     SYNTAX      Counter64
     MAX-ACCESS  read-only
     STATUS      current
     DESCRIPTION "Number of missing PWE packets."
     ::= { cienaCesPmTdmPwStatisticsBinEntry 3 }

   cienaCesPmTdmPwStatisticsBinReorder OBJECT-TYPE
     SYNTAX      Counter64
     MAX-ACCESS  read-only
     STATUS      current
     DESCRIPTION "Number of successfully reordered packets."
     ::= { cienaCesPmTdmPwStatisticsBinEntry 4 }

   cienaCesPmTdmPwStatisticsBinMissorder OBJECT-TYPE
     SYNTAX      Counter64
     MAX-ACCESS  read-only
     STATUS      current
     DESCRIPTION "Number of packets that cannot be reordered or dropped."
     ::= { cienaCesPmTdmPwStatisticsBinEntry 5 }

   cienaCesPmTdmPwStatisticsBinMalformed OBJECT-TYPE
     SYNTAX      Counter64
     MAX-ACCESS  read-only
     STATUS      current
     DESCRIPTION "Number of packets with invalid payload size of header."
     ::= { cienaCesPmTdmPwStatisticsBinEntry 6 }

   cienaCesPmTdmPwStatisticsBinUnderrun OBJECT-TYPE
     SYNTAX      Counter64
     MAX-ACCESS  read-only
     STATUS      current
     DESCRIPTION "Number of PDV buffer empty events."
     ::= { cienaCesPmTdmPwStatisticsBinEntry 7 }

  cienaCesPmTdmPwStatisticsBinOverrun OBJECT-TYPE
     SYNTAX      Counter64
     MAX-ACCESS  read-only
     STATUS      current
     DESCRIPTION "Number of PDV buffer full events."
     ::= { cienaCesPmTdmPwStatisticsBinEntry 8 }

   cienaCesPmTdmPwStatisticsBinEs OBJECT-TYPE
     SYNTAX      Counter64
     MAX-ACCESS  read-only
     STATUS      current
     DESCRIPTION "Errored seconds."
     ::= { cienaCesPmTdmPwStatisticsBinEntry 9 }

   cienaCesPmTdmPwStatisticsBinSes OBJECT-TYPE
     SYNTAX      Counter64
     MAX-ACCESS  read-only
     STATUS      current
     DESCRIPTION "Severely errored seconds."
     ::= { cienaCesPmTdmPwStatisticsBinEntry 10 }

   cienaCesPmTdmPwStatisticsBinUas OBJECT-TYPE
     SYNTAX      Counter64
     MAX-ACCESS  read-only
     STATUS      current
     DESCRIPTION "Unavailable seconds."
     ::= { cienaCesPmTdmPwStatisticsBinEntry 11 }

   cienaCesPmTdmPwStatisticsBinLops OBJECT-TYPE
     SYNTAX      Counter64
     MAX-ACCESS  read-only
     STATUS      current
     DESCRIPTION "Number of LOPS events."
     ::= { cienaCesPmTdmPwStatisticsBinEntry 12 }

   cienaCesPmTdmPwStatisticsBinLbit OBJECT-TYPE
     SYNTAX      Counter64
     MAX-ACCESS  read-only
     STATUS      current
     DESCRIPTION "Number of L-bit set events."
     ::= { cienaCesPmTdmPwStatisticsBinEntry 13 }

   cienaCesPmTdmPwStatisticsBinRbit OBJECT-TYPE
     SYNTAX      Counter64
     MAX-ACCESS  read-only
     STATUS      current
     DESCRIPTION "Number of R-bit set events."
     ::= { cienaCesPmTdmPwStatisticsBinEntry 14 }

   cienaCesPmTdmPwStatisticsBinMbit OBJECT-TYPE
     SYNTAX      Counter64
     MAX-ACCESS  read-only
     STATUS      current
     DESCRIPTION "Number of M-bit set events (CESoP specific counter)."
     ::= { cienaCesPmTdmPwStatisticsBinEntry 15 }

   cienaCesPmTdmPwStatisticsBinRxPkt OBJECT-TYPE
     SYNTAX      Counter64
     MAX-ACCESS  read-only
     STATUS      current
     DESCRIPTION "Number of valid received packet over a service instance (i.e. PW)."
     ::= { cienaCesPmTdmPwStatisticsBinEntry 16 }

   cienaCesPmTdmPwStatisticsBinTxPkt OBJECT-TYPE
     SYNTAX      Counter64
     MAX-ACCESS  read-only
     STATUS      current
     DESCRIPTION "Number of valid transmit packet over a service instance (i.e. PW)."
     ::= { cienaCesPmTdmPwStatisticsBinEntry 17 }

   cienaCesPmTdmPwStatisticsBinEsp OBJECT-TYPE
     SYNTAX      Counter64
     MAX-ACCESS  read-only
     STATUS      current
     DESCRIPTION "Path errored seconds."
     ::= { cienaCesPmTdmPwStatisticsBinEntry 18 }

   cienaCesPmTdmPwStatisticsBinSesp OBJECT-TYPE
     SYNTAX      Counter64
     MAX-ACCESS  read-only
     STATUS      current
     DESCRIPTION "Path severely errored seconds."
     ::= { cienaCesPmTdmPwStatisticsBinEntry 19 }

   cienaCesPmTdmPwStatisticsBinUasp OBJECT-TYPE
     SYNTAX      Counter64
     MAX-ACCESS  read-only
     STATUS      current
     DESCRIPTION "Path unavailable seconds."
     ::= { cienaCesPmTdmPwStatisticsBinEntry 20 }

   cienaCesPmTdmPwStatisticsBinCvp OBJECT-TYPE
     SYNTAX      Counter64
     MAX-ACCESS  read-only
     STATUS      current
     DESCRIPTION "Number of path code violation events."
     ::= { cienaCesPmTdmPwStatisticsBinEntry 21 }

   cienaCesPmTdmPwStatisticsBinFcp OBJECT-TYPE
     SYNTAX      Counter64
     MAX-ACCESS  read-only
     STATUS      current
     DESCRIPTION "Number of path fault counts."
     ::= { cienaCesPmTdmPwStatisticsBinEntry 22 }

   cienaCesPmTdmPwStatisticsBinAsp OBJECT-TYPE
     SYNTAX      Counter64
     MAX-ACCESS  read-only
     STATUS      current
     DESCRIPTION "Path available seconds."
     ::= { cienaCesPmTdmPwStatisticsBinEntry 23 }

   cienaCesPmTdmPwStatisticsBinTtp OBJECT-TYPE
     SYNTAX      Counter64
     MAX-ACCESS  read-only
     STATUS      current
     DESCRIPTION "Path total time seconds."
     ::= { cienaCesPmTdmPwStatisticsBinEntry 24 }


   --TdmPw Profile Stats, total statistics bin

   cienaCesPmTdmPwTotalStatisticsBinTable OBJECT-TYPE
     SYNTAX      SEQUENCE OF CienaCesPmTdmPwTotalStatisticsBinEntry
     MAX-ACCESS  not-accessible
     STATUS      current
     DESCRIPTION "The (conceptual) read-only table listing the bin statistics."
     ::= { cienaCesPmTdmPwStats 6 }

   cienaCesPmTdmPwTotalStatisticsBinEntry OBJECT-TYPE
     SYNTAX      CienaCesPmTdmPwTotalStatisticsBinEntry
     MAX-ACCESS  not-accessible
     STATUS      current
     DESCRIPTION
           "An entry (conceptual row) in the cienaPortPmTdmPwTotalStatisticsBinTable.
           This table lists the statistics for the total statistics bin of the PM instance."
     INDEX {cienaCesPmInstanceIndex}
     ::= { cienaCesPmTdmPwTotalStatisticsBinTable 1 }

   CienaCesPmTdmPwTotalStatisticsBinEntry ::=  SEQUENCE {
     cienaCesPmTdmPwTotalStatisticsBinStartTime                 DisplayString,
     cienaCesPmTdmPwTotalStatisticsBinMiss                      Counter64,
     cienaCesPmTdmPwTotalStatisticsBinReorder                   Counter64,
     cienaCesPmTdmPwTotalStatisticsBinMissorder                 Counter64,
     cienaCesPmTdmPwTotalStatisticsBinMalformed                 Counter64,
     cienaCesPmTdmPwTotalStatisticsBinUnderrun                  Counter64,
     cienaCesPmTdmPwTotalStatisticsBinOverrun                   Counter64,
     cienaCesPmTdmPwTotalStatisticsBinEs                        Counter64,
     cienaCesPmTdmPwTotalStatisticsBinSes                       Counter64,
     cienaCesPmTdmPwTotalStatisticsBinUas                       Counter64,
     cienaCesPmTdmPwTotalStatisticsBinLops                      Counter64,
     cienaCesPmTdmPwTotalStatisticsBinLbit                      Counter64,
     cienaCesPmTdmPwTotalStatisticsBinRbit                      Counter64,
     cienaCesPmTdmPwTotalStatisticsBinMbit                      Counter64,
     cienaCesPmTdmPwTotalStatisticsBinRxPkt                     Counter64,
     cienaCesPmTdmPwTotalStatisticsBinTxPkt                     Counter64,
     cienaCesPmTdmPwTotalStatisticsBinEsp                       Counter64,
     cienaCesPmTdmPwTotalStatisticsBinSesp                      Counter64,
     cienaCesPmTdmPwTotalStatisticsBinUasp                      Counter64,
     cienaCesPmTdmPwTotalStatisticsBinCvp                       Counter64,
     cienaCesPmTdmPwTotalStatisticsBinFcp                       Counter64,
     cienaCesPmTdmPwTotalStatisticsBinAsp                       Counter64,
     cienaCesPmTdmPwTotalStatisticsBinTtp                       Counter64
   }          

   cienaCesPmTdmPwTotalStatisticsBinStartTime OBJECT-TYPE
     SYNTAX      DisplayString
     MAX-ACCESS  read-only
     STATUS      current
     DESCRIPTION "Collection start time of the bin."
     ::= { cienaCesPmTdmPwTotalStatisticsBinEntry 1 }

   cienaCesPmTdmPwTotalStatisticsBinMiss OBJECT-TYPE
     SYNTAX      Counter64
     MAX-ACCESS  read-only
     STATUS      current
     DESCRIPTION "Number of missing PWE packets."
     ::= { cienaCesPmTdmPwTotalStatisticsBinEntry 2 }

   cienaCesPmTdmPwTotalStatisticsBinReorder OBJECT-TYPE
     SYNTAX      Counter64
     MAX-ACCESS  read-only
     STATUS      current
     DESCRIPTION "Number of successfully reordered packets."
     ::= { cienaCesPmTdmPwTotalStatisticsBinEntry 3 }

   cienaCesPmTdmPwTotalStatisticsBinMissorder OBJECT-TYPE
     SYNTAX      Counter64
     MAX-ACCESS  read-only
     STATUS      current
     DESCRIPTION "Number of packets that cannot be reordered or dropped."
     ::= { cienaCesPmTdmPwTotalStatisticsBinEntry 4 }

   cienaCesPmTdmPwTotalStatisticsBinMalformed OBJECT-TYPE
     SYNTAX      Counter64
     MAX-ACCESS  read-only
     STATUS      current
     DESCRIPTION "Number of packets with invalid payload size of header."
     ::= { cienaCesPmTdmPwTotalStatisticsBinEntry 5 }

   cienaCesPmTdmPwTotalStatisticsBinUnderrun OBJECT-TYPE
     SYNTAX      Counter64
     MAX-ACCESS  read-only
     STATUS      current
     DESCRIPTION "Number of PDV buffer empty events."
     ::= { cienaCesPmTdmPwTotalStatisticsBinEntry 6 }

  cienaCesPmTdmPwTotalStatisticsBinOverrun OBJECT-TYPE
     SYNTAX      Counter64
     MAX-ACCESS  read-only
     STATUS      current
     DESCRIPTION "Number of PDV buffer full events."
     ::= { cienaCesPmTdmPwTotalStatisticsBinEntry 7 }

   cienaCesPmTdmPwTotalStatisticsBinEs OBJECT-TYPE
     SYNTAX      Counter64
     MAX-ACCESS  read-only
     STATUS      current
     DESCRIPTION "Errored seconds."
     ::= { cienaCesPmTdmPwTotalStatisticsBinEntry 8 }

   cienaCesPmTdmPwTotalStatisticsBinSes OBJECT-TYPE
     SYNTAX      Counter64
     MAX-ACCESS  read-only
     STATUS      current
     DESCRIPTION "Severely errored seconds."
     ::= { cienaCesPmTdmPwTotalStatisticsBinEntry 9 }

   cienaCesPmTdmPwTotalStatisticsBinUas OBJECT-TYPE
     SYNTAX      Counter64
     MAX-ACCESS  read-only
     STATUS      current
     DESCRIPTION "Unavailable seconds."
     ::= { cienaCesPmTdmPwTotalStatisticsBinEntry 10 }

   cienaCesPmTdmPwTotalStatisticsBinLops OBJECT-TYPE
     SYNTAX      Counter64
     MAX-ACCESS  read-only
     STATUS      current
     DESCRIPTION "Number of LOPS events."
     ::= { cienaCesPmTdmPwTotalStatisticsBinEntry 11 }

   cienaCesPmTdmPwTotalStatisticsBinLbit OBJECT-TYPE
     SYNTAX      Counter64
     MAX-ACCESS  read-only
     STATUS      current
     DESCRIPTION "Number of L-bit set events."
     ::= { cienaCesPmTdmPwTotalStatisticsBinEntry 12 }

   cienaCesPmTdmPwTotalStatisticsBinRbit OBJECT-TYPE
     SYNTAX      Counter64
     MAX-ACCESS  read-only
     STATUS      current
     DESCRIPTION "Number of R-bit set events."
     ::= { cienaCesPmTdmPwTotalStatisticsBinEntry 13 }

   cienaCesPmTdmPwTotalStatisticsBinMbit OBJECT-TYPE
     SYNTAX      Counter64
     MAX-ACCESS  read-only
     STATUS      current
     DESCRIPTION "Number of M-bit set events (CESoP specific counter)."
     ::= { cienaCesPmTdmPwTotalStatisticsBinEntry 14 }

   cienaCesPmTdmPwTotalStatisticsBinRxPkt OBJECT-TYPE
     SYNTAX      Counter64
     MAX-ACCESS  read-only
     STATUS      current
     DESCRIPTION "Number of valid received packet over a service instance (i.e. PW)."
     ::= { cienaCesPmTdmPwTotalStatisticsBinEntry 15 }

   cienaCesPmTdmPwTotalStatisticsBinTxPkt OBJECT-TYPE
     SYNTAX      Counter64
     MAX-ACCESS  read-only
     STATUS      current
     DESCRIPTION "Number of valid transmit packet over a service instance (i.e. PW)."
     ::= { cienaCesPmTdmPwTotalStatisticsBinEntry 16 }

   cienaCesPmTdmPwTotalStatisticsBinEsp OBJECT-TYPE
     SYNTAX      Counter64
     MAX-ACCESS  read-only
     STATUS      current
     DESCRIPTION "Path errored seconds."
     ::= { cienaCesPmTdmPwTotalStatisticsBinEntry 17 }

   cienaCesPmTdmPwTotalStatisticsBinSesp OBJECT-TYPE
     SYNTAX      Counter64
     MAX-ACCESS  read-only
     STATUS      current
     DESCRIPTION "Path severely errored seconds."
     ::= { cienaCesPmTdmPwTotalStatisticsBinEntry 18 }

   cienaCesPmTdmPwTotalStatisticsBinUasp OBJECT-TYPE
     SYNTAX      Counter64
     MAX-ACCESS  read-only
     STATUS      current
     DESCRIPTION "Path unavailable seconds."
     ::= { cienaCesPmTdmPwTotalStatisticsBinEntry 19 }

   cienaCesPmTdmPwTotalStatisticsBinCvp OBJECT-TYPE
     SYNTAX      Counter64
     MAX-ACCESS  read-only
     STATUS      current
     DESCRIPTION "Number of path code violation events."
     ::= { cienaCesPmTdmPwTotalStatisticsBinEntry 20 }

   cienaCesPmTdmPwTotalStatisticsBinFcp OBJECT-TYPE
     SYNTAX      Counter64
     MAX-ACCESS  read-only
     STATUS      current
     DESCRIPTION "Number of path fault events."
     ::= { cienaCesPmTdmPwTotalStatisticsBinEntry 21 }

   cienaCesPmTdmPwTotalStatisticsBinAsp OBJECT-TYPE
     SYNTAX      Counter64
     MAX-ACCESS  read-only
     STATUS      current
     DESCRIPTION "Path available seconds."
     ::= { cienaCesPmTdmPwTotalStatisticsBinEntry 22 }

   cienaCesPmTdmPwTotalStatisticsBinTtp OBJECT-TYPE
     SYNTAX      Counter64
     MAX-ACCESS  read-only
     STATUS      current
     DESCRIPTION "Path total time seconds."
     ::= { cienaCesPmTdmPwTotalStatisticsBinEntry 23 }


   --BasicTxRxBiDir Profile Stats, history bins

   cienaCesPmBasicTxRxBiDirHistoryBinTable OBJECT-TYPE
     SYNTAX      SEQUENCE OF CienaCesPmBasicTxRxBiDirHistoryBinEntry
     MAX-ACCESS  not-accessible
     STATUS      current
     DESCRIPTION
           "The (conceptual) read-only table listing the bin statistics."  
     ::= { cienaCesPmBasicTxRxBiDirStats 1 }

   cienaCesPmBasicTxRxBiDirHistoryBinEntry OBJECT-TYPE
     SYNTAX      CienaCesPmBasicTxRxBiDirHistoryBinEntry
     MAX-ACCESS  not-accessible
     STATUS      current
     DESCRIPTION
           "An entry (conceptual row) in the cienaCesPmBasicTxRxBiDirHistoryBinTable.

           This table lists the statistics for all the history bins of the PM instance, as 
           specified by the bin-count object of the PM instance. History bins are displayed in the order
           so that #1 bin always represents the most recently completed bin and #2 - the bin previous to that
           and so on.

           The statistics are displayed for only the instances with valid bins (with start time >0), 
           as indicated by the operational state of the corresponding PM instance."  
     INDEX { cienaCesPmInstanceIndex, cienaCesPmBasicTxRxBiDirHistoryBinIndex }
     ::= { cienaCesPmBasicTxRxBiDirHistoryBinTable 1 }

   CienaCesPmBasicTxRxBiDirHistoryBinEntry ::=  SEQUENCE {
     cienaCesPmBasicTxRxBiDirHistoryBinIndex                         Unsigned32,
     cienaCesPmBasicTxRxBiDirHistoryBinStartTime                     DisplayString,
     cienaCesPmBasicTxRxBiDirHistoryBinEndTime                       DisplayString,
     cienaCesPmBasicTxRxBiDirHistoryBinClearTime                     DisplayString,
     cienaCesPmBasicTxRxBiDirHistoryBinDuration                      Unsigned32,   
     cienaCesPmBasicTxRxBiDirHistoryBinState                         PmBinState,
     cienaCesPmBasicTxRxBiDirHistoryBinFwdRxAcceptedBytes            Counter64,
     cienaCesPmBasicTxRxBiDirHistoryBinFwdRxAcceptedFrames           Counter64,
     cienaCesPmBasicTxRxBiDirHistoryBinFwdRxYellowBytes              Counter64,
     cienaCesPmBasicTxRxBiDirHistoryBinFwdRxYellowFrames             Counter64,
     cienaCesPmBasicTxRxBiDirHistoryBinFwdRxDroppedBytes             Counter64,
     cienaCesPmBasicTxRxBiDirHistoryBinFwdRxDroppedFrames            Counter64,
     cienaCesPmBasicTxRxBiDirHistoryBinFwdTxForwardedBytes           Counter64,
     cienaCesPmBasicTxRxBiDirHistoryBinFwdTxForwardedFrames          Counter64,
     cienaCesPmBasicTxRxBiDirHistoryBinFwdRxBytesPerSec              Counter64,
     cienaCesPmBasicTxRxBiDirHistoryBinFwdRxFramesPerSec             Counter64,
     cienaCesPmBasicTxRxBiDirHistoryBinFwdTxBytesPerSec              Counter64,
     cienaCesPmBasicTxRxBiDirHistoryBinFwdTxFramesPerSec             Counter64,
     cienaCesPmBasicTxRxBiDirHistoryBinRevRxAcceptedBytes            Counter64,
     cienaCesPmBasicTxRxBiDirHistoryBinRevRxAcceptedFrames           Counter64,
     cienaCesPmBasicTxRxBiDirHistoryBinRevRxYellowBytes              Counter64,
     cienaCesPmBasicTxRxBiDirHistoryBinRevRxYellowFrames             Counter64,
     cienaCesPmBasicTxRxBiDirHistoryBinRevRxDroppedBytes             Counter64,
     cienaCesPmBasicTxRxBiDirHistoryBinRevRxDroppedFrames            Counter64,
     cienaCesPmBasicTxRxBiDirHistoryBinRevTxForwardedBytes           Counter64,
     cienaCesPmBasicTxRxBiDirHistoryBinRevTxForwardedFrames          Counter64,
     cienaCesPmBasicTxRxBiDirHistoryBinRevRxBytesPerSec              Counter64,
     cienaCesPmBasicTxRxBiDirHistoryBinRevRxFramesPerSec             Counter64,
     cienaCesPmBasicTxRxBiDirHistoryBinRevTxBytesPerSec              Counter64,
     cienaCesPmBasicTxRxBiDirHistoryBinRevTxFramesPerSec             Counter64
   }

   cienaCesPmBasicTxRxBiDirHistoryBinIndex OBJECT-TYPE
     SYNTAX      Unsigned32 (1..65535) 
     MAX-ACCESS  not-accessible
     STATUS      current
     DESCRIPTION "Bin number associated with the PmBasicTxRxBiDirHistoryBin entry."
     ::= { cienaCesPmBasicTxRxBiDirHistoryBinEntry 1 }

   cienaCesPmBasicTxRxBiDirHistoryBinStartTime OBJECT-TYPE
     SYNTAX      DisplayString
     MAX-ACCESS  read-only
     STATUS      current
     DESCRIPTION "Collection start time of the bin."
     ::= { cienaCesPmBasicTxRxBiDirHistoryBinEntry 2 }

   cienaCesPmBasicTxRxBiDirHistoryBinEndTime OBJECT-TYPE
     SYNTAX      DisplayString
     MAX-ACCESS  read-only
     STATUS      current
     DESCRIPTION "Collection end time of the bin."
     ::= { cienaCesPmBasicTxRxBiDirHistoryBinEntry 3 }

   cienaCesPmBasicTxRxBiDirHistoryBinClearTime OBJECT-TYPE
     SYNTAX      DisplayString
     MAX-ACCESS  read-only
     STATUS      current
     DESCRIPTION "Clear time of the bin."
     ::= { cienaCesPmBasicTxRxBiDirHistoryBinEntry 4 }

   cienaCesPmBasicTxRxBiDirHistoryBinDuration OBJECT-TYPE
     SYNTAX      Unsigned32 (1..65535)  
     UNITS       "minutes"
     MAX-ACCESS  read-only
     STATUS      current
     DESCRIPTION "Duration of the bin."
     ::= { cienaCesPmBasicTxRxBiDirHistoryBinEntry 5 }

   cienaCesPmBasicTxRxBiDirHistoryBinState OBJECT-TYPE
     SYNTAX      PmBinState 
     MAX-ACCESS  read-only
     STATUS      current
     DESCRIPTION "State of the bin."
     ::= { cienaCesPmBasicTxRxBiDirHistoryBinEntry 6 }

   cienaCesPmBasicTxRxBiDirHistoryBinFwdRxAcceptedBytes OBJECT-TYPE
     SYNTAX      Counter64
     MAX-ACCESS  read-only
     STATUS      current
     DESCRIPTION "The number of forward tunnel accepted bytes on this PM instance."
     ::= { cienaCesPmBasicTxRxBiDirHistoryBinEntry 7 }

   cienaCesPmBasicTxRxBiDirHistoryBinFwdRxAcceptedFrames OBJECT-TYPE
     SYNTAX      Counter64
     MAX-ACCESS  read-only
     STATUS      current
     DESCRIPTION "The number of forward tunnel accepted frames on this PM instance."
     ::= { cienaCesPmBasicTxRxBiDirHistoryBinEntry 8 }

   cienaCesPmBasicTxRxBiDirHistoryBinFwdRxYellowBytes OBJECT-TYPE
     SYNTAX      Counter64
     MAX-ACCESS  read-only
     STATUS      current
     DESCRIPTION "The number of forward tunnel remarked bytes received on this PM instance."
     ::= { cienaCesPmBasicTxRxBiDirHistoryBinEntry 9 }

   cienaCesPmBasicTxRxBiDirHistoryBinFwdRxYellowFrames OBJECT-TYPE
     SYNTAX      Counter64
     MAX-ACCESS  read-only
     STATUS      current
     DESCRIPTION "The number of forward tunnel remarked frames received on this PM instance."
     ::= { cienaCesPmBasicTxRxBiDirHistoryBinEntry 10 }

   cienaCesPmBasicTxRxBiDirHistoryBinFwdRxDroppedBytes OBJECT-TYPE
     SYNTAX      Counter64
     MAX-ACCESS  read-only
     STATUS      current
     DESCRIPTION "The number of forward tunnel received bytes dropped on this PM instance."
     ::= { cienaCesPmBasicTxRxBiDirHistoryBinEntry 11 }

   cienaCesPmBasicTxRxBiDirHistoryBinFwdRxDroppedFrames OBJECT-TYPE
     SYNTAX      Counter64
     MAX-ACCESS  read-only
     STATUS      current
     DESCRIPTION "The number of forward tunnel received frames dropped on this PM instance."
     ::= { cienaCesPmBasicTxRxBiDirHistoryBinEntry 12 }

   cienaCesPmBasicTxRxBiDirHistoryBinFwdTxForwardedBytes OBJECT-TYPE
     SYNTAX      Counter64
     MAX-ACCESS  read-only
     STATUS      current
     DESCRIPTION "The number of forward tunnel bytes forwarded on this PM instance."
     ::= { cienaCesPmBasicTxRxBiDirHistoryBinEntry 13 }

   cienaCesPmBasicTxRxBiDirHistoryBinFwdTxForwardedFrames OBJECT-TYPE
     SYNTAX      Counter64
     MAX-ACCESS  read-only
     STATUS      current
     DESCRIPTION "The number of forward tunnel frames forwarded on this PM instance."
     ::= { cienaCesPmBasicTxRxBiDirHistoryBinEntry 14 }

   cienaCesPmBasicTxRxBiDirHistoryBinFwdRxBytesPerSec OBJECT-TYPE
     SYNTAX      Counter64
     MAX-ACCESS  read-only
     STATUS      current
     DESCRIPTION "The number of forward tunnel bytes received per second on this PM instance."
     ::= { cienaCesPmBasicTxRxBiDirHistoryBinEntry 15 }

   cienaCesPmBasicTxRxBiDirHistoryBinFwdRxFramesPerSec OBJECT-TYPE
     SYNTAX      Counter64
     MAX-ACCESS  read-only
     STATUS      current
     DESCRIPTION "The number of forward tunnel frames received per second on this PM instance."
     ::= { cienaCesPmBasicTxRxBiDirHistoryBinEntry 16 }

   cienaCesPmBasicTxRxBiDirHistoryBinFwdTxBytesPerSec OBJECT-TYPE
     SYNTAX      Counter64
     MAX-ACCESS  read-only
     STATUS      current
     DESCRIPTION "The number of forward tunnel bytes transmitted per second on this PM instance."
     ::= { cienaCesPmBasicTxRxBiDirHistoryBinEntry 17 }

   cienaCesPmBasicTxRxBiDirHistoryBinFwdTxFramesPerSec OBJECT-TYPE
     SYNTAX      Counter64
     MAX-ACCESS  read-only
     STATUS      current
     DESCRIPTION "The number of forward tunnel frames transmitted per second on this PM instance."
     ::= { cienaCesPmBasicTxRxBiDirHistoryBinEntry 18 }

   cienaCesPmBasicTxRxBiDirHistoryBinRevRxAcceptedBytes OBJECT-TYPE
     SYNTAX      Counter64
     MAX-ACCESS  read-only
     STATUS      current
     DESCRIPTION "The number of reverse tunnel accepted bytes on this PM instance."
     ::= { cienaCesPmBasicTxRxBiDirHistoryBinEntry 19 }

   cienaCesPmBasicTxRxBiDirHistoryBinRevRxAcceptedFrames OBJECT-TYPE
     SYNTAX      Counter64
     MAX-ACCESS  read-only
     STATUS      current
     DESCRIPTION "The number of reverse tunnel accepted frames on this PM instance."
     ::= { cienaCesPmBasicTxRxBiDirHistoryBinEntry 20 }

   cienaCesPmBasicTxRxBiDirHistoryBinRevRxYellowBytes OBJECT-TYPE
     SYNTAX      Counter64
     MAX-ACCESS  read-only
     STATUS      current
     DESCRIPTION "The number of reverse tunnel remarked bytes received on this PM instance."
     ::= { cienaCesPmBasicTxRxBiDirHistoryBinEntry 21 }

   cienaCesPmBasicTxRxBiDirHistoryBinRevRxYellowFrames OBJECT-TYPE
     SYNTAX      Counter64
     MAX-ACCESS  read-only
     STATUS      current
     DESCRIPTION "The number of reverse tunnel remarked frames received on this PM instance."
     ::= { cienaCesPmBasicTxRxBiDirHistoryBinEntry 22 }

   cienaCesPmBasicTxRxBiDirHistoryBinRevRxDroppedBytes OBJECT-TYPE
     SYNTAX      Counter64
     MAX-ACCESS  read-only
     STATUS      current
     DESCRIPTION "The number of reverse tunnel received bytes dropped on this PM instance."
     ::= { cienaCesPmBasicTxRxBiDirHistoryBinEntry 23 }

   cienaCesPmBasicTxRxBiDirHistoryBinRevRxDroppedFrames OBJECT-TYPE
     SYNTAX      Counter64
     MAX-ACCESS  read-only
     STATUS      current
     DESCRIPTION "The number of reverse tunnel received frames dropped on this PM instance."
     ::= { cienaCesPmBasicTxRxBiDirHistoryBinEntry 24 }

   cienaCesPmBasicTxRxBiDirHistoryBinRevTxForwardedBytes OBJECT-TYPE
     SYNTAX      Counter64
     MAX-ACCESS  read-only
     STATUS      current
     DESCRIPTION "The number of reverse tunnel bytes forwarded on this PM instance."
     ::= { cienaCesPmBasicTxRxBiDirHistoryBinEntry 25 }

   cienaCesPmBasicTxRxBiDirHistoryBinRevTxForwardedFrames OBJECT-TYPE
     SYNTAX      Counter64
     MAX-ACCESS  read-only
     STATUS      current
     DESCRIPTION "The number of reverse tunnel frames forwarded on this PM instance."
     ::= { cienaCesPmBasicTxRxBiDirHistoryBinEntry 26 }

   cienaCesPmBasicTxRxBiDirHistoryBinRevRxBytesPerSec OBJECT-TYPE
     SYNTAX      Counter64
     MAX-ACCESS  read-only
     STATUS      current
     DESCRIPTION "The number of reverse tunnel bytes received per second on this PM instance."
     ::= { cienaCesPmBasicTxRxBiDirHistoryBinEntry 27 }

   cienaCesPmBasicTxRxBiDirHistoryBinRevRxFramesPerSec OBJECT-TYPE
     SYNTAX      Counter64
     MAX-ACCESS  read-only
     STATUS      current
     DESCRIPTION "The number of reverse tunnel frames received per second on this PM instance."
     ::= { cienaCesPmBasicTxRxBiDirHistoryBinEntry 28 }

   cienaCesPmBasicTxRxBiDirHistoryBinRevTxBytesPerSec OBJECT-TYPE
     SYNTAX      Counter64
     MAX-ACCESS  read-only
     STATUS      current
     DESCRIPTION "The number of reverse tunnel bytes transmitted per second on this PM instance."
     ::= { cienaCesPmBasicTxRxBiDirHistoryBinEntry 29 }

   cienaCesPmBasicTxRxBiDirHistoryBinRevTxFramesPerSec OBJECT-TYPE
     SYNTAX      Counter64
     MAX-ACCESS  read-only
     STATUS      current
     DESCRIPTION "The number of reverse tunnel frames transmitted per second on this PM instance."
     ::= { cienaCesPmBasicTxRxBiDirHistoryBinEntry 30 }
 

   --BasicTxRxBiDir Profile Stats, current bin

   cienaCesPmBasicTxRxBiDirCurrBinTable OBJECT-TYPE
     SYNTAX      SEQUENCE OF CienaCesPmBasicTxRxBiDirCurrBinEntry
     MAX-ACCESS  not-accessible
     STATUS      current
     DESCRIPTION "The (conceptual) read-only table listing the bin statistics."
     ::= { cienaCesPmBasicTxRxBiDirStats 2 }

   cienaCesPmBasicTxRxBiDirCurrBinEntry OBJECT-TYPE
     SYNTAX      CienaCesPmBasicTxRxBiDirCurrBinEntry
     MAX-ACCESS  not-accessible
     STATUS      current
     DESCRIPTION
           "An entry (conceptual row) in the cienaCesPmBasicTxRxBiDirCurrBinTable.
           This table lists the statistics for the current bin of the PM instance." 
     INDEX {cienaCesPmInstanceIndex}
     ::= { cienaCesPmBasicTxRxBiDirCurrBinTable 1 }

   CienaCesPmBasicTxRxBiDirCurrBinEntry ::=  SEQUENCE {
     cienaCesPmBasicTxRxBiDirCurrBinStartTime                        DisplayString,
     cienaCesPmBasicTxRxBiDirCurrBinClearedTime                      DisplayString,
     cienaCesPmBasicTxRxBiDirCurrBinDuration                         Unsigned32,   
     cienaCesPmBasicTxRxBiDirCurrBinState                            PmBinState,
     cienaCesPmBasicTxRxBiDirCurrBinFwdRxAcceptedBytes               Counter64,
     cienaCesPmBasicTxRxBiDirCurrBinFwdRxAcceptedFrames              Counter64,
     cienaCesPmBasicTxRxBiDirCurrBinFwdRxYellowBytes                 Counter64,
     cienaCesPmBasicTxRxBiDirCurrBinFwdRxYellowFrames                Counter64,
     cienaCesPmBasicTxRxBiDirCurrBinFwdRxDroppedBytes                Counter64,
     cienaCesPmBasicTxRxBiDirCurrBinFwdRxDroppedFrames               Counter64,
     cienaCesPmBasicTxRxBiDirCurrBinFwdTxForwardedBytes              Counter64,
     cienaCesPmBasicTxRxBiDirCurrBinFwdTxForwardedFrames             Counter64,
     cienaCesPmBasicTxRxBiDirCurrBinFwdRxBytesPerSec                 Counter64,
     cienaCesPmBasicTxRxBiDirCurrBinFwdRxFramesPerSec                Counter64,
     cienaCesPmBasicTxRxBiDirCurrBinFwdTxBytesPerSec                 Counter64,
     cienaCesPmBasicTxRxBiDirCurrBinFwdTxFramesPerSec                Counter64,
     cienaCesPmBasicTxRxBiDirCurrBinRevRxAcceptedBytes               Counter64,
     cienaCesPmBasicTxRxBiDirCurrBinRevRxAcceptedFrames              Counter64,
     cienaCesPmBasicTxRxBiDirCurrBinRevRxYellowBytes                 Counter64,
     cienaCesPmBasicTxRxBiDirCurrBinRevRxYellowFrames                Counter64,
     cienaCesPmBasicTxRxBiDirCurrBinRevRxDroppedBytes                Counter64,
     cienaCesPmBasicTxRxBiDirCurrBinRevRxDroppedFrames               Counter64,
     cienaCesPmBasicTxRxBiDirCurrBinRevTxForwardedBytes              Counter64,
     cienaCesPmBasicTxRxBiDirCurrBinRevTxForwardedFrames             Counter64,
     cienaCesPmBasicTxRxBiDirCurrBinRevRxBytesPerSec                 Counter64,
     cienaCesPmBasicTxRxBiDirCurrBinRevRxFramesPerSec                Counter64,
     cienaCesPmBasicTxRxBiDirCurrBinRevTxBytesPerSec                 Counter64,
     cienaCesPmBasicTxRxBiDirCurrBinRevTxFramesPerSec                Counter64
  }

   cienaCesPmBasicTxRxBiDirCurrBinStartTime OBJECT-TYPE
     SYNTAX      DisplayString
     MAX-ACCESS  read-only
     STATUS      current
     DESCRIPTION "Collection start time of the bin."
     ::= { cienaCesPmBasicTxRxBiDirCurrBinEntry 1 }

   cienaCesPmBasicTxRxBiDirCurrBinClearedTime OBJECT-TYPE
     SYNTAX      DisplayString
     MAX-ACCESS  read-only
     STATUS      current
     DESCRIPTION "Cleared time of the bin."
     ::= { cienaCesPmBasicTxRxBiDirCurrBinEntry 2 }

  cienaCesPmBasicTxRxBiDirCurrBinDuration OBJECT-TYPE
     SYNTAX      Unsigned32 (1..65535)
     UNITS       "minutes"
     MAX-ACCESS  read-only
     STATUS      current
     DESCRIPTION "Duration of the bin."
     ::= { cienaCesPmBasicTxRxBiDirCurrBinEntry 3 }

   cienaCesPmBasicTxRxBiDirCurrBinState OBJECT-TYPE
     SYNTAX      PmBinState
     MAX-ACCESS  read-only
     STATUS      current
     DESCRIPTION "State of the bin."
     ::= { cienaCesPmBasicTxRxBiDirCurrBinEntry 4 }

   cienaCesPmBasicTxRxBiDirCurrBinFwdRxAcceptedBytes OBJECT-TYPE
     SYNTAX      Counter64
     MAX-ACCESS  read-only
     STATUS      current
     DESCRIPTION "The number of forward tunnel accepted bytes on this PM instance."
     ::= { cienaCesPmBasicTxRxBiDirCurrBinEntry 5 }

   cienaCesPmBasicTxRxBiDirCurrBinFwdRxAcceptedFrames OBJECT-TYPE
     SYNTAX      Counter64
     MAX-ACCESS  read-only
     STATUS      current
     DESCRIPTION "The number of forward tunnel accepted frames on this PM instance."
     ::= { cienaCesPmBasicTxRxBiDirCurrBinEntry 6 }

   cienaCesPmBasicTxRxBiDirCurrBinFwdRxYellowBytes OBJECT-TYPE
     SYNTAX      Counter64
     MAX-ACCESS  read-only
     STATUS      current
     DESCRIPTION "The number of forward tunnel remarked bytes received on this PM instance."
     ::= { cienaCesPmBasicTxRxBiDirCurrBinEntry 7 }

   cienaCesPmBasicTxRxBiDirCurrBinFwdRxYellowFrames OBJECT-TYPE
     SYNTAX      Counter64
     MAX-ACCESS  read-only
     STATUS      current
     DESCRIPTION "The number of forward tunnel remarked frames received on this PM instance."
     ::= { cienaCesPmBasicTxRxBiDirCurrBinEntry 8 }

   cienaCesPmBasicTxRxBiDirCurrBinFwdRxDroppedBytes OBJECT-TYPE
     SYNTAX      Counter64
     MAX-ACCESS  read-only
     STATUS      current
     DESCRIPTION "The number of forward tunnel received bytes dropped on this PM instance."
     ::= { cienaCesPmBasicTxRxBiDirCurrBinEntry 9 }

   cienaCesPmBasicTxRxBiDirCurrBinFwdRxDroppedFrames OBJECT-TYPE
     SYNTAX      Counter64
     MAX-ACCESS  read-only
     STATUS      current
     DESCRIPTION "The number of forward tunnel received frames dropped on this PM instance."
     ::= { cienaCesPmBasicTxRxBiDirCurrBinEntry 10 }

   cienaCesPmBasicTxRxBiDirCurrBinFwdTxForwardedBytes OBJECT-TYPE
     SYNTAX      Counter64
     MAX-ACCESS  read-only
     STATUS      current
     DESCRIPTION "The number of forward tunnel bytes forwarded on this PM instance."
     ::= { cienaCesPmBasicTxRxBiDirCurrBinEntry 11 }

   cienaCesPmBasicTxRxBiDirCurrBinFwdTxForwardedFrames OBJECT-TYPE
     SYNTAX      Counter64
     MAX-ACCESS  read-only
     STATUS      current
     DESCRIPTION "The number of forward tunnel frames forwarded on this PM instance."
     ::= { cienaCesPmBasicTxRxBiDirCurrBinEntry 12 }

   cienaCesPmBasicTxRxBiDirCurrBinFwdRxBytesPerSec OBJECT-TYPE
     SYNTAX      Counter64
     MAX-ACCESS  read-only
     STATUS      current
     DESCRIPTION "The number of forward tunnel bytes received per second on this PM instance."
     ::= { cienaCesPmBasicTxRxBiDirCurrBinEntry 13 }

   cienaCesPmBasicTxRxBiDirCurrBinFwdRxFramesPerSec OBJECT-TYPE
     SYNTAX      Counter64
     MAX-ACCESS  read-only
     STATUS      current
     DESCRIPTION "The number of forward tunnel frames received per second on this PM instance."
     ::= { cienaCesPmBasicTxRxBiDirCurrBinEntry 14 }

   cienaCesPmBasicTxRxBiDirCurrBinFwdTxBytesPerSec OBJECT-TYPE
     SYNTAX      Counter64
     MAX-ACCESS  read-only
     STATUS      current
     DESCRIPTION "The number of forward tunnel bytes transmitted per second on this PM instance."
     ::= { cienaCesPmBasicTxRxBiDirCurrBinEntry 15 }

   cienaCesPmBasicTxRxBiDirCurrBinFwdTxFramesPerSec OBJECT-TYPE
     SYNTAX      Counter64
     MAX-ACCESS  read-only
     STATUS      current
     DESCRIPTION "The number of forward tunnel frames transmitted per second on this PM instance."
     ::= { cienaCesPmBasicTxRxBiDirCurrBinEntry 16 }

   cienaCesPmBasicTxRxBiDirCurrBinRevRxAcceptedBytes OBJECT-TYPE
     SYNTAX      Counter64
     MAX-ACCESS  read-only
     STATUS      current
     DESCRIPTION "The number of reverse tunnel accepted bytes on this PM instance."
     ::= { cienaCesPmBasicTxRxBiDirCurrBinEntry 17 }

   cienaCesPmBasicTxRxBiDirCurrBinRevRxAcceptedFrames OBJECT-TYPE
     SYNTAX      Counter64
     MAX-ACCESS  read-only
     STATUS      current
     DESCRIPTION "The number of reverse tunnel accepted frames on this PM instance."
     ::= { cienaCesPmBasicTxRxBiDirCurrBinEntry 18 }

   cienaCesPmBasicTxRxBiDirCurrBinRevRxYellowBytes OBJECT-TYPE
     SYNTAX      Counter64
     MAX-ACCESS  read-only
     STATUS      current
     DESCRIPTION "The number of reverse tunnel remarked bytes received on this PM instance."
     ::= { cienaCesPmBasicTxRxBiDirCurrBinEntry 19 }

   cienaCesPmBasicTxRxBiDirCurrBinRevRxYellowFrames OBJECT-TYPE
     SYNTAX      Counter64
     MAX-ACCESS  read-only
     STATUS      current
     DESCRIPTION "The number of reverse tunnel remarked frames received on this PM instance."
     ::= { cienaCesPmBasicTxRxBiDirCurrBinEntry 20 }

   cienaCesPmBasicTxRxBiDirCurrBinRevRxDroppedBytes OBJECT-TYPE
     SYNTAX      Counter64
     MAX-ACCESS  read-only
     STATUS      current
     DESCRIPTION "The number of reverse tunnel received bytes dropped on this PM instance."
     ::= { cienaCesPmBasicTxRxBiDirCurrBinEntry 21 }

   cienaCesPmBasicTxRxBiDirCurrBinRevRxDroppedFrames OBJECT-TYPE
     SYNTAX      Counter64
     MAX-ACCESS  read-only
     STATUS      current
     DESCRIPTION "The number of reverse tunnel received frames dropped on this PM instance."
     ::= { cienaCesPmBasicTxRxBiDirCurrBinEntry 22 }

   cienaCesPmBasicTxRxBiDirCurrBinRevTxForwardedBytes OBJECT-TYPE
     SYNTAX      Counter64
     MAX-ACCESS  read-only
     STATUS      current
     DESCRIPTION "The number of reverse tunnel bytes forwarded on this PM instance."
     ::= { cienaCesPmBasicTxRxBiDirCurrBinEntry 23 }

   cienaCesPmBasicTxRxBiDirCurrBinRevTxForwardedFrames OBJECT-TYPE
     SYNTAX      Counter64
     MAX-ACCESS  read-only
     STATUS      current
     DESCRIPTION "The number of reverse tunnel frames forwarded on this PM instance."
     ::= { cienaCesPmBasicTxRxBiDirCurrBinEntry 24 }

   cienaCesPmBasicTxRxBiDirCurrBinRevRxBytesPerSec OBJECT-TYPE
     SYNTAX      Counter64
     MAX-ACCESS  read-only
     STATUS      current
     DESCRIPTION "The number of reverse tunnel bytes received per second on this PM instance."
     ::= { cienaCesPmBasicTxRxBiDirCurrBinEntry 25 }

   cienaCesPmBasicTxRxBiDirCurrBinRevRxFramesPerSec OBJECT-TYPE
     SYNTAX      Counter64
     MAX-ACCESS  read-only
     STATUS      current
     DESCRIPTION "The number of reverse tunnel frames received per second on this PM instance."
     ::= { cienaCesPmBasicTxRxBiDirCurrBinEntry 26 }

   cienaCesPmBasicTxRxBiDirCurrBinRevTxBytesPerSec OBJECT-TYPE
     SYNTAX      Counter64
     MAX-ACCESS  read-only
     STATUS      current
     DESCRIPTION "The number of reverse tunnel bytes transmitted per second on this PM instance."
     ::= { cienaCesPmBasicTxRxBiDirCurrBinEntry 27 }

   cienaCesPmBasicTxRxBiDirCurrBinRevTxFramesPerSec OBJECT-TYPE
     SYNTAX      Counter64
     MAX-ACCESS  read-only
     STATUS      current
     DESCRIPTION "The number of reverse tunnel frames transmitted per second on this PM instance."
     ::= { cienaCesPmBasicTxRxBiDirCurrBinEntry 28 }


   --BasicTxRxBiDir Profile Stats, current 24 hour bin

   cienaCesPmBasicTxRxBiDirCurr24HBinTable OBJECT-TYPE
     SYNTAX      SEQUENCE OF CienaCesPmBasicTxRxBiDirCurr24HBinEntry
     MAX-ACCESS  not-accessible
     STATUS      current
     DESCRIPTION "The (conceptual) read-only table listing the bin statistics."
     ::= { cienaCesPmBasicTxRxBiDirStats 3 }

   cienaCesPmBasicTxRxBiDirCurr24HBinEntry OBJECT-TYPE
     SYNTAX      CienaCesPmBasicTxRxBiDirCurr24HBinEntry
     MAX-ACCESS  not-accessible
     STATUS      current
     DESCRIPTION
           "An entry (conceptual row) in the cienaCesPmBasicTxRxBiDirCurr24HBinTable.

           This table lists the statistics for the current 24 Hours bin."
     INDEX {cienaCesPmInstanceIndex}
     ::= { cienaCesPmBasicTxRxBiDirCurr24HBinTable 1 }

   CienaCesPmBasicTxRxBiDirCurr24HBinEntry ::=  SEQUENCE {
     cienaCesPmBasicTxRxBiDirCurr24HBinStartTime                     DisplayString,
     cienaCesPmBasicTxRxBiDirCurr24HBinClearedTime                   DisplayString,
     cienaCesPmBasicTxRxBiDirCurr24HBinDuration                      Unsigned32,
     cienaCesPmBasicTxRxBiDirCurr24HBinState                         PmBinState,
     cienaCesPmBasicTxRxBiDirCurr24HBinFwdRxAcceptedBytes            Counter64,
     cienaCesPmBasicTxRxBiDirCurr24HBinFwdRxAcceptedFrames           Counter64,
     cienaCesPmBasicTxRxBiDirCurr24HBinFwdRxYellowBytes              Counter64,
     cienaCesPmBasicTxRxBiDirCurr24HBinFwdRxYellowFrames             Counter64,
     cienaCesPmBasicTxRxBiDirCurr24HBinFwdRxDroppedBytes             Counter64,
     cienaCesPmBasicTxRxBiDirCurr24HBinFwdRxDroppedFrames            Counter64,
     cienaCesPmBasicTxRxBiDirCurr24HBinFwdTxForwardedBytes           Counter64,
     cienaCesPmBasicTxRxBiDirCurr24HBinFwdTxForwardedFrames          Counter64,
     cienaCesPmBasicTxRxBiDirCurr24HBinFwdRxBytesPerSec              Counter64,
     cienaCesPmBasicTxRxBiDirCurr24HBinFwdRxFramesPerSec             Counter64,
     cienaCesPmBasicTxRxBiDirCurr24HBinFwdTxBytesPerSec              Counter64,
     cienaCesPmBasicTxRxBiDirCurr24HBinFwdTxFramesPerSec             Counter64,
     cienaCesPmBasicTxRxBiDirCurr24HBinRevRxAcceptedBytes            Counter64,
     cienaCesPmBasicTxRxBiDirCurr24HBinRevRxAcceptedFrames           Counter64,
     cienaCesPmBasicTxRxBiDirCurr24HBinRevRxYellowBytes              Counter64,
     cienaCesPmBasicTxRxBiDirCurr24HBinRevRxYellowFrames             Counter64,
     cienaCesPmBasicTxRxBiDirCurr24HBinRevRxDroppedBytes             Counter64,
     cienaCesPmBasicTxRxBiDirCurr24HBinRevRxDroppedFrames            Counter64,
     cienaCesPmBasicTxRxBiDirCurr24HBinRevTxForwardedBytes           Counter64,
     cienaCesPmBasicTxRxBiDirCurr24HBinRevTxForwardedFrames          Counter64,
     cienaCesPmBasicTxRxBiDirCurr24HBinRevRxBytesPerSec              Counter64,
     cienaCesPmBasicTxRxBiDirCurr24HBinRevRxFramesPerSec             Counter64,
     cienaCesPmBasicTxRxBiDirCurr24HBinRevTxBytesPerSec              Counter64,
     cienaCesPmBasicTxRxBiDirCurr24HBinRevTxFramesPerSec             Counter64
   }

   cienaCesPmBasicTxRxBiDirCurr24HBinStartTime OBJECT-TYPE
     SYNTAX      DisplayString
     MAX-ACCESS  read-only
     STATUS      current
     DESCRIPTION "Collection start time of the bin."
     ::= { cienaCesPmBasicTxRxBiDirCurr24HBinEntry 1 }

    cienaCesPmBasicTxRxBiDirCurr24HBinClearedTime OBJECT-TYPE
     SYNTAX      DisplayString
     MAX-ACCESS  read-only
     STATUS      current
     DESCRIPTION "Cleared time of the bin."
     ::= { cienaCesPmBasicTxRxBiDirCurr24HBinEntry 2 }

   cienaCesPmBasicTxRxBiDirCurr24HBinDuration OBJECT-TYPE
     SYNTAX      Unsigned32 (1..65535)
     UNITS       "minutes"
     MAX-ACCESS  read-only
     STATUS      current
     DESCRIPTION "Interval of the bin."
     ::= { cienaCesPmBasicTxRxBiDirCurr24HBinEntry 3 }

   cienaCesPmBasicTxRxBiDirCurr24HBinState OBJECT-TYPE
     SYNTAX      PmBinState
     MAX-ACCESS  read-only
     STATUS      current
     DESCRIPTION "State of the bin."
     ::= { cienaCesPmBasicTxRxBiDirCurr24HBinEntry 4 }

   cienaCesPmBasicTxRxBiDirCurr24HBinFwdRxAcceptedBytes OBJECT-TYPE
     SYNTAX      Counter64
     MAX-ACCESS  read-only
     STATUS      current
     DESCRIPTION "The number of forward tunnel accepted bytes on this PM instance."
     ::= { cienaCesPmBasicTxRxBiDirCurr24HBinEntry 5 }

   cienaCesPmBasicTxRxBiDirCurr24HBinFwdRxAcceptedFrames OBJECT-TYPE
     SYNTAX      Counter64
     MAX-ACCESS  read-only
     STATUS      current
     DESCRIPTION "The number of forward tunnel accepted frames on this PM instance."
     ::= { cienaCesPmBasicTxRxBiDirCurr24HBinEntry 6 }

   cienaCesPmBasicTxRxBiDirCurr24HBinFwdRxYellowBytes OBJECT-TYPE
     SYNTAX      Counter64
     MAX-ACCESS  read-only
     STATUS      current
     DESCRIPTION "The number of forward tunnel remarked bytes received on this PM instance."
     ::= { cienaCesPmBasicTxRxBiDirCurr24HBinEntry 7 }

   cienaCesPmBasicTxRxBiDirCurr24HBinFwdRxYellowFrames OBJECT-TYPE
     SYNTAX      Counter64
     MAX-ACCESS  read-only
     STATUS      current
     DESCRIPTION "The number of forward tunnel remarked frames received on this PM instance."
     ::= { cienaCesPmBasicTxRxBiDirCurr24HBinEntry 8 }

   cienaCesPmBasicTxRxBiDirCurr24HBinFwdRxDroppedBytes OBJECT-TYPE
     SYNTAX      Counter64
     MAX-ACCESS  read-only
     STATUS      current
     DESCRIPTION "The number of forward tunnel received bytes dropped on this PM instance."
     ::= { cienaCesPmBasicTxRxBiDirCurr24HBinEntry 9 }

   cienaCesPmBasicTxRxBiDirCurr24HBinFwdRxDroppedFrames OBJECT-TYPE
     SYNTAX      Counter64
     MAX-ACCESS  read-only
     STATUS      current
     DESCRIPTION "The number of forward tunnel received frames dropped on this PM instance."
     ::= { cienaCesPmBasicTxRxBiDirCurr24HBinEntry 10 }

   cienaCesPmBasicTxRxBiDirCurr24HBinFwdTxForwardedBytes OBJECT-TYPE
     SYNTAX      Counter64
     MAX-ACCESS  read-only
     STATUS      current
     DESCRIPTION "The number of forward tunnel bytes forwarded on this PM instance."
     ::= { cienaCesPmBasicTxRxBiDirCurr24HBinEntry 11 }

   cienaCesPmBasicTxRxBiDirCurr24HBinFwdTxForwardedFrames OBJECT-TYPE
     SYNTAX      Counter64
     MAX-ACCESS  read-only
     STATUS      current
     DESCRIPTION "The number of forward tunnel frames forwarded on this PM instance."
     ::= { cienaCesPmBasicTxRxBiDirCurr24HBinEntry 12 }

   cienaCesPmBasicTxRxBiDirCurr24HBinFwdRxBytesPerSec OBJECT-TYPE
     SYNTAX      Counter64
     MAX-ACCESS  read-only
     STATUS      current
     DESCRIPTION "The number of forward tunnel bytes received per second on this PM instance."
     ::= { cienaCesPmBasicTxRxBiDirCurr24HBinEntry 13 }

   cienaCesPmBasicTxRxBiDirCurr24HBinFwdRxFramesPerSec OBJECT-TYPE
     SYNTAX      Counter64
     MAX-ACCESS  read-only
     STATUS      current
     DESCRIPTION "The number of forward tunnel frames received per second on this PM instance."
     ::= { cienaCesPmBasicTxRxBiDirCurr24HBinEntry 14 }

   cienaCesPmBasicTxRxBiDirCurr24HBinFwdTxBytesPerSec OBJECT-TYPE
     SYNTAX      Counter64
     MAX-ACCESS  read-only
     STATUS      current
     DESCRIPTION "The number of forward tunnel bytes transmitted per second on this PM instance."
     ::= { cienaCesPmBasicTxRxBiDirCurr24HBinEntry 15 }

   cienaCesPmBasicTxRxBiDirCurr24HBinFwdTxFramesPerSec OBJECT-TYPE
     SYNTAX      Counter64
     MAX-ACCESS  read-only
     STATUS      current
     DESCRIPTION "The number of forward tunnel frames transmitted per second on this PM instance."
     ::= { cienaCesPmBasicTxRxBiDirCurr24HBinEntry 16 }
  
   cienaCesPmBasicTxRxBiDirCurr24HBinRevRxAcceptedBytes OBJECT-TYPE
     SYNTAX      Counter64
     MAX-ACCESS  read-only
     STATUS      current
     DESCRIPTION "The number of reverse tunnel accepted bytes on this PM instance."
     ::= { cienaCesPmBasicTxRxBiDirCurr24HBinEntry 17 }

   cienaCesPmBasicTxRxBiDirCurr24HBinRevRxAcceptedFrames OBJECT-TYPE
     SYNTAX      Counter64
     MAX-ACCESS  read-only
     STATUS      current
     DESCRIPTION "The number of reverse tunnel accepted frames on this PM instance."
     ::= { cienaCesPmBasicTxRxBiDirCurr24HBinEntry 18 }

   cienaCesPmBasicTxRxBiDirCurr24HBinRevRxYellowBytes OBJECT-TYPE
     SYNTAX      Counter64
     MAX-ACCESS  read-only
     STATUS      current
     DESCRIPTION "The number of reverse tunnel remarked bytes received on this PM instance."
     ::= { cienaCesPmBasicTxRxBiDirCurr24HBinEntry 19 }

   cienaCesPmBasicTxRxBiDirCurr24HBinRevRxYellowFrames OBJECT-TYPE
     SYNTAX      Counter64
     MAX-ACCESS  read-only
     STATUS      current
     DESCRIPTION "The number of reverse tunnel remarked frames received on this PM instance."
     ::= { cienaCesPmBasicTxRxBiDirCurr24HBinEntry 20 }

   cienaCesPmBasicTxRxBiDirCurr24HBinRevRxDroppedBytes OBJECT-TYPE
     SYNTAX      Counter64
     MAX-ACCESS  read-only
     STATUS      current
     DESCRIPTION "The number of reverse tunnel received bytes dropped on this PM instance."
     ::= { cienaCesPmBasicTxRxBiDirCurr24HBinEntry 21 }

   cienaCesPmBasicTxRxBiDirCurr24HBinRevRxDroppedFrames OBJECT-TYPE
     SYNTAX      Counter64
     MAX-ACCESS  read-only
     STATUS      current
     DESCRIPTION "The number of reverse tunnel received frames dropped on this PM instance."
     ::= { cienaCesPmBasicTxRxBiDirCurr24HBinEntry 22 }

   cienaCesPmBasicTxRxBiDirCurr24HBinRevTxForwardedBytes OBJECT-TYPE
     SYNTAX      Counter64
     MAX-ACCESS  read-only
     STATUS      current
     DESCRIPTION "The number of reverse tunnel bytes forwarded on this PM instance."
     ::= { cienaCesPmBasicTxRxBiDirCurr24HBinEntry 23 }

   cienaCesPmBasicTxRxBiDirCurr24HBinRevTxForwardedFrames OBJECT-TYPE
     SYNTAX      Counter64
     MAX-ACCESS  read-only
     STATUS      current
     DESCRIPTION "The number of reverse tunnel frames forwarded on this PM instance."
     ::= { cienaCesPmBasicTxRxBiDirCurr24HBinEntry 24 }

   cienaCesPmBasicTxRxBiDirCurr24HBinRevRxBytesPerSec OBJECT-TYPE
     SYNTAX      Counter64
     MAX-ACCESS  read-only
     STATUS      current
     DESCRIPTION "The number of reverse tunnel bytes received per second on this PM instance."
     ::= { cienaCesPmBasicTxRxBiDirCurr24HBinEntry 25 }

   cienaCesPmBasicTxRxBiDirCurr24HBinRevRxFramesPerSec OBJECT-TYPE
     SYNTAX      Counter64
     MAX-ACCESS  read-only
     STATUS      current
     DESCRIPTION "The number of reverse tunnel frames received per second on this PM instance."
     ::= { cienaCesPmBasicTxRxBiDirCurr24HBinEntry 26 }

   cienaCesPmBasicTxRxBiDirCurr24HBinRevTxBytesPerSec OBJECT-TYPE
     SYNTAX      Counter64
     MAX-ACCESS  read-only
     STATUS      current
     DESCRIPTION "The number of reverse tunnel bytes transmitted per second on this PM instance."
     ::= { cienaCesPmBasicTxRxBiDirCurr24HBinEntry 27 }

   cienaCesPmBasicTxRxBiDirCurr24HBinRevTxFramesPerSec OBJECT-TYPE
     SYNTAX      Counter64
     MAX-ACCESS  read-only
     STATUS      current
     DESCRIPTION "The number of reverse tunnel frames transmitted per second on this PM instance."
     ::= { cienaCesPmBasicTxRxBiDirCurr24HBinEntry 28 }


   --BasicTxRxBiDir Profile Stats, history 24 hour bin

   cienaCesPmBasicTxRxBiDirHist24HBinTable OBJECT-TYPE
     SYNTAX      SEQUENCE OF CienaCesPmBasicTxRxBiDirHist24HBinEntry
     MAX-ACCESS  not-accessible
     STATUS      current
     DESCRIPTION "The (conceptual) read-only table listing the bin statistics."
     ::= { cienaCesPmBasicTxRxBiDirStats 4 }

   cienaCesPmBasicTxRxBiDirHist24HBinEntry OBJECT-TYPE
     SYNTAX      CienaCesPmBasicTxRxBiDirHist24HBinEntry
     MAX-ACCESS  not-accessible
     STATUS      current
     DESCRIPTION
           "An entry (conceptual row) in the cienaCesPmBasicTxRxBiDirHist24HBinTable.

           This table lists the statistics for the history 24 hours bin."
     INDEX {cienaCesPmInstanceIndex}
     ::= { cienaCesPmBasicTxRxBiDirHist24HBinTable 1 }
        
   CienaCesPmBasicTxRxBiDirHist24HBinEntry ::=  SEQUENCE {
     cienaCesPmBasicTxRxBiDirHist24HBinStartTime                     DisplayString,
     cienaCesPmBasicTxRxBiDirHist24HBinEndTime                       DisplayString,
     cienaCesPmBasicTxRxBiDirHist24HBinClearTime                     DisplayString,
     cienaCesPmBasicTxRxBiDirHist24HBinDuration                      Unsigned32,
     cienaCesPmBasicTxRxBiDirHist24HBinState                         PmBinState,
     cienaCesPmBasicTxRxBiDirHist24HBinBasicFwdRxAcceptedBytes       Counter64,
     cienaCesPmBasicTxRxBiDirHist24HBinBasicFwdRxAcceptedFrames      Counter64,
     cienaCesPmBasicTxRxBiDirHist24HBinBasicFwdRxYellowBytes         Counter64,
     cienaCesPmBasicTxRxBiDirHist24HBinBasicFwdRxYellowFrames        Counter64,
     cienaCesPmBasicTxRxBiDirHist24HBinBasicFwdRxDroppedBytes        Counter64,
     cienaCesPmBasicTxRxBiDirHist24HBinBasicFwdRxDroppedFrames       Counter64,
     cienaCesPmBasicTxRxBiDirHist24HBinBasicFwdTxForwardedBytes      Counter64,
     cienaCesPmBasicTxRxBiDirHist24HBinBasicFwdTxForwardedFrames     Counter64,
     cienaCesPmBasicTxRxBiDirHist24HBinBasicFwdRxBytesPerSec         Counter64,
     cienaCesPmBasicTxRxBiDirHist24HBinBasicFwdRxFramesPerSec        Counter64,
     cienaCesPmBasicTxRxBiDirHist24HBinBasicFwdTxBytesPerSec         Counter64,
     cienaCesPmBasicTxRxBiDirHist24HBinBasicFwdTxFramesPerSec        Counter64,
     cienaCesPmBasicTxRxBiDirHist24HBinBasicRevRxAcceptedBytes       Counter64,
     cienaCesPmBasicTxRxBiDirHist24HBinBasicRevRxAcceptedFrames      Counter64,
     cienaCesPmBasicTxRxBiDirHist24HBinBasicRevRxYellowBytes         Counter64,
     cienaCesPmBasicTxRxBiDirHist24HBinBasicRevRxYellowFrames        Counter64,
     cienaCesPmBasicTxRxBiDirHist24HBinBasicRevRxDroppedBytes        Counter64,
     cienaCesPmBasicTxRxBiDirHist24HBinBasicRevRxDroppedFrames       Counter64,
     cienaCesPmBasicTxRxBiDirHist24HBinBasicRevTxForwardedBytes      Counter64,
     cienaCesPmBasicTxRxBiDirHist24HBinBasicRevTxForwardedFrames     Counter64,
     cienaCesPmBasicTxRxBiDirHist24HBinBasicRevRxBytesPerSec         Counter64,
     cienaCesPmBasicTxRxBiDirHist24HBinBasicRevRxFramesPerSec        Counter64,
     cienaCesPmBasicTxRxBiDirHist24HBinBasicRevTxBytesPerSec         Counter64,
     cienaCesPmBasicTxRxBiDirHist24HBinBasicRevTxFramesPerSec        Counter64
   }

   cienaCesPmBasicTxRxBiDirHist24HBinStartTime OBJECT-TYPE
     SYNTAX      DisplayString
     MAX-ACCESS  read-only
     STATUS      current
     DESCRIPTION "Collection start time of the bin."
     ::= { cienaCesPmBasicTxRxBiDirHist24HBinEntry 1 }

   cienaCesPmBasicTxRxBiDirHist24HBinEndTime OBJECT-TYPE
     SYNTAX      DisplayString
     MAX-ACCESS  read-only
     STATUS      current
     DESCRIPTION "Collection end time of the bin."
     ::= { cienaCesPmBasicTxRxBiDirHist24HBinEntry 2 }

   cienaCesPmBasicTxRxBiDirHist24HBinClearTime OBJECT-TYPE
     SYNTAX      DisplayString
     MAX-ACCESS  read-only
     STATUS      current
     DESCRIPTION "Collection clear time of the bin."
      ::= { cienaCesPmBasicTxRxBiDirHist24HBinEntry 3 }
   
   cienaCesPmBasicTxRxBiDirHist24HBinDuration OBJECT-TYPE
     SYNTAX      Unsigned32 (1..65535)
     UNITS       "minutes"
     MAX-ACCESS  read-only
     STATUS      current
     DESCRIPTION "Interval of the bin."
     ::= { cienaCesPmBasicTxRxBiDirHist24HBinEntry 4 }

  cienaCesPmBasicTxRxBiDirHist24HBinState OBJECT-TYPE
     SYNTAX      PmBinState
     MAX-ACCESS  read-only
     STATUS      current
     DESCRIPTION "State of the bin."
     ::= { cienaCesPmBasicTxRxBiDirHist24HBinEntry 5 }

   cienaCesPmBasicTxRxBiDirHist24HBinBasicFwdRxAcceptedBytes OBJECT-TYPE
     SYNTAX      Counter64
     MAX-ACCESS  read-only
     STATUS      current
     DESCRIPTION "The number of forward tunnel accepted bytes on this PM instance."
     ::= { cienaCesPmBasicTxRxBiDirHist24HBinEntry 6 }

   cienaCesPmBasicTxRxBiDirHist24HBinBasicFwdRxAcceptedFrames OBJECT-TYPE
     SYNTAX      Counter64
     MAX-ACCESS  read-only
     STATUS      current
     DESCRIPTION "The number of forward tunnel accepted frames on this PM instance."
     ::= { cienaCesPmBasicTxRxBiDirHist24HBinEntry 7 }

   cienaCesPmBasicTxRxBiDirHist24HBinBasicFwdRxYellowBytes OBJECT-TYPE
     SYNTAX      Counter64
     MAX-ACCESS  read-only
     STATUS      current
     DESCRIPTION "The number of forward tunnel remarked bytes received on this PM instance."
     ::= { cienaCesPmBasicTxRxBiDirHist24HBinEntry 8 }

   cienaCesPmBasicTxRxBiDirHist24HBinBasicFwdRxYellowFrames OBJECT-TYPE
     SYNTAX      Counter64
     MAX-ACCESS  read-only
     STATUS      current
     DESCRIPTION "The number of forward tunnel remarked frames received on this PM instance."
     ::= { cienaCesPmBasicTxRxBiDirHist24HBinEntry 9 }

   cienaCesPmBasicTxRxBiDirHist24HBinBasicFwdRxDroppedBytes OBJECT-TYPE
     SYNTAX      Counter64
     MAX-ACCESS  read-only
     STATUS      current
     DESCRIPTION "The number of forward tunnel received bytes dropped on this PM instance."
     ::= { cienaCesPmBasicTxRxBiDirHist24HBinEntry 10 }

   cienaCesPmBasicTxRxBiDirHist24HBinBasicFwdRxDroppedFrames OBJECT-TYPE
     SYNTAX      Counter64
     MAX-ACCESS  read-only
     STATUS      current
     DESCRIPTION "The number of forward tunnel received frames dropped on this PM instance."
     ::= { cienaCesPmBasicTxRxBiDirHist24HBinEntry 11 }

   cienaCesPmBasicTxRxBiDirHist24HBinBasicFwdTxForwardedBytes OBJECT-TYPE
     SYNTAX      Counter64
     MAX-ACCESS  read-only
     STATUS      current
     DESCRIPTION "The number of forward tunnel bytes forwarded on this PM instance."
     ::= { cienaCesPmBasicTxRxBiDirHist24HBinEntry 12 }

   cienaCesPmBasicTxRxBiDirHist24HBinBasicFwdTxForwardedFrames OBJECT-TYPE
     SYNTAX      Counter64
     MAX-ACCESS  read-only
     STATUS      current
     DESCRIPTION "The number of forward tunnel frames forwarded on this PM instance."
     ::= { cienaCesPmBasicTxRxBiDirHist24HBinEntry 13 }

   cienaCesPmBasicTxRxBiDirHist24HBinBasicFwdRxBytesPerSec OBJECT-TYPE
     SYNTAX      Counter64
     MAX-ACCESS  read-only
     STATUS      current
     DESCRIPTION "The number of forward tunnel bytes received per second on this PM instance."
     ::= { cienaCesPmBasicTxRxBiDirHist24HBinEntry 14 }

   cienaCesPmBasicTxRxBiDirHist24HBinBasicFwdRxFramesPerSec OBJECT-TYPE
     SYNTAX      Counter64
     MAX-ACCESS  read-only
     STATUS      current
     DESCRIPTION "The number of forward tunnel frames received per second on this PM instance."
     ::= { cienaCesPmBasicTxRxBiDirHist24HBinEntry 15 }

   cienaCesPmBasicTxRxBiDirHist24HBinBasicFwdTxBytesPerSec OBJECT-TYPE
     SYNTAX      Counter64
     MAX-ACCESS  read-only
     STATUS      current
     DESCRIPTION "The number of forward tunnel bytes transmitted per second on this PM instance."
     ::= { cienaCesPmBasicTxRxBiDirHist24HBinEntry 16 }

   cienaCesPmBasicTxRxBiDirHist24HBinBasicFwdTxFramesPerSec OBJECT-TYPE
     SYNTAX      Counter64
     MAX-ACCESS  read-only
     STATUS      current
     DESCRIPTION "The number of forward tunnel frames transmitted per second on this PM instance."
     ::= { cienaCesPmBasicTxRxBiDirHist24HBinEntry 17 }

   cienaCesPmBasicTxRxBiDirHist24HBinBasicRevRxAcceptedBytes OBJECT-TYPE
     SYNTAX      Counter64
     MAX-ACCESS  read-only
     STATUS      current
     DESCRIPTION "The number of reverse tunnel accepted bytes on this PM instance."
     ::= { cienaCesPmBasicTxRxBiDirHist24HBinEntry 18 }

   cienaCesPmBasicTxRxBiDirHist24HBinBasicRevRxAcceptedFrames OBJECT-TYPE
     SYNTAX      Counter64
     MAX-ACCESS  read-only
     STATUS      current
     DESCRIPTION "The number of reverse tunnel accepted frames on this PM instance."
     ::= { cienaCesPmBasicTxRxBiDirHist24HBinEntry 19 }

   cienaCesPmBasicTxRxBiDirHist24HBinBasicRevRxYellowBytes OBJECT-TYPE
     SYNTAX      Counter64
     MAX-ACCESS  read-only
     STATUS      current
     DESCRIPTION "The number of reverse tunnel remarked bytes received on this PM instance."
     ::= { cienaCesPmBasicTxRxBiDirHist24HBinEntry 20 }

   cienaCesPmBasicTxRxBiDirHist24HBinBasicRevRxYellowFrames OBJECT-TYPE
     SYNTAX      Counter64
     MAX-ACCESS  read-only
     STATUS      current
     DESCRIPTION "The number of reverse tunnel remarked frames received on this PM instance."
     ::= { cienaCesPmBasicTxRxBiDirHist24HBinEntry 21 }

   cienaCesPmBasicTxRxBiDirHist24HBinBasicRevRxDroppedBytes OBJECT-TYPE
     SYNTAX      Counter64
     MAX-ACCESS  read-only
     STATUS      current
     DESCRIPTION "The number of reverse tunnel received bytes dropped on this PM instance."
     ::= { cienaCesPmBasicTxRxBiDirHist24HBinEntry 22 }

   cienaCesPmBasicTxRxBiDirHist24HBinBasicRevRxDroppedFrames OBJECT-TYPE
     SYNTAX      Counter64
     MAX-ACCESS  read-only
     STATUS      current
     DESCRIPTION "The number of reverse tunnel received frames dropped on this PM instance."
     ::= { cienaCesPmBasicTxRxBiDirHist24HBinEntry 23 }

   cienaCesPmBasicTxRxBiDirHist24HBinBasicRevTxForwardedBytes OBJECT-TYPE
     SYNTAX      Counter64
     MAX-ACCESS  read-only
     STATUS      current
     DESCRIPTION "The number of reverse tunnel bytes forwarded on this PM instance."
     ::= { cienaCesPmBasicTxRxBiDirHist24HBinEntry 24 }

   cienaCesPmBasicTxRxBiDirHist24HBinBasicRevTxForwardedFrames OBJECT-TYPE
     SYNTAX      Counter64
     MAX-ACCESS  read-only
     STATUS      current
     DESCRIPTION "The number of reverse tunnel frames forwarded on this PM instance."
     ::= { cienaCesPmBasicTxRxBiDirHist24HBinEntry 25 }

   cienaCesPmBasicTxRxBiDirHist24HBinBasicRevRxBytesPerSec OBJECT-TYPE
     SYNTAX      Counter64
     MAX-ACCESS  read-only
     STATUS      current
     DESCRIPTION "The number of reverse tunnel bytes received per second on this PM instance."
     ::= { cienaCesPmBasicTxRxBiDirHist24HBinEntry 26 }

   cienaCesPmBasicTxRxBiDirHist24HBinBasicRevRxFramesPerSec OBJECT-TYPE
     SYNTAX      Counter64
     MAX-ACCESS  read-only
     STATUS      current
     DESCRIPTION "The number of reverse tunnel frames received per second on this PM instance."
     ::= { cienaCesPmBasicTxRxBiDirHist24HBinEntry 27 }

   cienaCesPmBasicTxRxBiDirHist24HBinBasicRevTxBytesPerSec OBJECT-TYPE
     SYNTAX      Counter64
     MAX-ACCESS  read-only
     STATUS      current
     DESCRIPTION "The number of reverse tunnel bytes transmitted per second on this PM instance."
     ::= { cienaCesPmBasicTxRxBiDirHist24HBinEntry 28 }

   cienaCesPmBasicTxRxBiDirHist24HBinBasicRevTxFramesPerSec OBJECT-TYPE
     SYNTAX      Counter64
     MAX-ACCESS  read-only
     STATUS      current
     DESCRIPTION "The number of reverse tunnel frames transmitted per second on this PM instance."
     ::= { cienaCesPmBasicTxRxBiDirHist24HBinEntry 29 }


   --BasicTxRxBiDir Profile Stats, statistics bin

   cienaCesPmBasicTxRxBiDirStatisticsBinTable OBJECT-TYPE
     SYNTAX      SEQUENCE OF CienaCesPmBasicTxRxBiDirStatisticsBinEntry
     MAX-ACCESS  not-accessible
     STATUS      current
     DESCRIPTION "The (conceptual) read-only table listing the bin statistics."
     ::= { cienaCesPmBasicTxRxBiDirStats 5 }

   cienaCesPmBasicTxRxBiDirStatisticsBinEntry OBJECT-TYPE
     SYNTAX      CienaCesPmBasicTxRxBiDirStatisticsBinEntry
     MAX-ACCESS  not-accessible
     STATUS      current
     DESCRIPTION
           "An entry (conceptual row) in the cienaCesPmBasicTxRxBiDirStatisticsBinTable.
           This table lists the statistics for the statistics bin of the PM instance." 
     INDEX {cienaCesPmInstanceIndex}
     ::= { cienaCesPmBasicTxRxBiDirStatisticsBinTable 1 }
        
   CienaCesPmBasicTxRxBiDirStatisticsBinEntry ::=  SEQUENCE {
     cienaCesPmBasicTxRxBiDirStatsBinStartTime                       DisplayString,
     cienaCesPmBasicTxRxBiDirStatsBinClearTime                       DisplayString,
     cienaCesPmBasicTxRxBiDirStatsBinFwdRxAcceptedBytes              Counter64,
     cienaCesPmBasicTxRxBiDirStatsBinFwdRxAcceptedFrames             Counter64,
     cienaCesPmBasicTxRxBiDirStatsBinFwdRxYellowBytes                Counter64,
     cienaCesPmBasicTxRxBiDirStatsBinFwdRxYellowFrames               Counter64,
     cienaCesPmBasicTxRxBiDirStatsBinFwdRxDroppedBytes               Counter64,
     cienaCesPmBasicTxRxBiDirStatsBinFwdRxDroppedFrames              Counter64,
     cienaCesPmBasicTxRxBiDirStatsBinFwdTxForwardedBytes             Counter64,
     cienaCesPmBasicTxRxBiDirStatsBinFwdTxForwardedFrames            Counter64,
     cienaCesPmBasicTxRxBiDirStatsBinFwdRxBytesPerSec                Counter64,
     cienaCesPmBasicTxRxBiDirStatsBinFwdRxFramesPerSec               Counter64,
     cienaCesPmBasicTxRxBiDirStatsBinFwdTxBytesPerSec                Counter64,
     cienaCesPmBasicTxRxBiDirStatsBinFwdTxFramesPerSec               Counter64,
     cienaCesPmBasicTxRxBiDirStatsBinRevRxAcceptedBytes              Counter64,
     cienaCesPmBasicTxRxBiDirStatsBinRevRxAcceptedFrames             Counter64,
     cienaCesPmBasicTxRxBiDirStatsBinRevRxYellowBytes                Counter64,
     cienaCesPmBasicTxRxBiDirStatsBinRevRxYellowFrames               Counter64,
     cienaCesPmBasicTxRxBiDirStatsBinRevRxDroppedBytes               Counter64,
     cienaCesPmBasicTxRxBiDirStatsBinRevRxDroppedFrames              Counter64,
     cienaCesPmBasicTxRxBiDirStatsBinRevTxForwardedBytes             Counter64,
     cienaCesPmBasicTxRxBiDirStatsBinRevTxForwardedFrames            Counter64,
     cienaCesPmBasicTxRxBiDirStatsBinRevRxBytesPerSec                Counter64,
     cienaCesPmBasicTxRxBiDirStatsBinRevRxFramesPerSec               Counter64,
     cienaCesPmBasicTxRxBiDirStatsBinRevTxBytesPerSec                Counter64,
     cienaCesPmBasicTxRxBiDirStatsBinRevTxFramesPerSec               Counter64
   }

   cienaCesPmBasicTxRxBiDirStatsBinStartTime OBJECT-TYPE
     SYNTAX      DisplayString
     MAX-ACCESS  read-only
     STATUS      current
     DESCRIPTION "Collection start time of the bin."
     ::= { cienaCesPmBasicTxRxBiDirStatisticsBinEntry 1 }

   cienaCesPmBasicTxRxBiDirStatsBinClearTime OBJECT-TYPE
     SYNTAX      DisplayString
     MAX-ACCESS  read-only
     STATUS      current
     DESCRIPTION "Collection clear time of the bin."
     ::= { cienaCesPmBasicTxRxBiDirStatisticsBinEntry 2 }

   cienaCesPmBasicTxRxBiDirStatsBinFwdRxAcceptedBytes OBJECT-TYPE
     SYNTAX      Counter64
     MAX-ACCESS  read-only
     STATUS      current
     DESCRIPTION "The number of forward tunnel accepted bytes on this PM instance."
     ::= { cienaCesPmBasicTxRxBiDirStatisticsBinEntry 3 }

   cienaCesPmBasicTxRxBiDirStatsBinFwdRxAcceptedFrames OBJECT-TYPE
     SYNTAX      Counter64
     MAX-ACCESS  read-only
     STATUS      current
     DESCRIPTION "The number of forward tunnel accepted frames on this PM instance."
     ::= { cienaCesPmBasicTxRxBiDirStatisticsBinEntry 4 }

   cienaCesPmBasicTxRxBiDirStatsBinFwdRxYellowBytes OBJECT-TYPE
     SYNTAX      Counter64
     MAX-ACCESS  read-only
     STATUS      current
     DESCRIPTION "The number of forward tunnel remarked bytes received on this PM instance."
     ::= { cienaCesPmBasicTxRxBiDirStatisticsBinEntry 5 }

   cienaCesPmBasicTxRxBiDirStatsBinFwdRxYellowFrames OBJECT-TYPE
     SYNTAX      Counter64
     MAX-ACCESS  read-only
     STATUS      current
     DESCRIPTION "The number of forward tunnel remarked frames received on this PM instance."
     ::= { cienaCesPmBasicTxRxBiDirStatisticsBinEntry 6 }

   cienaCesPmBasicTxRxBiDirStatsBinFwdRxDroppedBytes OBJECT-TYPE
     SYNTAX      Counter64
     MAX-ACCESS  read-only
     STATUS      current
     DESCRIPTION "The number of forward tunnel received bytes dropped on this PM instance."
     ::= { cienaCesPmBasicTxRxBiDirStatisticsBinEntry 7 }

   cienaCesPmBasicTxRxBiDirStatsBinFwdRxDroppedFrames OBJECT-TYPE
     SYNTAX      Counter64
     MAX-ACCESS  read-only
     STATUS      current
     DESCRIPTION "The number of forward tunnel received frames dropped on this PM instance."
     ::= { cienaCesPmBasicTxRxBiDirStatisticsBinEntry 8 }

   cienaCesPmBasicTxRxBiDirStatsBinFwdTxForwardedBytes OBJECT-TYPE
     SYNTAX      Counter64
     MAX-ACCESS  read-only
     STATUS      current
     DESCRIPTION "The number of forward tunnel bytes forwarded on this PM instance."
     ::= { cienaCesPmBasicTxRxBiDirStatisticsBinEntry 9 }

   cienaCesPmBasicTxRxBiDirStatsBinFwdTxForwardedFrames OBJECT-TYPE
     SYNTAX      Counter64
     MAX-ACCESS  read-only
     STATUS      current
     DESCRIPTION "The number of forward tunnel frames forwarded on this PM instance."
     ::= { cienaCesPmBasicTxRxBiDirStatisticsBinEntry 10 }

   cienaCesPmBasicTxRxBiDirStatsBinFwdRxBytesPerSec OBJECT-TYPE
     SYNTAX      Counter64
     MAX-ACCESS  read-only
     STATUS      current
     DESCRIPTION "The number of forward tunnel bytes received per second on this PM instance."
     ::= { cienaCesPmBasicTxRxBiDirStatisticsBinEntry 11 }

   cienaCesPmBasicTxRxBiDirStatsBinFwdRxFramesPerSec OBJECT-TYPE
     SYNTAX      Counter64
     MAX-ACCESS  read-only
     STATUS      current
     DESCRIPTION "The number of forward tunnel frames received per second on this PM instance."
     ::= { cienaCesPmBasicTxRxBiDirStatisticsBinEntry 12 }

   cienaCesPmBasicTxRxBiDirStatsBinFwdTxBytesPerSec OBJECT-TYPE
     SYNTAX      Counter64
     MAX-ACCESS  read-only
     STATUS      current
     DESCRIPTION "The number of forward tunnel bytes transmitted per second on this PM instance."
     ::= { cienaCesPmBasicTxRxBiDirStatisticsBinEntry 13 }

   cienaCesPmBasicTxRxBiDirStatsBinFwdTxFramesPerSec OBJECT-TYPE
     SYNTAX      Counter64
     MAX-ACCESS  read-only
     STATUS      current
     DESCRIPTION "The number of forward tunnel frames transmitted per second on this PM instance."
     ::= { cienaCesPmBasicTxRxBiDirStatisticsBinEntry 14 }

   cienaCesPmBasicTxRxBiDirStatsBinRevRxAcceptedBytes OBJECT-TYPE
     SYNTAX      Counter64
     MAX-ACCESS  read-only
     STATUS      current
     DESCRIPTION "The number of reverse tunnel accepted bytes on this PM instance."
     ::= { cienaCesPmBasicTxRxBiDirStatisticsBinEntry 15 }

   cienaCesPmBasicTxRxBiDirStatsBinRevRxAcceptedFrames OBJECT-TYPE
     SYNTAX      Counter64
     MAX-ACCESS  read-only
     STATUS      current
     DESCRIPTION "The number of reverse tunnel accepted frames on this PM instance."
     ::= { cienaCesPmBasicTxRxBiDirStatisticsBinEntry 16 }

   cienaCesPmBasicTxRxBiDirStatsBinRevRxYellowBytes OBJECT-TYPE
     SYNTAX      Counter64
     MAX-ACCESS  read-only
     STATUS      current
     DESCRIPTION "The number of reverse tunnel remarked bytes received on this PM instance."
     ::= { cienaCesPmBasicTxRxBiDirStatisticsBinEntry 17 }

   cienaCesPmBasicTxRxBiDirStatsBinRevRxYellowFrames OBJECT-TYPE
     SYNTAX      Counter64
     MAX-ACCESS  read-only
     STATUS      current
     DESCRIPTION "The number of reverse tunnel remarked frames received on this PM instance."
     ::= { cienaCesPmBasicTxRxBiDirStatisticsBinEntry 18 }

   cienaCesPmBasicTxRxBiDirStatsBinRevRxDroppedBytes OBJECT-TYPE
     SYNTAX      Counter64
     MAX-ACCESS  read-only
     STATUS      current
     DESCRIPTION "The number of reverse tunnel received bytes dropped on this PM instance."
     ::= { cienaCesPmBasicTxRxBiDirStatisticsBinEntry 19 }

   cienaCesPmBasicTxRxBiDirStatsBinRevRxDroppedFrames OBJECT-TYPE
     SYNTAX      Counter64
     MAX-ACCESS  read-only
     STATUS      current
     DESCRIPTION "The number of reverse tunnel received frames dropped on this PM instance."
     ::= { cienaCesPmBasicTxRxBiDirStatisticsBinEntry 20 }

   cienaCesPmBasicTxRxBiDirStatsBinRevTxForwardedBytes OBJECT-TYPE
     SYNTAX      Counter64
     MAX-ACCESS  read-only
     STATUS      current
     DESCRIPTION "The number of reverse tunnel bytes forwarded on this PM instance."
     ::= { cienaCesPmBasicTxRxBiDirStatisticsBinEntry 21 }

   cienaCesPmBasicTxRxBiDirStatsBinRevTxForwardedFrames OBJECT-TYPE
     SYNTAX      Counter64
     MAX-ACCESS  read-only
     STATUS      current
     DESCRIPTION "The number of reverse tunnel frames forwarded on this PM instance."
     ::= { cienaCesPmBasicTxRxBiDirStatisticsBinEntry 22 }

   cienaCesPmBasicTxRxBiDirStatsBinRevRxBytesPerSec OBJECT-TYPE
     SYNTAX      Counter64
     MAX-ACCESS  read-only
     STATUS      current
     DESCRIPTION "The number of reverse tunnel bytes received per second on this PM instance."
     ::= { cienaCesPmBasicTxRxBiDirStatisticsBinEntry 23 }

   cienaCesPmBasicTxRxBiDirStatsBinRevRxFramesPerSec OBJECT-TYPE
     SYNTAX      Counter64
     MAX-ACCESS  read-only
     STATUS      current
     DESCRIPTION "The number of reverse tunnel frames received per second on this PM instance."
     ::= { cienaCesPmBasicTxRxBiDirStatisticsBinEntry 24 }

   cienaCesPmBasicTxRxBiDirStatsBinRevTxBytesPerSec OBJECT-TYPE
     SYNTAX      Counter64
     MAX-ACCESS  read-only
     STATUS      current
     DESCRIPTION "The number of reverse tunnel bytes transmitted per second on this PM instance."
     ::= { cienaCesPmBasicTxRxBiDirStatisticsBinEntry 25 }

   cienaCesPmBasicTxRxBiDirStatsBinRevTxFramesPerSec OBJECT-TYPE
     SYNTAX      Counter64
     MAX-ACCESS  read-only
     STATUS      current
     DESCRIPTION "The number of reverse tunnel frames transmitted per second on this PM instance."
     ::= { cienaCesPmBasicTxRxBiDirStatisticsBinEntry 26 }


   --BasicTxRxBiDir Profile Stats, total statistics bin


   cienaCesPmBasicTxRxBiDirTotalStatisticsBinTable OBJECT-TYPE
     SYNTAX      SEQUENCE OF CienaCesPmBasicTxRxBiDirTotalStatisticsBinEntry
     MAX-ACCESS  not-accessible
     STATUS      current
     DESCRIPTION "The (conceptual) read-only table listing the bin statistics."
     ::= { cienaCesPmBasicTxRxBiDirStats 6 }

   cienaCesPmBasicTxRxBiDirTotalStatisticsBinEntry OBJECT-TYPE
     SYNTAX      CienaCesPmBasicTxRxBiDirTotalStatisticsBinEntry
     MAX-ACCESS  not-accessible
     STATUS      current
     DESCRIPTION
           "An entry (conceptual row) in the cienaCesPmBasicTxRxBiDirTotalStatisticsBinTable.
           This table lists the statistics for the total statistics bin of the PM instance."
     INDEX {cienaCesPmInstanceIndex}
     ::= { cienaCesPmBasicTxRxBiDirTotalStatisticsBinTable 1 }

   CienaCesPmBasicTxRxBiDirTotalStatisticsBinEntry ::=  SEQUENCE {
     cienaCesPmBasicTxRxBiDirTotalStatsBinStartTime                  DisplayString,
     cienaCesPmBasicTxRxBiDirTotalStatsBinFwdRxAcceptedBytes         Counter64,
     cienaCesPmBasicTxRxBiDirTotalStatsBinFwdRxAcceptedFrames        Counter64,
     cienaCesPmBasicTxRxBiDirTotalStatsBinFwdRxYellowBytes           Counter64,
     cienaCesPmBasicTxRxBiDirTotalStatsBinFwdRxYellowFrames          Counter64,
     cienaCesPmBasicTxRxBiDirTotalStatsBinFwdRxDroppedBytes          Counter64,
     cienaCesPmBasicTxRxBiDirTotalStatsBinFwdRxDroppedFrames         Counter64,
     cienaCesPmBasicTxRxBiDirTotalStatsBinFwdTxForwardedBytes        Counter64,
     cienaCesPmBasicTxRxBiDirTotalStatsBinFwdTxForwardedFrames       Counter64,
     cienaCesPmBasicTxRxBiDirTotalStatsBinFwdRxBytesPerSec           Counter64,
     cienaCesPmBasicTxRxBiDirTotalStatsBinFwdRxFramesPerSec          Counter64,
     cienaCesPmBasicTxRxBiDirTotalStatsBinFwdTxBytesPerSec           Counter64,
     cienaCesPmBasicTxRxBiDirTotalStatsBinFwdTxFramesPerSec          Counter64,
     cienaCesPmBasicTxRxBiDirTotalStatsBinRevRxAcceptedBytes         Counter64,
     cienaCesPmBasicTxRxBiDirTotalStatsBinRevRxAcceptedFrames        Counter64,
     cienaCesPmBasicTxRxBiDirTotalStatsBinRevRxYellowBytes           Counter64,
     cienaCesPmBasicTxRxBiDirTotalStatsBinRevRxYellowFrames          Counter64,
     cienaCesPmBasicTxRxBiDirTotalStatsBinRevRxDroppedBytes          Counter64,
     cienaCesPmBasicTxRxBiDirTotalStatsBinRevRxDroppedFrames         Counter64,
     cienaCesPmBasicTxRxBiDirTotalStatsBinRevTxForwardedBytes        Counter64,
     cienaCesPmBasicTxRxBiDirTotalStatsBinRevTxForwardedFrames       Counter64,
     cienaCesPmBasicTxRxBiDirTotalStatsBinRevRxBytesPerSec           Counter64,
     cienaCesPmBasicTxRxBiDirTotalStatsBinRevRxFramesPerSec          Counter64,
     cienaCesPmBasicTxRxBiDirTotalStatsBinRevTxBytesPerSec           Counter64,
     cienaCesPmBasicTxRxBiDirTotalStatsBinRevTxFramesPerSec          Counter64
   }

   cienaCesPmBasicTxRxBiDirTotalStatsBinStartTime OBJECT-TYPE
     SYNTAX      DisplayString
     MAX-ACCESS  read-only
     STATUS      current
     DESCRIPTION "Collection start time of the bin."
     ::= { cienaCesPmBasicTxRxBiDirTotalStatisticsBinEntry 1 }

   cienaCesPmBasicTxRxBiDirTotalStatsBinFwdRxAcceptedBytes OBJECT-TYPE
     SYNTAX      Counter64
     MAX-ACCESS  read-only
     STATUS      current
     DESCRIPTION "The number of forward tunnel accepted bytes on this PM instance."
     ::= { cienaCesPmBasicTxRxBiDirTotalStatisticsBinEntry 2 }

   cienaCesPmBasicTxRxBiDirTotalStatsBinFwdRxAcceptedFrames OBJECT-TYPE
     SYNTAX      Counter64
     MAX-ACCESS  read-only
     STATUS      current
     DESCRIPTION "The number of forward tunnel accepted frames on this PM instance."
     ::= { cienaCesPmBasicTxRxBiDirTotalStatisticsBinEntry 3 }

   cienaCesPmBasicTxRxBiDirTotalStatsBinFwdRxYellowBytes OBJECT-TYPE
     SYNTAX      Counter64
     MAX-ACCESS  read-only
     STATUS      current
     DESCRIPTION "The number of forward tunnel remarked bytes received on this PM instance."
     ::= { cienaCesPmBasicTxRxBiDirTotalStatisticsBinEntry 4 }

   cienaCesPmBasicTxRxBiDirTotalStatsBinFwdRxYellowFrames OBJECT-TYPE
     SYNTAX      Counter64
     MAX-ACCESS  read-only
     STATUS      current
     DESCRIPTION "The number of forward tunnel remarked frames received on this PM instance."
     ::= { cienaCesPmBasicTxRxBiDirTotalStatisticsBinEntry 5 }

   cienaCesPmBasicTxRxBiDirTotalStatsBinFwdRxDroppedBytes OBJECT-TYPE
     SYNTAX      Counter64
     MAX-ACCESS  read-only
     STATUS      current
     DESCRIPTION "The number of forward tunnel received bytes dropped on this PM instance."
     ::= { cienaCesPmBasicTxRxBiDirTotalStatisticsBinEntry 6 }

   cienaCesPmBasicTxRxBiDirTotalStatsBinFwdRxDroppedFrames OBJECT-TYPE
     SYNTAX      Counter64
     MAX-ACCESS  read-only
     STATUS      current
     DESCRIPTION "The number of forward tunnel received frames dropped on this PM instance."
     ::= { cienaCesPmBasicTxRxBiDirTotalStatisticsBinEntry 7 }

   cienaCesPmBasicTxRxBiDirTotalStatsBinFwdTxForwardedBytes OBJECT-TYPE
     SYNTAX      Counter64
     MAX-ACCESS  read-only
     STATUS      current
     DESCRIPTION "The number of forward tunnel bytes forwarded on this PM instance."
     ::= { cienaCesPmBasicTxRxBiDirTotalStatisticsBinEntry 8 }

   cienaCesPmBasicTxRxBiDirTotalStatsBinFwdTxForwardedFrames OBJECT-TYPE
     SYNTAX      Counter64
     MAX-ACCESS  read-only
     STATUS      current
     DESCRIPTION "The number of forward tunnel frames forwarded on this PM instance."
     ::= { cienaCesPmBasicTxRxBiDirTotalStatisticsBinEntry 9 }

   cienaCesPmBasicTxRxBiDirTotalStatsBinFwdRxBytesPerSec OBJECT-TYPE
     SYNTAX      Counter64
     MAX-ACCESS  read-only
     STATUS      current
     DESCRIPTION "The number of forward tunnel bytes received per second on this PM instance."
     ::= { cienaCesPmBasicTxRxBiDirTotalStatisticsBinEntry 10 }

   cienaCesPmBasicTxRxBiDirTotalStatsBinFwdRxFramesPerSec OBJECT-TYPE
     SYNTAX      Counter64
     MAX-ACCESS  read-only
     STATUS      current
     DESCRIPTION "The number of forward tunnel frames received per second on this PM instance."
     ::= { cienaCesPmBasicTxRxBiDirTotalStatisticsBinEntry 11 }

   cienaCesPmBasicTxRxBiDirTotalStatsBinFwdTxBytesPerSec OBJECT-TYPE
     SYNTAX      Counter64
     MAX-ACCESS  read-only
     STATUS      current
     DESCRIPTION "The number of forward tunnel bytes transmitted per second on this PM instance."
     ::= { cienaCesPmBasicTxRxBiDirTotalStatisticsBinEntry 12 }

   cienaCesPmBasicTxRxBiDirTotalStatsBinFwdTxFramesPerSec OBJECT-TYPE
     SYNTAX      Counter64
     MAX-ACCESS  read-only
     STATUS      current
     DESCRIPTION "The number of forward tunnel frames transmitted per second on this PM instance."
     ::= { cienaCesPmBasicTxRxBiDirTotalStatisticsBinEntry 13 }

   cienaCesPmBasicTxRxBiDirTotalStatsBinRevRxAcceptedBytes OBJECT-TYPE
     SYNTAX      Counter64
     MAX-ACCESS  read-only
     STATUS      current
     DESCRIPTION "The number of reverse tunnel accepted bytes on this PM instance."
     ::= { cienaCesPmBasicTxRxBiDirTotalStatisticsBinEntry 14 }

   cienaCesPmBasicTxRxBiDirTotalStatsBinRevRxAcceptedFrames OBJECT-TYPE
     SYNTAX      Counter64
     MAX-ACCESS  read-only
     STATUS      current
     DESCRIPTION "The number of reverse tunnel accepted frames on this PM instance."
     ::= { cienaCesPmBasicTxRxBiDirTotalStatisticsBinEntry 15 }

   cienaCesPmBasicTxRxBiDirTotalStatsBinRevRxYellowBytes OBJECT-TYPE
     SYNTAX      Counter64
     MAX-ACCESS  read-only
     STATUS      current
     DESCRIPTION "The number of reverse tunnel remarked bytes received on this PM instance."
     ::= { cienaCesPmBasicTxRxBiDirTotalStatisticsBinEntry 16 }

   cienaCesPmBasicTxRxBiDirTotalStatsBinRevRxYellowFrames OBJECT-TYPE
     SYNTAX      Counter64
     MAX-ACCESS  read-only
     STATUS      current
     DESCRIPTION "The number of reverse tunnel remarked frames received on this PM instance."
     ::= { cienaCesPmBasicTxRxBiDirTotalStatisticsBinEntry 17 }

   cienaCesPmBasicTxRxBiDirTotalStatsBinRevRxDroppedBytes OBJECT-TYPE
     SYNTAX      Counter64
     MAX-ACCESS  read-only
     STATUS      current
     DESCRIPTION "The number of reverse tunnel received bytes dropped on this PM instance."
     ::= { cienaCesPmBasicTxRxBiDirTotalStatisticsBinEntry 18 }

   cienaCesPmBasicTxRxBiDirTotalStatsBinRevRxDroppedFrames OBJECT-TYPE
     SYNTAX      Counter64
     MAX-ACCESS  read-only
     STATUS      current
     DESCRIPTION "The number of reverse tunnel received frames dropped on this PM instance."
     ::= { cienaCesPmBasicTxRxBiDirTotalStatisticsBinEntry 19 }

   cienaCesPmBasicTxRxBiDirTotalStatsBinRevTxForwardedBytes OBJECT-TYPE
     SYNTAX      Counter64
     MAX-ACCESS  read-only
     STATUS      current
     DESCRIPTION "The number of reverse tunnel bytes forwarded on this PM instance."
     ::= { cienaCesPmBasicTxRxBiDirTotalStatisticsBinEntry 20 }

   cienaCesPmBasicTxRxBiDirTotalStatsBinRevTxForwardedFrames OBJECT-TYPE
     SYNTAX      Counter64
     MAX-ACCESS  read-only
     STATUS      current
     DESCRIPTION "The number of reverse tunnel frames forwarded on this PM instance."
     ::= { cienaCesPmBasicTxRxBiDirTotalStatisticsBinEntry 21 }

   cienaCesPmBasicTxRxBiDirTotalStatsBinRevRxBytesPerSec OBJECT-TYPE
     SYNTAX      Counter64
     MAX-ACCESS  read-only
     STATUS      current
     DESCRIPTION "The number of reverse tunnel bytes received per second on this PM instance."
     ::= { cienaCesPmBasicTxRxBiDirTotalStatisticsBinEntry 22 }

   cienaCesPmBasicTxRxBiDirTotalStatsBinRevRxFramesPerSec OBJECT-TYPE
     SYNTAX      Counter64
     MAX-ACCESS  read-only
     STATUS      current
     DESCRIPTION "The number of reverse tunnel frames received per second on this PM instance."
     ::= { cienaCesPmBasicTxRxBiDirTotalStatisticsBinEntry 23 }

   cienaCesPmBasicTxRxBiDirTotalStatsBinRevTxBytesPerSec OBJECT-TYPE
     SYNTAX      Counter64
     MAX-ACCESS  read-only
     STATUS      current
     DESCRIPTION "The number of reverse tunnel bytes transmitted per second on this PM instance."
     ::= { cienaCesPmBasicTxRxBiDirTotalStatisticsBinEntry 24 }

   cienaCesPmBasicTxRxBiDirTotalStatsBinRevTxFramesPerSec OBJECT-TYPE
     SYNTAX      Counter64
     MAX-ACCESS  read-only
     STATUS      current
     DESCRIPTION "The number of reverse tunnel frames transmitted per second on this PM instance."
     ::= { cienaCesPmBasicTxRxBiDirTotalStatisticsBinEntry 25 }


   --BasicPtp Profile Stats, history bins

   cienaCesPmBasicPtpHistoryBinTable OBJECT-TYPE
     SYNTAX      SEQUENCE OF CienaCesPmBasicPtpHistoryBinEntry
     MAX-ACCESS  not-accessible
     STATUS      current
     DESCRIPTION
           "The (conceptual) read-only table listing the bin statistics."  
     ::= { cienaCesPmBasicPtpStats 1 }

   cienaCesPmBasicPtpHistoryBinEntry OBJECT-TYPE
     SYNTAX      CienaCesPmBasicPtpHistoryBinEntry
     MAX-ACCESS  not-accessible
     STATUS      current
     DESCRIPTION
           "An entry (conceptual row) in the cienaCesPmBasicPtpHistoryBinTable.

           This table lists the statistics for all the history bins of the PM instance, as 
           specified by the bin-count object of the PM instance. History bins are displayed in the order
           so that #1 bin always represents the most recently completed bin and #2 - the bin previous to that
           and so on.

           The statistics are displayed for only the instances with valid bins (with start time >0), 
           as indicated by the operational state of the corresponding PM instance."  
     INDEX { cienaCesPmInstanceIndex, cienaCesPmBasicPtpHistoryBinIndex }
     ::= { cienaCesPmBasicPtpHistoryBinTable 1 }

   CienaCesPmBasicPtpHistoryBinEntry ::=  SEQUENCE {
     cienaCesPmBasicPtpHistoryBinIndex                         Unsigned32,
     cienaCesPmBasicPtpHistoryBinStartTime                     DisplayString,
     cienaCesPmBasicPtpHistoryBinEndTime                       DisplayString,
     cienaCesPmBasicPtpHistoryBinClearTime                     DisplayString,
     cienaCesPmBasicPtpHistoryBinDuration                      Unsigned32,   
     cienaCesPmBasicPtpHistoryBinState                         PmBinState,
     cienaCesPmBasicPtpHistoryBinFieldsUnsupported             PmProfileFieldMapBasicPtp,
     cienaCesPmBasicPtpHistoryBinFieldsInvalid                 PmProfileFieldMapBasicPtp,
     cienaCesPmBasicPtpHistoryBinOprOch                        PmInteger32Milli,
     cienaCesPmBasicPtpHistoryBinOprnOch                       Integer32,
     cienaCesPmBasicPtpHistoryBinOprMinOch                     PmInteger32Milli,
     cienaCesPmBasicPtpHistoryBinOprMaxOch                     PmInteger32Milli,
     cienaCesPmBasicPtpHistoryBinOprAvgOch                     PmInteger32Milli,
     cienaCesPmBasicPtpHistoryBinOptOch                        PmInteger32Milli,
     cienaCesPmBasicPtpHistoryBinOptMinOch                     PmInteger32Milli,
     cienaCesPmBasicPtpHistoryBinOptMaxOch                     PmInteger32Milli,
     cienaCesPmBasicPtpHistoryBinOptAvgOch                     PmInteger32Milli,
     cienaCesPmBasicPtpHistoryBinOprOts                        PmInteger32Milli,
     cienaCesPmBasicPtpHistoryBinOprnOts                       Integer32,
     cienaCesPmBasicPtpHistoryBinOprMinOts                     PmInteger32Milli,
     cienaCesPmBasicPtpHistoryBinOprMaxOts                     PmInteger32Milli,
     cienaCesPmBasicPtpHistoryBinOprAvgOts                     PmInteger32Milli,
     cienaCesPmBasicPtpHistoryBinDgdAvgOch                     Counter64,
     cienaCesPmBasicPtpHistoryBinDgdMaxOch                     Counter64
   }

   cienaCesPmBasicPtpHistoryBinIndex OBJECT-TYPE
     SYNTAX      Unsigned32 (1..65535) 
     MAX-ACCESS  not-accessible
     STATUS      current
     DESCRIPTION "Bin number associated with the PmBasicPtpHistoryBin entry."
     ::= { cienaCesPmBasicPtpHistoryBinEntry 1 }

   cienaCesPmBasicPtpHistoryBinStartTime OBJECT-TYPE
     SYNTAX      DisplayString
     MAX-ACCESS  read-only
     STATUS      current
     DESCRIPTION "Collection start time of the bin."
     ::= { cienaCesPmBasicPtpHistoryBinEntry 2 }

   cienaCesPmBasicPtpHistoryBinEndTime OBJECT-TYPE
     SYNTAX      DisplayString
     MAX-ACCESS  read-only
     STATUS      current
     DESCRIPTION "Collection end time of the bin."
     ::= { cienaCesPmBasicPtpHistoryBinEntry 3 }

   cienaCesPmBasicPtpHistoryBinClearTime OBJECT-TYPE
     SYNTAX      DisplayString
     MAX-ACCESS  read-only
     STATUS      current
     DESCRIPTION "Clear time of the bin."
     ::= { cienaCesPmBasicPtpHistoryBinEntry 4 }

   cienaCesPmBasicPtpHistoryBinDuration OBJECT-TYPE
     SYNTAX      Unsigned32 (1..65535)  
     UNITS       "minutes"
     MAX-ACCESS  read-only
     STATUS      current
     DESCRIPTION "Duration of the bin."
     ::= { cienaCesPmBasicPtpHistoryBinEntry 5 }

   cienaCesPmBasicPtpHistoryBinState OBJECT-TYPE
     SYNTAX      PmBinState 
     MAX-ACCESS  read-only
     STATUS      current
     DESCRIPTION "State of the bin."
     ::= { cienaCesPmBasicPtpHistoryBinEntry 6 }

   cienaCesPmBasicPtpHistoryBinFieldsUnsupported OBJECT-TYPE
     SYNTAX      PmProfileFieldMapBasicPtp
     MAX-ACCESS  read-only
     STATUS      current
     DESCRIPTION "Mapping of the fields within this profile which have been declared
                  unsupported.  The value of any fields indicated by this object within
                  the same table row should be disregarded."
     ::= { cienaCesPmBasicPtpHistoryBinEntry 7 }

   cienaCesPmBasicPtpHistoryBinFieldsInvalid OBJECT-TYPE
     SYNTAX      PmProfileFieldMapBasicPtp
     MAX-ACCESS  read-only
     STATUS      current
     DESCRIPTION "Mapping of the fields within this profile which have been declared
                  invalid.  The value of any fields indicated by this object within
                  the same table row should be treated as untrustworthy."
     ::= { cienaCesPmBasicPtpHistoryBinEntry 8 }

   cienaCesPmBasicPtpHistoryBinOprOch OBJECT-TYPE
     SYNTAX      PmInteger32Milli
     MAX-ACCESS  read-only
     STATUS      current
     DESCRIPTION "Optical Power Receive, Optical Channel."
     ::= { cienaCesPmBasicPtpHistoryBinEntry 9 }

   cienaCesPmBasicPtpHistoryBinOprnOch OBJECT-TYPE
     SYNTAX      Integer32
     MAX-ACCESS  read-only
     STATUS      current
     DESCRIPTION "Normalized Optical Power Receive, Optical Channel."
     ::= { cienaCesPmBasicPtpHistoryBinEntry 10 }

   cienaCesPmBasicPtpHistoryBinOprMinOch OBJECT-TYPE
     SYNTAX      PmInteger32Milli
     MAX-ACCESS  read-only
     STATUS      current
     DESCRIPTION "Minimum Optical Channel Power Receive."
     ::= { cienaCesPmBasicPtpHistoryBinEntry 11 }

   cienaCesPmBasicPtpHistoryBinOprMaxOch OBJECT-TYPE
     SYNTAX      PmInteger32Milli
     MAX-ACCESS  read-only
     STATUS      current
     DESCRIPTION "Maximum Optical Channel Power Receive."
     ::= { cienaCesPmBasicPtpHistoryBinEntry 12 }

   cienaCesPmBasicPtpHistoryBinOprAvgOch OBJECT-TYPE
     SYNTAX      PmInteger32Milli
     MAX-ACCESS  read-only
     STATUS      current
     DESCRIPTION "Average Optical Channel Power Receive."
     ::= { cienaCesPmBasicPtpHistoryBinEntry 13 }

   cienaCesPmBasicPtpHistoryBinOptOch OBJECT-TYPE
     SYNTAX      PmInteger32Milli
     MAX-ACCESS  read-only
     STATUS      current
     DESCRIPTION "Optical Power Transmit, Optical Channel."
     ::= { cienaCesPmBasicPtpHistoryBinEntry 14 }

   cienaCesPmBasicPtpHistoryBinOptMinOch OBJECT-TYPE
     SYNTAX      PmInteger32Milli
     MAX-ACCESS  read-only
     STATUS      current
     DESCRIPTION "Minimum Optical Channel Power Transmit."
     ::= { cienaCesPmBasicPtpHistoryBinEntry 15 }

   cienaCesPmBasicPtpHistoryBinOptMaxOch OBJECT-TYPE
     SYNTAX      PmInteger32Milli
     MAX-ACCESS  read-only
     STATUS      current
     DESCRIPTION "Maximum Optical Channel Power Transmit."
     ::= { cienaCesPmBasicPtpHistoryBinEntry 16 }

   cienaCesPmBasicPtpHistoryBinOptAvgOch OBJECT-TYPE
     SYNTAX      PmInteger32Milli
     MAX-ACCESS  read-only
     STATUS      current
     DESCRIPTION "Average Optical Channel Power Transmit."
     ::= { cienaCesPmBasicPtpHistoryBinEntry 17 }

   cienaCesPmBasicPtpHistoryBinOprOts OBJECT-TYPE
     SYNTAX      PmInteger32Milli
     MAX-ACCESS  read-only
     STATUS      current
     DESCRIPTION "Total Optical Power Receive, Optical Channel."
     ::= { cienaCesPmBasicPtpHistoryBinEntry 18 }

   cienaCesPmBasicPtpHistoryBinOprnOts OBJECT-TYPE
     SYNTAX      Integer32
     MAX-ACCESS  read-only
     STATUS      current
     DESCRIPTION "Total Normalized Optical Power Receive, Optical Channel."
     ::= { cienaCesPmBasicPtpHistoryBinEntry 19 }

   cienaCesPmBasicPtpHistoryBinOprMinOts OBJECT-TYPE
     SYNTAX      PmInteger32Milli
     MAX-ACCESS  read-only
     STATUS      current
     DESCRIPTION "Total Minimum Optical Channel Power Receive."
     ::= { cienaCesPmBasicPtpHistoryBinEntry 20 }

   cienaCesPmBasicPtpHistoryBinOprMaxOts OBJECT-TYPE
     SYNTAX      PmInteger32Milli
     MAX-ACCESS  read-only
     STATUS      current
     DESCRIPTION "Total Maximum Optical Channel Power Receive."
     ::= { cienaCesPmBasicPtpHistoryBinEntry 21 }

   cienaCesPmBasicPtpHistoryBinOprAvgOts OBJECT-TYPE
     SYNTAX      PmInteger32Milli
     MAX-ACCESS  read-only
     STATUS      current
     DESCRIPTION "Total Average Optical Channel Power Receive."
     ::= { cienaCesPmBasicPtpHistoryBinEntry 22 }

   cienaCesPmBasicPtpHistoryBinDgdAvgOch OBJECT-TYPE
     SYNTAX      Counter64
     MAX-ACCESS  read-only
     STATUS      current
     DESCRIPTION "Differential Group Delay (Average), Optical Channel."
     ::= { cienaCesPmBasicPtpHistoryBinEntry 23 }

   cienaCesPmBasicPtpHistoryBinDgdMaxOch OBJECT-TYPE
     SYNTAX      Counter64
     MAX-ACCESS  read-only
     STATUS      current
     DESCRIPTION "Differential Group Delay (Max), Optical Channel."
     ::= { cienaCesPmBasicPtpHistoryBinEntry 24 }


   --BasicPtp Profile Stats, current bin

   cienaCesPmBasicPtpCurrBinTable OBJECT-TYPE
     SYNTAX      SEQUENCE OF CienaCesPmBasicPtpCurrBinEntry
     MAX-ACCESS  not-accessible
     STATUS      current
     DESCRIPTION "The (conceptual) read-only table listing the bin statistics."
     ::= { cienaCesPmBasicPtpStats 2 }

   cienaCesPmBasicPtpCurrBinEntry OBJECT-TYPE
     SYNTAX      CienaCesPmBasicPtpCurrBinEntry
     MAX-ACCESS  not-accessible
     STATUS      current
     DESCRIPTION
           "An entry (conceptual row) in the cienaCesPmBasicPtpCurrBinTable.
           This table lists the statistics for the current bin of the PM instance." 
     INDEX {cienaCesPmInstanceIndex}
     ::= { cienaCesPmBasicPtpCurrBinTable 1 }

   CienaCesPmBasicPtpCurrBinEntry ::=  SEQUENCE {
     cienaCesPmBasicPtpCurrBinStartTime                        DisplayString,
     cienaCesPmBasicPtpCurrBinClearedTime                      DisplayString,
     cienaCesPmBasicPtpCurrBinDuration                         Unsigned32,   
     cienaCesPmBasicPtpCurrBinState                            PmBinState,
     cienaCesPmBasicPtpCurrBinFieldsUnsupported                PmProfileFieldMapBasicPtp,
     cienaCesPmBasicPtpCurrBinFieldsInvalid                    PmProfileFieldMapBasicPtp,
     cienaCesPmBasicPtpCurrBinOprOch                           PmInteger32Milli,
     cienaCesPmBasicPtpCurrBinOprnOch                          Integer32,
     cienaCesPmBasicPtpCurrBinOprMinOch                        PmInteger32Milli,
     cienaCesPmBasicPtpCurrBinOprMaxOch                        PmInteger32Milli,
     cienaCesPmBasicPtpCurrBinOprAvgOch                        PmInteger32Milli,
     cienaCesPmBasicPtpCurrBinOptOch                           PmInteger32Milli,
     cienaCesPmBasicPtpCurrBinOptMinOch                        PmInteger32Milli,
     cienaCesPmBasicPtpCurrBinOptMaxOch                        PmInteger32Milli,
     cienaCesPmBasicPtpCurrBinOptAvgOch                        PmInteger32Milli,
     cienaCesPmBasicPtpCurrBinOprOts                           PmInteger32Milli,
     cienaCesPmBasicPtpCurrBinOprnOts                          Integer32,
     cienaCesPmBasicPtpCurrBinOprMinOts                        PmInteger32Milli,
     cienaCesPmBasicPtpCurrBinOprMaxOts                        PmInteger32Milli,
     cienaCesPmBasicPtpCurrBinOprAvgOts                        PmInteger32Milli,
     cienaCesPmBasicPtpCurrBinDgdAvgOch                        Counter64,
     cienaCesPmBasicPtpCurrBinDgdMaxOch                        Counter64
  }

   cienaCesPmBasicPtpCurrBinStartTime OBJECT-TYPE
     SYNTAX      DisplayString
     MAX-ACCESS  read-only
     STATUS      current
     DESCRIPTION "Collection start time of the bin."
     ::= { cienaCesPmBasicPtpCurrBinEntry 1 }

   cienaCesPmBasicPtpCurrBinClearedTime OBJECT-TYPE
     SYNTAX      DisplayString
     MAX-ACCESS  read-only
     STATUS      current
     DESCRIPTION "Cleared time of the bin."
     ::= { cienaCesPmBasicPtpCurrBinEntry 2 }

  cienaCesPmBasicPtpCurrBinDuration OBJECT-TYPE
     SYNTAX      Unsigned32 (1..65535)
     UNITS       "minutes"
     MAX-ACCESS  read-only
     STATUS      current
     DESCRIPTION "Duration of the bin."
     ::= { cienaCesPmBasicPtpCurrBinEntry 3 }

   cienaCesPmBasicPtpCurrBinState OBJECT-TYPE
     SYNTAX      PmBinState
     MAX-ACCESS  read-only
     STATUS      current
     DESCRIPTION "State of the bin."
     ::= { cienaCesPmBasicPtpCurrBinEntry 4 }

   cienaCesPmBasicPtpCurrBinFieldsUnsupported OBJECT-TYPE
     SYNTAX      PmProfileFieldMapBasicPtp
     MAX-ACCESS  read-only
     STATUS      current
     DESCRIPTION "Mapping of the fields within this profile which have been declared
                  unsupported.  The value of any fields indicated by this object within
                  the same table row should be disregarded."
     ::= { cienaCesPmBasicPtpCurrBinEntry 5 }

   cienaCesPmBasicPtpCurrBinFieldsInvalid OBJECT-TYPE
     SYNTAX      PmProfileFieldMapBasicPtp
     MAX-ACCESS  read-only
     STATUS      current
     DESCRIPTION "Mapping of the fields within this profile which have been declared
                  invalid.  The value of any fields indicated by this object within
                  the same table row should be treated as untrustworthy."
     ::= { cienaCesPmBasicPtpCurrBinEntry 6 }

   cienaCesPmBasicPtpCurrBinOprOch OBJECT-TYPE
     SYNTAX      PmInteger32Milli
     MAX-ACCESS  read-only
     STATUS      current
     DESCRIPTION "Optical Power Receive, Optical Channel."
     ::= { cienaCesPmBasicPtpCurrBinEntry 7 }

   cienaCesPmBasicPtpCurrBinOprnOch OBJECT-TYPE
     SYNTAX      Integer32
     MAX-ACCESS  read-only
     STATUS      current
     DESCRIPTION "Normalized Optical Power Receive, Optical Channel."
     ::= { cienaCesPmBasicPtpCurrBinEntry 8 }

   cienaCesPmBasicPtpCurrBinOprMinOch OBJECT-TYPE
     SYNTAX      PmInteger32Milli
     MAX-ACCESS  read-only
     STATUS      current
     DESCRIPTION "Minimum Optical Channel Power Receive."
     ::= { cienaCesPmBasicPtpCurrBinEntry 9 }

   cienaCesPmBasicPtpCurrBinOprMaxOch OBJECT-TYPE
     SYNTAX      PmInteger32Milli
     MAX-ACCESS  read-only
     STATUS      current
     DESCRIPTION "Maximum Optical Channel Power Receive."
     ::= { cienaCesPmBasicPtpCurrBinEntry 10 }

   cienaCesPmBasicPtpCurrBinOprAvgOch OBJECT-TYPE
     SYNTAX      PmInteger32Milli
     MAX-ACCESS  read-only
     STATUS      current
     DESCRIPTION "Average Optical Channel Power Receive."
     ::= { cienaCesPmBasicPtpCurrBinEntry 11 }

   cienaCesPmBasicPtpCurrBinOptOch OBJECT-TYPE
     SYNTAX      PmInteger32Milli
     MAX-ACCESS  read-only
     STATUS      current
     DESCRIPTION "Optical Power Transmit, Optical Channel."
     ::= { cienaCesPmBasicPtpCurrBinEntry 12 }

   cienaCesPmBasicPtpCurrBinOptMinOch OBJECT-TYPE
     SYNTAX      PmInteger32Milli
     MAX-ACCESS  read-only
     STATUS      current
     DESCRIPTION "Minimum Optical Channel Power Transmit."
     ::= { cienaCesPmBasicPtpCurrBinEntry 13 }

   cienaCesPmBasicPtpCurrBinOptMaxOch OBJECT-TYPE
     SYNTAX      PmInteger32Milli
     MAX-ACCESS  read-only
     STATUS      current
     DESCRIPTION "Maximum Optical Channel Power Transmit."
     ::= { cienaCesPmBasicPtpCurrBinEntry 14 }

   cienaCesPmBasicPtpCurrBinOptAvgOch OBJECT-TYPE
     SYNTAX      PmInteger32Milli
     MAX-ACCESS  read-only
     STATUS      current
     DESCRIPTION "Average Optical Channel Power Transmit."
     ::= { cienaCesPmBasicPtpCurrBinEntry 15 }

   cienaCesPmBasicPtpCurrBinOprOts OBJECT-TYPE
     SYNTAX      PmInteger32Milli
     MAX-ACCESS  read-only
     STATUS      current
     DESCRIPTION "Total Optical Power Receive, Optical Channel."
     ::= { cienaCesPmBasicPtpCurrBinEntry 16 }

   cienaCesPmBasicPtpCurrBinOprnOts OBJECT-TYPE
     SYNTAX      Integer32
     MAX-ACCESS  read-only
     STATUS      current
     DESCRIPTION "Total Normalized Optical Power Receive, Optical Channel."
     ::= { cienaCesPmBasicPtpCurrBinEntry 17 }

   cienaCesPmBasicPtpCurrBinOprMinOts OBJECT-TYPE
     SYNTAX      PmInteger32Milli
     MAX-ACCESS  read-only
     STATUS      current
     DESCRIPTION "Total Minimum Optical Channel Power Receive."
     ::= { cienaCesPmBasicPtpCurrBinEntry 18 }

   cienaCesPmBasicPtpCurrBinOprMaxOts OBJECT-TYPE
     SYNTAX      PmInteger32Milli
     MAX-ACCESS  read-only
     STATUS      current
     DESCRIPTION "Total Maximum Optical Channel Power Receive."
     ::= { cienaCesPmBasicPtpCurrBinEntry 19 }

   cienaCesPmBasicPtpCurrBinOprAvgOts OBJECT-TYPE
     SYNTAX      PmInteger32Milli
     MAX-ACCESS  read-only
     STATUS      current
     DESCRIPTION "Total Average Optical Channel Power Receive."
     ::= { cienaCesPmBasicPtpCurrBinEntry 20 }

   cienaCesPmBasicPtpCurrBinDgdAvgOch OBJECT-TYPE
     SYNTAX      Counter64
     MAX-ACCESS  read-only
     STATUS      current
     DESCRIPTION "Differential Group Delay (Average), Optical Channel."
     ::= { cienaCesPmBasicPtpCurrBinEntry 21 }

   cienaCesPmBasicPtpCurrBinDgdMaxOch OBJECT-TYPE
     SYNTAX      Counter64
     MAX-ACCESS  read-only
     STATUS      current
     DESCRIPTION "Differential Group Delay (Max), Optical Channel."
     ::= { cienaCesPmBasicPtpCurrBinEntry 22 }


   --BasicPtp Profile Stats, current 24 hour bin

   cienaCesPmBasicPtpCurr24HBinTable OBJECT-TYPE
     SYNTAX      SEQUENCE OF CienaCesPmBasicPtpCurr24HBinEntry
     MAX-ACCESS  not-accessible
     STATUS      current
     DESCRIPTION "The (conceptual) read-only table listing the bin statistics."
     ::= { cienaCesPmBasicPtpStats 3 }

   cienaCesPmBasicPtpCurr24HBinEntry OBJECT-TYPE
     SYNTAX      CienaCesPmBasicPtpCurr24HBinEntry
     MAX-ACCESS  not-accessible
     STATUS      current
     DESCRIPTION
           "An entry (conceptual row) in the cienaCesPmBasicPtpCurr24HBinTable.

           This table lists the statistics for the current 24 Hours bin."
     INDEX {cienaCesPmInstanceIndex}
     ::= { cienaCesPmBasicPtpCurr24HBinTable 1 }

   CienaCesPmBasicPtpCurr24HBinEntry ::=  SEQUENCE {
     cienaCesPmBasicPtpCurr24HBinStartTime                     DisplayString,
     cienaCesPmBasicPtpCurr24HBinClearedTime                   DisplayString,
     cienaCesPmBasicPtpCurr24HBinDuration                      Unsigned32,
     cienaCesPmBasicPtpCurr24HBinState                         PmBinState,
     cienaCesPmBasicPtpCurr24HBinFieldsUnsupported             PmProfileFieldMapBasicPtp,
     cienaCesPmBasicPtpCurr24HBinFieldsInvalid                 PmProfileFieldMapBasicPtp,
     cienaCesPmBasicPtpCurr24HBinOprOch                        PmInteger32Milli,
     cienaCesPmBasicPtpCurr24HBinOprnOch                       Integer32,
     cienaCesPmBasicPtpCurr24HBinOprMinOch                     PmInteger32Milli,
     cienaCesPmBasicPtpCurr24HBinOprMaxOch                     PmInteger32Milli,
     cienaCesPmBasicPtpCurr24HBinOprAvgOch                     PmInteger32Milli,
     cienaCesPmBasicPtpCurr24HBinOptOch                        PmInteger32Milli,
     cienaCesPmBasicPtpCurr24HBinOptMinOch                     PmInteger32Milli,
     cienaCesPmBasicPtpCurr24HBinOptMaxOch                     PmInteger32Milli,
     cienaCesPmBasicPtpCurr24HBinOptAvgOch                     PmInteger32Milli,
     cienaCesPmBasicPtpCurr24HBinOprOts                        PmInteger32Milli,
     cienaCesPmBasicPtpCurr24HBinOprnOts                       Integer32,
     cienaCesPmBasicPtpCurr24HBinOprMinOts                     PmInteger32Milli,
     cienaCesPmBasicPtpCurr24HBinOprMaxOts                     PmInteger32Milli,
     cienaCesPmBasicPtpCurr24HBinOprAvgOts                     PmInteger32Milli,
     cienaCesPmBasicPtpCurr24HBinDgdAvgOch                     Counter64,
     cienaCesPmBasicPtpCurr24HBinDgdMaxOch                     Counter64
   }

   cienaCesPmBasicPtpCurr24HBinStartTime OBJECT-TYPE
     SYNTAX      DisplayString
     MAX-ACCESS  read-only
     STATUS      current
     DESCRIPTION "Collection start time of the bin."
     ::= { cienaCesPmBasicPtpCurr24HBinEntry 1 }

    cienaCesPmBasicPtpCurr24HBinClearedTime OBJECT-TYPE
     SYNTAX      DisplayString
     MAX-ACCESS  read-only
     STATUS      current
     DESCRIPTION "Cleared time of the bin."
     ::= { cienaCesPmBasicPtpCurr24HBinEntry 2 }

   cienaCesPmBasicPtpCurr24HBinDuration OBJECT-TYPE
     SYNTAX      Unsigned32 (1..65535)
     UNITS       "minutes"
     MAX-ACCESS  read-only
     STATUS      current
     DESCRIPTION "Interval of the bin."
     ::= { cienaCesPmBasicPtpCurr24HBinEntry 3 }

   cienaCesPmBasicPtpCurr24HBinState OBJECT-TYPE
     SYNTAX      PmBinState
     MAX-ACCESS  read-only
     STATUS      current
     DESCRIPTION "State of the bin."
     ::= { cienaCesPmBasicPtpCurr24HBinEntry 4 }

   cienaCesPmBasicPtpCurr24HBinFieldsUnsupported OBJECT-TYPE
     SYNTAX      PmProfileFieldMapBasicPtp
     MAX-ACCESS  read-only
     STATUS      current
     DESCRIPTION "Mapping of the fields within this profile which have been declared
                  unsupported.  The value of any fields indicated by this object within
                  the same table row should be disregarded."
     ::= { cienaCesPmBasicPtpCurr24HBinEntry 5 }

   cienaCesPmBasicPtpCurr24HBinFieldsInvalid OBJECT-TYPE
     SYNTAX      PmProfileFieldMapBasicPtp
     MAX-ACCESS  read-only
     STATUS      current
     DESCRIPTION "Mapping of the fields within this profile which have been declared
                  invalid.  The value of any fields indicated by this object within
                  the same table row should be treated as untrustworthy."
     ::= { cienaCesPmBasicPtpCurr24HBinEntry 6 }

   cienaCesPmBasicPtpCurr24HBinOprOch OBJECT-TYPE
     SYNTAX      PmInteger32Milli
     MAX-ACCESS  read-only
     STATUS      current
     DESCRIPTION "Optical Power Receive, Optical Channel."
     ::= { cienaCesPmBasicPtpCurr24HBinEntry 7 }

   cienaCesPmBasicPtpCurr24HBinOprnOch OBJECT-TYPE
     SYNTAX      Integer32
     MAX-ACCESS  read-only
     STATUS      current
     DESCRIPTION "Normalized Optical Power Receive, Optical Channel."
     ::= { cienaCesPmBasicPtpCurr24HBinEntry 8 }

   cienaCesPmBasicPtpCurr24HBinOprMinOch OBJECT-TYPE
     SYNTAX      PmInteger32Milli
     MAX-ACCESS  read-only
     STATUS      current
     DESCRIPTION "Minimum Optical Channel Power Receive."
     ::= { cienaCesPmBasicPtpCurr24HBinEntry 9 }

   cienaCesPmBasicPtpCurr24HBinOprMaxOch OBJECT-TYPE
     SYNTAX      PmInteger32Milli
     MAX-ACCESS  read-only
     STATUS      current
     DESCRIPTION "Maximum Optical Channel Power Receive."
     ::= { cienaCesPmBasicPtpCurr24HBinEntry 10 }

   cienaCesPmBasicPtpCurr24HBinOprAvgOch OBJECT-TYPE
     SYNTAX      PmInteger32Milli
     MAX-ACCESS  read-only
     STATUS      current
     DESCRIPTION "Average Optical Channel Power Receive."
     ::= { cienaCesPmBasicPtpCurr24HBinEntry 11 }

   cienaCesPmBasicPtpCurr24HBinOptOch OBJECT-TYPE
     SYNTAX      PmInteger32Milli
     MAX-ACCESS  read-only
     STATUS      current
     DESCRIPTION "Optical Power Transmit, Optical Channel."
     ::= { cienaCesPmBasicPtpCurr24HBinEntry 12 }

   cienaCesPmBasicPtpCurr24HBinOptMinOch OBJECT-TYPE
     SYNTAX      PmInteger32Milli
     MAX-ACCESS  read-only
     STATUS      current
     DESCRIPTION "Minimum Optical Channel Power Transmit."
     ::= { cienaCesPmBasicPtpCurr24HBinEntry 13 }

   cienaCesPmBasicPtpCurr24HBinOptMaxOch OBJECT-TYPE
     SYNTAX      PmInteger32Milli
     MAX-ACCESS  read-only
     STATUS      current
     DESCRIPTION "Maximum Optical Channel Power Transmit."
     ::= { cienaCesPmBasicPtpCurr24HBinEntry 14 }

   cienaCesPmBasicPtpCurr24HBinOptAvgOch OBJECT-TYPE
     SYNTAX      PmInteger32Milli
     MAX-ACCESS  read-only
     STATUS      current
     DESCRIPTION "Average Optical Channel Power Transmit."
     ::= { cienaCesPmBasicPtpCurr24HBinEntry 15 }

   cienaCesPmBasicPtpCurr24HBinOprOts OBJECT-TYPE
     SYNTAX      PmInteger32Milli
     MAX-ACCESS  read-only
     STATUS      current
     DESCRIPTION "Total Optical Power Receive, Optical Channel."
     ::= { cienaCesPmBasicPtpCurr24HBinEntry 16 }

   cienaCesPmBasicPtpCurr24HBinOprnOts OBJECT-TYPE
     SYNTAX      Integer32
     MAX-ACCESS  read-only
     STATUS      current
     DESCRIPTION "Total Normalized Optical Power Receive, Optical Channel."
     ::= { cienaCesPmBasicPtpCurr24HBinEntry 17 }

   cienaCesPmBasicPtpCurr24HBinOprMinOts OBJECT-TYPE
     SYNTAX      PmInteger32Milli
     MAX-ACCESS  read-only
     STATUS      current
     DESCRIPTION "Total Minimum Optical Channel Power Receive."
     ::= { cienaCesPmBasicPtpCurr24HBinEntry 18 }

   cienaCesPmBasicPtpCurr24HBinOprMaxOts OBJECT-TYPE
     SYNTAX      PmInteger32Milli
     MAX-ACCESS  read-only
     STATUS      current
     DESCRIPTION "Total Maximum Optical Channel Power Receive."
     ::= { cienaCesPmBasicPtpCurr24HBinEntry 19 }

   cienaCesPmBasicPtpCurr24HBinOprAvgOts OBJECT-TYPE
     SYNTAX      PmInteger32Milli
     MAX-ACCESS  read-only
     STATUS      current
     DESCRIPTION "Total Average Optical Channel Power Receive."
     ::= { cienaCesPmBasicPtpCurr24HBinEntry 20 }

   cienaCesPmBasicPtpCurr24HBinDgdAvgOch OBJECT-TYPE
     SYNTAX      Counter64
     MAX-ACCESS  read-only
     STATUS      current
     DESCRIPTION "Differential Group Delay (Average), Optical Channel."
     ::= { cienaCesPmBasicPtpCurr24HBinEntry 21 }

   cienaCesPmBasicPtpCurr24HBinDgdMaxOch OBJECT-TYPE
     SYNTAX      Counter64
     MAX-ACCESS  read-only
     STATUS      current
     DESCRIPTION "Differential Group Delay (Max), Optical Channel."
     ::= { cienaCesPmBasicPtpCurr24HBinEntry 22 }


   --BasicPtp Profile Stats, history 24 hour bin

   cienaCesPmBasicPtpHist24HBinTable OBJECT-TYPE
     SYNTAX      SEQUENCE OF CienaCesPmBasicPtpHist24HBinEntry
     MAX-ACCESS  not-accessible
     STATUS      current
     DESCRIPTION "The (conceptual) read-only table listing the bin statistics."
     ::= { cienaCesPmBasicPtpStats 4 }

   cienaCesPmBasicPtpHist24HBinEntry OBJECT-TYPE
     SYNTAX      CienaCesPmBasicPtpHist24HBinEntry
     MAX-ACCESS  not-accessible
     STATUS      current
     DESCRIPTION
           "An entry (conceptual row) in the cienaCesPmBasicPtpHist24HBinTable.

           This table lists the statistics for the history 24 hours bin."
     INDEX {cienaCesPmInstanceIndex}
     ::= { cienaCesPmBasicPtpHist24HBinTable 1 }
        
   CienaCesPmBasicPtpHist24HBinEntry ::=  SEQUENCE {
     cienaCesPmBasicPtpHist24HBinStartTime                     DisplayString,
     cienaCesPmBasicPtpHist24HBinEndTime                       DisplayString,
     cienaCesPmBasicPtpHist24HBinClearTime                     DisplayString,
     cienaCesPmBasicPtpHist24HBinDuration                      Unsigned32,
     cienaCesPmBasicPtpHist24HBinState                         PmBinState,
     cienaCesPmBasicPtpHist24HBinFieldsUnsupported             PmProfileFieldMapBasicPtp,
     cienaCesPmBasicPtpHist24HBinFieldsInvalid                 PmProfileFieldMapBasicPtp,
     cienaCesPmBasicPtpHist24HBinOprOch                        PmInteger32Milli,
     cienaCesPmBasicPtpHist24HBinOprnOch                       Integer32,
     cienaCesPmBasicPtpHist24HBinOprMinOch                     PmInteger32Milli,
     cienaCesPmBasicPtpHist24HBinOprMaxOch                     PmInteger32Milli,
     cienaCesPmBasicPtpHist24HBinOprAvgOch                     PmInteger32Milli,
     cienaCesPmBasicPtpHist24HBinOptOch                        PmInteger32Milli,
     cienaCesPmBasicPtpHist24HBinOptMinOch                     PmInteger32Milli,
     cienaCesPmBasicPtpHist24HBinOptMaxOch                     PmInteger32Milli,
     cienaCesPmBasicPtpHist24HBinOptAvgOch                     PmInteger32Milli,
     cienaCesPmBasicPtpHist24HBinOprOts                        PmInteger32Milli,
     cienaCesPmBasicPtpHist24HBinOprnOts                       Integer32,
     cienaCesPmBasicPtpHist24HBinOprMinOts                     PmInteger32Milli,
     cienaCesPmBasicPtpHist24HBinOprMaxOts                     PmInteger32Milli,
     cienaCesPmBasicPtpHist24HBinOprAvgOts                     PmInteger32Milli,
     cienaCesPmBasicPtpHist24HBinDgdAvgOch                     Counter64,
     cienaCesPmBasicPtpHist24HBinDgdMaxOch                     Counter64
   }

   cienaCesPmBasicPtpHist24HBinStartTime OBJECT-TYPE
     SYNTAX      DisplayString
     MAX-ACCESS  read-only
     STATUS      current
     DESCRIPTION "Collection start time of the bin."
     ::= { cienaCesPmBasicPtpHist24HBinEntry 1 }

   cienaCesPmBasicPtpHist24HBinEndTime OBJECT-TYPE
     SYNTAX      DisplayString
     MAX-ACCESS  read-only
     STATUS      current
     DESCRIPTION "Collection end time of the bin."
     ::= { cienaCesPmBasicPtpHist24HBinEntry 2 }

   cienaCesPmBasicPtpHist24HBinClearTime OBJECT-TYPE
     SYNTAX      DisplayString
     MAX-ACCESS  read-only
     STATUS      current
     DESCRIPTION "Collection clear time of the bin."
      ::= { cienaCesPmBasicPtpHist24HBinEntry 3 }
   
   cienaCesPmBasicPtpHist24HBinDuration OBJECT-TYPE
     SYNTAX      Unsigned32 (1..65535)
     UNITS       "minutes"
     MAX-ACCESS  read-only
     STATUS      current
     DESCRIPTION "Interval of the bin."
     ::= { cienaCesPmBasicPtpHist24HBinEntry 4 }

   cienaCesPmBasicPtpHist24HBinState OBJECT-TYPE
     SYNTAX      PmBinState
     MAX-ACCESS  read-only
     STATUS      current
     DESCRIPTION "State of the bin."
     ::= { cienaCesPmBasicPtpHist24HBinEntry 5 }

   cienaCesPmBasicPtpHist24HBinFieldsUnsupported OBJECT-TYPE
     SYNTAX      PmProfileFieldMapBasicPtp
     MAX-ACCESS  read-only
     STATUS      current
     DESCRIPTION "Mapping of the fields within this profile which have been declared
                  unsupported.  The value of any fields indicated by this object within
                  the same table row should be disregarded."
     ::= { cienaCesPmBasicPtpHist24HBinEntry 6 }

   cienaCesPmBasicPtpHist24HBinFieldsInvalid OBJECT-TYPE
     SYNTAX      PmProfileFieldMapBasicPtp
     MAX-ACCESS  read-only
     STATUS      current
     DESCRIPTION "Mapping of the fields within this profile which have been declared
                  invalid.  The value of any fields indicated by this object within
                  the same table row should be treated as untrustworthy."
     ::= { cienaCesPmBasicPtpHist24HBinEntry 7 }

   cienaCesPmBasicPtpHist24HBinOprOch OBJECT-TYPE
     SYNTAX      PmInteger32Milli
     MAX-ACCESS  read-only
     STATUS      current
     DESCRIPTION "Optical Power Receive, Optical Channel."
     ::= { cienaCesPmBasicPtpHist24HBinEntry 8 }

   cienaCesPmBasicPtpHist24HBinOprnOch OBJECT-TYPE
     SYNTAX      Integer32
     MAX-ACCESS  read-only
     STATUS      current
     DESCRIPTION "Normalized Optical Power Receive, Optical Channel."
     ::= { cienaCesPmBasicPtpHist24HBinEntry 9 }

   cienaCesPmBasicPtpHist24HBinOprMinOch OBJECT-TYPE
     SYNTAX      PmInteger32Milli
     MAX-ACCESS  read-only
     STATUS      current
     DESCRIPTION "Minimum Optical Channel Power Receive."
     ::= { cienaCesPmBasicPtpHist24HBinEntry 10 }

   cienaCesPmBasicPtpHist24HBinOprMaxOch OBJECT-TYPE
     SYNTAX      PmInteger32Milli
     MAX-ACCESS  read-only
     STATUS      current
     DESCRIPTION "Maximum Optical Channel Power Receive."
     ::= { cienaCesPmBasicPtpHist24HBinEntry 11 }

   cienaCesPmBasicPtpHist24HBinOprAvgOch OBJECT-TYPE
     SYNTAX      PmInteger32Milli
     MAX-ACCESS  read-only
     STATUS      current
     DESCRIPTION "Average Optical Channel Power Receive."
     ::= { cienaCesPmBasicPtpHist24HBinEntry 12 }

   cienaCesPmBasicPtpHist24HBinOptOch OBJECT-TYPE
     SYNTAX      PmInteger32Milli
     MAX-ACCESS  read-only
     STATUS      current
     DESCRIPTION "Optical Power Transmit, Optical Channel."
     ::= { cienaCesPmBasicPtpHist24HBinEntry 13 }

   cienaCesPmBasicPtpHist24HBinOptMinOch OBJECT-TYPE
     SYNTAX      PmInteger32Milli
     MAX-ACCESS  read-only
     STATUS      current
     DESCRIPTION "Minimum Optical Channel Power Transmit."
     ::= { cienaCesPmBasicPtpHist24HBinEntry 14 }

   cienaCesPmBasicPtpHist24HBinOptMaxOch OBJECT-TYPE
     SYNTAX      PmInteger32Milli
     MAX-ACCESS  read-only
     STATUS      current
     DESCRIPTION "Maximum Optical Channel Power Transmit."
     ::= { cienaCesPmBasicPtpHist24HBinEntry 15 }

   cienaCesPmBasicPtpHist24HBinOptAvgOch OBJECT-TYPE
     SYNTAX      PmInteger32Milli
     MAX-ACCESS  read-only
     STATUS      current
     DESCRIPTION "Average Optical Channel Power Transmit."
     ::= { cienaCesPmBasicPtpHist24HBinEntry 16 }

   cienaCesPmBasicPtpHist24HBinOprOts OBJECT-TYPE
     SYNTAX      PmInteger32Milli
     MAX-ACCESS  read-only
     STATUS      current
     DESCRIPTION "Total Optical Power Receive, Optical Channel."
     ::= { cienaCesPmBasicPtpHist24HBinEntry 17 }

   cienaCesPmBasicPtpHist24HBinOprnOts OBJECT-TYPE
     SYNTAX      Integer32
     MAX-ACCESS  read-only
     STATUS      current
     DESCRIPTION "Total Normalized Optical Power Receive, Optical Channel."
     ::= { cienaCesPmBasicPtpHist24HBinEntry 18 }

   cienaCesPmBasicPtpHist24HBinOprMinOts OBJECT-TYPE
     SYNTAX      PmInteger32Milli
     MAX-ACCESS  read-only
     STATUS      current
     DESCRIPTION "Total Minimum Optical Channel Power Receive."
     ::= { cienaCesPmBasicPtpHist24HBinEntry 19 }

   cienaCesPmBasicPtpHist24HBinOprMaxOts OBJECT-TYPE
     SYNTAX      PmInteger32Milli
     MAX-ACCESS  read-only
     STATUS      current
     DESCRIPTION "Total Maximum Optical Channel Power Receive."
     ::= { cienaCesPmBasicPtpHist24HBinEntry 20 }

   cienaCesPmBasicPtpHist24HBinOprAvgOts OBJECT-TYPE
     SYNTAX      PmInteger32Milli
     MAX-ACCESS  read-only
     STATUS      current
     DESCRIPTION "Total Average Optical Channel Power Receive."
     ::= { cienaCesPmBasicPtpHist24HBinEntry 21 }

   cienaCesPmBasicPtpHist24HBinDgdAvgOch OBJECT-TYPE
     SYNTAX      Counter64
     MAX-ACCESS  read-only
     STATUS      current
     DESCRIPTION "Differential Group Delay (Average), Optical Channel."
     ::= { cienaCesPmBasicPtpHist24HBinEntry 22 }

   cienaCesPmBasicPtpHist24HBinDgdMaxOch OBJECT-TYPE
     SYNTAX      Counter64
     MAX-ACCESS  read-only
     STATUS      current
     DESCRIPTION "Differential Group Delay (Max), Optical Channel."
     ::= { cienaCesPmBasicPtpHist24HBinEntry 23 }


   --BasicPtp Profile Stats, statistics bin

   cienaCesPmBasicPtpStatisticsBinTable OBJECT-TYPE
     SYNTAX      SEQUENCE OF CienaCesPmBasicPtpStatisticsBinEntry
     MAX-ACCESS  not-accessible
     STATUS      current
     DESCRIPTION "The (conceptual) read-only table listing the bin statistics."
     ::= { cienaCesPmBasicPtpStats 5 }

   cienaCesPmBasicPtpStatisticsBinEntry OBJECT-TYPE
     SYNTAX      CienaCesPmBasicPtpStatisticsBinEntry
     MAX-ACCESS  not-accessible
     STATUS      current
     DESCRIPTION
           "An entry (conceptual row) in the cienaCesPmBasicPtpStatisticsBinTable.
           This table lists the statistics for the statistics bin of the PM instance." 
     INDEX {cienaCesPmInstanceIndex}
     ::= { cienaCesPmBasicPtpStatisticsBinTable 1 }
        
   CienaCesPmBasicPtpStatisticsBinEntry ::=  SEQUENCE {
     cienaCesPmBasicPtpStatsBinStartTime                       DisplayString,
     cienaCesPmBasicPtpStatsBinClearTime                       DisplayString,
     cienaCesPmBasicPtpStatsBinOprOch                          PmInteger32Milli,
     cienaCesPmBasicPtpStatsBinOprnOch                         Integer32,
     cienaCesPmBasicPtpStatsBinOprMinOch                       PmInteger32Milli,
     cienaCesPmBasicPtpStatsBinOprMaxOch                       PmInteger32Milli,
     cienaCesPmBasicPtpStatsBinOprAvgOch                       PmInteger32Milli,
     cienaCesPmBasicPtpStatsBinOptOch                          PmInteger32Milli,
     cienaCesPmBasicPtpStatsBinOptMinOch                       PmInteger32Milli,
     cienaCesPmBasicPtpStatsBinOptMaxOch                       PmInteger32Milli,
     cienaCesPmBasicPtpStatsBinOptAvgOch                       PmInteger32Milli,
     cienaCesPmBasicPtpStatsBinOprOts                          PmInteger32Milli,
     cienaCesPmBasicPtpStatsBinOprnOts                         Integer32,
     cienaCesPmBasicPtpStatsBinOprMinOts                       PmInteger32Milli,
     cienaCesPmBasicPtpStatsBinOprMaxOts                       PmInteger32Milli,
     cienaCesPmBasicPtpStatsBinOprAvgOts                       PmInteger32Milli,
     cienaCesPmBasicPtpStatsBinDgdAvgOch                       Counter64,
     cienaCesPmBasicPtpStatsBinDgdMaxOch                       Counter64
   }

   cienaCesPmBasicPtpStatsBinStartTime OBJECT-TYPE
     SYNTAX      DisplayString
     MAX-ACCESS  read-only
     STATUS      current
     DESCRIPTION "Collection start time of the bin."
     ::= { cienaCesPmBasicPtpStatisticsBinEntry 1 }

   cienaCesPmBasicPtpStatsBinClearTime OBJECT-TYPE
     SYNTAX      DisplayString
     MAX-ACCESS  read-only
     STATUS      current
     DESCRIPTION "Collection clear time of the bin."
     ::= { cienaCesPmBasicPtpStatisticsBinEntry 2 }

   cienaCesPmBasicPtpStatsBinOprOch OBJECT-TYPE
     SYNTAX      PmInteger32Milli
     MAX-ACCESS  read-only
     STATUS      current
     DESCRIPTION "Optical Power Receive, Optical Channel."
     ::= { cienaCesPmBasicPtpStatisticsBinEntry 3 }

   cienaCesPmBasicPtpStatsBinOprnOch OBJECT-TYPE
     SYNTAX      Integer32
     MAX-ACCESS  read-only
     STATUS      current
     DESCRIPTION "Normalized Optical Power Receive, Optical Channel."
     ::= { cienaCesPmBasicPtpStatisticsBinEntry 4 }

   cienaCesPmBasicPtpStatsBinOprMinOch OBJECT-TYPE
     SYNTAX      PmInteger32Milli
     MAX-ACCESS  read-only
     STATUS      current
     DESCRIPTION "Minimum Optical Channel Power Receive."
     ::= { cienaCesPmBasicPtpStatisticsBinEntry 5 }

   cienaCesPmBasicPtpStatsBinOprMaxOch OBJECT-TYPE
     SYNTAX      PmInteger32Milli
     MAX-ACCESS  read-only
     STATUS      current
     DESCRIPTION "Maximum Optical Channel Power Receive."
     ::= { cienaCesPmBasicPtpStatisticsBinEntry 6 }

   cienaCesPmBasicPtpStatsBinOprAvgOch OBJECT-TYPE
     SYNTAX      PmInteger32Milli
     MAX-ACCESS  read-only
     STATUS      current
     DESCRIPTION "Average Optical Channel Power Receive."
     ::= { cienaCesPmBasicPtpStatisticsBinEntry 7 }

   cienaCesPmBasicPtpStatsBinOptOch OBJECT-TYPE
     SYNTAX      PmInteger32Milli
     MAX-ACCESS  read-only
     STATUS      current
     DESCRIPTION "Optical Power Transmit, Optical Channel."
     ::= { cienaCesPmBasicPtpStatisticsBinEntry 8 }

   cienaCesPmBasicPtpStatsBinOptMinOch OBJECT-TYPE
     SYNTAX      PmInteger32Milli
     MAX-ACCESS  read-only
     STATUS      current
     DESCRIPTION "Minimum Optical Channel Power Transmit."
     ::= { cienaCesPmBasicPtpStatisticsBinEntry 9 }

   cienaCesPmBasicPtpStatsBinOptMaxOch OBJECT-TYPE
     SYNTAX      PmInteger32Milli
     MAX-ACCESS  read-only
     STATUS      current
     DESCRIPTION "Maximum Optical Channel Power Transmit."
     ::= { cienaCesPmBasicPtpStatisticsBinEntry 10 }

   cienaCesPmBasicPtpStatsBinOptAvgOch OBJECT-TYPE
     SYNTAX      PmInteger32Milli
     MAX-ACCESS  read-only
     STATUS      current
     DESCRIPTION "Average Optical Channel Power Transmit."
     ::= { cienaCesPmBasicPtpStatisticsBinEntry 11 }

   cienaCesPmBasicPtpStatsBinOprOts OBJECT-TYPE
     SYNTAX      PmInteger32Milli
     MAX-ACCESS  read-only
     STATUS      current
     DESCRIPTION "Total Optical Power Receive, Optical Channel."
     ::= { cienaCesPmBasicPtpStatisticsBinEntry 12 }

   cienaCesPmBasicPtpStatsBinOprnOts OBJECT-TYPE
     SYNTAX      Integer32
     MAX-ACCESS  read-only
     STATUS      current
     DESCRIPTION "Total Normalized Optical Power Receive, Optical Channel."
     ::= { cienaCesPmBasicPtpStatisticsBinEntry 13 }

   cienaCesPmBasicPtpStatsBinOprMinOts OBJECT-TYPE
     SYNTAX      PmInteger32Milli
     MAX-ACCESS  read-only
     STATUS      current
     DESCRIPTION "Total Minimum Optical Channel Power Receive."
     ::= { cienaCesPmBasicPtpStatisticsBinEntry 14 }

   cienaCesPmBasicPtpStatsBinOprMaxOts OBJECT-TYPE
     SYNTAX      PmInteger32Milli
     MAX-ACCESS  read-only
     STATUS      current
     DESCRIPTION "Total Maximum Optical Channel Power Receive."
     ::= { cienaCesPmBasicPtpStatisticsBinEntry 15 }

   cienaCesPmBasicPtpStatsBinOprAvgOts OBJECT-TYPE
     SYNTAX      PmInteger32Milli
     MAX-ACCESS  read-only
     STATUS      current
     DESCRIPTION "Total Average Optical Channel Power Receive."
     ::= { cienaCesPmBasicPtpStatisticsBinEntry 16 }

   cienaCesPmBasicPtpStatsBinDgdAvgOch OBJECT-TYPE
     SYNTAX      Counter64
     MAX-ACCESS  read-only
     STATUS      current
     DESCRIPTION "Differential Group Delay (Average), Optical Channel."
     ::= { cienaCesPmBasicPtpStatisticsBinEntry 17 }

   cienaCesPmBasicPtpStatsBinDgdMaxOch OBJECT-TYPE
     SYNTAX      Counter64
     MAX-ACCESS  read-only
     STATUS      current
     DESCRIPTION "Differential Group Delay (Max), Optical Channel."
     ::= { cienaCesPmBasicPtpStatisticsBinEntry 18 }


   --BasicPtp Profile Stats, total statistics bin


   cienaCesPmBasicPtpTotalStatisticsBinTable OBJECT-TYPE
     SYNTAX      SEQUENCE OF CienaCesPmBasicPtpTotalStatisticsBinEntry
     MAX-ACCESS  not-accessible
     STATUS      current
     DESCRIPTION "The (conceptual) read-only table listing the bin statistics."
     ::= { cienaCesPmBasicPtpStats 6 }

   cienaCesPmBasicPtpTotalStatisticsBinEntry OBJECT-TYPE
     SYNTAX      CienaCesPmBasicPtpTotalStatisticsBinEntry
     MAX-ACCESS  not-accessible
     STATUS      current
     DESCRIPTION
           "An entry (conceptual row) in the cienaCesPmBasicPtpTotalStatisticsBinTable.
           This table lists the statistics for the total statistics bin of the PM instance."
     INDEX {cienaCesPmInstanceIndex}
     ::= { cienaCesPmBasicPtpTotalStatisticsBinTable 1 }

   CienaCesPmBasicPtpTotalStatisticsBinEntry ::=  SEQUENCE {
     cienaCesPmBasicPtpTotalStatsBinStartTime                  DisplayString,
     cienaCesPmBasicPtpTotalStatsBinOprOch                     PmInteger32Milli,
     cienaCesPmBasicPtpTotalStatsBinOprnOch                    Integer32,
     cienaCesPmBasicPtpTotalStatsBinOprMinOch                  PmInteger32Milli,
     cienaCesPmBasicPtpTotalStatsBinOprMaxOch                  PmInteger32Milli,
     cienaCesPmBasicPtpTotalStatsBinOprAvgOch                  PmInteger32Milli,
     cienaCesPmBasicPtpTotalStatsBinOptOch                     PmInteger32Milli,
     cienaCesPmBasicPtpTotalStatsBinOptMinOch                  PmInteger32Milli,
     cienaCesPmBasicPtpTotalStatsBinOptMaxOch                  PmInteger32Milli,
     cienaCesPmBasicPtpTotalStatsBinOptAvgOch                  PmInteger32Milli,
     cienaCesPmBasicPtpTotalStatsBinOprOts                     PmInteger32Milli,
     cienaCesPmBasicPtpTotalStatsBinOprnOts                    Integer32,
     cienaCesPmBasicPtpTotalStatsBinOprMinOts                  PmInteger32Milli,
     cienaCesPmBasicPtpTotalStatsBinOprMaxOts                  PmInteger32Milli,
     cienaCesPmBasicPtpTotalStatsBinOprAvgOts                  PmInteger32Milli,
     cienaCesPmBasicPtpTotalStatsBinDgdAvgOch                  Counter64,
     cienaCesPmBasicPtpTotalStatsBinDgdMaxOch                  Counter64
   }

   cienaCesPmBasicPtpTotalStatsBinStartTime OBJECT-TYPE
     SYNTAX      DisplayString
     MAX-ACCESS  read-only
     STATUS      current
     DESCRIPTION "Collection start time of the bin."
     ::= { cienaCesPmBasicPtpTotalStatisticsBinEntry 1 }

   cienaCesPmBasicPtpTotalStatsBinOprOch OBJECT-TYPE
     SYNTAX      PmInteger32Milli
     MAX-ACCESS  read-only
     STATUS      current
     DESCRIPTION "Optical Power Receive, Optical Channel."
     ::= { cienaCesPmBasicPtpTotalStatisticsBinEntry 2 }

   cienaCesPmBasicPtpTotalStatsBinOprnOch OBJECT-TYPE
     SYNTAX      Integer32
     MAX-ACCESS  read-only
     STATUS      current
     DESCRIPTION "Normalized Optical Power Receive, Optical Channel."
     ::= { cienaCesPmBasicPtpTotalStatisticsBinEntry 3 }

   cienaCesPmBasicPtpTotalStatsBinOprMinOch OBJECT-TYPE
     SYNTAX      PmInteger32Milli
     MAX-ACCESS  read-only
     STATUS      current
     DESCRIPTION "Minimum Optical Channel Power Receive."
     ::= { cienaCesPmBasicPtpTotalStatisticsBinEntry 4 }

   cienaCesPmBasicPtpTotalStatsBinOprMaxOch OBJECT-TYPE
     SYNTAX      PmInteger32Milli
     MAX-ACCESS  read-only
     STATUS      current
     DESCRIPTION "Maximum Optical Channel Power Receive."
     ::= { cienaCesPmBasicPtpTotalStatisticsBinEntry 5 }

   cienaCesPmBasicPtpTotalStatsBinOprAvgOch OBJECT-TYPE
     SYNTAX      PmInteger32Milli
     MAX-ACCESS  read-only
     STATUS      current
     DESCRIPTION "Average Optical Channel Power Receive."
     ::= { cienaCesPmBasicPtpTotalStatisticsBinEntry 6 }

   cienaCesPmBasicPtpTotalStatsBinOptOch OBJECT-TYPE
     SYNTAX      PmInteger32Milli
     MAX-ACCESS  read-only
     STATUS      current
     DESCRIPTION "Optical Power Transmit, Optical Channel."
     ::= { cienaCesPmBasicPtpTotalStatisticsBinEntry 7 }

   cienaCesPmBasicPtpTotalStatsBinOptMinOch OBJECT-TYPE
     SYNTAX      PmInteger32Milli
     MAX-ACCESS  read-only
     STATUS      current
     DESCRIPTION "Minimum Optical Channel Power Transmit."
     ::= { cienaCesPmBasicPtpTotalStatisticsBinEntry 8 }

   cienaCesPmBasicPtpTotalStatsBinOptMaxOch OBJECT-TYPE
     SYNTAX      PmInteger32Milli
     MAX-ACCESS  read-only
     STATUS      current
     DESCRIPTION "Maximum Optical Channel Power Transmit."
     ::= { cienaCesPmBasicPtpTotalStatisticsBinEntry 9 }

   cienaCesPmBasicPtpTotalStatsBinOptAvgOch OBJECT-TYPE
     SYNTAX      PmInteger32Milli
     MAX-ACCESS  read-only
     STATUS      current
     DESCRIPTION "Average Optical Channel Power Transmit."
     ::= { cienaCesPmBasicPtpTotalStatisticsBinEntry 10 }

   cienaCesPmBasicPtpTotalStatsBinOprOts OBJECT-TYPE
     SYNTAX      PmInteger32Milli
     MAX-ACCESS  read-only
     STATUS      current
     DESCRIPTION "Total Optical Power Receive, Optical Channel."
     ::= { cienaCesPmBasicPtpTotalStatisticsBinEntry 11 }

   cienaCesPmBasicPtpTotalStatsBinOprnOts OBJECT-TYPE
     SYNTAX      Integer32
     MAX-ACCESS  read-only
     STATUS      current
     DESCRIPTION "Total Normalized Optical Power Receive, Optical Channel."
     ::= { cienaCesPmBasicPtpTotalStatisticsBinEntry 12 }

   cienaCesPmBasicPtpTotalStatsBinOprMinOts OBJECT-TYPE
     SYNTAX      PmInteger32Milli
     MAX-ACCESS  read-only
     STATUS      current
     DESCRIPTION "Total Minimum Optical Channel Power Receive."
     ::= { cienaCesPmBasicPtpTotalStatisticsBinEntry 13 }

   cienaCesPmBasicPtpTotalStatsBinOprMaxOts OBJECT-TYPE
     SYNTAX      PmInteger32Milli
     MAX-ACCESS  read-only
     STATUS      current
     DESCRIPTION "Total Maximum Optical Channel Power Receive."
     ::= { cienaCesPmBasicPtpTotalStatisticsBinEntry 14 }

   cienaCesPmBasicPtpTotalStatsBinOprAvgOts OBJECT-TYPE
     SYNTAX      PmInteger32Milli
     MAX-ACCESS  read-only
     STATUS      current
     DESCRIPTION "Total Average Optical Channel Power Receive."
     ::= { cienaCesPmBasicPtpTotalStatisticsBinEntry 15 }

   cienaCesPmBasicPtpTotalStatsBinDgdAvgOch OBJECT-TYPE
     SYNTAX      Counter64
     MAX-ACCESS  read-only
     STATUS      current
     DESCRIPTION "Differential Group Delay (Average), Optical Channel."
     ::= { cienaCesPmBasicPtpTotalStatisticsBinEntry 16 }

   cienaCesPmBasicPtpTotalStatsBinDgdMaxOch OBJECT-TYPE
     SYNTAX      Counter64
     MAX-ACCESS  read-only
     STATUS      current
     DESCRIPTION "Differential Group Delay (Max), Optical Channel."
     ::= { cienaCesPmBasicPtpTotalStatisticsBinEntry 17 }



   --BasicOtu Profile Stats, history bins

   cienaCesPmBasicOtuHistoryBinTable OBJECT-TYPE
     SYNTAX      SEQUENCE OF CienaCesPmBasicOtuHistoryBinEntry
     MAX-ACCESS  not-accessible
     STATUS      current
     DESCRIPTION
           "The (conceptual) read-only table listing the bin statistics."  
     ::= { cienaCesPmBasicOtuStats 1 }

   cienaCesPmBasicOtuHistoryBinEntry OBJECT-TYPE
     SYNTAX      CienaCesPmBasicOtuHistoryBinEntry
     MAX-ACCESS  not-accessible
     STATUS      current
     DESCRIPTION
           "An entry (conceptual row) in the cienaCesPmBasicOtuHistoryBinTable.

           This table lists the statistics for all the history bins of the PM instance, as 
           specified by the bin-count object of the PM instance. History bins are displayed in the order
           so that #1 bin always represents the most recently completed bin and #2 - the bin previous to that
           and so on.

           The statistics are displayed for only the instances with valid bins (with start time >0), 
           as indicated by the operational state of the corresponding PM instance."  
     INDEX { cienaCesPmInstanceIndex, cienaCesPmBasicOtuHistoryBinIndex }
     ::= { cienaCesPmBasicOtuHistoryBinTable 1 }

   CienaCesPmBasicOtuHistoryBinEntry ::=  SEQUENCE {
     cienaCesPmBasicOtuHistoryBinIndex                         Unsigned32,
     cienaCesPmBasicOtuHistoryBinStartTime                     DisplayString,
     cienaCesPmBasicOtuHistoryBinEndTime                       DisplayString,
     cienaCesPmBasicOtuHistoryBinClearTime                     DisplayString,
     cienaCesPmBasicOtuHistoryBinDuration                      Unsigned32,   
     cienaCesPmBasicOtuHistoryBinState                         PmBinState,
     cienaCesPmBasicOtuHistoryBinFieldsUnsupported             PmProfileFieldMapBasicOtu,
     cienaCesPmBasicOtuHistoryBinFieldsInvalid                 PmProfileFieldMapBasicOtu,
     cienaCesPmBasicOtuHistoryBinCvOtu                         Counter64,
     cienaCesPmBasicOtuHistoryBinEsOtu                         Counter64,
     cienaCesPmBasicOtuHistoryBinSesOtu                        Counter64,
     cienaCesPmBasicOtuHistoryBinSefsOtu                       Counter64,
     cienaCesPmBasicOtuHistoryBinFecOtu                        Counter64,
     cienaCesPmBasicOtuHistoryBinHccsOtu                       Counter64,
     cienaCesPmBasicOtuHistoryBinPrfBerOtu                     PmCounter64Atto,
     cienaCesPmBasicOtuHistoryBinPrfBerMaxOtu                  PmCounter64Atto,
     cienaCesPmBasicOtuHistoryBinPfBerEOtu                     PmCounter64Atto,
     cienaCesPmBasicOtuHistoryBinQMinOtu                       PmInteger32Milli,
     cienaCesPmBasicOtuHistoryBinQMaxOtu                       PmInteger32Milli,
     cienaCesPmBasicOtuHistoryBinQAvgOtu                       PmInteger32Milli,
     cienaCesPmBasicOtuHistoryBinQStdevOtu                     PmInteger32Milli,
     cienaCesPmBasicOtuHistoryBinUncFecBlkOtu                  Counter64
   }

   cienaCesPmBasicOtuHistoryBinIndex OBJECT-TYPE
     SYNTAX      Unsigned32 (1..65535) 
     MAX-ACCESS  not-accessible
     STATUS      current
     DESCRIPTION "Bin number associated with the PmBasicOtuHistoryBin entry."
     ::= { cienaCesPmBasicOtuHistoryBinEntry 1 }

   cienaCesPmBasicOtuHistoryBinStartTime OBJECT-TYPE
     SYNTAX      DisplayString
     MAX-ACCESS  read-only
     STATUS      current
     DESCRIPTION "Collection start time of the bin."
     ::= { cienaCesPmBasicOtuHistoryBinEntry 2 }

   cienaCesPmBasicOtuHistoryBinEndTime OBJECT-TYPE
     SYNTAX      DisplayString
     MAX-ACCESS  read-only
     STATUS      current
     DESCRIPTION "Collection end time of the bin."
     ::= { cienaCesPmBasicOtuHistoryBinEntry 3 }

   cienaCesPmBasicOtuHistoryBinClearTime OBJECT-TYPE
     SYNTAX      DisplayString
     MAX-ACCESS  read-only
     STATUS      current
     DESCRIPTION "Clear time of the bin."
     ::= { cienaCesPmBasicOtuHistoryBinEntry 4 }

   cienaCesPmBasicOtuHistoryBinDuration OBJECT-TYPE
     SYNTAX      Unsigned32 (1..65535)  
     UNITS       "minutes"
     MAX-ACCESS  read-only
     STATUS      current
     DESCRIPTION "Duration of the bin."
     ::= { cienaCesPmBasicOtuHistoryBinEntry 5 }

   cienaCesPmBasicOtuHistoryBinState OBJECT-TYPE
     SYNTAX      PmBinState 
     MAX-ACCESS  read-only
     STATUS      current
     DESCRIPTION "State of the bin."
     ::= { cienaCesPmBasicOtuHistoryBinEntry 6 }

   cienaCesPmBasicOtuHistoryBinFieldsUnsupported OBJECT-TYPE
     SYNTAX      PmProfileFieldMapBasicOtu
     MAX-ACCESS  read-only
     STATUS      current
     DESCRIPTION "Mapping of the fields within this profile which have been declared
                  unsupported.  The value of any fields indicated by this object within
                  the same table row should be disregarded."
     ::= { cienaCesPmBasicOtuHistoryBinEntry 7 }

   cienaCesPmBasicOtuHistoryBinFieldsInvalid OBJECT-TYPE
     SYNTAX      PmProfileFieldMapBasicOtu
     MAX-ACCESS  read-only
     STATUS      current
     DESCRIPTION "Mapping of the fields within this profile which have been declared
                  invalid.  The value of any fields indicated by this object within
                  the same table row should be treated as untrustworthy."
     ::= { cienaCesPmBasicOtuHistoryBinEntry 8 }

   cienaCesPmBasicOtuHistoryBinCvOtu OBJECT-TYPE
     SYNTAX      Counter64
     MAX-ACCESS  read-only
     STATUS      current
     DESCRIPTION "Coding Violation, Optical Transport Unit."
     ::= { cienaCesPmBasicOtuHistoryBinEntry 9 }

   cienaCesPmBasicOtuHistoryBinEsOtu OBJECT-TYPE
     SYNTAX      Counter64
     MAX-ACCESS  read-only
     STATUS      current
     DESCRIPTION "Errored Seconds, Optical Transport Unit."
     ::= { cienaCesPmBasicOtuHistoryBinEntry 10 }

   cienaCesPmBasicOtuHistoryBinSesOtu OBJECT-TYPE
     SYNTAX      Counter64
     MAX-ACCESS  read-only
     STATUS      current
     DESCRIPTION "Severely Errored Seconds, Optical Transport Unit."
     ::= { cienaCesPmBasicOtuHistoryBinEntry 11 }

   cienaCesPmBasicOtuHistoryBinSefsOtu OBJECT-TYPE
     SYNTAX      Counter64
     MAX-ACCESS  read-only
     STATUS      current
     DESCRIPTION "Severely Errored Framed Seconds, Optical Transport Unit."
     ::= { cienaCesPmBasicOtuHistoryBinEntry 12 }

   cienaCesPmBasicOtuHistoryBinFecOtu OBJECT-TYPE
     SYNTAX      Counter64
     MAX-ACCESS  read-only
     STATUS      current
     DESCRIPTION "Forward Error Correction, Optical Transport Unit."
     ::= { cienaCesPmBasicOtuHistoryBinEntry 13 }

   cienaCesPmBasicOtuHistoryBinHccsOtu OBJECT-TYPE
     SYNTAX      Counter64
     MAX-ACCESS  read-only
     STATUS      current
     DESCRIPTION "High Correction Count Seconds, Optical Transport Unit."
     ::= { cienaCesPmBasicOtuHistoryBinEntry 14 }

   cienaCesPmBasicOtuHistoryBinPrfBerOtu OBJECT-TYPE
     SYNTAX      PmCounter64Atto
     MAX-ACCESS  read-only
     STATUS      current
     DESCRIPTION "Pre-FEC Bit Error Rate, Optical Transport Unit."
     ::= { cienaCesPmBasicOtuHistoryBinEntry 15 }

   cienaCesPmBasicOtuHistoryBinPrfBerMaxOtu OBJECT-TYPE
     SYNTAX      PmCounter64Atto
     MAX-ACCESS  read-only
     STATUS      current
     DESCRIPTION "Pre-FEC Bit Max Error Rate, Optical Transport Unit."
     ::= { cienaCesPmBasicOtuHistoryBinEntry 16 }

   cienaCesPmBasicOtuHistoryBinPfBerEOtu OBJECT-TYPE
     SYNTAX      PmCounter64Atto
     MAX-ACCESS  read-only
     STATUS      current
     DESCRIPTION "Post-FEC Bit Error Rate Estimate, Optical Transport Unit."
     ::= { cienaCesPmBasicOtuHistoryBinEntry 17 }

   cienaCesPmBasicOtuHistoryBinQMinOtu OBJECT-TYPE
     SYNTAX      PmInteger32Milli
     MAX-ACCESS  read-only
     STATUS      current
     DESCRIPTION "Quality Factor Minimum, Optical Transport Unit."
     ::= { cienaCesPmBasicOtuHistoryBinEntry 18 }

   cienaCesPmBasicOtuHistoryBinQMaxOtu OBJECT-TYPE
     SYNTAX      PmInteger32Milli
     MAX-ACCESS  read-only
     STATUS      current
     DESCRIPTION "Quality Factor Maximum, Optical Transport Unit."
     ::= { cienaCesPmBasicOtuHistoryBinEntry 19 }

   cienaCesPmBasicOtuHistoryBinQAvgOtu OBJECT-TYPE
     SYNTAX      PmInteger32Milli
     MAX-ACCESS  read-only
     STATUS      current
     DESCRIPTION "Quality Factor Average, Optical Transport Unit."
     ::= { cienaCesPmBasicOtuHistoryBinEntry 20 }

   cienaCesPmBasicOtuHistoryBinQStdevOtu OBJECT-TYPE
     SYNTAX      PmInteger32Milli
     MAX-ACCESS  read-only
     STATUS      current
     DESCRIPTION "Quality Factor Standard Deviation, Optical Transport Unit."
     ::= { cienaCesPmBasicOtuHistoryBinEntry 21 }

   cienaCesPmBasicOtuHistoryBinUncFecBlkOtu OBJECT-TYPE
     SYNTAX      Counter64
     MAX-ACCESS  read-only
     STATUS      current
     DESCRIPTION "Uncorrected FEC blocks, Optical Transport Unit."
     ::= { cienaCesPmBasicOtuHistoryBinEntry 22 }


   --BasicOtu Profile Stats, current bin

   cienaCesPmBasicOtuCurrBinTable OBJECT-TYPE
     SYNTAX      SEQUENCE OF CienaCesPmBasicOtuCurrBinEntry
     MAX-ACCESS  not-accessible
     STATUS      current
     DESCRIPTION "The (conceptual) read-only table listing the bin statistics."
     ::= { cienaCesPmBasicOtuStats 2 }

   cienaCesPmBasicOtuCurrBinEntry OBJECT-TYPE
     SYNTAX      CienaCesPmBasicOtuCurrBinEntry
     MAX-ACCESS  not-accessible
     STATUS      current
     DESCRIPTION
           "An entry (conceptual row) in the cienaCesPmBasicOtuCurrBinTable.
           This table lists the statistics for the current bin of the PM instance." 
     INDEX {cienaCesPmInstanceIndex}
     ::= { cienaCesPmBasicOtuCurrBinTable 1 }

   CienaCesPmBasicOtuCurrBinEntry ::=  SEQUENCE {
     cienaCesPmBasicOtuCurrBinStartTime                        DisplayString,
     cienaCesPmBasicOtuCurrBinClearedTime                      DisplayString,
     cienaCesPmBasicOtuCurrBinDuration                         Unsigned32,   
     cienaCesPmBasicOtuCurrBinState                            PmBinState,
     cienaCesPmBasicOtuCurrBinFieldsUnsupported                PmProfileFieldMapBasicOtu,
     cienaCesPmBasicOtuCurrBinFieldsInvalid                    PmProfileFieldMapBasicOtu,
     cienaCesPmBasicOtuCurrBinCvOtu                            Counter64,
     cienaCesPmBasicOtuCurrBinEsOtu                            Counter64,
     cienaCesPmBasicOtuCurrBinSesOtu                           Counter64,
     cienaCesPmBasicOtuCurrBinSefsOtu                          Counter64,
     cienaCesPmBasicOtuCurrBinFecOtu                           Counter64,
     cienaCesPmBasicOtuCurrBinHccsOtu                          Counter64,
     cienaCesPmBasicOtuCurrBinPrfBerOtu                        PmCounter64Atto,
     cienaCesPmBasicOtuCurrBinPrfBerMaxOtu                     PmCounter64Atto,
     cienaCesPmBasicOtuCurrBinPfBerEOtu                        PmCounter64Atto,
     cienaCesPmBasicOtuCurrBinQMinOtu                          PmInteger32Milli,
     cienaCesPmBasicOtuCurrBinQMaxOtu                          PmInteger32Milli,
     cienaCesPmBasicOtuCurrBinQAvgOtu                          PmInteger32Milli,
     cienaCesPmBasicOtuCurrBinQStdevOtu                        PmInteger32Milli,
     cienaCesPmBasicOtuCurrBinUncFecBlkOtu                     Counter64
  }

   cienaCesPmBasicOtuCurrBinStartTime OBJECT-TYPE
     SYNTAX      DisplayString
     MAX-ACCESS  read-only
     STATUS      current
     DESCRIPTION "Collection start time of the bin."
     ::= { cienaCesPmBasicOtuCurrBinEntry 1 }

   cienaCesPmBasicOtuCurrBinClearedTime OBJECT-TYPE
     SYNTAX      DisplayString
     MAX-ACCESS  read-only
     STATUS      current
     DESCRIPTION "Cleared time of the bin."
     ::= { cienaCesPmBasicOtuCurrBinEntry 2 }

  cienaCesPmBasicOtuCurrBinDuration OBJECT-TYPE
     SYNTAX      Unsigned32 (1..65535)
     UNITS       "minutes"
     MAX-ACCESS  read-only
     STATUS      current
     DESCRIPTION "Duration of the bin."
     ::= { cienaCesPmBasicOtuCurrBinEntry 3 }

   cienaCesPmBasicOtuCurrBinState OBJECT-TYPE
     SYNTAX      PmBinState
     MAX-ACCESS  read-only
     STATUS      current
     DESCRIPTION "State of the bin."
     ::= { cienaCesPmBasicOtuCurrBinEntry 4 }

   cienaCesPmBasicOtuCurrBinFieldsUnsupported OBJECT-TYPE
     SYNTAX      PmProfileFieldMapBasicOtu
     MAX-ACCESS  read-only
     STATUS      current
     DESCRIPTION "Mapping of the fields within this profile which have been declared
                  unsupported.  The value of any fields indicated by this object within
                  the same table row should be disregarded."
     ::= { cienaCesPmBasicOtuCurrBinEntry 5 }

   cienaCesPmBasicOtuCurrBinFieldsInvalid OBJECT-TYPE
     SYNTAX      PmProfileFieldMapBasicOtu
     MAX-ACCESS  read-only
     STATUS      current
     DESCRIPTION "Mapping of the fields within this profile which have been declared
                  invalid.  The value of any fields indicated by this object within
                  the same table row should be treated as untrustworthy."
     ::= { cienaCesPmBasicOtuCurrBinEntry 6 }

   cienaCesPmBasicOtuCurrBinCvOtu OBJECT-TYPE
     SYNTAX      Counter64
     MAX-ACCESS  read-only
     STATUS      current
     DESCRIPTION "Coding Violation, Optical Transport Unit."
     ::= { cienaCesPmBasicOtuCurrBinEntry 7 }

   cienaCesPmBasicOtuCurrBinEsOtu OBJECT-TYPE
     SYNTAX      Counter64
     MAX-ACCESS  read-only
     STATUS      current
     DESCRIPTION "Errored Seconds, Optical Transport Unit."
     ::= { cienaCesPmBasicOtuCurrBinEntry 8 }

   cienaCesPmBasicOtuCurrBinSesOtu OBJECT-TYPE
     SYNTAX      Counter64
     MAX-ACCESS  read-only
     STATUS      current
     DESCRIPTION "Severely Errored Seconds, Optical Transport Unit."
     ::= { cienaCesPmBasicOtuCurrBinEntry 9 }

   cienaCesPmBasicOtuCurrBinSefsOtu OBJECT-TYPE
     SYNTAX      Counter64
     MAX-ACCESS  read-only
     STATUS      current
     DESCRIPTION "Severely Errored Framed Seconds, Optical Transport Unit."
     ::= { cienaCesPmBasicOtuCurrBinEntry 10 }

   cienaCesPmBasicOtuCurrBinFecOtu OBJECT-TYPE
     SYNTAX      Counter64
     MAX-ACCESS  read-only
     STATUS      current
     DESCRIPTION "Forward Error Correction, Optical Transport Unit."
     ::= { cienaCesPmBasicOtuCurrBinEntry 11 }

   cienaCesPmBasicOtuCurrBinHccsOtu OBJECT-TYPE
     SYNTAX      Counter64
     MAX-ACCESS  read-only
     STATUS      current
     DESCRIPTION "High Correction Count Seconds, Optical Transport Unit."
     ::= { cienaCesPmBasicOtuCurrBinEntry 12 }

   cienaCesPmBasicOtuCurrBinPrfBerOtu OBJECT-TYPE
     SYNTAX      PmCounter64Atto
     MAX-ACCESS  read-only
     STATUS      current
     DESCRIPTION "Pre-FEC Bit Error Rate, Optical Transport Unit."
     ::= { cienaCesPmBasicOtuCurrBinEntry 13 }

   cienaCesPmBasicOtuCurrBinPrfBerMaxOtu OBJECT-TYPE
     SYNTAX      PmCounter64Atto
     MAX-ACCESS  read-only
     STATUS      current
     DESCRIPTION "Pre-FEC Bit Max Error Rate, Optical Transport Unit."
     ::= { cienaCesPmBasicOtuCurrBinEntry 14 }

   cienaCesPmBasicOtuCurrBinPfBerEOtu OBJECT-TYPE
     SYNTAX      PmCounter64Atto
     MAX-ACCESS  read-only
     STATUS      current
     DESCRIPTION "Post-FEC Bit Error Rate Estimate, Optical Transport Unit."
     ::= { cienaCesPmBasicOtuCurrBinEntry 15 }

   cienaCesPmBasicOtuCurrBinQMinOtu OBJECT-TYPE
     SYNTAX      PmInteger32Milli
     MAX-ACCESS  read-only
     STATUS      current
     DESCRIPTION "Quality Factor Minimum, Optical Transport Unit."
     ::= { cienaCesPmBasicOtuCurrBinEntry 16 }

   cienaCesPmBasicOtuCurrBinQMaxOtu OBJECT-TYPE
     SYNTAX      PmInteger32Milli
     MAX-ACCESS  read-only
     STATUS      current
     DESCRIPTION "Quality Factor Maximum, Optical Transport Unit."
     ::= { cienaCesPmBasicOtuCurrBinEntry 17 }

   cienaCesPmBasicOtuCurrBinQAvgOtu OBJECT-TYPE
     SYNTAX      PmInteger32Milli
     MAX-ACCESS  read-only
     STATUS      current
     DESCRIPTION "Quality Factor Average, Optical Transport Unit."
     ::= { cienaCesPmBasicOtuCurrBinEntry 18 }

   cienaCesPmBasicOtuCurrBinQStdevOtu OBJECT-TYPE
     SYNTAX      PmInteger32Milli
     MAX-ACCESS  read-only
     STATUS      current
     DESCRIPTION "Quality Factor Standard Deviation, Optical Transport Unit."
     ::= { cienaCesPmBasicOtuCurrBinEntry 19 }

   cienaCesPmBasicOtuCurrBinUncFecBlkOtu OBJECT-TYPE
     SYNTAX      Counter64
     MAX-ACCESS  read-only
     STATUS      current
     DESCRIPTION "Uncorrected FEC blocks, Optical Transport Unit."
     ::= { cienaCesPmBasicOtuCurrBinEntry 20 }


   --BasicOtu Profile Stats, current 24 hour bin

   cienaCesPmBasicOtuCurr24HBinTable OBJECT-TYPE
     SYNTAX      SEQUENCE OF CienaCesPmBasicOtuCurr24HBinEntry
     MAX-ACCESS  not-accessible
     STATUS      current
     DESCRIPTION "The (conceptual) read-only table listing the bin statistics."
     ::= { cienaCesPmBasicOtuStats 3 }

   cienaCesPmBasicOtuCurr24HBinEntry OBJECT-TYPE
     SYNTAX      CienaCesPmBasicOtuCurr24HBinEntry
     MAX-ACCESS  not-accessible
     STATUS      current
     DESCRIPTION
           "An entry (conceptual row) in the cienaCesPmBasicOtuCurr24HBinTable.

           This table lists the statistics for the current 24 Hours bin."
     INDEX {cienaCesPmInstanceIndex}
     ::= { cienaCesPmBasicOtuCurr24HBinTable 1 }

   CienaCesPmBasicOtuCurr24HBinEntry ::=  SEQUENCE {
     cienaCesPmBasicOtuCurr24HBinStartTime                     DisplayString,
     cienaCesPmBasicOtuCurr24HBinClearedTime                   DisplayString,
     cienaCesPmBasicOtuCurr24HBinDuration                      Unsigned32,
     cienaCesPmBasicOtuCurr24HBinState                         PmBinState,
     cienaCesPmBasicOtuCurr24HBinFieldsUnsupported             PmProfileFieldMapBasicOtu,
     cienaCesPmBasicOtuCurr24HBinFieldsInvalid                 PmProfileFieldMapBasicOtu,
     cienaCesPmBasicOtuCurr24HBinCvOtu                         Counter64,
     cienaCesPmBasicOtuCurr24HBinEsOtu                         Counter64,
     cienaCesPmBasicOtuCurr24HBinSesOtu                        Counter64,
     cienaCesPmBasicOtuCurr24HBinSefsOtu                       Counter64,
     cienaCesPmBasicOtuCurr24HBinFecOtu                        Counter64,
     cienaCesPmBasicOtuCurr24HBinHccsOtu                       Counter64,
     cienaCesPmBasicOtuCurr24HBinPrfBerOtu                     PmCounter64Atto,
     cienaCesPmBasicOtuCurr24HBinPrfBerMaxOtu                  PmCounter64Atto,
     cienaCesPmBasicOtuCurr24HBinPfBerEOtu                     PmCounter64Atto,
     cienaCesPmBasicOtuCurr24HBinQMinOtu                       PmInteger32Milli,
     cienaCesPmBasicOtuCurr24HBinQMaxOtu                       PmInteger32Milli,
     cienaCesPmBasicOtuCurr24HBinQAvgOtu                       PmInteger32Milli,
     cienaCesPmBasicOtuCurr24HBinQStdevOtu                     PmInteger32Milli,
     cienaCesPmBasicOtuCurr24HBinUncFecBlkOtu                  Counter64
   }

   cienaCesPmBasicOtuCurr24HBinStartTime OBJECT-TYPE
     SYNTAX      DisplayString
     MAX-ACCESS  read-only
     STATUS      current
     DESCRIPTION "Collection start time of the bin."
     ::= { cienaCesPmBasicOtuCurr24HBinEntry 1 }

    cienaCesPmBasicOtuCurr24HBinClearedTime OBJECT-TYPE
     SYNTAX      DisplayString
     MAX-ACCESS  read-only
     STATUS      current
     DESCRIPTION "Cleared time of the bin."
     ::= { cienaCesPmBasicOtuCurr24HBinEntry 2 }

   cienaCesPmBasicOtuCurr24HBinDuration OBJECT-TYPE
     SYNTAX      Unsigned32 (1..65535)
     UNITS       "minutes"
     MAX-ACCESS  read-only
     STATUS      current
     DESCRIPTION "Interval of the bin."
     ::= { cienaCesPmBasicOtuCurr24HBinEntry 3 }

   cienaCesPmBasicOtuCurr24HBinState OBJECT-TYPE
     SYNTAX      PmBinState
     MAX-ACCESS  read-only
     STATUS      current
     DESCRIPTION "State of the bin."
     ::= { cienaCesPmBasicOtuCurr24HBinEntry 4 }

   cienaCesPmBasicOtuCurr24HBinFieldsUnsupported OBJECT-TYPE
     SYNTAX      PmProfileFieldMapBasicOtu
     MAX-ACCESS  read-only
     STATUS      current
     DESCRIPTION "Mapping of the fields within this profile which have been declared
                  unsupported.  The value of any fields indicated by this object within
                  the same table row should be disregarded."
     ::= { cienaCesPmBasicOtuCurr24HBinEntry 5 }

   cienaCesPmBasicOtuCurr24HBinFieldsInvalid OBJECT-TYPE
     SYNTAX      PmProfileFieldMapBasicOtu
     MAX-ACCESS  read-only
     STATUS      current
     DESCRIPTION "Mapping of the fields within this profile which have been declared
                  invalid.  The value of any fields indicated by this object within
                  the same table row should be treated as untrustworthy."
     ::= { cienaCesPmBasicOtuCurr24HBinEntry 6 }

   cienaCesPmBasicOtuCurr24HBinCvOtu OBJECT-TYPE
     SYNTAX      Counter64
     MAX-ACCESS  read-only
     STATUS      current
     DESCRIPTION "Coding Violation, Optical Transport Unit."
     ::= { cienaCesPmBasicOtuCurr24HBinEntry 7 }

   cienaCesPmBasicOtuCurr24HBinEsOtu OBJECT-TYPE
     SYNTAX      Counter64
     MAX-ACCESS  read-only
     STATUS      current
     DESCRIPTION "Errored Seconds, Optical Transport Unit."
     ::= { cienaCesPmBasicOtuCurr24HBinEntry 8 }

   cienaCesPmBasicOtuCurr24HBinSesOtu OBJECT-TYPE
     SYNTAX      Counter64
     MAX-ACCESS  read-only
     STATUS      current
     DESCRIPTION "Severely Errored Seconds, Optical Transport Unit."
     ::= { cienaCesPmBasicOtuCurr24HBinEntry 9 }

   cienaCesPmBasicOtuCurr24HBinSefsOtu OBJECT-TYPE
     SYNTAX      Counter64
     MAX-ACCESS  read-only
     STATUS      current
     DESCRIPTION "Severely Errored Framed Seconds, Optical Transport Unit."
     ::= { cienaCesPmBasicOtuCurr24HBinEntry 10 }

   cienaCesPmBasicOtuCurr24HBinFecOtu OBJECT-TYPE
     SYNTAX      Counter64
     MAX-ACCESS  read-only
     STATUS      current
     DESCRIPTION "Forward Error Correction, Optical Transport Unit."
     ::= { cienaCesPmBasicOtuCurr24HBinEntry 11 }

   cienaCesPmBasicOtuCurr24HBinHccsOtu OBJECT-TYPE
     SYNTAX      Counter64
     MAX-ACCESS  read-only
     STATUS      current
     DESCRIPTION "High Correction Count Seconds, Optical Transport Unit."
     ::= { cienaCesPmBasicOtuCurr24HBinEntry 12 }

   cienaCesPmBasicOtuCurr24HBinPrfBerOtu OBJECT-TYPE
     SYNTAX      PmCounter64Atto
     MAX-ACCESS  read-only
     STATUS      current
     DESCRIPTION "Pre-FEC Bit Error Rate, Optical Transport Unit."
     ::= { cienaCesPmBasicOtuCurr24HBinEntry 13 }

   cienaCesPmBasicOtuCurr24HBinPrfBerMaxOtu OBJECT-TYPE
     SYNTAX      PmCounter64Atto
     MAX-ACCESS  read-only
     STATUS      current
     DESCRIPTION "Pre-FEC Bit Max Error Rate, Optical Transport Unit."
     ::= { cienaCesPmBasicOtuCurr24HBinEntry 14 }

   cienaCesPmBasicOtuCurr24HBinPfBerEOtu OBJECT-TYPE
     SYNTAX      PmCounter64Atto
     MAX-ACCESS  read-only
     STATUS      current
     DESCRIPTION "Post-FEC Bit Error Rate Estimate, Optical Transport Unit."
     ::= { cienaCesPmBasicOtuCurr24HBinEntry 15 }

   cienaCesPmBasicOtuCurr24HBinQMinOtu OBJECT-TYPE
     SYNTAX      PmInteger32Milli
     MAX-ACCESS  read-only
     STATUS      current
     DESCRIPTION "Quality Factor Minimum, Optical Transport Unit."
     ::= { cienaCesPmBasicOtuCurr24HBinEntry 16 }

   cienaCesPmBasicOtuCurr24HBinQMaxOtu OBJECT-TYPE
     SYNTAX      PmInteger32Milli
     MAX-ACCESS  read-only
     STATUS      current
     DESCRIPTION "Quality Factor Maximum, Optical Transport Unit."
     ::= { cienaCesPmBasicOtuCurr24HBinEntry 17 }

   cienaCesPmBasicOtuCurr24HBinQAvgOtu OBJECT-TYPE
     SYNTAX      PmInteger32Milli
     MAX-ACCESS  read-only
     STATUS      current
     DESCRIPTION "Quality Factor Average, Optical Transport Unit."
     ::= { cienaCesPmBasicOtuCurr24HBinEntry 18 }

   cienaCesPmBasicOtuCurr24HBinQStdevOtu OBJECT-TYPE
     SYNTAX      PmInteger32Milli
     MAX-ACCESS  read-only
     STATUS      current
     DESCRIPTION "Quality Factor Standard Deviation, Optical Transport Unit."
     ::= { cienaCesPmBasicOtuCurr24HBinEntry 19 }

   cienaCesPmBasicOtuCurr24HBinUncFecBlkOtu OBJECT-TYPE
     SYNTAX      Counter64
     MAX-ACCESS  read-only
     STATUS      current
     DESCRIPTION "Uncorrected FEC blocks, Optical Transport Unit."
     ::= { cienaCesPmBasicOtuCurr24HBinEntry 20 }


   --BasicOtu Profile Stats, history 24 hour bin

   cienaCesPmBasicOtuHist24HBinTable OBJECT-TYPE
     SYNTAX      SEQUENCE OF CienaCesPmBasicOtuHist24HBinEntry
     MAX-ACCESS  not-accessible
     STATUS      current
     DESCRIPTION "The (conceptual) read-only table listing the bin statistics."
     ::= { cienaCesPmBasicOtuStats 4 }

   cienaCesPmBasicOtuHist24HBinEntry OBJECT-TYPE
     SYNTAX      CienaCesPmBasicOtuHist24HBinEntry
     MAX-ACCESS  not-accessible
     STATUS      current
     DESCRIPTION
           "An entry (conceptual row) in the cienaCesPmBasicOtuHist24HBinTable.

           This table lists the statistics for the history 24 hours bin."
     INDEX {cienaCesPmInstanceIndex}
     ::= { cienaCesPmBasicOtuHist24HBinTable 1 }
        
   CienaCesPmBasicOtuHist24HBinEntry ::=  SEQUENCE {
     cienaCesPmBasicOtuHist24HBinStartTime                     DisplayString,
     cienaCesPmBasicOtuHist24HBinEndTime                       DisplayString,
     cienaCesPmBasicOtuHist24HBinClearTime                     DisplayString,
     cienaCesPmBasicOtuHist24HBinDuration                      Unsigned32,
     cienaCesPmBasicOtuHist24HBinState                         PmBinState,
     cienaCesPmBasicOtuHist24HBinFieldsUnsupported             PmProfileFieldMapBasicOtu,
     cienaCesPmBasicOtuHist24HBinFieldsInvalid                 PmProfileFieldMapBasicOtu,
     cienaCesPmBasicOtuHist24HBinCvOtu                         Counter64,
     cienaCesPmBasicOtuHist24HBinEsOtu                         Counter64,
     cienaCesPmBasicOtuHist24HBinSesOtu                        Counter64,
     cienaCesPmBasicOtuHist24HBinSefsOtu                       Counter64,
     cienaCesPmBasicOtuHist24HBinFecOtu                        Counter64,
     cienaCesPmBasicOtuHist24HBinHccsOtu                       Counter64,
     cienaCesPmBasicOtuHist24HBinPrfBerOtu                     PmCounter64Atto,
     cienaCesPmBasicOtuHist24HBinPrfBerMaxOtu                  PmCounter64Atto,
     cienaCesPmBasicOtuHist24HBinPfBerEOtu                     PmCounter64Atto,
     cienaCesPmBasicOtuHist24HBinQMinOtu                       PmInteger32Milli,
     cienaCesPmBasicOtuHist24HBinQMaxOtu                       PmInteger32Milli,
     cienaCesPmBasicOtuHist24HBinQAvgOtu                       PmInteger32Milli,
     cienaCesPmBasicOtuHist24HBinQStdevOtu                     PmInteger32Milli,
     cienaCesPmBasicOtuHist24HBinUncFecBlkOtu                  Counter64
   }

   cienaCesPmBasicOtuHist24HBinStartTime OBJECT-TYPE
     SYNTAX      DisplayString
     MAX-ACCESS  read-only
     STATUS      current
     DESCRIPTION "Collection start time of the bin."
     ::= { cienaCesPmBasicOtuHist24HBinEntry 1 }

   cienaCesPmBasicOtuHist24HBinEndTime OBJECT-TYPE
     SYNTAX      DisplayString
     MAX-ACCESS  read-only
     STATUS      current
     DESCRIPTION "Collection end time of the bin."
     ::= { cienaCesPmBasicOtuHist24HBinEntry 2 }

   cienaCesPmBasicOtuHist24HBinClearTime OBJECT-TYPE
     SYNTAX      DisplayString
     MAX-ACCESS  read-only
     STATUS      current
     DESCRIPTION "Collection clear time of the bin."
      ::= { cienaCesPmBasicOtuHist24HBinEntry 3 }
   
   cienaCesPmBasicOtuHist24HBinDuration OBJECT-TYPE
     SYNTAX      Unsigned32 (1..65535)
     UNITS       "minutes"
     MAX-ACCESS  read-only
     STATUS      current
     DESCRIPTION "Interval of the bin."
     ::= { cienaCesPmBasicOtuHist24HBinEntry 4 }

   cienaCesPmBasicOtuHist24HBinState OBJECT-TYPE
     SYNTAX      PmBinState
     MAX-ACCESS  read-only
     STATUS      current
     DESCRIPTION "State of the bin."
     ::= { cienaCesPmBasicOtuHist24HBinEntry 5 }

   cienaCesPmBasicOtuHist24HBinFieldsUnsupported OBJECT-TYPE
     SYNTAX      PmProfileFieldMapBasicOtu
     MAX-ACCESS  read-only
     STATUS      current
     DESCRIPTION "Mapping of the fields within this profile which have been declared
                  unsupported.  The value of any fields indicated by this object within
                  the same table row should be disregarded."
     ::= { cienaCesPmBasicOtuHist24HBinEntry 6 }

   cienaCesPmBasicOtuHist24HBinFieldsInvalid OBJECT-TYPE
     SYNTAX      PmProfileFieldMapBasicOtu
     MAX-ACCESS  read-only
     STATUS      current
     DESCRIPTION "Mapping of the fields within this profile which have been declared
                  invalid.  The value of any fields indicated by this object within
                  the same table row should be treated as untrustworthy."
     ::= { cienaCesPmBasicOtuHist24HBinEntry 7 }

   cienaCesPmBasicOtuHist24HBinCvOtu OBJECT-TYPE
     SYNTAX      Counter64
     MAX-ACCESS  read-only
     STATUS      current
     DESCRIPTION "Coding Violation, Optical Transport Unit."
     ::= { cienaCesPmBasicOtuHist24HBinEntry 8 }

   cienaCesPmBasicOtuHist24HBinEsOtu OBJECT-TYPE
     SYNTAX      Counter64
     MAX-ACCESS  read-only
     STATUS      current
     DESCRIPTION "Errored Seconds, Optical Transport Unit."
     ::= { cienaCesPmBasicOtuHist24HBinEntry 9 }

   cienaCesPmBasicOtuHist24HBinSesOtu OBJECT-TYPE
     SYNTAX      Counter64
     MAX-ACCESS  read-only
     STATUS      current
     DESCRIPTION "Severely Errored Seconds, Optical Transport Unit."
     ::= { cienaCesPmBasicOtuHist24HBinEntry 10 }

   cienaCesPmBasicOtuHist24HBinSefsOtu OBJECT-TYPE
     SYNTAX      Counter64
     MAX-ACCESS  read-only
     STATUS      current
     DESCRIPTION "Severely Errored Framed Seconds, Optical Transport Unit."
     ::= { cienaCesPmBasicOtuHist24HBinEntry 11 }

   cienaCesPmBasicOtuHist24HBinFecOtu OBJECT-TYPE
     SYNTAX      Counter64
     MAX-ACCESS  read-only
     STATUS      current
     DESCRIPTION "Forward Error Correction, Optical Transport Unit."
     ::= { cienaCesPmBasicOtuHist24HBinEntry 12 }

   cienaCesPmBasicOtuHist24HBinHccsOtu OBJECT-TYPE
     SYNTAX      Counter64
     MAX-ACCESS  read-only
     STATUS      current
     DESCRIPTION "High Correction Count Seconds, Optical Transport Unit."
     ::= { cienaCesPmBasicOtuHist24HBinEntry 13 }

   cienaCesPmBasicOtuHist24HBinPrfBerOtu OBJECT-TYPE
     SYNTAX      PmCounter64Atto
     MAX-ACCESS  read-only
     STATUS      current
     DESCRIPTION "Pre-FEC Bit Error Rate, Optical Transport Unit."
     ::= { cienaCesPmBasicOtuHist24HBinEntry 14 }

   cienaCesPmBasicOtuHist24HBinPrfBerMaxOtu OBJECT-TYPE
     SYNTAX      PmCounter64Atto
     MAX-ACCESS  read-only
     STATUS      current
     DESCRIPTION "Pre-FEC Bit Max Error Rate, Optical Transport Unit."
     ::= { cienaCesPmBasicOtuHist24HBinEntry 15 }

   cienaCesPmBasicOtuHist24HBinPfBerEOtu OBJECT-TYPE
     SYNTAX      PmCounter64Atto
     MAX-ACCESS  read-only
     STATUS      current
     DESCRIPTION "Post-FEC Bit Error Rate Estimate, Optical Transport Unit."
     ::= { cienaCesPmBasicOtuHist24HBinEntry 16 }

   cienaCesPmBasicOtuHist24HBinQMinOtu OBJECT-TYPE
     SYNTAX      PmInteger32Milli
     MAX-ACCESS  read-only
     STATUS      current
     DESCRIPTION "Quality Factor Minimum, Optical Transport Unit."
     ::= { cienaCesPmBasicOtuHist24HBinEntry 17 }

   cienaCesPmBasicOtuHist24HBinQMaxOtu OBJECT-TYPE
     SYNTAX      PmInteger32Milli
     MAX-ACCESS  read-only
     STATUS      current
     DESCRIPTION "Quality Factor Maximum, Optical Transport Unit."
     ::= { cienaCesPmBasicOtuHist24HBinEntry 18 }

   cienaCesPmBasicOtuHist24HBinQAvgOtu OBJECT-TYPE
     SYNTAX      PmInteger32Milli
     MAX-ACCESS  read-only
     STATUS      current
     DESCRIPTION "Quality Factor Average, Optical Transport Unit."
     ::= { cienaCesPmBasicOtuHist24HBinEntry 19 }

   cienaCesPmBasicOtuHist24HBinQStdevOtu OBJECT-TYPE
     SYNTAX      PmInteger32Milli
     MAX-ACCESS  read-only
     STATUS      current
     DESCRIPTION "Quality Factor Standard Deviation, Optical Transport Unit."
     ::= { cienaCesPmBasicOtuHist24HBinEntry 20 }

   cienaCesPmBasicOtuHist24HBinUncFecBlkOtu OBJECT-TYPE
     SYNTAX      Counter64
     MAX-ACCESS  read-only
     STATUS      current
     DESCRIPTION "Uncorrected FEC blocks, Optical Transport Unit."
     ::= { cienaCesPmBasicOtuHist24HBinEntry 21 }


   --BasicOtu Profile Stats, statistics bin

   cienaCesPmBasicOtuStatisticsBinTable OBJECT-TYPE
     SYNTAX      SEQUENCE OF CienaCesPmBasicOtuStatisticsBinEntry
     MAX-ACCESS  not-accessible
     STATUS      current
     DESCRIPTION "The (conceptual) read-only table listing the bin statistics."
     ::= { cienaCesPmBasicOtuStats 5 }

   cienaCesPmBasicOtuStatisticsBinEntry OBJECT-TYPE
     SYNTAX      CienaCesPmBasicOtuStatisticsBinEntry
     MAX-ACCESS  not-accessible
     STATUS      current
     DESCRIPTION
           "An entry (conceptual row) in the cienaCesPmBasicOtuStatisticsBinTable.
           This table lists the statistics for the statistics bin of the PM instance." 
     INDEX {cienaCesPmInstanceIndex}
     ::= { cienaCesPmBasicOtuStatisticsBinTable 1 }
        
   CienaCesPmBasicOtuStatisticsBinEntry ::=  SEQUENCE {
     cienaCesPmBasicOtuStatsBinStartTime                       DisplayString,
     cienaCesPmBasicOtuStatsBinClearTime                       DisplayString,
     cienaCesPmBasicOtuStatsBinCvOtu                           Counter64,
     cienaCesPmBasicOtuStatsBinEsOtu                           Counter64,
     cienaCesPmBasicOtuStatsBinSesOtu                          Counter64,
     cienaCesPmBasicOtuStatsBinSefsOtu                         Counter64,
     cienaCesPmBasicOtuStatsBinFecOtu                          Counter64,
     cienaCesPmBasicOtuStatsBinHccsOtu                         Counter64,
     cienaCesPmBasicOtuStatsBinPrfBerOtu                       PmCounter64Atto,
     cienaCesPmBasicOtuStatsBinPrfBerMaxOtu                    PmCounter64Atto,
     cienaCesPmBasicOtuStatsBinPfBerEOtu                       PmCounter64Atto,
     cienaCesPmBasicOtuStatsBinQMinOtu                         PmInteger32Milli,
     cienaCesPmBasicOtuStatsBinQMaxOtu                         PmInteger32Milli,
     cienaCesPmBasicOtuStatsBinQAvgOtu                         PmInteger32Milli,
     cienaCesPmBasicOtuStatsBinQStdevOtu                       PmInteger32Milli,
     cienaCesPmBasicOtuStatsBinUncFecBlkOtu                    Counter64
   }

   cienaCesPmBasicOtuStatsBinStartTime OBJECT-TYPE
     SYNTAX      DisplayString
     MAX-ACCESS  read-only
     STATUS      current
     DESCRIPTION "Collection start time of the bin."
     ::= { cienaCesPmBasicOtuStatisticsBinEntry 1 }

   cienaCesPmBasicOtuStatsBinClearTime OBJECT-TYPE
     SYNTAX      DisplayString
     MAX-ACCESS  read-only
     STATUS      current
     DESCRIPTION "Collection clear time of the bin."
     ::= { cienaCesPmBasicOtuStatisticsBinEntry 2 }

   cienaCesPmBasicOtuStatsBinCvOtu OBJECT-TYPE
     SYNTAX      Counter64
     MAX-ACCESS  read-only
     STATUS      current
     DESCRIPTION "Coding Violation, Optical Transport Unit."
     ::= { cienaCesPmBasicOtuStatisticsBinEntry 3 }

   cienaCesPmBasicOtuStatsBinEsOtu OBJECT-TYPE
     SYNTAX      Counter64
     MAX-ACCESS  read-only
     STATUS      current
     DESCRIPTION "Errored Seconds, Optical Transport Unit."
     ::= { cienaCesPmBasicOtuStatisticsBinEntry 4 }

   cienaCesPmBasicOtuStatsBinSesOtu OBJECT-TYPE
     SYNTAX      Counter64
     MAX-ACCESS  read-only
     STATUS      current
     DESCRIPTION "Severely Errored Seconds, Optical Transport Unit."
     ::= { cienaCesPmBasicOtuStatisticsBinEntry 5 }

   cienaCesPmBasicOtuStatsBinSefsOtu OBJECT-TYPE
     SYNTAX      Counter64
     MAX-ACCESS  read-only
     STATUS      current
     DESCRIPTION "Severely Errored Framed Seconds, Optical Transport Unit."
     ::= { cienaCesPmBasicOtuStatisticsBinEntry 6 }

   cienaCesPmBasicOtuStatsBinFecOtu OBJECT-TYPE
     SYNTAX      Counter64
     MAX-ACCESS  read-only
     STATUS      current
     DESCRIPTION "Forward Error Correction, Optical Transport Unit."
     ::= { cienaCesPmBasicOtuStatisticsBinEntry 7 }

   cienaCesPmBasicOtuStatsBinHccsOtu OBJECT-TYPE
     SYNTAX      Counter64
     MAX-ACCESS  read-only
     STATUS      current
     DESCRIPTION "High Correction Count Seconds, Optical Transport Unit."
     ::= { cienaCesPmBasicOtuStatisticsBinEntry 8 }

   cienaCesPmBasicOtuStatsBinPrfBerOtu OBJECT-TYPE
     SYNTAX      PmCounter64Atto
     MAX-ACCESS  read-only
     STATUS      current
     DESCRIPTION "Pre-FEC Bit Error Rate, Optical Transport Unit."
     ::= { cienaCesPmBasicOtuStatisticsBinEntry 9 }

   cienaCesPmBasicOtuStatsBinPrfBerMaxOtu OBJECT-TYPE
     SYNTAX      PmCounter64Atto
     MAX-ACCESS  read-only
     STATUS      current
     DESCRIPTION "Pre-FEC Bit Max Error Rate, Optical Transport Unit."
     ::= { cienaCesPmBasicOtuStatisticsBinEntry 10 }

   cienaCesPmBasicOtuStatsBinPfBerEOtu OBJECT-TYPE
     SYNTAX      PmCounter64Atto
     MAX-ACCESS  read-only
     STATUS      current
     DESCRIPTION "Post-FEC Bit Error Rate Estimate, Optical Transport Unit."
     ::= { cienaCesPmBasicOtuStatisticsBinEntry 11 }

   cienaCesPmBasicOtuStatsBinQMinOtu OBJECT-TYPE
     SYNTAX      PmInteger32Milli
     MAX-ACCESS  read-only
     STATUS      current
     DESCRIPTION "Quality Factor Minimum, Optical Transport Unit."
     ::= { cienaCesPmBasicOtuStatisticsBinEntry 12 }

   cienaCesPmBasicOtuStatsBinQMaxOtu OBJECT-TYPE
     SYNTAX      PmInteger32Milli
     MAX-ACCESS  read-only
     STATUS      current
     DESCRIPTION "Quality Factor Maximum, Optical Transport Unit."
     ::= { cienaCesPmBasicOtuStatisticsBinEntry 13 }

   cienaCesPmBasicOtuStatsBinQAvgOtu OBJECT-TYPE
     SYNTAX      PmInteger32Milli
     MAX-ACCESS  read-only
     STATUS      current
     DESCRIPTION "Quality Factor Average, Optical Transport Unit."
     ::= { cienaCesPmBasicOtuStatisticsBinEntry 14 }

   cienaCesPmBasicOtuStatsBinQStdevOtu OBJECT-TYPE
     SYNTAX      PmInteger32Milli
     MAX-ACCESS  read-only
     STATUS      current
     DESCRIPTION "Quality Factor Standard Deviation, Optical Transport Unit."
     ::= { cienaCesPmBasicOtuStatisticsBinEntry 15 }

   cienaCesPmBasicOtuStatsBinUncFecBlkOtu OBJECT-TYPE
     SYNTAX      Counter64
     MAX-ACCESS  read-only
     STATUS      current
     DESCRIPTION "Uncorrected FEC blocks, Optical Transport Unit."
     ::= { cienaCesPmBasicOtuStatisticsBinEntry 16 }


   --BasicOtu Profile Stats, total statistics bin


   cienaCesPmBasicOtuTotalStatisticsBinTable OBJECT-TYPE
     SYNTAX      SEQUENCE OF CienaCesPmBasicOtuTotalStatisticsBinEntry
     MAX-ACCESS  not-accessible
     STATUS      current
     DESCRIPTION "The (conceptual) read-only table listing the bin statistics."
     ::= { cienaCesPmBasicOtuStats 6 }

   cienaCesPmBasicOtuTotalStatisticsBinEntry OBJECT-TYPE
     SYNTAX      CienaCesPmBasicOtuTotalStatisticsBinEntry
     MAX-ACCESS  not-accessible
     STATUS      current
     DESCRIPTION
           "An entry (conceptual row) in the cienaCesPmBasicOtuTotalStatisticsBinTable.
           This table lists the statistics for the total statistics bin of the PM instance."
     INDEX {cienaCesPmInstanceIndex}
     ::= { cienaCesPmBasicOtuTotalStatisticsBinTable 1 }

   CienaCesPmBasicOtuTotalStatisticsBinEntry ::=  SEQUENCE {
     cienaCesPmBasicOtuTotalStatsBinStartTime                  DisplayString,
     cienaCesPmBasicOtuTotalStatsBinCvOtu                      Counter64,
     cienaCesPmBasicOtuTotalStatsBinEsOtu                      Counter64,
     cienaCesPmBasicOtuTotalStatsBinSesOtu                     Counter64,
     cienaCesPmBasicOtuTotalStatsBinSefsOtu                    Counter64,
     cienaCesPmBasicOtuTotalStatsBinFecOtu                     Counter64,
     cienaCesPmBasicOtuTotalStatsBinHccsOtu                    Counter64,
     cienaCesPmBasicOtuTotalStatsBinPrfBerOtu                  PmCounter64Atto,
     cienaCesPmBasicOtuTotalStatsBinPrfBerMaxOtu               PmCounter64Atto,
     cienaCesPmBasicOtuTotalStatsBinPfBerEOtu                  PmCounter64Atto,
     cienaCesPmBasicOtuTotalStatsBinQMinOtu                    PmInteger32Milli,
     cienaCesPmBasicOtuTotalStatsBinQMaxOtu                    PmInteger32Milli,
     cienaCesPmBasicOtuTotalStatsBinQAvgOtu                    PmInteger32Milli,
     cienaCesPmBasicOtuTotalStatsBinQStdevOtu                  PmInteger32Milli,
     cienaCesPmBasicOtuTotalStatsBinUncFecBlkOtu               Counter64
   }

   cienaCesPmBasicOtuTotalStatsBinStartTime OBJECT-TYPE
     SYNTAX      DisplayString
     MAX-ACCESS  read-only
     STATUS      current
     DESCRIPTION "Collection start time of the bin."
     ::= { cienaCesPmBasicOtuTotalStatisticsBinEntry 1 }

   cienaCesPmBasicOtuTotalStatsBinCvOtu OBJECT-TYPE
     SYNTAX      Counter64
     MAX-ACCESS  read-only
     STATUS      current
     DESCRIPTION "Coding Violation, Optical Transport Unit."
     ::= { cienaCesPmBasicOtuTotalStatisticsBinEntry 2 }

   cienaCesPmBasicOtuTotalStatsBinEsOtu OBJECT-TYPE
     SYNTAX      Counter64
     MAX-ACCESS  read-only
     STATUS      current
     DESCRIPTION "Errored Seconds, Optical Transport Unit."
     ::= { cienaCesPmBasicOtuTotalStatisticsBinEntry 3 }

   cienaCesPmBasicOtuTotalStatsBinSesOtu OBJECT-TYPE
     SYNTAX      Counter64
     MAX-ACCESS  read-only
     STATUS      current
     DESCRIPTION "Severely Errored Seconds, Optical Transport Unit."
     ::= { cienaCesPmBasicOtuTotalStatisticsBinEntry 4 }

   cienaCesPmBasicOtuTotalStatsBinSefsOtu OBJECT-TYPE
     SYNTAX      Counter64
     MAX-ACCESS  read-only
     STATUS      current
     DESCRIPTION "Severely Errored Framed Seconds, Optical Transport Unit."
     ::= { cienaCesPmBasicOtuTotalStatisticsBinEntry 5 }

   cienaCesPmBasicOtuTotalStatsBinFecOtu OBJECT-TYPE
     SYNTAX      Counter64
     MAX-ACCESS  read-only
     STATUS      current
     DESCRIPTION "Forward Error Correction, Optical Transport Unit."
     ::= { cienaCesPmBasicOtuTotalStatisticsBinEntry 6 }

   cienaCesPmBasicOtuTotalStatsBinHccsOtu OBJECT-TYPE
     SYNTAX      Counter64
     MAX-ACCESS  read-only
     STATUS      current
     DESCRIPTION "High Correction Count Seconds, Optical Transport Unit."
     ::= { cienaCesPmBasicOtuTotalStatisticsBinEntry 7 }

   cienaCesPmBasicOtuTotalStatsBinPrfBerOtu OBJECT-TYPE
     SYNTAX      PmCounter64Atto
     MAX-ACCESS  read-only
     STATUS      current
     DESCRIPTION "Pre-FEC Bit Error Rate, Optical Transport Unit."
     ::= { cienaCesPmBasicOtuTotalStatisticsBinEntry 8 }

   cienaCesPmBasicOtuTotalStatsBinPrfBerMaxOtu OBJECT-TYPE
     SYNTAX      PmCounter64Atto
     MAX-ACCESS  read-only
     STATUS      current
     DESCRIPTION "Pre-FEC Bit Max Error Rate, Optical Transport Unit."
     ::= { cienaCesPmBasicOtuTotalStatisticsBinEntry 9 }

   cienaCesPmBasicOtuTotalStatsBinPfBerEOtu OBJECT-TYPE
     SYNTAX      PmCounter64Atto
     MAX-ACCESS  read-only
     STATUS      current
     DESCRIPTION "Post-FEC Bit Error Rate Estimate, Optical Transport Unit."
     ::= { cienaCesPmBasicOtuTotalStatisticsBinEntry 10 }

   cienaCesPmBasicOtuTotalStatsBinQMinOtu OBJECT-TYPE
     SYNTAX      PmInteger32Milli
     MAX-ACCESS  read-only
     STATUS      current
     DESCRIPTION "Quality Factor Minimum, Optical Transport Unit."
     ::= { cienaCesPmBasicOtuTotalStatisticsBinEntry 11 }

   cienaCesPmBasicOtuTotalStatsBinQMaxOtu OBJECT-TYPE
     SYNTAX      PmInteger32Milli
     MAX-ACCESS  read-only
     STATUS      current
     DESCRIPTION "Quality Factor Maximum, Optical Transport Unit."
     ::= { cienaCesPmBasicOtuTotalStatisticsBinEntry 12 }

   cienaCesPmBasicOtuTotalStatsBinQAvgOtu OBJECT-TYPE
     SYNTAX      PmInteger32Milli
     MAX-ACCESS  read-only
     STATUS      current
     DESCRIPTION "Quality Factor Average, Optical Transport Unit."
     ::= { cienaCesPmBasicOtuTotalStatisticsBinEntry 13 }

   cienaCesPmBasicOtuTotalStatsBinQStdevOtu OBJECT-TYPE
     SYNTAX      PmInteger32Milli
     MAX-ACCESS  read-only
     STATUS      current
     DESCRIPTION "Quality Factor Standard Deviation, Optical Transport Unit."
     ::= { cienaCesPmBasicOtuTotalStatisticsBinEntry 14 }

   cienaCesPmBasicOtuTotalStatsBinUncFecBlkOtu OBJECT-TYPE
     SYNTAX      Counter64
     MAX-ACCESS  read-only
     STATUS      current
     DESCRIPTION "Uncorrected FEC blocks, Optical Transport Unit."
     ::= { cienaCesPmBasicOtuTotalStatisticsBinEntry 15 }


   --BasicOdu Profile Stats, history bins

   cienaCesPmBasicOduHistoryBinTable OBJECT-TYPE
     SYNTAX      SEQUENCE OF CienaCesPmBasicOduHistoryBinEntry
     MAX-ACCESS  not-accessible
     STATUS      current
     DESCRIPTION
           "The (conceptual) read-only table listing the bin statistics."  
     ::= { cienaCesPmBasicOduStats 1 }

   cienaCesPmBasicOduHistoryBinEntry OBJECT-TYPE
     SYNTAX      CienaCesPmBasicOduHistoryBinEntry
     MAX-ACCESS  not-accessible
     STATUS      current
     DESCRIPTION
           "An entry (conceptual row) in the cienaCesPmBasicOduHistoryBinTable.

           This table lists the statistics for all the history bins of the PM instance, as 
           specified by the bin-count object of the PM instance. History bins are displayed in the order
           so that #1 bin always represents the most recently completed bin and #2 - the bin previous to that
           and so on.

           The statistics are displayed for only the instances with valid bins (with start time >0), 
           as indicated by the operational state of the corresponding PM instance."  
     INDEX { cienaCesPmInstanceIndex, cienaCesPmBasicOduHistoryBinIndex }
     ::= { cienaCesPmBasicOduHistoryBinTable 1 }

   CienaCesPmBasicOduHistoryBinEntry ::=  SEQUENCE {
     cienaCesPmBasicOduHistoryBinIndex                         Unsigned32,
     cienaCesPmBasicOduHistoryBinStartTime                     DisplayString,
     cienaCesPmBasicOduHistoryBinEndTime                       DisplayString,
     cienaCesPmBasicOduHistoryBinClearTime                     DisplayString,
     cienaCesPmBasicOduHistoryBinDuration                      Unsigned32,   
     cienaCesPmBasicOduHistoryBinState                         PmBinState,
     cienaCesPmBasicOduHistoryBinFieldsUnsupported             PmProfileFieldMapBasicOdu,
     cienaCesPmBasicOduHistoryBinFieldsInvalid                 PmProfileFieldMapBasicOdu,
     cienaCesPmBasicOduHistoryBinCvOdu                         Counter64,
     cienaCesPmBasicOduHistoryBinEsOdu                         Counter64,
     cienaCesPmBasicOduHistoryBinSesOdu                        Counter64,
     cienaCesPmBasicOduHistoryBinUasOdu                        Counter64,
     cienaCesPmBasicOduHistoryBinFcOdu                         Counter64
   }

   cienaCesPmBasicOduHistoryBinIndex OBJECT-TYPE
     SYNTAX      Unsigned32 (1..65535) 
     MAX-ACCESS  not-accessible
     STATUS      current
     DESCRIPTION "Bin number associated with the PmBasicOduHistoryBin entry."
     ::= { cienaCesPmBasicOduHistoryBinEntry 1 }

   cienaCesPmBasicOduHistoryBinStartTime OBJECT-TYPE
     SYNTAX      DisplayString
     MAX-ACCESS  read-only
     STATUS      current
     DESCRIPTION "Collection start time of the bin."
     ::= { cienaCesPmBasicOduHistoryBinEntry 2 }

   cienaCesPmBasicOduHistoryBinEndTime OBJECT-TYPE
     SYNTAX      DisplayString
     MAX-ACCESS  read-only
     STATUS      current
     DESCRIPTION "Collection end time of the bin."
     ::= { cienaCesPmBasicOduHistoryBinEntry 3 }

   cienaCesPmBasicOduHistoryBinClearTime OBJECT-TYPE
     SYNTAX      DisplayString
     MAX-ACCESS  read-only
     STATUS      current
     DESCRIPTION "Clear time of the bin."
     ::= { cienaCesPmBasicOduHistoryBinEntry 4 }

   cienaCesPmBasicOduHistoryBinDuration OBJECT-TYPE
     SYNTAX      Unsigned32 (1..65535)  
     UNITS       "minutes"
     MAX-ACCESS  read-only
     STATUS      current
     DESCRIPTION "Duration of the bin."
     ::= { cienaCesPmBasicOduHistoryBinEntry 5 }

   cienaCesPmBasicOduHistoryBinState OBJECT-TYPE
     SYNTAX      PmBinState 
     MAX-ACCESS  read-only
     STATUS      current
     DESCRIPTION "State of the bin."
     ::= { cienaCesPmBasicOduHistoryBinEntry 6 }

   cienaCesPmBasicOduHistoryBinFieldsUnsupported OBJECT-TYPE
     SYNTAX      PmProfileFieldMapBasicOdu
     MAX-ACCESS  read-only
     STATUS      current
     DESCRIPTION "Mapping of the fields within this profile which have been declared
                  unsupported.  The value of any fields indicated by this object within
                  the same table row should be disregarded."
     ::= { cienaCesPmBasicOduHistoryBinEntry 7 }

   cienaCesPmBasicOduHistoryBinFieldsInvalid OBJECT-TYPE
     SYNTAX      PmProfileFieldMapBasicOdu
     MAX-ACCESS  read-only
     STATUS      current
     DESCRIPTION "Mapping of the fields within this profile which have been declared
                  invalid.  The value of any fields indicated by this object within
                  the same table row should be treated as untrustworthy."
     ::= { cienaCesPmBasicOduHistoryBinEntry 8 }

   cienaCesPmBasicOduHistoryBinCvOdu OBJECT-TYPE
     SYNTAX      Counter64
     MAX-ACCESS  read-only
     STATUS      current
     DESCRIPTION "Coding Violation, Optical Data Unit."
     ::= { cienaCesPmBasicOduHistoryBinEntry 9 }

   cienaCesPmBasicOduHistoryBinEsOdu OBJECT-TYPE
     SYNTAX      Counter64
     MAX-ACCESS  read-only
     STATUS      current
     DESCRIPTION "Errored Seconds, Optical Data Unit."
     ::= { cienaCesPmBasicOduHistoryBinEntry 10 }

   cienaCesPmBasicOduHistoryBinSesOdu OBJECT-TYPE
     SYNTAX      Counter64
     MAX-ACCESS  read-only
     STATUS      current
     DESCRIPTION "Severely Errored Seconds, Optical Data Unit."
     ::= { cienaCesPmBasicOduHistoryBinEntry 11 }

   cienaCesPmBasicOduHistoryBinUasOdu OBJECT-TYPE
     SYNTAX      Counter64
     MAX-ACCESS  read-only
     STATUS      current
     DESCRIPTION "Unavailable Seconds, Optical Data Unit."
     ::= { cienaCesPmBasicOduHistoryBinEntry 12 }

   cienaCesPmBasicOduHistoryBinFcOdu OBJECT-TYPE
     SYNTAX      Counter64
     MAX-ACCESS  read-only
     STATUS      current
     DESCRIPTION "Failure Count, Optical Data Unit."
     ::= { cienaCesPmBasicOduHistoryBinEntry 13 }


   --BasicOdu Profile Stats, current bin

   cienaCesPmBasicOduCurrBinTable OBJECT-TYPE
     SYNTAX      SEQUENCE OF CienaCesPmBasicOduCurrBinEntry
     MAX-ACCESS  not-accessible
     STATUS      current
     DESCRIPTION "The (conceptual) read-only table listing the bin statistics."
     ::= { cienaCesPmBasicOduStats 2 }

   cienaCesPmBasicOduCurrBinEntry OBJECT-TYPE
     SYNTAX      CienaCesPmBasicOduCurrBinEntry
     MAX-ACCESS  not-accessible
     STATUS      current
     DESCRIPTION
           "An entry (conceptual row) in the cienaCesPmBasicOduCurrBinTable.
           This table lists the statistics for the current bin of the PM instance." 
     INDEX {cienaCesPmInstanceIndex}
     ::= { cienaCesPmBasicOduCurrBinTable 1 }

   CienaCesPmBasicOduCurrBinEntry ::=  SEQUENCE {
     cienaCesPmBasicOduCurrBinStartTime                        DisplayString,
     cienaCesPmBasicOduCurrBinClearedTime                      DisplayString,
     cienaCesPmBasicOduCurrBinDuration                         Unsigned32,   
     cienaCesPmBasicOduCurrBinState                            PmBinState,
     cienaCesPmBasicOduCurrBinFieldsUnsupported                PmProfileFieldMapBasicOdu,
     cienaCesPmBasicOduCurrBinFieldsInvalid                    PmProfileFieldMapBasicOdu,
     cienaCesPmBasicOduCurrBinCvOdu                            Counter64,
     cienaCesPmBasicOduCurrBinEsOdu                            Counter64,
     cienaCesPmBasicOduCurrBinSesOdu                           Counter64,
     cienaCesPmBasicOduCurrBinUasOdu                           Counter64,
     cienaCesPmBasicOduCurrBinFcOdu                            Counter64
  }

   cienaCesPmBasicOduCurrBinStartTime OBJECT-TYPE
     SYNTAX      DisplayString
     MAX-ACCESS  read-only
     STATUS      current
     DESCRIPTION "Collection start time of the bin."
     ::= { cienaCesPmBasicOduCurrBinEntry 1 }

   cienaCesPmBasicOduCurrBinClearedTime OBJECT-TYPE
     SYNTAX      DisplayString
     MAX-ACCESS  read-only
     STATUS      current
     DESCRIPTION "Cleared time of the bin."
     ::= { cienaCesPmBasicOduCurrBinEntry 2 }

  cienaCesPmBasicOduCurrBinDuration OBJECT-TYPE
     SYNTAX      Unsigned32 (1..65535)
     UNITS       "minutes"
     MAX-ACCESS  read-only
     STATUS      current
     DESCRIPTION "Duration of the bin."
     ::= { cienaCesPmBasicOduCurrBinEntry 3 }

   cienaCesPmBasicOduCurrBinState OBJECT-TYPE
     SYNTAX      PmBinState
     MAX-ACCESS  read-only
     STATUS      current
     DESCRIPTION "State of the bin."
     ::= { cienaCesPmBasicOduCurrBinEntry 4 }

   cienaCesPmBasicOduCurrBinFieldsUnsupported OBJECT-TYPE
     SYNTAX      PmProfileFieldMapBasicOdu
     MAX-ACCESS  read-only
     STATUS      current
     DESCRIPTION "Mapping of the fields within this profile which have been declared
                  unsupported.  The value of any fields indicated by this object within
                  the same table row should be disregarded."
     ::= { cienaCesPmBasicOduCurrBinEntry 5 }

   cienaCesPmBasicOduCurrBinFieldsInvalid OBJECT-TYPE
     SYNTAX      PmProfileFieldMapBasicOdu
     MAX-ACCESS  read-only
     STATUS      current
     DESCRIPTION "Mapping of the fields within this profile which have been declared
                  invalid.  The value of any fields indicated by this object within
                  the same table row should be treated as untrustworthy."
     ::= { cienaCesPmBasicOduCurrBinEntry 6 }

   cienaCesPmBasicOduCurrBinCvOdu OBJECT-TYPE
     SYNTAX      Counter64
     MAX-ACCESS  read-only
     STATUS      current
     DESCRIPTION "Coding Violation, Optical Data Unit."
     ::= { cienaCesPmBasicOduCurrBinEntry 7 }

   cienaCesPmBasicOduCurrBinEsOdu OBJECT-TYPE
     SYNTAX      Counter64
     MAX-ACCESS  read-only
     STATUS      current
     DESCRIPTION "Errored Seconds, Optical Data Unit."
     ::= { cienaCesPmBasicOduCurrBinEntry 8 }

   cienaCesPmBasicOduCurrBinSesOdu OBJECT-TYPE
     SYNTAX      Counter64
     MAX-ACCESS  read-only
     STATUS      current
     DESCRIPTION "Severely Errored Seconds, Optical Data Unit."
     ::= { cienaCesPmBasicOduCurrBinEntry 9 }

   cienaCesPmBasicOduCurrBinUasOdu OBJECT-TYPE
     SYNTAX      Counter64
     MAX-ACCESS  read-only
     STATUS      current
     DESCRIPTION "Unavailable Seconds, Optical Data Unit."
     ::= { cienaCesPmBasicOduCurrBinEntry 10 }

   cienaCesPmBasicOduCurrBinFcOdu OBJECT-TYPE
     SYNTAX      Counter64
     MAX-ACCESS  read-only
     STATUS      current
     DESCRIPTION "Failure Count, Optical Data Unit."
     ::= { cienaCesPmBasicOduCurrBinEntry 11 }


   --BasicOdu Profile Stats, current 24 hour bin

   cienaCesPmBasicOduCurr24HBinTable OBJECT-TYPE
     SYNTAX      SEQUENCE OF CienaCesPmBasicOduCurr24HBinEntry
     MAX-ACCESS  not-accessible
     STATUS      current
     DESCRIPTION "The (conceptual) read-only table listing the bin statistics."
     ::= { cienaCesPmBasicOduStats 3 }

   cienaCesPmBasicOduCurr24HBinEntry OBJECT-TYPE
     SYNTAX      CienaCesPmBasicOduCurr24HBinEntry
     MAX-ACCESS  not-accessible
     STATUS      current
     DESCRIPTION
           "An entry (conceptual row) in the cienaCesPmBasicOduCurr24HBinTable.

           This table lists the statistics for the current 24 Hours bin."
     INDEX {cienaCesPmInstanceIndex}
     ::= { cienaCesPmBasicOduCurr24HBinTable 1 }

   CienaCesPmBasicOduCurr24HBinEntry ::=  SEQUENCE {
     cienaCesPmBasicOduCurr24HBinStartTime                     DisplayString,
     cienaCesPmBasicOduCurr24HBinClearedTime                   DisplayString,
     cienaCesPmBasicOduCurr24HBinDuration                      Unsigned32,
     cienaCesPmBasicOduCurr24HBinState                         PmBinState,
     cienaCesPmBasicOduCurr24HBinFieldsUnsupported             PmProfileFieldMapBasicOdu,
     cienaCesPmBasicOduCurr24HBinFieldsInvalid                 PmProfileFieldMapBasicOdu,
     cienaCesPmBasicOduCurr24HBinCvOdu                         Counter64,
     cienaCesPmBasicOduCurr24HBinEsOdu                         Counter64,
     cienaCesPmBasicOduCurr24HBinSesOdu                        Counter64,
     cienaCesPmBasicOduCurr24HBinUasOdu                        Counter64,
     cienaCesPmBasicOduCurr24HBinFcOdu                         Counter64
   }

   cienaCesPmBasicOduCurr24HBinStartTime OBJECT-TYPE
     SYNTAX      DisplayString
     MAX-ACCESS  read-only
     STATUS      current
     DESCRIPTION "Collection start time of the bin."
     ::= { cienaCesPmBasicOduCurr24HBinEntry 1 }

    cienaCesPmBasicOduCurr24HBinClearedTime OBJECT-TYPE
     SYNTAX      DisplayString
     MAX-ACCESS  read-only
     STATUS      current
     DESCRIPTION "Cleared time of the bin."
     ::= { cienaCesPmBasicOduCurr24HBinEntry 2 }

   cienaCesPmBasicOduCurr24HBinDuration OBJECT-TYPE
     SYNTAX      Unsigned32 (1..65535)
     UNITS       "minutes"
     MAX-ACCESS  read-only
     STATUS      current
     DESCRIPTION "Interval of the bin."
     ::= { cienaCesPmBasicOduCurr24HBinEntry 3 }

   cienaCesPmBasicOduCurr24HBinState OBJECT-TYPE
     SYNTAX      PmBinState
     MAX-ACCESS  read-only
     STATUS      current
     DESCRIPTION "State of the bin."
     ::= { cienaCesPmBasicOduCurr24HBinEntry 4 }

   cienaCesPmBasicOduCurr24HBinFieldsUnsupported OBJECT-TYPE
     SYNTAX      PmProfileFieldMapBasicOdu
     MAX-ACCESS  read-only
     STATUS      current
     DESCRIPTION "Mapping of the fields within this profile which have been declared
                  unsupported.  The value of any fields indicated by this object within
                  the same table row should be disregarded."
     ::= { cienaCesPmBasicOduCurr24HBinEntry 5 }

   cienaCesPmBasicOduCurr24HBinFieldsInvalid OBJECT-TYPE
     SYNTAX      PmProfileFieldMapBasicOdu
     MAX-ACCESS  read-only
     STATUS      current
     DESCRIPTION "Mapping of the fields within this profile which have been declared
                  invalid.  The value of any fields indicated by this object within
                  the same table row should be treated as untrustworthy."
     ::= { cienaCesPmBasicOduCurr24HBinEntry 6 }

   cienaCesPmBasicOduCurr24HBinCvOdu OBJECT-TYPE
     SYNTAX      Counter64
     MAX-ACCESS  read-only
     STATUS      current
     DESCRIPTION "Coding Violation, Optical Data Unit."
     ::= { cienaCesPmBasicOduCurr24HBinEntry 7 }

   cienaCesPmBasicOduCurr24HBinEsOdu OBJECT-TYPE
     SYNTAX      Counter64
     MAX-ACCESS  read-only
     STATUS      current
     DESCRIPTION "Errored Seconds, Optical Data Unit."
     ::= { cienaCesPmBasicOduCurr24HBinEntry 8 }

   cienaCesPmBasicOduCurr24HBinSesOdu OBJECT-TYPE
     SYNTAX      Counter64
     MAX-ACCESS  read-only
     STATUS      current
     DESCRIPTION "Severely Errored Seconds, Optical Data Unit."
     ::= { cienaCesPmBasicOduCurr24HBinEntry 9 }

   cienaCesPmBasicOduCurr24HBinUasOdu OBJECT-TYPE
     SYNTAX      Counter64
     MAX-ACCESS  read-only
     STATUS      current
     DESCRIPTION "Unavailable Seconds, Optical Data Unit."
     ::= { cienaCesPmBasicOduCurr24HBinEntry 10 }

   cienaCesPmBasicOduCurr24HBinFcOdu OBJECT-TYPE
     SYNTAX      Counter64
     MAX-ACCESS  read-only
     STATUS      current
     DESCRIPTION "Failure Count, Optical Data Unit."
     ::= { cienaCesPmBasicOduCurr24HBinEntry 11 }


   --BasicOdu Profile Stats, history 24 hour bin

   cienaCesPmBasicOduHist24HBinTable OBJECT-TYPE
     SYNTAX      SEQUENCE OF CienaCesPmBasicOduHist24HBinEntry
     MAX-ACCESS  not-accessible
     STATUS      current
     DESCRIPTION "The (conceptual) read-only table listing the bin statistics."
     ::= { cienaCesPmBasicOduStats 4 }

   cienaCesPmBasicOduHist24HBinEntry OBJECT-TYPE
     SYNTAX      CienaCesPmBasicOduHist24HBinEntry
     MAX-ACCESS  not-accessible
     STATUS      current
     DESCRIPTION
           "An entry (conceptual row) in the cienaCesPmBasicOduHist24HBinTable.

           This table lists the statistics for the history 24 hours bin."
     INDEX {cienaCesPmInstanceIndex}
     ::= { cienaCesPmBasicOduHist24HBinTable 1 }
        
   CienaCesPmBasicOduHist24HBinEntry ::=  SEQUENCE {
     cienaCesPmBasicOduHist24HBinStartTime                     DisplayString,
     cienaCesPmBasicOduHist24HBinEndTime                       DisplayString,
     cienaCesPmBasicOduHist24HBinClearTime                     DisplayString,
     cienaCesPmBasicOduHist24HBinDuration                      Unsigned32,
     cienaCesPmBasicOduHist24HBinState                         PmBinState,
     cienaCesPmBasicOduHist24HBinFieldsUnsupported             PmProfileFieldMapBasicOdu,
     cienaCesPmBasicOduHist24HBinFieldsInvalid                 PmProfileFieldMapBasicOdu,
     cienaCesPmBasicOduHist24HBinCvOdu                         Counter64,
     cienaCesPmBasicOduHist24HBinEsOdu                         Counter64,
     cienaCesPmBasicOduHist24HBinSesOdu                        Counter64,
     cienaCesPmBasicOduHist24HBinUasOdu                        Counter64,
     cienaCesPmBasicOduHist24HBinFcOdu                         Counter64
   }

   cienaCesPmBasicOduHist24HBinStartTime OBJECT-TYPE
     SYNTAX      DisplayString
     MAX-ACCESS  read-only
     STATUS      current
     DESCRIPTION "Collection start time of the bin."
     ::= { cienaCesPmBasicOduHist24HBinEntry 1 }

   cienaCesPmBasicOduHist24HBinEndTime OBJECT-TYPE
     SYNTAX      DisplayString
     MAX-ACCESS  read-only
     STATUS      current
     DESCRIPTION "Collection end time of the bin."
     ::= { cienaCesPmBasicOduHist24HBinEntry 2 }

   cienaCesPmBasicOduHist24HBinClearTime OBJECT-TYPE
     SYNTAX      DisplayString
     MAX-ACCESS  read-only
     STATUS      current
     DESCRIPTION "Collection clear time of the bin."
      ::= { cienaCesPmBasicOduHist24HBinEntry 3 }
   
   cienaCesPmBasicOduHist24HBinDuration OBJECT-TYPE
     SYNTAX      Unsigned32 (1..65535)
     UNITS       "minutes"
     MAX-ACCESS  read-only
     STATUS      current
     DESCRIPTION "Interval of the bin."
     ::= { cienaCesPmBasicOduHist24HBinEntry 4 }

  cienaCesPmBasicOduHist24HBinState OBJECT-TYPE
     SYNTAX      PmBinState
     MAX-ACCESS  read-only
     STATUS      current
     DESCRIPTION "State of the bin."
     ::= { cienaCesPmBasicOduHist24HBinEntry 5 }

   cienaCesPmBasicOduHist24HBinFieldsUnsupported OBJECT-TYPE
     SYNTAX      PmProfileFieldMapBasicOdu
     MAX-ACCESS  read-only
     STATUS      current
     DESCRIPTION "Mapping of the fields within this profile which have been declared
                  unsupported.  The value of any fields indicated by this object within
                  the same table row should be disregarded."
     ::= { cienaCesPmBasicOduHist24HBinEntry 6 }

   cienaCesPmBasicOduHist24HBinFieldsInvalid OBJECT-TYPE
     SYNTAX      PmProfileFieldMapBasicOdu
     MAX-ACCESS  read-only
     STATUS      current
     DESCRIPTION "Mapping of the fields within this profile which have been declared
                  invalid.  The value of any fields indicated by this object within
                  the same table row should be treated as untrustworthy."
     ::= { cienaCesPmBasicOduHist24HBinEntry 7 }

   cienaCesPmBasicOduHist24HBinCvOdu OBJECT-TYPE
     SYNTAX      Counter64
     MAX-ACCESS  read-only
     STATUS      current
     DESCRIPTION "Coding Violation, Optical Data Unit."
     ::= { cienaCesPmBasicOduHist24HBinEntry 8 }

   cienaCesPmBasicOduHist24HBinEsOdu OBJECT-TYPE
     SYNTAX      Counter64
     MAX-ACCESS  read-only
     STATUS      current
     DESCRIPTION "Errored Seconds, Optical Data Unit."
     ::= { cienaCesPmBasicOduHist24HBinEntry 9 }

   cienaCesPmBasicOduHist24HBinSesOdu OBJECT-TYPE
     SYNTAX      Counter64
     MAX-ACCESS  read-only
     STATUS      current
     DESCRIPTION "Severely Errored Seconds, Optical Data Unit."
     ::= { cienaCesPmBasicOduHist24HBinEntry 10 }

   cienaCesPmBasicOduHist24HBinUasOdu OBJECT-TYPE
     SYNTAX      Counter64
     MAX-ACCESS  read-only
     STATUS      current
     DESCRIPTION "Unavailable Seconds, Optical Data Unit."
     ::= { cienaCesPmBasicOduHist24HBinEntry 11 }

   cienaCesPmBasicOduHist24HBinFcOdu OBJECT-TYPE
     SYNTAX      Counter64
     MAX-ACCESS  read-only
     STATUS      current
     DESCRIPTION "Failure Count, Optical Data Unit."
     ::= { cienaCesPmBasicOduHist24HBinEntry 12 }


   --BasicOdu Profile Stats, statistics bin

   cienaCesPmBasicOduStatisticsBinTable OBJECT-TYPE
     SYNTAX      SEQUENCE OF CienaCesPmBasicOduStatisticsBinEntry
     MAX-ACCESS  not-accessible
     STATUS      current
     DESCRIPTION "The (conceptual) read-only table listing the bin statistics."
     ::= { cienaCesPmBasicOduStats 5 }

   cienaCesPmBasicOduStatisticsBinEntry OBJECT-TYPE
     SYNTAX      CienaCesPmBasicOduStatisticsBinEntry
     MAX-ACCESS  not-accessible
     STATUS      current
     DESCRIPTION
           "An entry (conceptual row) in the cienaCesPmBasicOduStatisticsBinTable.
           This table lists the statistics for the statistics bin of the PM instance." 
     INDEX {cienaCesPmInstanceIndex}
     ::= { cienaCesPmBasicOduStatisticsBinTable 1 }
        
   CienaCesPmBasicOduStatisticsBinEntry ::=  SEQUENCE {
     cienaCesPmBasicOduStatsBinStartTime                       DisplayString,
     cienaCesPmBasicOduStatsBinClearTime                       DisplayString,
     cienaCesPmBasicOduStatsBinCvOdu                           Counter64,
     cienaCesPmBasicOduStatsBinEsOdu                           Counter64,
     cienaCesPmBasicOduStatsBinSesOdu                          Counter64,
     cienaCesPmBasicOduStatsBinUasOdu                          Counter64,
     cienaCesPmBasicOduStatsBinFcOdu                           Counter64
   }

   cienaCesPmBasicOduStatsBinStartTime OBJECT-TYPE
     SYNTAX      DisplayString
     MAX-ACCESS  read-only
     STATUS      current
     DESCRIPTION "Collection start time of the bin."
     ::= { cienaCesPmBasicOduStatisticsBinEntry 1 }

   cienaCesPmBasicOduStatsBinClearTime OBJECT-TYPE
     SYNTAX      DisplayString
     MAX-ACCESS  read-only
     STATUS      current
     DESCRIPTION "Collection clear time of the bin."
     ::= { cienaCesPmBasicOduStatisticsBinEntry 2 }

   cienaCesPmBasicOduStatsBinCvOdu OBJECT-TYPE
     SYNTAX      Counter64
     MAX-ACCESS  read-only
     STATUS      current
     DESCRIPTION "Coding Violation, Optical Data Unit."
     ::= { cienaCesPmBasicOduStatisticsBinEntry 3 }

   cienaCesPmBasicOduStatsBinEsOdu OBJECT-TYPE
     SYNTAX      Counter64
     MAX-ACCESS  read-only
     STATUS      current
     DESCRIPTION "Errored Seconds, Optical Data Unit."
     ::= { cienaCesPmBasicOduStatisticsBinEntry 4 }

   cienaCesPmBasicOduStatsBinSesOdu OBJECT-TYPE
     SYNTAX      Counter64
     MAX-ACCESS  read-only
     STATUS      current
     DESCRIPTION "Severely Errored Seconds, Optical Data Unit."
     ::= { cienaCesPmBasicOduStatisticsBinEntry 5 }

   cienaCesPmBasicOduStatsBinUasOdu OBJECT-TYPE
     SYNTAX      Counter64
     MAX-ACCESS  read-only
     STATUS      current
     DESCRIPTION "Unavailable Seconds, Optical Data Unit."
     ::= { cienaCesPmBasicOduStatisticsBinEntry 6 }

   cienaCesPmBasicOduStatsBinFcOdu OBJECT-TYPE
     SYNTAX      Counter64
     MAX-ACCESS  read-only
     STATUS      current
     DESCRIPTION "Failure Count, Optical Data Unit."
     ::= { cienaCesPmBasicOduStatisticsBinEntry 7 }


   --BasicOdu Profile Stats, total statistics bin


   cienaCesPmBasicOduTotalStatisticsBinTable OBJECT-TYPE
     SYNTAX      SEQUENCE OF CienaCesPmBasicOduTotalStatisticsBinEntry
     MAX-ACCESS  not-accessible
     STATUS      current
     DESCRIPTION "The (conceptual) read-only table listing the bin statistics."
     ::= { cienaCesPmBasicOduStats 6 }

   cienaCesPmBasicOduTotalStatisticsBinEntry OBJECT-TYPE
     SYNTAX      CienaCesPmBasicOduTotalStatisticsBinEntry
     MAX-ACCESS  not-accessible
     STATUS      current
     DESCRIPTION
           "An entry (conceptual row) in the cienaCesPmBasicOduTotalStatisticsBinTable.
           This table lists the statistics for the total statistics bin of the PM instance."
     INDEX {cienaCesPmInstanceIndex}
     ::= { cienaCesPmBasicOduTotalStatisticsBinTable 1 }

   CienaCesPmBasicOduTotalStatisticsBinEntry ::=  SEQUENCE {
     cienaCesPmBasicOduTotalStatsBinStartTime                  DisplayString,
     cienaCesPmBasicOduTotalStatsBinCvOdu                      Counter64,
     cienaCesPmBasicOduTotalStatsBinEsOdu                      Counter64,
     cienaCesPmBasicOduTotalStatsBinSesOdu                     Counter64,
     cienaCesPmBasicOduTotalStatsBinUasOdu                     Counter64,
     cienaCesPmBasicOduTotalStatsBinFcOdu                      Counter64
   }

   cienaCesPmBasicOduTotalStatsBinStartTime OBJECT-TYPE
     SYNTAX      DisplayString
     MAX-ACCESS  read-only
     STATUS      current
     DESCRIPTION "Collection start time of the bin."
     ::= { cienaCesPmBasicOduTotalStatisticsBinEntry 1 }

   cienaCesPmBasicOduTotalStatsBinCvOdu OBJECT-TYPE
     SYNTAX      Counter64
     MAX-ACCESS  read-only
     STATUS      current
     DESCRIPTION "Coding Violation, Optical Data Unit."
     ::= { cienaCesPmBasicOduTotalStatisticsBinEntry 2 }

   cienaCesPmBasicOduTotalStatsBinEsOdu OBJECT-TYPE
     SYNTAX      Counter64
     MAX-ACCESS  read-only
     STATUS      current
     DESCRIPTION "Errored Seconds, Optical Data Unit."
     ::= { cienaCesPmBasicOduTotalStatisticsBinEntry 3 }

   cienaCesPmBasicOduTotalStatsBinSesOdu OBJECT-TYPE
     SYNTAX      Counter64
     MAX-ACCESS  read-only
     STATUS      current
     DESCRIPTION "Severely Errored Seconds, Optical Data Unit."
     ::= { cienaCesPmBasicOduTotalStatisticsBinEntry 4 }

   cienaCesPmBasicOduTotalStatsBinUasOdu OBJECT-TYPE
     SYNTAX      Counter64
     MAX-ACCESS  read-only
     STATUS      current
     DESCRIPTION "Unavailable Seconds, Optical Data Unit."
     ::= { cienaCesPmBasicOduTotalStatisticsBinEntry 5 }

   cienaCesPmBasicOduTotalStatsBinFcOdu OBJECT-TYPE
     SYNTAX      Counter64
     MAX-ACCESS  read-only
     STATUS      current
     DESCRIPTION "Failure Count, Optical Data Unit."
     ::= { cienaCesPmBasicOduTotalStatisticsBinEntry 6 }


   --TdmOCnPort Profile Stats, history bins

   cienaCesPmTdmOCnPortHistoryBinTable OBJECT-TYPE
     SYNTAX      SEQUENCE OF CienaCesPmTdmOCnPortHistoryBinEntry
     MAX-ACCESS  not-accessible
     STATUS      current
     DESCRIPTION
           "The (conceptual) read-only table listing the bin statistics."
     ::= { cienaCesPmTdmOCnPortStats 1 }

   cienaCesPmTdmOCnPortHistoryBinEntry OBJECT-TYPE
     SYNTAX      CienaCesPmTdmOCnPortHistoryBinEntry
     MAX-ACCESS  not-accessible
     STATUS      current
     DESCRIPTION
           "An entry (conceptual row) in the cienaPortPmTdmOCnPortHistoryBinTable.

           This table lists the statistics for all the history bins of the PM instance, as 
           specified by the bin-count object of the PM instance.  History bins are displayed in the order
           so that #1 bin always represents the most recently completed bin and #2 - the bin previous to that
           and so on.

           The statistics are displayed for only the instances with valid bins (with start time >0), 
           as indicated by the operational state of the corresponding PM instance."
     INDEX { cienaCesPmInstanceIndex, cienaCesPmTdmOCnPortHistoryBinIndex }
     ::= { cienaCesPmTdmOCnPortHistoryBinTable 1 }

   CienaCesPmTdmOCnPortHistoryBinEntry ::=  SEQUENCE {
     cienaCesPmTdmOCnPortHistoryBinIndex                             Unsigned32,
     cienaCesPmTdmOCnPortHistoryBinStartTime                         DisplayString,
     cienaCesPmTdmOCnPortHistoryBinEndTime                           DisplayString,
     cienaCesPmTdmOCnPortHistoryBinClearTime                         DisplayString,
     cienaCesPmTdmOCnPortHistoryBinDuration                          Unsigned32,
     cienaCesPmTdmOCnPortHistoryBinState                             PmBinState,
     cienaCesPmTdmOCnPortHistoryBinCvl                               Counter64,
     cienaCesPmTdmOCnPortHistoryBinEsl                               Counter64,
     cienaCesPmTdmOCnPortHistoryBinSesl                              Counter64,
     cienaCesPmTdmOCnPortHistoryBinAisl                              Counter64,
     cienaCesPmTdmOCnPortHistoryBinUasl                              Counter64,
     cienaCesPmTdmOCnPortHistoryBinEss                               Counter64,
     cienaCesPmTdmOCnPortHistoryBinSess                              Counter64,
     cienaCesPmTdmOCnPortHistoryBinLoss                              Counter64,
     cienaCesPmTdmOCnPortHistoryBinCvs                               Counter64,
     cienaCesPmTdmOCnPortHistoryBinSefss                             Counter64,
     cienaCesPmTdmOCnPortHistoryBinEb                                Counter64,
     cienaCesPmTdmOCnPortHistoryBinBbe                               Counter64,
     cienaCesPmTdmOCnPortHistoryBinEs                                Counter64,
     cienaCesPmTdmOCnPortHistoryBinSes                               Counter64,
     cienaCesPmTdmOCnPortHistoryBinAs                                Counter64,
     cienaCesPmTdmOCnPortHistoryBinUas                               Counter64,
     cienaCesPmTdmOCnPortHistoryBinTt                                Counter64
   }
   cienaCesPmTdmOCnPortHistoryBinIndex OBJECT-TYPE
     SYNTAX      Unsigned32 (1..65535)
     MAX-ACCESS  not-accessible
     STATUS      current
     DESCRIPTION "Bin number associated with the PmTdmOCnPortHistoryBin entry."
     ::= { cienaCesPmTdmOCnPortHistoryBinEntry 1 }

   cienaCesPmTdmOCnPortHistoryBinStartTime OBJECT-TYPE
     SYNTAX      DisplayString
     MAX-ACCESS  read-only
     STATUS      current
     DESCRIPTION "Collection start time of the bin."
     ::= { cienaCesPmTdmOCnPortHistoryBinEntry 2 }

   cienaCesPmTdmOCnPortHistoryBinEndTime OBJECT-TYPE
     SYNTAX      DisplayString
     MAX-ACCESS  read-only
     STATUS      current
     DESCRIPTION "Collection end time of the bin."
     ::= { cienaCesPmTdmOCnPortHistoryBinEntry 3 }

   cienaCesPmTdmOCnPortHistoryBinClearTime OBJECT-TYPE
     SYNTAX      DisplayString
     MAX-ACCESS  read-only
     STATUS      current
     DESCRIPTION "Collection clear time of the bin."
     ::= { cienaCesPmTdmOCnPortHistoryBinEntry 4 }

   cienaCesPmTdmOCnPortHistoryBinDuration OBJECT-TYPE
     SYNTAX      Unsigned32 (1..65535)
     UNITS       "minutes"
     MAX-ACCESS  read-only
     STATUS      current
     DESCRIPTION "Duration of the bin."
     ::= { cienaCesPmTdmOCnPortHistoryBinEntry 5 }

   cienaCesPmTdmOCnPortHistoryBinState OBJECT-TYPE
     SYNTAX      PmBinState
     MAX-ACCESS  read-only
     STATUS      current
     DESCRIPTION "State of the bin."
     ::= { cienaCesPmTdmOCnPortHistoryBinEntry 6 }

   cienaCesPmTdmOCnPortHistoryBinCvl OBJECT-TYPE
     SYNTAX      Counter64
     MAX-ACCESS  read-only
     STATUS      current
     DESCRIPTION "Line, Code violations."
     ::= { cienaCesPmTdmOCnPortHistoryBinEntry 7 }

   cienaCesPmTdmOCnPortHistoryBinEsl OBJECT-TYPE
     SYNTAX      Counter64
     MAX-ACCESS  read-only
     STATUS      current
     DESCRIPTION "Line, Errored seconds."
     ::= { cienaCesPmTdmOCnPortHistoryBinEntry 8 }

   cienaCesPmTdmOCnPortHistoryBinSesl OBJECT-TYPE
     SYNTAX      Counter64
     MAX-ACCESS  read-only
     STATUS      current
     DESCRIPTION "Line, Severely errored seconds."
     ::= { cienaCesPmTdmOCnPortHistoryBinEntry 9 }

   cienaCesPmTdmOCnPortHistoryBinAisl OBJECT-TYPE
     SYNTAX      Counter64
     MAX-ACCESS  read-only
     STATUS      current
     DESCRIPTION "Line, Alarm indication signal seconds."
     ::= { cienaCesPmTdmOCnPortHistoryBinEntry 10 }

   cienaCesPmTdmOCnPortHistoryBinUasl OBJECT-TYPE
     SYNTAX      Counter64
     MAX-ACCESS  read-only
     STATUS      current
     DESCRIPTION "Line, Unavailable seconds."
     ::= { cienaCesPmTdmOCnPortHistoryBinEntry 11 }

   cienaCesPmTdmOCnPortHistoryBinEss OBJECT-TYPE
     SYNTAX      Counter64
     MAX-ACCESS  read-only
     STATUS      current
     DESCRIPTION "Section, Errored seconds."
     ::= { cienaCesPmTdmOCnPortHistoryBinEntry 12 }

   cienaCesPmTdmOCnPortHistoryBinSess OBJECT-TYPE
     SYNTAX      Counter64
     MAX-ACCESS  read-only
     STATUS      current
     DESCRIPTION "Section, Severely errored seconds."
     ::= { cienaCesPmTdmOCnPortHistoryBinEntry 13 }

   cienaCesPmTdmOCnPortHistoryBinLoss OBJECT-TYPE
     SYNTAX      Counter64
     MAX-ACCESS  read-only
     STATUS      current
     DESCRIPTION "Section, Unavailable seconds."
     ::= { cienaCesPmTdmOCnPortHistoryBinEntry 14 }

   cienaCesPmTdmOCnPortHistoryBinCvs OBJECT-TYPE
     SYNTAX      Counter64
     MAX-ACCESS  read-only
     STATUS      current
     DESCRIPTION "Section, Code violation count."
     ::= { cienaCesPmTdmOCnPortHistoryBinEntry 15 }

   cienaCesPmTdmOCnPortHistoryBinSefss OBJECT-TYPE
     SYNTAX      Counter64
     MAX-ACCESS  read-only
     STATUS      current
     DESCRIPTION "Section, Severely errored frame seconds."
     ::= { cienaCesPmTdmOCnPortHistoryBinEntry 16 }

     cienaCesPmTdmOCnPortHistoryBinEb OBJECT-TYPE
     SYNTAX      Counter64
     MAX-ACCESS  read-only
     STATUS      current
     DESCRIPTION "Errored Blocks."
     ::= { cienaCesPmTdmOCnPortHistoryBinEntry 17 }

     cienaCesPmTdmOCnPortHistoryBinBbe OBJECT-TYPE
     SYNTAX      Counter64
     MAX-ACCESS  read-only
     STATUS      current
     DESCRIPTION "Backgroup Block Errors."
     ::= { cienaCesPmTdmOCnPortHistoryBinEntry 18 }

     cienaCesPmTdmOCnPortHistoryBinEs OBJECT-TYPE
     SYNTAX      Counter64
     MAX-ACCESS  read-only
     STATUS      current
     DESCRIPTION "Errored seconds."
     ::= { cienaCesPmTdmOCnPortHistoryBinEntry 19 }

     cienaCesPmTdmOCnPortHistoryBinSes OBJECT-TYPE
     SYNTAX      Counter64
     MAX-ACCESS  read-only
     STATUS      current
     DESCRIPTION "Severely Errored seconds."
     ::= { cienaCesPmTdmOCnPortHistoryBinEntry 20 }

     cienaCesPmTdmOCnPortHistoryBinAs OBJECT-TYPE
     SYNTAX      Counter64
     MAX-ACCESS  read-only
     STATUS      current
     DESCRIPTION "Available seconds."
     ::= { cienaCesPmTdmOCnPortHistoryBinEntry 21 }

     cienaCesPmTdmOCnPortHistoryBinUas OBJECT-TYPE
     SYNTAX      Counter64
     MAX-ACCESS  read-only
     STATUS      current
     DESCRIPTION "Unavailable seconds."
     ::= { cienaCesPmTdmOCnPortHistoryBinEntry 22 }

     cienaCesPmTdmOCnPortHistoryBinTt OBJECT-TYPE
     SYNTAX      Counter64
     MAX-ACCESS  read-only
     STATUS      current
     DESCRIPTION "Total Time seconds."
     ::= { cienaCesPmTdmOCnPortHistoryBinEntry 23 }


   --TdmOCnPort Profile Stats, current bin

   cienaCesPmTdmOCnPortCurrBinTable OBJECT-TYPE
     SYNTAX      SEQUENCE OF CienaCesPmTdmOCnPortCurrBinEntry
     MAX-ACCESS  not-accessible
     STATUS      current
     DESCRIPTION "The (conceptual) read-only table listing the bin statistics."
     ::= { cienaCesPmTdmOCnPortStats 2 }

   cienaCesPmTdmOCnPortCurrBinEntry OBJECT-TYPE
     SYNTAX      CienaCesPmTdmOCnPortCurrBinEntry
     MAX-ACCESS  not-accessible
     STATUS      current
     DESCRIPTION
           "An entry (conceptual row) in the cienaPortPmTdmOCnPortCurrBinTable.
           This table lists the statistics for the current bin of the PM instance."
     INDEX {cienaCesPmInstanceIndex}
     ::= { cienaCesPmTdmOCnPortCurrBinTable 1 }

   CienaCesPmTdmOCnPortCurrBinEntry ::=  SEQUENCE {
     cienaCesPmTdmOCnPortCurrBinStartTime                            DisplayString,
     cienaCesPmTdmOCnPortCurrBinClearTime                            DisplayString,
     cienaCesPmTdmOCnPortCurrBinDuration                             Unsigned32,
     cienaCesPmTdmOCnPortCurrBinState                                PmBinState,
     cienaCesPmTdmOCnPortCurrBinCvl                                  Counter64,
     cienaCesPmTdmOCnPortCurrBinEsl                                  Counter64,
     cienaCesPmTdmOCnPortCurrBinSesl                                 Counter64,
     cienaCesPmTdmOCnPortCurrBinAisl                                 Counter64,
     cienaCesPmTdmOCnPortCurrBinUasl                                 Counter64,
     cienaCesPmTdmOCnPortCurrBinEss                                  Counter64,
     cienaCesPmTdmOCnPortCurrBinSess                                 Counter64,
     cienaCesPmTdmOCnPortCurrBinLoss                                 Counter64,
     cienaCesPmTdmOCnPortCurrBinCvs                                  Counter64,
     cienaCesPmTdmOCnPortCurrBinSefss                                Counter64,
     cienaCesPmTdmOCnPortCurrBinEb                                   Counter64,
     cienaCesPmTdmOCnPortCurrBinBbe                                  Counter64,
     cienaCesPmTdmOCnPortCurrBinEs                                   Counter64,
     cienaCesPmTdmOCnPortCurrBinSes                                  Counter64,
     cienaCesPmTdmOCnPortCurrBinAs                                   Counter64,
     cienaCesPmTdmOCnPortCurrBinUas                                  Counter64,
     cienaCesPmTdmOCnPortCurrBinTt                                   Counter64
   }

   cienaCesPmTdmOCnPortCurrBinStartTime OBJECT-TYPE
     SYNTAX      DisplayString
     MAX-ACCESS  read-only
     STATUS      current
     DESCRIPTION "Collection start time of the bin."
     ::= { cienaCesPmTdmOCnPortCurrBinEntry 1 }

   cienaCesPmTdmOCnPortCurrBinClearTime OBJECT-TYPE
     SYNTAX      DisplayString
     MAX-ACCESS  read-only
     STATUS      current
     DESCRIPTION "Cleared time of the bin."
     ::= { cienaCesPmTdmOCnPortCurrBinEntry 2 }

   cienaCesPmTdmOCnPortCurrBinDuration OBJECT-TYPE
     SYNTAX      Unsigned32 (1..65535)
     UNITS       "minutes"
     MAX-ACCESS  read-only
     STATUS      current
     DESCRIPTION "Interval of the bin."
     ::= { cienaCesPmTdmOCnPortCurrBinEntry 3 }

   cienaCesPmTdmOCnPortCurrBinState OBJECT-TYPE
     SYNTAX      PmBinState
     MAX-ACCESS  read-only
     STATUS      current
     DESCRIPTION "State of the bin."
     ::= { cienaCesPmTdmOCnPortCurrBinEntry 4 }

   cienaCesPmTdmOCnPortCurrBinCvl OBJECT-TYPE
     SYNTAX      Counter64
     MAX-ACCESS  read-only
     STATUS      current
     DESCRIPTION "Line, Code violations."
     ::= { cienaCesPmTdmOCnPortCurrBinEntry 5 }

  cienaCesPmTdmOCnPortCurrBinEsl OBJECT-TYPE
     SYNTAX      Counter64
     MAX-ACCESS  read-only
     STATUS      current
     DESCRIPTION "Line, Errored seconds."
     ::= { cienaCesPmTdmOCnPortCurrBinEntry 6 }

   cienaCesPmTdmOCnPortCurrBinSesl OBJECT-TYPE
     SYNTAX      Counter64
     MAX-ACCESS  read-only
     STATUS      current
     DESCRIPTION "Line, Severely errored seconds."
     ::= { cienaCesPmTdmOCnPortCurrBinEntry 7 }

   cienaCesPmTdmOCnPortCurrBinAisl OBJECT-TYPE
     SYNTAX      Counter64
     MAX-ACCESS  read-only
     STATUS      current
     DESCRIPTION "Line, Alarm indication signal seconds."
     ::= { cienaCesPmTdmOCnPortCurrBinEntry 8 }

   cienaCesPmTdmOCnPortCurrBinUasl OBJECT-TYPE
     SYNTAX      Counter64
     MAX-ACCESS  read-only
     STATUS      current
     DESCRIPTION "Line, Unavailable seconds."
     ::= { cienaCesPmTdmOCnPortCurrBinEntry 9 }

   cienaCesPmTdmOCnPortCurrBinEss OBJECT-TYPE
     SYNTAX      Counter64
     MAX-ACCESS  read-only
     STATUS      current
     DESCRIPTION "Section, Errored seconds."
     ::= { cienaCesPmTdmOCnPortCurrBinEntry 10 }

   cienaCesPmTdmOCnPortCurrBinSess OBJECT-TYPE
     SYNTAX      Counter64
     MAX-ACCESS  read-only
     STATUS      current
     DESCRIPTION "Section, Severely errored seconds."
     ::= { cienaCesPmTdmOCnPortCurrBinEntry 11 }

   cienaCesPmTdmOCnPortCurrBinLoss OBJECT-TYPE
     SYNTAX      Counter64
     MAX-ACCESS  read-only
     STATUS      current
     DESCRIPTION "Section, Loss of signal seconds."
     ::= { cienaCesPmTdmOCnPortCurrBinEntry 12 }

   cienaCesPmTdmOCnPortCurrBinCvs OBJECT-TYPE
     SYNTAX      Counter64
     MAX-ACCESS  read-only
     STATUS      current
     DESCRIPTION "Section, Code violation count."
     ::= { cienaCesPmTdmOCnPortCurrBinEntry 13 }

   cienaCesPmTdmOCnPortCurrBinSefss OBJECT-TYPE
     SYNTAX      Counter64
     MAX-ACCESS  read-only
     STATUS      current
     DESCRIPTION "Section, Severely errored frame seconds."
     ::= { cienaCesPmTdmOCnPortCurrBinEntry 14 }

     cienaCesPmTdmOCnPortCurrBinEb OBJECT-TYPE
     SYNTAX      Counter64
     MAX-ACCESS  read-only
     STATUS      current
     DESCRIPTION "Errored Blocks."
     ::= { cienaCesPmTdmOCnPortCurrBinEntry 15 }

     cienaCesPmTdmOCnPortCurrBinBbe OBJECT-TYPE
     SYNTAX      Counter64
     MAX-ACCESS  read-only
     STATUS      current
     DESCRIPTION "Backgroup Block Errors."
     ::= { cienaCesPmTdmOCnPortCurrBinEntry 16 }

     cienaCesPmTdmOCnPortCurrBinEs OBJECT-TYPE
     SYNTAX      Counter64
     MAX-ACCESS  read-only
     STATUS      current
     DESCRIPTION "Errored seconds."
     ::= { cienaCesPmTdmOCnPortCurrBinEntry 17 }

     cienaCesPmTdmOCnPortCurrBinSes OBJECT-TYPE
     SYNTAX      Counter64
     MAX-ACCESS  read-only
     STATUS      current
     DESCRIPTION "Severely Errored seconds."
     ::= { cienaCesPmTdmOCnPortCurrBinEntry 18 }

     cienaCesPmTdmOCnPortCurrBinAs OBJECT-TYPE
     SYNTAX      Counter64
     MAX-ACCESS  read-only
     STATUS      current
     DESCRIPTION "Available seconds."
     ::= { cienaCesPmTdmOCnPortCurrBinEntry 19 }

     cienaCesPmTdmOCnPortCurrBinUas OBJECT-TYPE
     SYNTAX      Counter64
     MAX-ACCESS  read-only
     STATUS      current
     DESCRIPTION "Unavailable seconds."
     ::= { cienaCesPmTdmOCnPortCurrBinEntry 20 }

     cienaCesPmTdmOCnPortCurrBinTt OBJECT-TYPE
     SYNTAX      Counter64
     MAX-ACCESS  read-only
     STATUS      current
     DESCRIPTION "Total Time seconds."
     ::= { cienaCesPmTdmOCnPortCurrBinEntry 21 }

   --TdmOCnPort Profile Stats, current 24 hour bin
  
   cienaCesPmTdmOCnPortCurr24HBinTable OBJECT-TYPE
     SYNTAX      SEQUENCE OF CienaCesPmTdmOCnPortCurr24HBinEntry
     MAX-ACCESS  not-accessible
     STATUS      current
     DESCRIPTION "The (conceptual) read-only table listing the bin statistics."
     ::= { cienaCesPmTdmOCnPortStats 3 }

   cienaCesPmTdmOCnPortCurr24HBinEntry OBJECT-TYPE
     SYNTAX      CienaCesPmTdmOCnPortCurr24HBinEntry
     MAX-ACCESS  not-accessible
     STATUS      current
     DESCRIPTION
           "An entry (conceptual row) in the cienaPortPmTdmOCnPortCurr24HBinTable.
           This table lists the statistics for the current 24 hours bin."
     INDEX {cienaCesPmInstanceIndex }
     ::= { cienaCesPmTdmOCnPortCurr24HBinTable 1 }

   CienaCesPmTdmOCnPortCurr24HBinEntry ::=  SEQUENCE {
     cienaCesPmTdmOCnPortCurr24HBinStartTime                         DisplayString,
     cienaCesPmTdmOCnPortCurr24HBinClearTime                         DisplayString,
     cienaCesPmTdmOCnPortCurr24HBinDuration                          Unsigned32,
     cienaCesPmTdmOCnPortCurr24HBinState                             PmBinState,
     cienaCesPmTdmOCnPortCurr24HBinCvl                               Counter64,
     cienaCesPmTdmOCnPortCurr24HBinEsl                               Counter64,
     cienaCesPmTdmOCnPortCurr24HBinSesl                              Counter64,
     cienaCesPmTdmOCnPortCurr24HBinAisl                              Counter64,
     cienaCesPmTdmOCnPortCurr24HBinUasl                              Counter64,
     cienaCesPmTdmOCnPortCurr24HBinEss                               Counter64,
     cienaCesPmTdmOCnPortCurr24HBinSess                              Counter64,
     cienaCesPmTdmOCnPortCurr24HBinLoss                              Counter64,
     cienaCesPmTdmOCnPortCurr24HBinCvs                               Counter64,
     cienaCesPmTdmOCnPortCurr24HBinSefss                             Counter64,
     cienaCesPmTdmOCnPortCurr24HBinEb                                Counter64,
     cienaCesPmTdmOCnPortCurr24HBinBbe                               Counter64,
     cienaCesPmTdmOCnPortCurr24HBinEs                                Counter64,
     cienaCesPmTdmOCnPortCurr24HBinSes                               Counter64,
     cienaCesPmTdmOCnPortCurr24HBinAs                                Counter64,
     cienaCesPmTdmOCnPortCurr24HBinUas                               Counter64,
     cienaCesPmTdmOCnPortCurr24HBinTt                                Counter64
   } 

   cienaCesPmTdmOCnPortCurr24HBinStartTime OBJECT-TYPE
     SYNTAX      DisplayString
     MAX-ACCESS  read-only
     STATUS      current
     DESCRIPTION "Collection start time of the bin."
     ::= { cienaCesPmTdmOCnPortCurr24HBinEntry 1 }

   cienaCesPmTdmOCnPortCurr24HBinClearTime OBJECT-TYPE
     SYNTAX      DisplayString
     MAX-ACCESS  read-only
     STATUS      current
     DESCRIPTION "Cleared time of the bin."
     ::= { cienaCesPmTdmOCnPortCurr24HBinEntry 2 }

   cienaCesPmTdmOCnPortCurr24HBinDuration OBJECT-TYPE
     SYNTAX      Unsigned32 (1..65535)
     UNITS       "minutes"
     MAX-ACCESS  read-only
     STATUS      current
     DESCRIPTION "Duration of the bin."
     ::= { cienaCesPmTdmOCnPortCurr24HBinEntry 3 }

   cienaCesPmTdmOCnPortCurr24HBinState OBJECT-TYPE
     SYNTAX      PmBinState
     MAX-ACCESS  read-only
     STATUS      current
     DESCRIPTION "State of the bin."
     ::= { cienaCesPmTdmOCnPortCurr24HBinEntry 4 }

   cienaCesPmTdmOCnPortCurr24HBinCvl OBJECT-TYPE
     SYNTAX      Counter64
     MAX-ACCESS  read-only
     STATUS      current
     DESCRIPTION "Line, Code violations."
     ::= { cienaCesPmTdmOCnPortCurr24HBinEntry 5 }

   cienaCesPmTdmOCnPortCurr24HBinEsl OBJECT-TYPE
     SYNTAX      Counter64
     MAX-ACCESS  read-only
     STATUS      current
     DESCRIPTION "Line, Errored seconds."
     ::= { cienaCesPmTdmOCnPortCurr24HBinEntry 6 }

   cienaCesPmTdmOCnPortCurr24HBinSesl OBJECT-TYPE
     SYNTAX      Counter64
     MAX-ACCESS  read-only
     STATUS      current
     DESCRIPTION "Line, Severely errored seconds."
     ::= { cienaCesPmTdmOCnPortCurr24HBinEntry 7 }

   cienaCesPmTdmOCnPortCurr24HBinAisl OBJECT-TYPE
     SYNTAX      Counter64
     MAX-ACCESS  read-only
     STATUS      current
     DESCRIPTION "Line, Alarm indication signal seconds."
     ::= { cienaCesPmTdmOCnPortCurr24HBinEntry 8 }

   cienaCesPmTdmOCnPortCurr24HBinUasl OBJECT-TYPE
     SYNTAX      Counter64
     MAX-ACCESS  read-only
     STATUS      current
     DESCRIPTION "Line, Unavailable seconds."
     ::= { cienaCesPmTdmOCnPortCurr24HBinEntry 9 }

   cienaCesPmTdmOCnPortCurr24HBinEss OBJECT-TYPE
     SYNTAX      Counter64
     MAX-ACCESS  read-only
     STATUS      current
     DESCRIPTION "Section, Errored seconds."
     ::= { cienaCesPmTdmOCnPortCurr24HBinEntry 10 }

   cienaCesPmTdmOCnPortCurr24HBinSess OBJECT-TYPE
     SYNTAX      Counter64
     MAX-ACCESS  read-only
     STATUS      current
     DESCRIPTION "Section, Severely errored seconds."
     ::= { cienaCesPmTdmOCnPortCurr24HBinEntry 11 }

   cienaCesPmTdmOCnPortCurr24HBinLoss OBJECT-TYPE
     SYNTAX      Counter64
     MAX-ACCESS  read-only
     STATUS      current
     DESCRIPTION "Section, Loss of signal seconds."
     ::= { cienaCesPmTdmOCnPortCurr24HBinEntry 12 }

   cienaCesPmTdmOCnPortCurr24HBinCvs OBJECT-TYPE
     SYNTAX      Counter64
     MAX-ACCESS  read-only
     STATUS      current
     DESCRIPTION "Section, Code violation count."
     ::= { cienaCesPmTdmOCnPortCurr24HBinEntry 13 }

   cienaCesPmTdmOCnPortCurr24HBinSefss OBJECT-TYPE
     SYNTAX      Counter64
     MAX-ACCESS  read-only
     STATUS      current
     DESCRIPTION "Section, Severely errored frame seconds."
     ::= { cienaCesPmTdmOCnPortCurr24HBinEntry 14 }

     cienaCesPmTdmOCnPortCurr24HBinEb OBJECT-TYPE
     SYNTAX      Counter64
     MAX-ACCESS  read-only
     STATUS      current
     DESCRIPTION "Errored Blocks."
     ::= { cienaCesPmTdmOCnPortCurr24HBinEntry 15 }

     cienaCesPmTdmOCnPortCurr24HBinBbe OBJECT-TYPE
     SYNTAX      Counter64
     MAX-ACCESS  read-only
     STATUS      current
     DESCRIPTION "Backgroup Block Errors."
     ::= { cienaCesPmTdmOCnPortCurr24HBinEntry 16 }

     cienaCesPmTdmOCnPortCurr24HBinEs OBJECT-TYPE
     SYNTAX      Counter64
     MAX-ACCESS  read-only
     STATUS      current
     DESCRIPTION "Errored seconds."
     ::= { cienaCesPmTdmOCnPortCurr24HBinEntry 17 }

     cienaCesPmTdmOCnPortCurr24HBinSes OBJECT-TYPE
     SYNTAX      Counter64
     MAX-ACCESS  read-only
     STATUS      current
     DESCRIPTION "Severely Errored seconds."
     ::= { cienaCesPmTdmOCnPortCurr24HBinEntry 18 }

     cienaCesPmTdmOCnPortCurr24HBinAs OBJECT-TYPE
     SYNTAX      Counter64
     MAX-ACCESS  read-only
     STATUS      current
     DESCRIPTION "Available seconds."
     ::= { cienaCesPmTdmOCnPortCurr24HBinEntry 19 }

     cienaCesPmTdmOCnPortCurr24HBinUas OBJECT-TYPE
     SYNTAX      Counter64
     MAX-ACCESS  read-only
     STATUS      current
     DESCRIPTION "Unavailable seconds."
     ::= { cienaCesPmTdmOCnPortCurr24HBinEntry 20 }

     cienaCesPmTdmOCnPortCurr24HBinTt OBJECT-TYPE
     SYNTAX      Counter64
     MAX-ACCESS  read-only
     STATUS      current
     DESCRIPTION "Total Time seconds."
     ::= { cienaCesPmTdmOCnPortCurr24HBinEntry 21 }

   --TdmOCnPort Profile Stats, history 24 hour bin
  
   cienaCesPmTdmOCnPortHist24HBinTable OBJECT-TYPE
     SYNTAX      SEQUENCE OF CienaCesPmTdmOCnPortHist24HBinEntry
     MAX-ACCESS  not-accessible
     STATUS      current
     DESCRIPTION "The (conceptual) read-only Table listing the Bin Statistics."
     ::= { cienaCesPmTdmOCnPortStats 4 }

   cienaCesPmTdmOCnPortHist24HBinEntry OBJECT-TYPE
     SYNTAX      CienaCesPmTdmOCnPortHist24HBinEntry
     MAX-ACCESS  not-accessible
     STATUS      current
     DESCRIPTION
           "An entry (conceptual row) in the cienaPortPmTdmOCnPortHist24HBinTable.
           This table lists the statistics for the history 24 hours bin."
     INDEX {cienaCesPmInstanceIndex}
     ::= { cienaCesPmTdmOCnPortHist24HBinTable 1 }

   CienaCesPmTdmOCnPortHist24HBinEntry ::=  SEQUENCE {
     cienaCesPmTdmOCnPortHist24HBinStartTime                         DisplayString,
     cienaCesPmTdmOCnPortHist24HBinEndTime                           DisplayString,
     cienaCesPmTdmOCnPortHist24HBinClearTime                         DisplayString,
     cienaCesPmTdmOCnPortHist24HBinDuration                          Unsigned32,
     cienaCesPmTdmOCnPortHist24HBinState                             PmBinState,
     cienaCesPmTdmOCnPortHist24HBinCvl                               Counter64,
     cienaCesPmTdmOCnPortHist24HBinEsl                               Counter64,
     cienaCesPmTdmOCnPortHist24HBinSesl                              Counter64,
     cienaCesPmTdmOCnPortHist24HBinAisl                              Counter64,
     cienaCesPmTdmOCnPortHist24HBinUasl                              Counter64,
     cienaCesPmTdmOCnPortHist24HBinEss                               Counter64,
     cienaCesPmTdmOCnPortHist24HBinSess                              Counter64,
     cienaCesPmTdmOCnPortHist24HBinLoss                              Counter64,
     cienaCesPmTdmOCnPortHist24HBinCvs                               Counter64,
     cienaCesPmTdmOCnPortHist24HBinSefss                             Counter64,
     cienaCesPmTdmOCnPortHist24HBinEb                                Counter64,
     cienaCesPmTdmOCnPortHist24HBinBbe                               Counter64,
     cienaCesPmTdmOCnPortHist24HBinEs                                Counter64,
     cienaCesPmTdmOCnPortHist24HBinSes                               Counter64,
     cienaCesPmTdmOCnPortHist24HBinAs                                Counter64,
     cienaCesPmTdmOCnPortHist24HBinUas                               Counter64,
     cienaCesPmTdmOCnPortHist24HBinTt                                Counter64
   }

   cienaCesPmTdmOCnPortHist24HBinStartTime OBJECT-TYPE
     SYNTAX      DisplayString
     MAX-ACCESS  read-only
     STATUS      current
     DESCRIPTION "Collection start time of the bin."
     ::= { cienaCesPmTdmOCnPortHist24HBinEntry 1 }

   cienaCesPmTdmOCnPortHist24HBinEndTime OBJECT-TYPE
     SYNTAX      DisplayString
     MAX-ACCESS  read-only
     STATUS      current
     DESCRIPTION "Collection end time for the bin."
     ::= { cienaCesPmTdmOCnPortHist24HBinEntry 2 }

   cienaCesPmTdmOCnPortHist24HBinClearTime OBJECT-TYPE
     SYNTAX      DisplayString
     MAX-ACCESS  read-only
     STATUS      current
     DESCRIPTION "Cleared time of the bin."
     ::= { cienaCesPmTdmOCnPortHist24HBinEntry 3 }

   cienaCesPmTdmOCnPortHist24HBinDuration OBJECT-TYPE
     SYNTAX      Unsigned32 (1..65535)
     UNITS       "minutes"
     MAX-ACCESS  read-only
     STATUS      current
     DESCRIPTION "Duration of the bin."
     ::= { cienaCesPmTdmOCnPortHist24HBinEntry 4 }

   cienaCesPmTdmOCnPortHist24HBinState OBJECT-TYPE
     SYNTAX      PmBinState
     MAX-ACCESS  read-only
     STATUS      current
     DESCRIPTION "State of the bin."
     ::= { cienaCesPmTdmOCnPortHist24HBinEntry 5 }

   cienaCesPmTdmOCnPortHist24HBinCvl OBJECT-TYPE
     SYNTAX      Counter64
     MAX-ACCESS  read-only
     STATUS      current
     DESCRIPTION "Line, Code violations."
     ::= { cienaCesPmTdmOCnPortHist24HBinEntry 6 }

   cienaCesPmTdmOCnPortHist24HBinEsl OBJECT-TYPE
     SYNTAX      Counter64
     MAX-ACCESS  read-only
     STATUS      current
     DESCRIPTION "Line, Errored seconds."
     ::= { cienaCesPmTdmOCnPortHist24HBinEntry 7 }

   cienaCesPmTdmOCnPortHist24HBinSesl OBJECT-TYPE
     SYNTAX      Counter64
     MAX-ACCESS  read-only
     STATUS      current
     DESCRIPTION "Line, Severely errored seconds."
     ::= { cienaCesPmTdmOCnPortHist24HBinEntry 8 }

   cienaCesPmTdmOCnPortHist24HBinAisl OBJECT-TYPE
     SYNTAX      Counter64
     MAX-ACCESS  read-only
     STATUS      current
     DESCRIPTION "Line, Alarm indication signal seconds."
     ::= { cienaCesPmTdmOCnPortHist24HBinEntry 9 }

   cienaCesPmTdmOCnPortHist24HBinUasl OBJECT-TYPE
     SYNTAX      Counter64
     MAX-ACCESS  read-only
     STATUS      current
     DESCRIPTION "Line, Unavailable seconds."
     ::= { cienaCesPmTdmOCnPortHist24HBinEntry 10 }

   cienaCesPmTdmOCnPortHist24HBinEss OBJECT-TYPE
     SYNTAX      Counter64
     MAX-ACCESS  read-only
     STATUS      current
     DESCRIPTION "Section, Errored seconds."
     ::= { cienaCesPmTdmOCnPortHist24HBinEntry 11 }

   cienaCesPmTdmOCnPortHist24HBinSess OBJECT-TYPE
     SYNTAX      Counter64
     MAX-ACCESS  read-only
     STATUS      current
     DESCRIPTION "Section, Severely errored seconds."
     ::= { cienaCesPmTdmOCnPortHist24HBinEntry 12 }

   cienaCesPmTdmOCnPortHist24HBinLoss OBJECT-TYPE
     SYNTAX      Counter64
     MAX-ACCESS  read-only
     STATUS      current
     DESCRIPTION "Section, Loss of signal seconds."
     ::= { cienaCesPmTdmOCnPortHist24HBinEntry 13 }

   cienaCesPmTdmOCnPortHist24HBinCvs OBJECT-TYPE
     SYNTAX      Counter64
     MAX-ACCESS  read-only
     STATUS      current
     DESCRIPTION "Section, Code violation count."
     ::= { cienaCesPmTdmOCnPortHist24HBinEntry 14 }

   cienaCesPmTdmOCnPortHist24HBinSefss OBJECT-TYPE
     SYNTAX      Counter64
     MAX-ACCESS  read-only
     STATUS      current
     DESCRIPTION "Section, Severely errored frame seconds."
     ::= { cienaCesPmTdmOCnPortHist24HBinEntry 15 }

     cienaCesPmTdmOCnPortHist24HBinEb OBJECT-TYPE
     SYNTAX      Counter64
     MAX-ACCESS  read-only
     STATUS      current
     DESCRIPTION "Errored Blocks."
     ::= { cienaCesPmTdmOCnPortHist24HBinEntry 16 }

     cienaCesPmTdmOCnPortHist24HBinBbe OBJECT-TYPE
     SYNTAX      Counter64
     MAX-ACCESS  read-only
     STATUS      current
     DESCRIPTION "Backgroup Block Errors."
     ::= { cienaCesPmTdmOCnPortHist24HBinEntry 17 }

     cienaCesPmTdmOCnPortHist24HBinEs OBJECT-TYPE
     SYNTAX      Counter64
     MAX-ACCESS  read-only
     STATUS      current
     DESCRIPTION "Errored seconds."
     ::= { cienaCesPmTdmOCnPortHist24HBinEntry 18 }

     cienaCesPmTdmOCnPortHist24HBinSes OBJECT-TYPE
     SYNTAX      Counter64
     MAX-ACCESS  read-only
     STATUS      current
     DESCRIPTION "Severely Errored seconds."
     ::= { cienaCesPmTdmOCnPortHist24HBinEntry 19 }

     cienaCesPmTdmOCnPortHist24HBinAs OBJECT-TYPE
     SYNTAX      Counter64
     MAX-ACCESS  read-only
     STATUS      current
     DESCRIPTION "Available seconds."
     ::= { cienaCesPmTdmOCnPortHist24HBinEntry 20 }

     cienaCesPmTdmOCnPortHist24HBinUas OBJECT-TYPE
     SYNTAX      Counter64
     MAX-ACCESS  read-only
     STATUS      current
     DESCRIPTION "Unavailable seconds."
     ::= { cienaCesPmTdmOCnPortHist24HBinEntry 21 }

     cienaCesPmTdmOCnPortHist24HBinTt OBJECT-TYPE
     SYNTAX      Counter64
     MAX-ACCESS  read-only
     STATUS      current
     DESCRIPTION "Total Time seconds."
     ::= { cienaCesPmTdmOCnPortHist24HBinEntry 22 }

   --TdmOCnPort Profile Stats, statistics bin

   cienaCesPmTdmOCnPortStatisticsBinTable OBJECT-TYPE
     SYNTAX      SEQUENCE OF CienaCesPmTdmOCnPortStatisticsBinEntry
     MAX-ACCESS  not-accessible
     STATUS      current
     DESCRIPTION "The (conceptual) read-only table listing the bin statistics."
     ::= { cienaCesPmTdmOCnPortStats 5 }

   cienaCesPmTdmOCnPortStatisticsBinEntry OBJECT-TYPE
     SYNTAX      CienaCesPmTdmOCnPortStatisticsBinEntry
     MAX-ACCESS  not-accessible
     STATUS      current
     DESCRIPTION
           "An entry (conceptual row) in the cienaPortPmTdmOCnPortStatisticsBinTable.
           This table lists the statistics for the statistics bin of the PM instance."
     INDEX {cienaCesPmInstanceIndex}
     ::= { cienaCesPmTdmOCnPortStatisticsBinTable 1 }

   CienaCesPmTdmOCnPortStatisticsBinEntry ::=  SEQUENCE {
     cienaCesPmTdmOCnPortStatisticsBinStartTime                      DisplayString,
     cienaCesPmTdmOCnPortStatisticsBinClearTime                      DisplayString,
     cienaCesPmTdmOCnPortStatisticsBinCvl                            Counter64,
     cienaCesPmTdmOCnPortStatisticsBinEsl                            Counter64,
     cienaCesPmTdmOCnPortStatisticsBinSesl                           Counter64,
     cienaCesPmTdmOCnPortStatisticsBinAisl                           Counter64,
     cienaCesPmTdmOCnPortStatisticsBinUasl                           Counter64,   
     cienaCesPmTdmOCnPortStatisticsBinEss                            Counter64,
     cienaCesPmTdmOCnPortStatisticsBinSess                           Counter64, 
     cienaCesPmTdmOCnPortStatisticsBinLoss                           Counter64,
     cienaCesPmTdmOCnPortStatisticsBinCvs                            Counter64,
     cienaCesPmTdmOCnPortStatisticsBinSefss                          Counter64,
     cienaCesPmTdmOCnPortStatisticsBinEb                             Counter64,
     cienaCesPmTdmOCnPortStatisticsBinBbe                            Counter64,
     cienaCesPmTdmOCnPortStatisticsBinEs                             Counter64,
     cienaCesPmTdmOCnPortStatisticsBinSes                            Counter64,
     cienaCesPmTdmOCnPortStatisticsBinAs                             Counter64,
     cienaCesPmTdmOCnPortStatisticsBinUas                            Counter64,
     cienaCesPmTdmOCnPortStatisticsBinTt                             Counter64
   }          

   cienaCesPmTdmOCnPortStatisticsBinStartTime OBJECT-TYPE
     SYNTAX      DisplayString
     MAX-ACCESS  read-only
     STATUS      current
     DESCRIPTION "Collection start time of the bin."
     ::= { cienaCesPmTdmOCnPortStatisticsBinEntry 1 }

   cienaCesPmTdmOCnPortStatisticsBinClearTime OBJECT-TYPE
     SYNTAX      DisplayString
     MAX-ACCESS  read-only
     STATUS      current
     DESCRIPTION "Cleared time of the bin."
     ::= { cienaCesPmTdmOCnPortStatisticsBinEntry 2 }

   cienaCesPmTdmOCnPortStatisticsBinCvl OBJECT-TYPE
     SYNTAX      Counter64
     MAX-ACCESS  read-only
     STATUS      current
     DESCRIPTION "Line, Code violations."
     ::= { cienaCesPmTdmOCnPortStatisticsBinEntry 3 }

   cienaCesPmTdmOCnPortStatisticsBinEsl OBJECT-TYPE
     SYNTAX      Counter64
     MAX-ACCESS  read-only
     STATUS      current
     DESCRIPTION "Line, Errored seconds."
     ::= { cienaCesPmTdmOCnPortStatisticsBinEntry 4 }

   cienaCesPmTdmOCnPortStatisticsBinSesl OBJECT-TYPE
     SYNTAX      Counter64
     MAX-ACCESS  read-only
     STATUS      current
     DESCRIPTION "Line, Severely errored seconds."
     ::= { cienaCesPmTdmOCnPortStatisticsBinEntry 5 }

   cienaCesPmTdmOCnPortStatisticsBinAisl OBJECT-TYPE
     SYNTAX      Counter64
     MAX-ACCESS  read-only
     STATUS      current
     DESCRIPTION "Line, Alarm indication signal seconds."
     ::= { cienaCesPmTdmOCnPortStatisticsBinEntry 6 }

   cienaCesPmTdmOCnPortStatisticsBinUasl OBJECT-TYPE
     SYNTAX      Counter64
     MAX-ACCESS  read-only
     STATUS      current
     DESCRIPTION "Line, Unavailable seconds."
     ::= { cienaCesPmTdmOCnPortStatisticsBinEntry 7 }

  cienaCesPmTdmOCnPortStatisticsBinEss OBJECT-TYPE
     SYNTAX      Counter64
     MAX-ACCESS  read-only
     STATUS      current
     DESCRIPTION "Section, Errored seconds."
     ::= { cienaCesPmTdmOCnPortStatisticsBinEntry 8 }

   cienaCesPmTdmOCnPortStatisticsBinSess OBJECT-TYPE
     SYNTAX      Counter64
     MAX-ACCESS  read-only
     STATUS      current
     DESCRIPTION "Section, Severely errored seconds."
     ::= { cienaCesPmTdmOCnPortStatisticsBinEntry 9 }

   cienaCesPmTdmOCnPortStatisticsBinLoss OBJECT-TYPE
     SYNTAX      Counter64
     MAX-ACCESS  read-only
     STATUS      current
     DESCRIPTION "Section, Loss of signal seconds."
     ::= { cienaCesPmTdmOCnPortStatisticsBinEntry 10 }

   cienaCesPmTdmOCnPortStatisticsBinCvs OBJECT-TYPE
     SYNTAX      Counter64
     MAX-ACCESS  read-only
     STATUS      current
     DESCRIPTION "Section, Code violation count."
     ::= { cienaCesPmTdmOCnPortStatisticsBinEntry 11 }

   cienaCesPmTdmOCnPortStatisticsBinSefss OBJECT-TYPE
     SYNTAX      Counter64
     MAX-ACCESS  read-only
     STATUS      current
     DESCRIPTION "Section, Severely errored frame seconds."
     ::= { cienaCesPmTdmOCnPortStatisticsBinEntry 12 }

     cienaCesPmTdmOCnPortStatisticsBinEb OBJECT-TYPE
     SYNTAX      Counter64
     MAX-ACCESS  read-only
     STATUS      current
     DESCRIPTION "Errored Blocks."
     ::= { cienaCesPmTdmOCnPortStatisticsBinEntry 13 }

     cienaCesPmTdmOCnPortStatisticsBinBbe OBJECT-TYPE
     SYNTAX      Counter64
     MAX-ACCESS  read-only
     STATUS      current
     DESCRIPTION "Backgroup Block Errors."
     ::= { cienaCesPmTdmOCnPortStatisticsBinEntry 14 }

     cienaCesPmTdmOCnPortStatisticsBinEs OBJECT-TYPE
     SYNTAX      Counter64
     MAX-ACCESS  read-only
     STATUS      current
     DESCRIPTION "Errored seconds."
     ::= { cienaCesPmTdmOCnPortStatisticsBinEntry 15 }

     cienaCesPmTdmOCnPortStatisticsBinSes OBJECT-TYPE
     SYNTAX      Counter64
     MAX-ACCESS  read-only
     STATUS      current
     DESCRIPTION "Severely Errored seconds."
     ::= { cienaCesPmTdmOCnPortStatisticsBinEntry 16 }

     cienaCesPmTdmOCnPortStatisticsBinAs OBJECT-TYPE
     SYNTAX      Counter64
     MAX-ACCESS  read-only
     STATUS      current
     DESCRIPTION "Available seconds."
     ::= { cienaCesPmTdmOCnPortStatisticsBinEntry 17 }

     cienaCesPmTdmOCnPortStatisticsBinUas OBJECT-TYPE
     SYNTAX      Counter64
     MAX-ACCESS  read-only
     STATUS      current
     DESCRIPTION "Unavailable seconds."
     ::= { cienaCesPmTdmOCnPortStatisticsBinEntry 18 }

     cienaCesPmTdmOCnPortStatisticsBinTt OBJECT-TYPE
     SYNTAX      Counter64
     MAX-ACCESS  read-only
     STATUS      current
     DESCRIPTION "Total Time seconds."
     ::= { cienaCesPmTdmOCnPortStatisticsBinEntry 19 }

   --TdmOCnPort Profile Stats, total statistics bin

   cienaCesPmTdmOCnPortTotalStatisticsBinTable OBJECT-TYPE
     SYNTAX      SEQUENCE OF CienaCesPmTdmOCnPortTotalStatisticsBinEntry
     MAX-ACCESS  not-accessible
     STATUS      current
     DESCRIPTION "The (conceptual) read-only table listing the bin statistics."
     ::= { cienaCesPmTdmOCnPortStats 6 }

   cienaCesPmTdmOCnPortTotalStatisticsBinEntry OBJECT-TYPE
     SYNTAX      CienaCesPmTdmOCnPortTotalStatisticsBinEntry
     MAX-ACCESS  not-accessible
     STATUS      current
     DESCRIPTION
           "An entry (conceptual row) in the cienaPortPmTdmOCnPortTotalStatisticsBinTable.
           This table lists the statistics for the total statistics bin of the PM instance."
     INDEX {cienaCesPmInstanceIndex}
     ::= { cienaCesPmTdmOCnPortTotalStatisticsBinTable 1 }

   CienaCesPmTdmOCnPortTotalStatisticsBinEntry ::=  SEQUENCE {
     cienaCesPmTdmOCnPortTotalStatisticsBinStartTime                 DisplayString,
     cienaCesPmTdmOCnPortTotalStatisticsBinCvl                       Counter64,
     cienaCesPmTdmOCnPortTotalStatisticsBinEsl                       Counter64,
     cienaCesPmTdmOCnPortTotalStatisticsBinSesl                      Counter64,
     cienaCesPmTdmOCnPortTotalStatisticsBinAisl                      Counter64,
     cienaCesPmTdmOCnPortTotalStatisticsBinUasl                      Counter64,   
     cienaCesPmTdmOCnPortTotalStatisticsBinEss                       Counter64,
     cienaCesPmTdmOCnPortTotalStatisticsBinSess                      Counter64, 
     cienaCesPmTdmOCnPortTotalStatisticsBinLoss                      Counter64,
     cienaCesPmTdmOCnPortTotalStatisticsBinCvs                       Counter64,
     cienaCesPmTdmOCnPortTotalStatisticsBinSefss                     Counter64,
     cienaCesPmTdmOCnPortTotalStatisticsBinEb                        Counter64,
     cienaCesPmTdmOCnPortTotalStatisticsBinBbe                       Counter64,
     cienaCesPmTdmOCnPortTotalStatisticsBinEs                        Counter64,
     cienaCesPmTdmOCnPortTotalStatisticsBinSes                       Counter64,
     cienaCesPmTdmOCnPortTotalStatisticsBinAs                        Counter64,
     cienaCesPmTdmOCnPortTotalStatisticsBinUas                       Counter64,
     cienaCesPmTdmOCnPortTotalStatisticsBinTt                        Counter64
   }          

   cienaCesPmTdmOCnPortTotalStatisticsBinStartTime OBJECT-TYPE
     SYNTAX      DisplayString
     MAX-ACCESS  read-only
     STATUS      current
     DESCRIPTION "Collection start time of the bin."
     ::= { cienaCesPmTdmOCnPortTotalStatisticsBinEntry 1 }

   cienaCesPmTdmOCnPortTotalStatisticsBinCvl OBJECT-TYPE
     SYNTAX      Counter64
     MAX-ACCESS  read-only
     STATUS      current
     DESCRIPTION "Line, Code violations."
     ::= { cienaCesPmTdmOCnPortTotalStatisticsBinEntry 2 }

   cienaCesPmTdmOCnPortTotalStatisticsBinEsl OBJECT-TYPE
     SYNTAX      Counter64
     MAX-ACCESS  read-only
     STATUS      current
     DESCRIPTION "Line, Errored seconds."
     ::= { cienaCesPmTdmOCnPortTotalStatisticsBinEntry 3 }

   cienaCesPmTdmOCnPortTotalStatisticsBinSesl OBJECT-TYPE
     SYNTAX      Counter64
     MAX-ACCESS  read-only
     STATUS      current
     DESCRIPTION "Line, Severely errored seconds."
     ::= { cienaCesPmTdmOCnPortTotalStatisticsBinEntry 4 }

   cienaCesPmTdmOCnPortTotalStatisticsBinAisl OBJECT-TYPE
     SYNTAX      Counter64
     MAX-ACCESS  read-only
     STATUS      current
     DESCRIPTION "Line, Alarm indication signal seconds."
     ::= { cienaCesPmTdmOCnPortTotalStatisticsBinEntry 5 }

   cienaCesPmTdmOCnPortTotalStatisticsBinUasl OBJECT-TYPE
     SYNTAX      Counter64
     MAX-ACCESS  read-only
     STATUS      current
     DESCRIPTION "Line, Unavailable seconds."
     ::= { cienaCesPmTdmOCnPortTotalStatisticsBinEntry 6 }

  cienaCesPmTdmOCnPortTotalStatisticsBinEss OBJECT-TYPE
     SYNTAX      Counter64
     MAX-ACCESS  read-only
     STATUS      current
     DESCRIPTION "Section, Errored seconds."
     ::= { cienaCesPmTdmOCnPortTotalStatisticsBinEntry 7 }

   cienaCesPmTdmOCnPortTotalStatisticsBinSess OBJECT-TYPE
     SYNTAX      Counter64
     MAX-ACCESS  read-only
     STATUS      current
     DESCRIPTION "Section, Severely errored seconds."
     ::= { cienaCesPmTdmOCnPortTotalStatisticsBinEntry 8 }

   cienaCesPmTdmOCnPortTotalStatisticsBinLoss OBJECT-TYPE
     SYNTAX      Counter64
     MAX-ACCESS  read-only
     STATUS      current
     DESCRIPTION "Section, Loss of signal seconds."
     ::= { cienaCesPmTdmOCnPortTotalStatisticsBinEntry 9 }

   cienaCesPmTdmOCnPortTotalStatisticsBinCvs OBJECT-TYPE
     SYNTAX      Counter64
     MAX-ACCESS  read-only
     STATUS      current
     DESCRIPTION "Section, Code violation count."
     ::= { cienaCesPmTdmOCnPortTotalStatisticsBinEntry 10 }

   cienaCesPmTdmOCnPortTotalStatisticsBinSefss OBJECT-TYPE
     SYNTAX      Counter64
     MAX-ACCESS  read-only
     STATUS      current
     DESCRIPTION "Section, Severely errored frame seconds."
     ::= { cienaCesPmTdmOCnPortTotalStatisticsBinEntry 11 }

     cienaCesPmTdmOCnPortTotalStatisticsBinEb OBJECT-TYPE
     SYNTAX      Counter64
     MAX-ACCESS  read-only
     STATUS      current
     DESCRIPTION "Errored Blocks."
     ::= { cienaCesPmTdmOCnPortTotalStatisticsBinEntry 12 }

     cienaCesPmTdmOCnPortTotalStatisticsBinBbe OBJECT-TYPE
     SYNTAX      Counter64
     MAX-ACCESS  read-only
     STATUS      current
     DESCRIPTION "Backgroup Block Errors."
     ::= { cienaCesPmTdmOCnPortTotalStatisticsBinEntry 13 }

     cienaCesPmTdmOCnPortTotalStatisticsBinEs OBJECT-TYPE
     SYNTAX      Counter64
     MAX-ACCESS  read-only
     STATUS      current
     DESCRIPTION "Errored seconds."
     ::= { cienaCesPmTdmOCnPortTotalStatisticsBinEntry 14 }

     cienaCesPmTdmOCnPortTotalStatisticsBinSes OBJECT-TYPE
     SYNTAX      Counter64
     MAX-ACCESS  read-only
     STATUS      current
     DESCRIPTION "Severely Errored seconds."
     ::= { cienaCesPmTdmOCnPortTotalStatisticsBinEntry 15 }

     cienaCesPmTdmOCnPortTotalStatisticsBinAs OBJECT-TYPE
     SYNTAX      Counter64
     MAX-ACCESS  read-only
     STATUS      current
     DESCRIPTION "Available seconds."
     ::= { cienaCesPmTdmOCnPortTotalStatisticsBinEntry 16 }

     cienaCesPmTdmOCnPortTotalStatisticsBinUas OBJECT-TYPE
     SYNTAX      Counter64
     MAX-ACCESS  read-only
     STATUS      current
     DESCRIPTION "Unavailable seconds."
     ::= { cienaCesPmTdmOCnPortTotalStatisticsBinEntry 17 }

     cienaCesPmTdmOCnPortTotalStatisticsBinTt OBJECT-TYPE
     SYNTAX      Counter64
     MAX-ACCESS  read-only
     STATUS      current
     DESCRIPTION "Total Time seconds."
     ::= { cienaCesPmTdmOCnPortTotalStatisticsBinEntry 18 }

   --TdmDS3Port Profile Stats, history bins

   cienaCesPmTdmDS3PortHistoryBinTable OBJECT-TYPE
     SYNTAX      SEQUENCE OF CienaCesPmTdmDS3PortHistoryBinEntry
     MAX-ACCESS  not-accessible
     STATUS      current
     DESCRIPTION
           "The (conceptual) read-only table listing the bin statistics."
     ::= { cienaCesPmTdmDS3PortStats 1 }

   cienaCesPmTdmDS3PortHistoryBinEntry OBJECT-TYPE
     SYNTAX      CienaCesPmTdmDS3PortHistoryBinEntry
     MAX-ACCESS  not-accessible
     STATUS      current
     DESCRIPTION
           "An entry (conceptual row) in the cienaPortPmTdmDS3PortHistoryBinTable.

           This table lists the statistics for all the history bins of the PM instance, as 
           specified by the bin-count object of the PM instance.  History bins are displayed in the order
           so that #1 bin always represents the most recently completed bin and #2 - the bin previous to that
           and so on.

           The statistics are displayed for only the instances with valid bins (with start time >0), 
           as indicated by the operational state of the corresponding PM instance."
     INDEX { cienaCesPmInstanceIndex, cienaCesPmTdmDS3PortHistoryBinIndex }
     ::= { cienaCesPmTdmDS3PortHistoryBinTable 1 }

   CienaCesPmTdmDS3PortHistoryBinEntry ::=  SEQUENCE {
     cienaCesPmTdmDS3PortHistoryBinIndex                             Unsigned32,
     cienaCesPmTdmDS3PortHistoryBinStartTime                         DisplayString,
     cienaCesPmTdmDS3PortHistoryBinEndTime                           DisplayString,
     cienaCesPmTdmDS3PortHistoryBinClearTime                         DisplayString,
     cienaCesPmTdmDS3PortHistoryBinDuration                          Unsigned32,
     cienaCesPmTdmDS3PortHistoryBinState                             PmBinState,
     cienaCesPmTdmDS3PortHistoryBinCvl                               Counter64,
     cienaCesPmTdmDS3PortHistoryBinEsl                               Counter64,
     cienaCesPmTdmDS3PortHistoryBinSesl                              Counter64,
     cienaCesPmTdmDS3PortHistoryBinLoss                              Counter64,
     cienaCesPmTdmDS3PortHistoryBinPcv                               Counter64,
     cienaCesPmTdmDS3PortHistoryBinPes                               Counter64,
     cienaCesPmTdmDS3PortHistoryBinPses                              Counter64,
     cienaCesPmTdmDS3PortHistoryBinPuas                              Counter64,
     cienaCesPmTdmDS3PortHistoryBinSefs                              Counter64
   }
   cienaCesPmTdmDS3PortHistoryBinIndex OBJECT-TYPE
     SYNTAX      Unsigned32 (1..65535)
     MAX-ACCESS  not-accessible
     STATUS      current
     DESCRIPTION "Bin number associated with the PmTdmDS3PortHistoryBin entry."
     ::= { cienaCesPmTdmDS3PortHistoryBinEntry 1 }

   cienaCesPmTdmDS3PortHistoryBinStartTime OBJECT-TYPE
     SYNTAX      DisplayString
     MAX-ACCESS  read-only
     STATUS      current
     DESCRIPTION "Collection start time of the bin."
     ::= { cienaCesPmTdmDS3PortHistoryBinEntry 2 }

   cienaCesPmTdmDS3PortHistoryBinEndTime OBJECT-TYPE
     SYNTAX      DisplayString
     MAX-ACCESS  read-only
     STATUS      current
     DESCRIPTION "Collection end time of the bin."
     ::= { cienaCesPmTdmDS3PortHistoryBinEntry 3 }

   cienaCesPmTdmDS3PortHistoryBinClearTime OBJECT-TYPE
     SYNTAX      DisplayString
     MAX-ACCESS  read-only
     STATUS      current
     DESCRIPTION "Collection clear time of the bin."
     ::= { cienaCesPmTdmDS3PortHistoryBinEntry 4 }

   cienaCesPmTdmDS3PortHistoryBinDuration OBJECT-TYPE
     SYNTAX      Unsigned32 (1..65535)
     UNITS       "minutes"
     MAX-ACCESS  read-only
     STATUS      current
     DESCRIPTION "Duration of the bin."
     ::= { cienaCesPmTdmDS3PortHistoryBinEntry 5 }

   cienaCesPmTdmDS3PortHistoryBinState OBJECT-TYPE
     SYNTAX      PmBinState
     MAX-ACCESS  read-only
     STATUS      current
     DESCRIPTION "State of the bin."
     ::= { cienaCesPmTdmDS3PortHistoryBinEntry 6 }

   cienaCesPmTdmDS3PortHistoryBinCvl OBJECT-TYPE
     SYNTAX      Counter64
     MAX-ACCESS  read-only
     STATUS      current
     DESCRIPTION "Line, Code violations."
     ::= { cienaCesPmTdmDS3PortHistoryBinEntry 7 }

   cienaCesPmTdmDS3PortHistoryBinEsl OBJECT-TYPE
     SYNTAX      Counter64
     MAX-ACCESS  read-only
     STATUS      current
     DESCRIPTION "Line, Errored seconds."
     ::= { cienaCesPmTdmDS3PortHistoryBinEntry 8 }

   cienaCesPmTdmDS3PortHistoryBinSesl OBJECT-TYPE
     SYNTAX      Counter64
     MAX-ACCESS  read-only
     STATUS      current
     DESCRIPTION "Line, Severely errored seconds."
     ::= { cienaCesPmTdmDS3PortHistoryBinEntry 9 }

   cienaCesPmTdmDS3PortHistoryBinLoss OBJECT-TYPE
     SYNTAX      Counter64
     MAX-ACCESS  read-only
     STATUS      current
     DESCRIPTION "Line, Loss of signal seconds."
     ::= { cienaCesPmTdmDS3PortHistoryBinEntry 10 }

   cienaCesPmTdmDS3PortHistoryBinPcv OBJECT-TYPE
     SYNTAX      Counter64
     MAX-ACCESS  read-only
     STATUS      current
     DESCRIPTION "Number of p-bit code violations."
     ::= { cienaCesPmTdmDS3PortHistoryBinEntry 11 }

   cienaCesPmTdmDS3PortHistoryBinPes OBJECT-TYPE
     SYNTAX      Counter64
     MAX-ACCESS  read-only
     STATUS      current
     DESCRIPTION "P-bit errored seconds."
     ::= { cienaCesPmTdmDS3PortHistoryBinEntry 12 }

   cienaCesPmTdmDS3PortHistoryBinPses OBJECT-TYPE
     SYNTAX      Counter64
     MAX-ACCESS  read-only
     STATUS      current
     DESCRIPTION "P-bit severely errored seconds."
     ::= { cienaCesPmTdmDS3PortHistoryBinEntry 13 }

   cienaCesPmTdmDS3PortHistoryBinPuas OBJECT-TYPE
     SYNTAX      Counter64
     MAX-ACCESS  read-only
     STATUS      current
     DESCRIPTION "P-bit unavilable seconds."
     ::= { cienaCesPmTdmDS3PortHistoryBinEntry 14 }

   cienaCesPmTdmDS3PortHistoryBinSefs OBJECT-TYPE
     SYNTAX      Counter64
     MAX-ACCESS  read-only
     STATUS      current
     DESCRIPTION "Severely errored frame seconds."
     ::= { cienaCesPmTdmDS3PortHistoryBinEntry 15 }


   --TdmDS3Port Profile Stats, current bin

   cienaCesPmTdmDS3PortCurrBinTable OBJECT-TYPE
     SYNTAX      SEQUENCE OF CienaCesPmTdmDS3PortCurrBinEntry
     MAX-ACCESS  not-accessible
     STATUS      current
     DESCRIPTION "The (conceptual) read-only table listing the bin statistics."
     ::= { cienaCesPmTdmDS3PortStats 2 }

   cienaCesPmTdmDS3PortCurrBinEntry OBJECT-TYPE
     SYNTAX      CienaCesPmTdmDS3PortCurrBinEntry
     MAX-ACCESS  not-accessible
     STATUS      current
     DESCRIPTION
           "An entry (conceptual row) in the cienaPortPmTdmDS3PortCurrBinTable.
           This table lists the statistics for the current bin of the PM instance."
     INDEX {cienaCesPmInstanceIndex}
     ::= { cienaCesPmTdmDS3PortCurrBinTable 1 }

   CienaCesPmTdmDS3PortCurrBinEntry ::=  SEQUENCE {
     cienaCesPmTdmDS3PortCurrBinStartTime                            DisplayString,
     cienaCesPmTdmDS3PortCurrBinClearTime                            DisplayString,
     cienaCesPmTdmDS3PortCurrBinDuration                             Unsigned32,
     cienaCesPmTdmDS3PortCurrBinState                                PmBinState,
     cienaCesPmTdmDS3PortCurrBinCvl                                  Counter64,
     cienaCesPmTdmDS3PortCurrBinEsl                                  Counter64,
     cienaCesPmTdmDS3PortCurrBinSesl                                 Counter64,
     cienaCesPmTdmDS3PortCurrBinLoss                                 Counter64,
     cienaCesPmTdmDS3PortCurrBinPcv                                  Counter64,
     cienaCesPmTdmDS3PortCurrBinPes                                  Counter64,
     cienaCesPmTdmDS3PortCurrBinPses                                 Counter64,
     cienaCesPmTdmDS3PortCurrBinPuas                                 Counter64,
     cienaCesPmTdmDS3PortCurrBinSefs                                 Counter64
   }

   cienaCesPmTdmDS3PortCurrBinStartTime OBJECT-TYPE
     SYNTAX      DisplayString
     MAX-ACCESS  read-only
     STATUS      current
     DESCRIPTION "Collection start time of the bin."
     ::= { cienaCesPmTdmDS3PortCurrBinEntry 1 }

   cienaCesPmTdmDS3PortCurrBinClearTime OBJECT-TYPE
     SYNTAX      DisplayString
     MAX-ACCESS  read-only
     STATUS      current
     DESCRIPTION "Cleared time of the bin."
     ::= { cienaCesPmTdmDS3PortCurrBinEntry 2 }

   cienaCesPmTdmDS3PortCurrBinDuration OBJECT-TYPE
     SYNTAX      Unsigned32 (1..65535)
     UNITS       "minutes"
     MAX-ACCESS  read-only
     STATUS      current
     DESCRIPTION "Interval of the bin."
     ::= { cienaCesPmTdmDS3PortCurrBinEntry 3 }

   cienaCesPmTdmDS3PortCurrBinState OBJECT-TYPE
     SYNTAX      PmBinState
     MAX-ACCESS  read-only
     STATUS      current
     DESCRIPTION "State of the bin."
     ::= { cienaCesPmTdmDS3PortCurrBinEntry 4 }

   cienaCesPmTdmDS3PortCurrBinCvl OBJECT-TYPE
     SYNTAX      Counter64
     MAX-ACCESS  read-only
     STATUS      current
     DESCRIPTION "Line, Code violations."
     ::= { cienaCesPmTdmDS3PortCurrBinEntry 5 }

  cienaCesPmTdmDS3PortCurrBinEsl OBJECT-TYPE
     SYNTAX      Counter64
     MAX-ACCESS  read-only
     STATUS      current
     DESCRIPTION "Line, Errored seconds."
     ::= { cienaCesPmTdmDS3PortCurrBinEntry 6 }

   cienaCesPmTdmDS3PortCurrBinSesl OBJECT-TYPE
     SYNTAX      Counter64
     MAX-ACCESS  read-only
     STATUS      current
     DESCRIPTION "Line, Severely errored seconds."
     ::= { cienaCesPmTdmDS3PortCurrBinEntry 7 }

  cienaCesPmTdmDS3PortCurrBinLoss OBJECT-TYPE
     SYNTAX      Counter64
     MAX-ACCESS  read-only
     STATUS      current
     DESCRIPTION "Line, Loss of signal seconds."
     ::= { cienaCesPmTdmDS3PortCurrBinEntry 8 }

   cienaCesPmTdmDS3PortCurrBinPcv OBJECT-TYPE
     SYNTAX      Counter64
     MAX-ACCESS  read-only
     STATUS      current
     DESCRIPTION "Number of p-bit code violations."
     ::= { cienaCesPmTdmDS3PortCurrBinEntry 9 }

   cienaCesPmTdmDS3PortCurrBinPes OBJECT-TYPE
     SYNTAX      Counter64
     MAX-ACCESS  read-only
     STATUS      current
     DESCRIPTION "P-bit errored seconds."
     ::= { cienaCesPmTdmDS3PortCurrBinEntry 10 }

   cienaCesPmTdmDS3PortCurrBinPses OBJECT-TYPE
     SYNTAX      Counter64
     MAX-ACCESS  read-only
     STATUS      current
     DESCRIPTION "P-bit severely errored seconds."
     ::= { cienaCesPmTdmDS3PortCurrBinEntry 11 }

   cienaCesPmTdmDS3PortCurrBinPuas OBJECT-TYPE
     SYNTAX      Counter64
     MAX-ACCESS  read-only
     STATUS      current
     DESCRIPTION "P-bit unavailable seconds."
     ::= { cienaCesPmTdmDS3PortCurrBinEntry 12 }

   cienaCesPmTdmDS3PortCurrBinSefs OBJECT-TYPE
     SYNTAX      Counter64
     MAX-ACCESS  read-only
     STATUS      current
     DESCRIPTION "Severely errored frame seconds."
     ::= { cienaCesPmTdmDS3PortCurrBinEntry 13 }


   --TdmDS3Port Profile Stats, current 24 hour bin
  
   cienaCesPmTdmDS3PortCurr24HBinTable OBJECT-TYPE
     SYNTAX      SEQUENCE OF CienaCesPmTdmDS3PortCurr24HBinEntry
     MAX-ACCESS  not-accessible
     STATUS      current
     DESCRIPTION "The (conceptual) read-only table listing the bin statistics."
     ::= { cienaCesPmTdmDS3PortStats 3 }

   cienaCesPmTdmDS3PortCurr24HBinEntry OBJECT-TYPE
     SYNTAX      CienaCesPmTdmDS3PortCurr24HBinEntry
     MAX-ACCESS  not-accessible
     STATUS      current
     DESCRIPTION
           "An entry (conceptual row) in the cienaPortPmTdmDS3PortCurr24HBinTable.
           This table lists the statistics for the current 24 hours bin."
     INDEX {cienaCesPmInstanceIndex }
     ::= { cienaCesPmTdmDS3PortCurr24HBinTable 1 }

   CienaCesPmTdmDS3PortCurr24HBinEntry ::=  SEQUENCE {
     cienaCesPmTdmDS3PortCurr24HBinStartTime                         DisplayString,
     cienaCesPmTdmDS3PortCurr24HBinClearTime                         DisplayString,
     cienaCesPmTdmDS3PortCurr24HBinDuration                          Unsigned32,
     cienaCesPmTdmDS3PortCurr24HBinState                             PmBinState,
     cienaCesPmTdmDS3PortCurr24HBinCvl                               Counter64,
     cienaCesPmTdmDS3PortCurr24HBinEsl                               Counter64,
     cienaCesPmTdmDS3PortCurr24HBinSesl                              Counter64,
     cienaCesPmTdmDS3PortCurr24HBinLoss                              Counter64,
     cienaCesPmTdmDS3PortCurr24HBinPcv                               Counter64,
     cienaCesPmTdmDS3PortCurr24HBinPes                               Counter64,
     cienaCesPmTdmDS3PortCurr24HBinPses                              Counter64,
     cienaCesPmTdmDS3PortCurr24HBinPuas                              Counter64,
     cienaCesPmTdmDS3PortCurr24HBinSefs                              Counter64
   } 

   cienaCesPmTdmDS3PortCurr24HBinStartTime OBJECT-TYPE
     SYNTAX      DisplayString
     MAX-ACCESS  read-only
     STATUS      current
     DESCRIPTION "Collection start time of the bin."
     ::= { cienaCesPmTdmDS3PortCurr24HBinEntry 1 }

   cienaCesPmTdmDS3PortCurr24HBinClearTime OBJECT-TYPE
     SYNTAX      DisplayString
     MAX-ACCESS  read-only
     STATUS      current
     DESCRIPTION "Cleared time of the bin."
     ::= { cienaCesPmTdmDS3PortCurr24HBinEntry 2 }

   cienaCesPmTdmDS3PortCurr24HBinDuration OBJECT-TYPE
     SYNTAX      Unsigned32 (1..65535)
     UNITS       "minutes"
     MAX-ACCESS  read-only
     STATUS      current
     DESCRIPTION "Duration of the bin."
     ::= { cienaCesPmTdmDS3PortCurr24HBinEntry 3 }

   cienaCesPmTdmDS3PortCurr24HBinState OBJECT-TYPE
     SYNTAX      PmBinState
     MAX-ACCESS  read-only
     STATUS      current
     DESCRIPTION "State of the bin."
     ::= { cienaCesPmTdmDS3PortCurr24HBinEntry 4 }

   cienaCesPmTdmDS3PortCurr24HBinCvl OBJECT-TYPE
     SYNTAX      Counter64
     MAX-ACCESS  read-only
     STATUS      current
     DESCRIPTION "Line, Code violations."
     ::= { cienaCesPmTdmDS3PortCurr24HBinEntry 5 }

   cienaCesPmTdmDS3PortCurr24HBinEsl OBJECT-TYPE
     SYNTAX      Counter64
     MAX-ACCESS  read-only
     STATUS      current
     DESCRIPTION "Line, Errored seconds."
     ::= { cienaCesPmTdmDS3PortCurr24HBinEntry 6 }

   cienaCesPmTdmDS3PortCurr24HBinSesl OBJECT-TYPE
     SYNTAX      Counter64
     MAX-ACCESS  read-only
     STATUS      current
     DESCRIPTION "Line, Severely errored seconds."
     ::= { cienaCesPmTdmDS3PortCurr24HBinEntry 7 }

   cienaCesPmTdmDS3PortCurr24HBinLoss OBJECT-TYPE
     SYNTAX      Counter64
     MAX-ACCESS  read-only
     STATUS      current
     DESCRIPTION "Line, Loss of signal seconds."
     ::= { cienaCesPmTdmDS3PortCurr24HBinEntry 8 }

   cienaCesPmTdmDS3PortCurr24HBinPcv OBJECT-TYPE
     SYNTAX      Counter64
     MAX-ACCESS  read-only
     STATUS      current
     DESCRIPTION "Number of p-bit code violations."
     ::= { cienaCesPmTdmDS3PortCurr24HBinEntry 9 }

   cienaCesPmTdmDS3PortCurr24HBinPes OBJECT-TYPE
     SYNTAX      Counter64
     MAX-ACCESS  read-only
     STATUS      current
     DESCRIPTION "P-bit errored seconds."
     ::= { cienaCesPmTdmDS3PortCurr24HBinEntry 10 }

   cienaCesPmTdmDS3PortCurr24HBinPses OBJECT-TYPE
     SYNTAX      Counter64
     MAX-ACCESS  read-only
     STATUS      current
     DESCRIPTION "P-bit severely errored seconds."
     ::= { cienaCesPmTdmDS3PortCurr24HBinEntry 11 }

   cienaCesPmTdmDS3PortCurr24HBinPuas OBJECT-TYPE
     SYNTAX      Counter64
     MAX-ACCESS  read-only
     STATUS      current
     DESCRIPTION "P-bit unavailable seconds."
     ::= { cienaCesPmTdmDS3PortCurr24HBinEntry 12 }

   cienaCesPmTdmDS3PortCurr24HBinSefs OBJECT-TYPE
     SYNTAX      Counter64
     MAX-ACCESS  read-only
     STATUS      current
     DESCRIPTION "Severely errored frame seconds."
     ::= { cienaCesPmTdmDS3PortCurr24HBinEntry 13 }


   --TdmDS3Port Profile Stats, history 24 hour bin
  
   cienaCesPmTdmDS3PortHist24HBinTable OBJECT-TYPE
     SYNTAX      SEQUENCE OF CienaCesPmTdmDS3PortHist24HBinEntry
     MAX-ACCESS  not-accessible
     STATUS      current
     DESCRIPTION "The (conceptual) read-only Table listing the Bin Statistics."
     ::= { cienaCesPmTdmDS3PortStats 4 }

   cienaCesPmTdmDS3PortHist24HBinEntry OBJECT-TYPE
     SYNTAX      CienaCesPmTdmDS3PortHist24HBinEntry
     MAX-ACCESS  not-accessible
     STATUS      current
     DESCRIPTION
           "An entry (conceptual row) in the cienaPortPmTdmDS3PortHist24HBinTable.
           This table lists the statistics for the history 24 hours bin."
     INDEX {cienaCesPmInstanceIndex}
     ::= { cienaCesPmTdmDS3PortHist24HBinTable 1 }

   CienaCesPmTdmDS3PortHist24HBinEntry ::=  SEQUENCE {
     cienaCesPmTdmDS3PortHist24HBinStartTime                         DisplayString,
     cienaCesPmTdmDS3PortHist24HBinEndTime                           DisplayString,
     cienaCesPmTdmDS3PortHist24HBinClearTime                         DisplayString,
     cienaCesPmTdmDS3PortHist24HBinDuration                          Unsigned32,
     cienaCesPmTdmDS3PortHist24HBinState                             PmBinState,
     cienaCesPmTdmDS3PortHist24HBinCvl                               Counter64,
     cienaCesPmTdmDS3PortHist24HBinEsl                               Counter64,
     cienaCesPmTdmDS3PortHist24HBinSesl                              Counter64,
     cienaCesPmTdmDS3PortHist24HBinLoss                              Counter64,
     cienaCesPmTdmDS3PortHist24HBinPcv                               Counter64,
     cienaCesPmTdmDS3PortHist24HBinPes                               Counter64,
     cienaCesPmTdmDS3PortHist24HBinPses                              Counter64,
     cienaCesPmTdmDS3PortHist24HBinPuas                              Counter64,
     cienaCesPmTdmDS3PortHist24HBinSefs                              Counter64
   }

   cienaCesPmTdmDS3PortHist24HBinStartTime OBJECT-TYPE
     SYNTAX      DisplayString
     MAX-ACCESS  read-only
     STATUS      current
     DESCRIPTION "Collection start time of the bin."
     ::= { cienaCesPmTdmDS3PortHist24HBinEntry 1 }

   cienaCesPmTdmDS3PortHist24HBinEndTime OBJECT-TYPE
     SYNTAX      DisplayString
     MAX-ACCESS  read-only
     STATUS      current
     DESCRIPTION "Collection end time for the bin."
     ::= { cienaCesPmTdmDS3PortHist24HBinEntry 2 }

   cienaCesPmTdmDS3PortHist24HBinClearTime OBJECT-TYPE
     SYNTAX      DisplayString
     MAX-ACCESS  read-only
     STATUS      current
     DESCRIPTION "Cleared time of the bin."
     ::= { cienaCesPmTdmDS3PortHist24HBinEntry 3 }

   cienaCesPmTdmDS3PortHist24HBinDuration OBJECT-TYPE
     SYNTAX      Unsigned32 (1..65535)
     UNITS       "minutes"
     MAX-ACCESS  read-only
     STATUS      current
     DESCRIPTION "Duration of the bin."
     ::= { cienaCesPmTdmDS3PortHist24HBinEntry 4 }

   cienaCesPmTdmDS3PortHist24HBinState OBJECT-TYPE
     SYNTAX      PmBinState
     MAX-ACCESS  read-only
     STATUS      current
     DESCRIPTION "State of the bin."
     ::= { cienaCesPmTdmDS3PortHist24HBinEntry 5 }

   cienaCesPmTdmDS3PortHist24HBinCvl OBJECT-TYPE
     SYNTAX      Counter64
     MAX-ACCESS  read-only
     STATUS      current
     DESCRIPTION "Line, Code violations."
     ::= { cienaCesPmTdmDS3PortHist24HBinEntry 6 }

   cienaCesPmTdmDS3PortHist24HBinEsl OBJECT-TYPE
     SYNTAX      Counter64
     MAX-ACCESS  read-only
     STATUS      current
     DESCRIPTION "Line, Errored seconds."
     ::= { cienaCesPmTdmDS3PortHist24HBinEntry 7 }

   cienaCesPmTdmDS3PortHist24HBinSesl OBJECT-TYPE
     SYNTAX      Counter64
     MAX-ACCESS  read-only
     STATUS      current
     DESCRIPTION "Line, Severely Errored seconds."
     ::= { cienaCesPmTdmDS3PortHist24HBinEntry 8 }

   cienaCesPmTdmDS3PortHist24HBinLoss OBJECT-TYPE
     SYNTAX      Counter64
     MAX-ACCESS  read-only
     STATUS      current
     DESCRIPTION "Line, Loss of signal seconds."
     ::= { cienaCesPmTdmDS3PortHist24HBinEntry 9 }

   cienaCesPmTdmDS3PortHist24HBinPcv OBJECT-TYPE
     SYNTAX      Counter64
     MAX-ACCESS  read-only
     STATUS      current
     DESCRIPTION "Number of p-bit code violations."
     ::= { cienaCesPmTdmDS3PortHist24HBinEntry 10 }

   cienaCesPmTdmDS3PortHist24HBinPes OBJECT-TYPE
     SYNTAX      Counter64
     MAX-ACCESS  read-only
     STATUS      current
     DESCRIPTION "P-bit errored seconds."
     ::= { cienaCesPmTdmDS3PortHist24HBinEntry 11 }

   cienaCesPmTdmDS3PortHist24HBinPses OBJECT-TYPE
     SYNTAX      Counter64
     MAX-ACCESS  read-only
     STATUS      current
     DESCRIPTION "P-bit severely errored seconds."
     ::= { cienaCesPmTdmDS3PortHist24HBinEntry 12 }

   cienaCesPmTdmDS3PortHist24HBinPuas OBJECT-TYPE
     SYNTAX      Counter64
     MAX-ACCESS  read-only
     STATUS      current
     DESCRIPTION "P-bit unavailable seconds."
     ::= { cienaCesPmTdmDS3PortHist24HBinEntry 13 }

   cienaCesPmTdmDS3PortHist24HBinSefs OBJECT-TYPE
     SYNTAX      Counter64
     MAX-ACCESS  read-only
     STATUS      current
     DESCRIPTION "Severely errored frame seconds."
     ::= { cienaCesPmTdmDS3PortHist24HBinEntry 14 }


   --TdmDS3Port Profile Stats, statistics bin

   cienaCesPmTdmDS3PortStatisticsBinTable OBJECT-TYPE
     SYNTAX      SEQUENCE OF CienaCesPmTdmDS3PortStatisticsBinEntry
     MAX-ACCESS  not-accessible
     STATUS      current
     DESCRIPTION "The (conceptual) read-only table listing the bin statistics."
     ::= { cienaCesPmTdmDS3PortStats 5 }

   cienaCesPmTdmDS3PortStatisticsBinEntry OBJECT-TYPE
     SYNTAX      CienaCesPmTdmDS3PortStatisticsBinEntry
     MAX-ACCESS  not-accessible
     STATUS      current
     DESCRIPTION
           "An entry (conceptual row) in the cienaPortPmTdmDS3PortStatisticsBinTable.
           This table lists the statistics for the statistics bin of the PM instance."
     INDEX {cienaCesPmInstanceIndex}
     ::= { cienaCesPmTdmDS3PortStatisticsBinTable 1 }

   CienaCesPmTdmDS3PortStatisticsBinEntry ::=  SEQUENCE {
     cienaCesPmTdmDS3PortStatisticsBinStartTime                      DisplayString,
     cienaCesPmTdmDS3PortStatisticsBinClearTime                      DisplayString,
     cienaCesPmTdmDS3PortStatisticsBinCvl                            Counter64,
     cienaCesPmTdmDS3PortStatisticsBinEsl                            Counter64,
     cienaCesPmTdmDS3PortStatisticsBinSesl                           Counter64,
     cienaCesPmTdmDS3PortStatisticsBinLoss                           Counter64,
     cienaCesPmTdmDS3PortStatisticsBinPcv                            Counter64,
     cienaCesPmTdmDS3PortStatisticsBinPes                            Counter64,
     cienaCesPmTdmDS3PortStatisticsBinPses                           Counter64,
     cienaCesPmTdmDS3PortStatisticsBinPuas                           Counter64,
     cienaCesPmTdmDS3PortStatisticsBinSefs                           Counter64
   }          

   cienaCesPmTdmDS3PortStatisticsBinStartTime OBJECT-TYPE
     SYNTAX      DisplayString
     MAX-ACCESS  read-only
     STATUS      current
     DESCRIPTION "Collection start time of the bin."
     ::= { cienaCesPmTdmDS3PortStatisticsBinEntry 1 }

   cienaCesPmTdmDS3PortStatisticsBinClearTime OBJECT-TYPE
     SYNTAX      DisplayString
     MAX-ACCESS  read-only
     STATUS      current
     DESCRIPTION "Cleared time of the bin."
     ::= { cienaCesPmTdmDS3PortStatisticsBinEntry 2 }

   cienaCesPmTdmDS3PortStatisticsBinCvl OBJECT-TYPE
     SYNTAX      Counter64
     MAX-ACCESS  read-only
     STATUS      current
     DESCRIPTION "Line, Code violations."
     ::= { cienaCesPmTdmDS3PortStatisticsBinEntry 3 }

   cienaCesPmTdmDS3PortStatisticsBinEsl OBJECT-TYPE
     SYNTAX      Counter64
     MAX-ACCESS  read-only
     STATUS      current
     DESCRIPTION "Line, Errored seconds."
     ::= { cienaCesPmTdmDS3PortStatisticsBinEntry 4 }

   cienaCesPmTdmDS3PortStatisticsBinSesl OBJECT-TYPE
     SYNTAX      Counter64
     MAX-ACCESS  read-only
     STATUS      current
     DESCRIPTION "Line, Severely errored seconds."
     ::= { cienaCesPmTdmDS3PortStatisticsBinEntry 5 }

   cienaCesPmTdmDS3PortStatisticsBinLoss OBJECT-TYPE
     SYNTAX      Counter64
     MAX-ACCESS  read-only
     STATUS      current
     DESCRIPTION "Line, Loss of signal seconds."
     ::= { cienaCesPmTdmDS3PortStatisticsBinEntry 6 }

   cienaCesPmTdmDS3PortStatisticsBinPcv OBJECT-TYPE
     SYNTAX      Counter64
     MAX-ACCESS  read-only
     STATUS      current
     DESCRIPTION "Number of p-bit code violation events."
     ::= { cienaCesPmTdmDS3PortStatisticsBinEntry 7 }

   cienaCesPmTdmDS3PortStatisticsBinPes OBJECT-TYPE
     SYNTAX      Counter64
     MAX-ACCESS  read-only
     STATUS      current
     DESCRIPTION "P-bit errored seconds."
     ::= { cienaCesPmTdmDS3PortStatisticsBinEntry 8 }

   cienaCesPmTdmDS3PortStatisticsBinPses OBJECT-TYPE
     SYNTAX      Counter64
     MAX-ACCESS  read-only
     STATUS      current
     DESCRIPTION "C-bit severely errored seconds."
     ::= { cienaCesPmTdmDS3PortStatisticsBinEntry 9 }

   cienaCesPmTdmDS3PortStatisticsBinPuas OBJECT-TYPE
     SYNTAX      Counter64
     MAX-ACCESS  read-only
     STATUS      current
     DESCRIPTION "P-bit unavailable seconds."
     ::= { cienaCesPmTdmDS3PortStatisticsBinEntry 10 }

   cienaCesPmTdmDS3PortStatisticsBinSefs OBJECT-TYPE
     SYNTAX      Counter64
     MAX-ACCESS  read-only
     STATUS      current
     DESCRIPTION "Severely errored frame seconds."
     ::= { cienaCesPmTdmDS3PortStatisticsBinEntry 11 }


   --TdmDS3Port Profile Stats, total statistics bin

   cienaCesPmTdmDS3PortTotalStatisticsBinTable OBJECT-TYPE
     SYNTAX      SEQUENCE OF CienaCesPmTdmDS3PortTotalStatisticsBinEntry
     MAX-ACCESS  not-accessible
     STATUS      current
     DESCRIPTION "The (conceptual) read-only table listing the bin statistics."
     ::= { cienaCesPmTdmDS3PortStats 6 }

   cienaCesPmTdmDS3PortTotalStatisticsBinEntry OBJECT-TYPE
     SYNTAX      CienaCesPmTdmDS3PortTotalStatisticsBinEntry
     MAX-ACCESS  not-accessible
     STATUS      current
     DESCRIPTION
           "An entry (conceptual row) in the cienaPortPmTdmDS3PortTotalStatisticsBinTable.
           This table lists the statistics for the total statistics bin of the PM instance."
     INDEX {cienaCesPmInstanceIndex}
     ::= { cienaCesPmTdmDS3PortTotalStatisticsBinTable 1 }

   CienaCesPmTdmDS3PortTotalStatisticsBinEntry ::=  SEQUENCE {
     cienaCesPmTdmDS3PortTotalStatisticsBinStartTime                 DisplayString,
     cienaCesPmTdmDS3PortTotalStatisticsBinCvl                       Counter64,
     cienaCesPmTdmDS3PortTotalStatisticsBinEsl                       Counter64,
     cienaCesPmTdmDS3PortTotalStatisticsBinSesl                      Counter64,
     cienaCesPmTdmDS3PortTotalStatisticsBinLoss                      Counter64,
     cienaCesPmTdmDS3PortTotalStatisticsBinPcv                       Counter64,
     cienaCesPmTdmDS3PortTotalStatisticsBinPes                       Counter64,
     cienaCesPmTdmDS3PortTotalStatisticsBinPses                      Counter64,
     cienaCesPmTdmDS3PortTotalStatisticsBinPuas                      Counter64,
     cienaCesPmTdmDS3PortTotalStatisticsBinSefs                      Counter64
   }          

   cienaCesPmTdmDS3PortTotalStatisticsBinStartTime OBJECT-TYPE
     SYNTAX      DisplayString
     MAX-ACCESS  read-only
     STATUS      current
     DESCRIPTION "Collection start time of the bin."
     ::= { cienaCesPmTdmDS3PortTotalStatisticsBinEntry 1 }

   cienaCesPmTdmDS3PortTotalStatisticsBinCvl OBJECT-TYPE
     SYNTAX      Counter64
     MAX-ACCESS  read-only
     STATUS      current
     DESCRIPTION "Line, Code violations."
     ::= { cienaCesPmTdmDS3PortTotalStatisticsBinEntry 2 }

   cienaCesPmTdmDS3PortTotalStatisticsBinEsl OBJECT-TYPE
     SYNTAX      Counter64
     MAX-ACCESS  read-only
     STATUS      current
     DESCRIPTION "Line, Errored seconds."
     ::= { cienaCesPmTdmDS3PortTotalStatisticsBinEntry 3 }

   cienaCesPmTdmDS3PortTotalStatisticsBinSesl OBJECT-TYPE
     SYNTAX      Counter64
     MAX-ACCESS  read-only
     STATUS      current
     DESCRIPTION "Line, Severely Errored seconds."
     ::= { cienaCesPmTdmDS3PortTotalStatisticsBinEntry 4 }

   cienaCesPmTdmDS3PortTotalStatisticsBinLoss OBJECT-TYPE
     SYNTAX      Counter64
     MAX-ACCESS  read-only
     STATUS      current
     DESCRIPTION "Line, Loss of signal seconds."
     ::= { cienaCesPmTdmDS3PortTotalStatisticsBinEntry 5 }

   cienaCesPmTdmDS3PortTotalStatisticsBinPcv OBJECT-TYPE
     SYNTAX      Counter64
     MAX-ACCESS  read-only
     STATUS      current
     DESCRIPTION "Number of p-bit code violation events."
     ::= { cienaCesPmTdmDS3PortTotalStatisticsBinEntry 6 }

   cienaCesPmTdmDS3PortTotalStatisticsBinPes OBJECT-TYPE
     SYNTAX      Counter64
     MAX-ACCESS  read-only
     STATUS      current
     DESCRIPTION "P-bit errored seconds."
     ::= { cienaCesPmTdmDS3PortTotalStatisticsBinEntry 7 }

   cienaCesPmTdmDS3PortTotalStatisticsBinPses OBJECT-TYPE
     SYNTAX      Counter64
     MAX-ACCESS  read-only
     STATUS      current
     DESCRIPTION "P-bit severely errored seconds."
     ::= { cienaCesPmTdmDS3PortTotalStatisticsBinEntry 8 }

   cienaCesPmTdmDS3PortTotalStatisticsBinPuas OBJECT-TYPE
     SYNTAX      Counter64
     MAX-ACCESS  read-only
     STATUS      current
     DESCRIPTION "P-bit unavailable seconds."
     ::= { cienaCesPmTdmDS3PortTotalStatisticsBinEntry 9 }

   cienaCesPmTdmDS3PortTotalStatisticsBinSefs OBJECT-TYPE
     SYNTAX      Counter64
     MAX-ACCESS  read-only
     STATUS      current
     DESCRIPTION "Severely errored frame seconds."
     ::= { cienaCesPmTdmDS3PortTotalStatisticsBinEntry 10 }


   --BasicTx Profile Stats

   cienaCesPmBasicTxHistoryBinTable OBJECT-TYPE
     SYNTAX      SEQUENCE OF CienaCesPmBasicTxHistoryBinEntry
     MAX-ACCESS  not-accessible
     STATUS      current
     DESCRIPTION "The (conceptual) read-only table listing the basic Tx
                  profile statistics."
     ::= { cienaCesPmBasicTxStats 1 }

   cienaCesPmBasicTxHistoryBinEntry OBJECT-TYPE
     SYNTAX      CienaCesPmBasicTxHistoryBinEntry
     MAX-ACCESS  not-accessible
     STATUS      current
     DESCRIPTION
           "An entry (conceptual row) in the cienaCesPmBasicTxHistoryBinTable.

            This table lists the statistics for all the history bins of the PM
            instance, as specified by the bin-count object of the PM instance.
            History bins are displayed in the order so that #1 bin always
            represents the most recently completed bin and #2 - the bin previous
            to that and so on.

            The statistics are displayed for only the instances with valid bins
            (with start time >0), as indicated by the operational state of the
            corresponding PM instance."
     INDEX { cienaCesPmInstanceIndex, cienaCesPmBasicTxHistoryBinIndex }
     ::= { cienaCesPmBasicTxHistoryBinTable 1 }

   CienaCesPmBasicTxHistoryBinEntry ::= SEQUENCE {
     cienaCesPmBasicTxHistoryBinIndex                                Unsigned32,
     cienaCesPmBasicTxHistoryBinStartTime                            DisplayString,
     cienaCesPmBasicTxHistoryBinEndTime                              DisplayString,
     cienaCesPmBasicTxHistoryBinClearTime                            DisplayString,
     cienaCesPmBasicTxHistoryBinDuration                             Unsigned32,
     cienaCesPmBasicTxHistoryBinState                                PmBinState,
     cienaCesPmBasicTxHistoryBinTxForwardedBytes                     Counter64,
     cienaCesPmBasicTxHistoryBinTxForwardedFrames                    Counter64,
     cienaCesPmBasicTxHistoryBinTxBytesPerSec                        Counter64,
     cienaCesPmBasicTxHistoryBinTxFramesPerSec                       Counter64
   }

   cienaCesPmBasicTxHistoryBinIndex OBJECT-TYPE
     SYNTAX      Unsigned32 (1..65535)
     MAX-ACCESS  not-accessible
     STATUS      current
     DESCRIPTION "Bin number associated with the PmBasicTxHistoryBin entry."
     ::= { cienaCesPmBasicTxHistoryBinEntry 1 }

   cienaCesPmBasicTxHistoryBinStartTime OBJECT-TYPE
     SYNTAX      DisplayString
     MAX-ACCESS  read-only
     STATUS      current
     DESCRIPTION "Collection start time of the bin."
     ::= { cienaCesPmBasicTxHistoryBinEntry 2 }

   cienaCesPmBasicTxHistoryBinEndTime OBJECT-TYPE
     SYNTAX      DisplayString
     MAX-ACCESS  read-only
     STATUS      current
     DESCRIPTION "Collection end time of the bin."
   ::= {cienaCesPmBasicTxHistoryBinEntry 3 }

   cienaCesPmBasicTxHistoryBinClearTime OBJECT-TYPE
     SYNTAX      DisplayString
     MAX-ACCESS  read-only
     STATUS      current
     DESCRIPTION "Clear time of the bin."
   ::= {  cienaCesPmBasicTxHistoryBinEntry 4 }

   cienaCesPmBasicTxHistoryBinDuration OBJECT-TYPE
     SYNTAX      Unsigned32 (1..65535)
     UNITS       "minutes"
     MAX-ACCESS  read-only
     STATUS      current
     DESCRIPTION "Duration of the bin."
     ::= { cienaCesPmBasicTxHistoryBinEntry 5 }

   cienaCesPmBasicTxHistoryBinState OBJECT-TYPE
     SYNTAX      PmBinState
     MAX-ACCESS  read-only
     STATUS      current
     DESCRIPTION "State of the bin."
     ::= { cienaCesPmBasicTxHistoryBinEntry 6 }

   cienaCesPmBasicTxHistoryBinTxForwardedBytes OBJECT-TYPE
     SYNTAX      Counter64
     MAX-ACCESS  read-only
     STATUS      current
     DESCRIPTION "The number of bytes forwarded on this PM instance."
     ::= { cienaCesPmBasicTxHistoryBinEntry 7 }

   cienaCesPmBasicTxHistoryBinTxForwardedFrames OBJECT-TYPE
     SYNTAX      Counter64
     MAX-ACCESS  read-only
     STATUS      current
     DESCRIPTION "The number of frames forwarded on this PM instance."
     ::= { cienaCesPmBasicTxHistoryBinEntry 8 }

   cienaCesPmBasicTxHistoryBinTxBytesPerSec OBJECT-TYPE
     SYNTAX      Counter64
     MAX-ACCESS  read-only
     STATUS      current
     DESCRIPTION "The number of bytes transmitted per second on this PM
                  instance."
     ::= { cienaCesPmBasicTxHistoryBinEntry 9 }

   cienaCesPmBasicTxHistoryBinTxFramesPerSec OBJECT-TYPE
     SYNTAX      Counter64
     MAX-ACCESS  read-only
     STATUS      current
     DESCRIPTION
             "The number of frames transmitted per second on this PM instance."
     ::= { cienaCesPmBasicTxHistoryBinEntry 10 }

 -- BasicTx Current Bin Table

   cienaCesPmBasicTxCurrBinTable OBJECT-TYPE
     SYNTAX      SEQUENCE OF CienaCesPmBasicTxCurrBinEntry
     MAX-ACCESS  not-accessible
     STATUS      current
     DESCRIPTION
            "The (conceptual) read-only table listing the basic TxRx profile
             statistics."
     ::= { cienaCesPmBasicTxStats 2 }

   cienaCesPmBasicTxCurrBinEntry OBJECT-TYPE
     SYNTAX      CienaCesPmBasicTxCurrBinEntry
     MAX-ACCESS  not-accessible
     STATUS      current
     DESCRIPTION
           "An entry (conceptual row) in the cienaCesPmBasicTxCurrBinTable.
            This table lists the statistics for the current bin of the PM
            instance."
     INDEX {cienaCesPmInstanceIndex}
     ::= { cienaCesPmBasicTxCurrBinTable 1 }

   CienaCesPmBasicTxCurrBinEntry ::= SEQUENCE {
     cienaCesPmBasicTxCurrBinStartTime                               DisplayString,
     cienaCesPmBasicTxCurrBinClearedTime                             DisplayString,
     cienaCesPmBasicTxCurrBinDuration                                Unsigned32,
     cienaCesPmBasicTxCurrBinState                                   PmBinState,
     cienaCesPmBasicTxCurrBinTxForwardedBytes                        Counter64,
     cienaCesPmBasicTxCurrBinTxForwardedFrames                       Counter64,
     cienaCesPmBasicTxCurrBinTxBytesPerSec                           Counter64,
     cienaCesPmBasicTxCurrBinTxFramesPerSec                          Counter64
   }
   cienaCesPmBasicTxCurrBinStartTime OBJECT-TYPE
     SYNTAX      DisplayString
     MAX-ACCESS  read-only
     STATUS      current
     DESCRIPTION "Collection start time of the bin."
     ::= { cienaCesPmBasicTxCurrBinEntry 1 }

   cienaCesPmBasicTxCurrBinClearedTime OBJECT-TYPE
     SYNTAX      DisplayString
     MAX-ACCESS  read-only
     STATUS      current
     DESCRIPTION "Cleared time of the bin."
     ::= { cienaCesPmBasicTxCurrBinEntry 2 }

   cienaCesPmBasicTxCurrBinDuration OBJECT-TYPE
     SYNTAX      Unsigned32 (1..65535)
     UNITS       "minutes"
     MAX-ACCESS  read-only
     STATUS      current
     DESCRIPTION "Duration of the bin."
     ::= { cienaCesPmBasicTxCurrBinEntry 3 }

   cienaCesPmBasicTxCurrBinState OBJECT-TYPE
     SYNTAX      PmBinState
     MAX-ACCESS  read-only
     STATUS      current
     DESCRIPTION "State of the bin."
     ::= { cienaCesPmBasicTxCurrBinEntry 4 }
  
   cienaCesPmBasicTxCurrBinTxForwardedBytes OBJECT-TYPE
     SYNTAX      Counter64
     MAX-ACCESS  read-only
     STATUS      current
     DESCRIPTION "The number of bytes forwarded on this PM instance."
     ::= { cienaCesPmBasicTxCurrBinEntry 5 }

   cienaCesPmBasicTxCurrBinTxForwardedFrames OBJECT-TYPE
     SYNTAX      Counter64
     MAX-ACCESS  read-only
     STATUS      current
     DESCRIPTION "The number of frames forwarded on this PM instance."
     ::= { cienaCesPmBasicTxCurrBinEntry 6 }

   cienaCesPmBasicTxCurrBinTxBytesPerSec OBJECT-TYPE
     SYNTAX      Counter64
     MAX-ACCESS  read-only
     STATUS      current
     DESCRIPTION "The number of bytes transmitted per second on this PM
                  instance."
     ::= { cienaCesPmBasicTxCurrBinEntry 7 }

   cienaCesPmBasicTxCurrBinTxFramesPerSec OBJECT-TYPE
     SYNTAX      Counter64
     MAX-ACCESS  read-only
     STATUS      current
     DESCRIPTION
             "The number of frames transmitted per second on this PM instance."
     ::= { cienaCesPmBasicTxCurrBinEntry 8 }

   --BasicTx Profile Stats - current 24 hour bin table  

   cienaCesPmBasicTxCurr24HBinTable OBJECT-TYPE
     SYNTAX      SEQUENCE OF CienaCesPmBasicTxCurr24HBinEntry
     MAX-ACCESS  not-accessible
     STATUS      current
     DESCRIPTION
            "The (conceptual) read-only Table listing the basic TxRx profile
             statistics."
     ::= { cienaCesPmBasicTxStats 3 }

   cienaCesPmBasicTxCurr24HBinEntry OBJECT-TYPE
     SYNTAX      CienaCesPmBasicTxCurr24HBinEntry
     MAX-ACCESS  not-accessible
     STATUS      current
     DESCRIPTION
           "An entry (conceptual row) in the cienaCesPmBasicTxCurr24HBinTable.

           This table lists the statistics for the current 24 Hours bin."
     INDEX {cienaCesPmInstanceIndex}
     ::= { cienaCesPmBasicTxCurr24HBinTable 1 }

   CienaCesPmBasicTxCurr24HBinEntry ::= SEQUENCE {
     cienaCesPmBasicTxCurr24HBinStartTime                            DisplayString,
     cienaCesPmBasicTxCurr24HBinClearedTime                          DisplayString,
     cienaCesPmBasicTxCurr24HBinDuration                             Unsigned32,
     cienaCesPmBasicTxCurr24HBinState                                PmBinState,
     cienaCesPmBasicTxCurr24HBinTxForwardedBytes                     Counter64,
     cienaCesPmBasicTxCurr24HBinTxForwardedFrames                    Counter64,
     cienaCesPmBasicTxCurr24HBinTxBytesPerSec                        Counter64,
     cienaCesPmBasicTxCurr24HBinTxFramesPerSec                       Counter64
   }
   cienaCesPmBasicTxCurr24HBinStartTime OBJECT-TYPE
     SYNTAX      DisplayString
     MAX-ACCESS  read-only
     STATUS      current
     DESCRIPTION "Collection start time of the bin."
     ::= { cienaCesPmBasicTxCurr24HBinEntry 1 }

   cienaCesPmBasicTxCurr24HBinClearedTime OBJECT-TYPE
     SYNTAX      DisplayString
     MAX-ACCESS  read-only
     STATUS      current
     DESCRIPTION "Cleared time of the bin."
     ::= { cienaCesPmBasicTxCurr24HBinEntry 2 }

   cienaCesPmBasicTxCurr24HBinDuration OBJECT-TYPE
     SYNTAX      Unsigned32 (1..65535)
     UNITS       "minutes"
     MAX-ACCESS  read-only
     STATUS      current
     DESCRIPTION "Interval of the bin."
     ::= { cienaCesPmBasicTxCurr24HBinEntry 3 }

   cienaCesPmBasicTxCurr24HBinState OBJECT-TYPE
     SYNTAX      PmBinState
     MAX-ACCESS  read-only
     STATUS      current
     DESCRIPTION "State of the bin."
     ::= { cienaCesPmBasicTxCurr24HBinEntry 4 }

   cienaCesPmBasicTxCurr24HBinTxForwardedBytes OBJECT-TYPE
     SYNTAX      Counter64
     MAX-ACCESS  read-only
     STATUS      current
     DESCRIPTION "The number of bytes forwarded on this PM instance."
     ::= { cienaCesPmBasicTxCurr24HBinEntry 5 }

   cienaCesPmBasicTxCurr24HBinTxForwardedFrames OBJECT-TYPE
     SYNTAX      Counter64
     MAX-ACCESS  read-only
     STATUS      current
     DESCRIPTION "The number of frames forwarded on this PM instance."
     ::= { cienaCesPmBasicTxCurr24HBinEntry 6 }

   cienaCesPmBasicTxCurr24HBinTxBytesPerSec OBJECT-TYPE
     SYNTAX      Counter64
     MAX-ACCESS  read-only
     STATUS      current
     DESCRIPTION "The number of bytes transmitted per second on this PM
                  instance."
     ::= { cienaCesPmBasicTxCurr24HBinEntry 7 }

   cienaCesPmBasicTxCurr24HBinTxFramesPerSec OBJECT-TYPE
     SYNTAX      Counter64
     MAX-ACCESS  read-only
     STATUS      current
     DESCRIPTION "The number of frames transmitted per second on this PM
                  instance."
     ::= { cienaCesPmBasicTxCurr24HBinEntry 8 }

   --BasicTx Profile Stats - history 24 hour bin table  

   cienaCesPmBasicTxHist24HBinTable OBJECT-TYPE
     SYNTAX      SEQUENCE OF CienaCesPmBasicTxHist24HBinEntry
     MAX-ACCESS  not-accessible
     STATUS      current
     DESCRIPTION "The (conceptual) read-only table listing the basic TxRx
                  profile statistics."
     ::= { cienaCesPmBasicTxStats 4 }

   cienaCesPmBasicTxHist24HBinEntry OBJECT-TYPE
     SYNTAX      CienaCesPmBasicTxHist24HBinEntry
     MAX-ACCESS  not-accessible
     STATUS      current
     DESCRIPTION
           "An entry (conceptual row) in the cienaCesPmBasicTxHist24HBinTable.

           This table lists the statistics for the history 24 hours bin."
     INDEX {cienaCesPmInstanceIndex}
     ::= { cienaCesPmBasicTxHist24HBinTable 1 }

   CienaCesPmBasicTxHist24HBinEntry ::= SEQUENCE {
     cienaCesPmBasicTxHist24HBinStartTime                            DisplayString,
     cienaCesPmBasicTxHist24HBinEndTime                              DisplayString,
     cienaCesPmBasicTxHist24HBinClearTime                            DisplayString,
     cienaCesPmBasicTxHist24HBinDuration                             Unsigned32,
     cienaCesPmBasicTxHist24HBinState                                PmBinState,
     cienaCesPmBasicTxHist24HBinBasicTxForwardedBytes                Counter64,
     cienaCesPmBasicTxHist24HBinBasicTxForwardedFrames               Counter64,
     cienaCesPmBasicTxHist24HBinBasicTxBytesPerSec                   Counter64,
     cienaCesPmBasicTxHist24HBinBasicTxFramesPerSec                  Counter64
   }
   cienaCesPmBasicTxHist24HBinStartTime OBJECT-TYPE
     SYNTAX      DisplayString
     MAX-ACCESS  read-only
     STATUS      current
     DESCRIPTION "Collection start time of the bin."
     ::= { cienaCesPmBasicTxHist24HBinEntry 1 }

   cienaCesPmBasicTxHist24HBinEndTime OBJECT-TYPE
     SYNTAX      DisplayString
     MAX-ACCESS  read-only
     STATUS      current
     DESCRIPTION "Collection end time of the bin."
     ::= { cienaCesPmBasicTxHist24HBinEntry 2 }

   cienaCesPmBasicTxHist24HBinClearTime OBJECT-TYPE
     SYNTAX      DisplayString
     MAX-ACCESS  read-only
     STATUS      current
     DESCRIPTION "Collection clear time of the bin."
      ::= { cienaCesPmBasicTxHist24HBinEntry 3 }

   cienaCesPmBasicTxHist24HBinDuration OBJECT-TYPE
     SYNTAX      Unsigned32 (1..65535)
     UNITS       "minutes"
     MAX-ACCESS  read-only
     STATUS      current
     DESCRIPTION "Interval of the bin."
     ::= { cienaCesPmBasicTxHist24HBinEntry 4 }

   cienaCesPmBasicTxHist24HBinState OBJECT-TYPE
     SYNTAX      PmBinState
     MAX-ACCESS  read-only
     STATUS      current
     DESCRIPTION "State of the bin."
     ::= { cienaCesPmBasicTxHist24HBinEntry 5 }

   cienaCesPmBasicTxHist24HBinBasicTxForwardedBytes OBJECT-TYPE
     SYNTAX      Counter64
     MAX-ACCESS  read-only
     STATUS      current
     DESCRIPTION "The number of bytes forwarded on this PM instance."
     ::= { cienaCesPmBasicTxHist24HBinEntry 6 }

   cienaCesPmBasicTxHist24HBinBasicTxForwardedFrames OBJECT-TYPE
     SYNTAX      Counter64
     MAX-ACCESS  read-only
     STATUS      current
     DESCRIPTION "The number of frames forwarded on this PM instance."
     ::= { cienaCesPmBasicTxHist24HBinEntry 7 }

   cienaCesPmBasicTxHist24HBinBasicTxBytesPerSec OBJECT-TYPE
     SYNTAX      Counter64
     MAX-ACCESS  read-only
     STATUS      current
     DESCRIPTION "The number of bytes transmitted per second on this PM
                  instance."
     ::= { cienaCesPmBasicTxHist24HBinEntry 8 }

   cienaCesPmBasicTxHist24HBinBasicTxFramesPerSec OBJECT-TYPE
     SYNTAX      Counter64
     MAX-ACCESS  read-only
     STATUS      current
     DESCRIPTION "The number of frames transmitted per second on this PM
                  instance."
     ::= { cienaCesPmBasicTxHist24HBinEntry 9 }

   --BasicTx Profile Stats, statistics bin

   cienaCesPmBasicTxStatisticsBinTable OBJECT-TYPE
     SYNTAX      SEQUENCE OF CienaCesPmBasicTxStatisticsBinEntry
     MAX-ACCESS  not-accessible
     STATUS      current
     DESCRIPTION "The (conceptual) read-only table listing the bin statistics."
     ::= { cienaCesPmBasicTxStats 5 }

   cienaCesPmBasicTxStatisticsBinEntry OBJECT-TYPE
     SYNTAX      CienaCesPmBasicTxStatisticsBinEntry
     MAX-ACCESS  not-accessible
     STATUS      current
     DESCRIPTION "An entry (conceptual row) in the
                  cienaCesPmBasicTxStatisticsBinTable.

                  This table lists the statistics for the statistics bin of the
                  PM instance."
     INDEX {cienaCesPmInstanceIndex}
     ::= { cienaCesPmBasicTxStatisticsBinTable 1 }

   CienaCesPmBasicTxStatisticsBinEntry ::= SEQUENCE {
     cienaCesPmBasicTxStatsBinStartTime                              DisplayString,
     cienaCesPmBasicTxStatsBinClearTime                              DisplayString,
     cienaCesPmBasicTxStatsBinTxForwardedBytes                       Counter64,
     cienaCesPmBasicTxStatsBinTxForwardedFrames                      Counter64,
     cienaCesPmBasicTxStatsBinTxBytesPerSec                          Counter64,
     cienaCesPmBasicTxStatsBinTxFramesPerSec                         Counter64
   }

   cienaCesPmBasicTxStatsBinStartTime OBJECT-TYPE
     SYNTAX      DisplayString
     MAX-ACCESS  read-only
     STATUS      current
     DESCRIPTION "Collection start time of the bin."
     ::= { cienaCesPmBasicTxStatisticsBinEntry 1 }

   cienaCesPmBasicTxStatsBinClearTime OBJECT-TYPE
     SYNTAX      DisplayString
     MAX-ACCESS  read-only
     STATUS      current
     DESCRIPTION "Collection clear time of the bin."
     ::= { cienaCesPmBasicTxStatisticsBinEntry 2 }

   cienaCesPmBasicTxStatsBinTxForwardedBytes OBJECT-TYPE
     SYNTAX      Counter64
     MAX-ACCESS  read-only
     STATUS      current
     DESCRIPTION "The number of bytes forwarded on this PM instance."
     ::= { cienaCesPmBasicTxStatisticsBinEntry 3 }

   cienaCesPmBasicTxStatsBinTxForwardedFrames OBJECT-TYPE
     SYNTAX      Counter64
     MAX-ACCESS  read-only
     STATUS      current
     DESCRIPTION "The number of frames forwarded on this PM instance."
     ::= { cienaCesPmBasicTxStatisticsBinEntry 4 }

   cienaCesPmBasicTxStatsBinTxBytesPerSec OBJECT-TYPE
     SYNTAX      Counter64
     MAX-ACCESS  read-only
     STATUS      current
     DESCRIPTION "The number of bytes transmitted per second on this PM
                  instance."
     ::= { cienaCesPmBasicTxStatisticsBinEntry 5 }

   cienaCesPmBasicTxStatsBinTxFramesPerSec OBJECT-TYPE
     SYNTAX      Counter64
     MAX-ACCESS  read-only
     STATUS      current
     DESCRIPTION "The number of frames transmitted per second on this PM
                  instance."
     ::= { cienaCesPmBasicTxStatisticsBinEntry 6 }

   --BasicTx Profile Stats, total statistics bin

   cienaCesPmBasicTxTotalStatisticsBinTable OBJECT-TYPE
     SYNTAX      SEQUENCE OF CienaCesPmBasicTxTotalStatisticsBinEntry
     MAX-ACCESS  not-accessible
     STATUS      current
     DESCRIPTION "The (conceptual) read-only table listing the bin statistics."
     ::= { cienaCesPmBasicTxStats 6 }

   cienaCesPmBasicTxTotalStatisticsBinEntry OBJECT-TYPE
     SYNTAX      CienaCesPmBasicTxTotalStatisticsBinEntry
     MAX-ACCESS  not-accessible
     STATUS      current
     DESCRIPTION "An entry (conceptual row) in the
                  cienaCesPmBasicTxTotalStatisticsBinTable.

                  This table lists the statistics for the total statistics bin
                  of the PM instance."
     INDEX {cienaCesPmInstanceIndex}
     ::= { cienaCesPmBasicTxTotalStatisticsBinTable 1 }

   CienaCesPmBasicTxTotalStatisticsBinEntry ::= SEQUENCE {
     cienaCesPmBasicTxTotalStatsBinStartTime                         DisplayString,
     cienaCesPmBasicTxTotalStatsBinTxForwardedBytes                  Counter64,
     cienaCesPmBasicTxTotalStatsBinTxForwardedFrames                 Counter64,
     cienaCesPmBasicTxTotalStatsBinTxBytesPerSec                     Counter64,
     cienaCesPmBasicTxTotalStatsBinTxFramesPerSec                    Counter64
   }

   cienaCesPmBasicTxTotalStatsBinStartTime OBJECT-TYPE
     SYNTAX      DisplayString
     MAX-ACCESS  read-only
     STATUS      current
     DESCRIPTION "Collection start time of the bin."
     ::= { cienaCesPmBasicTxTotalStatisticsBinEntry 1 }

   cienaCesPmBasicTxTotalStatsBinTxForwardedBytes OBJECT-TYPE
     SYNTAX      Counter64
     MAX-ACCESS  read-only
     STATUS      current
     DESCRIPTION "The number of bytes forwarded on this PM instance."
     ::= { cienaCesPmBasicTxTotalStatisticsBinEntry 2 }

   cienaCesPmBasicTxTotalStatsBinTxForwardedFrames OBJECT-TYPE
     SYNTAX      Counter64
     MAX-ACCESS  read-only
     STATUS      current
     DESCRIPTION "The number of frames forwarded on this PM instance."
     ::= { cienaCesPmBasicTxTotalStatisticsBinEntry 3 }

   cienaCesPmBasicTxTotalStatsBinTxBytesPerSec OBJECT-TYPE
     SYNTAX      Counter64
     MAX-ACCESS  read-only
     STATUS      current
     DESCRIPTION "The number of bytes transmitted per second on this PM
                  instance."
     ::= { cienaCesPmBasicTxTotalStatisticsBinEntry 4 }

   cienaCesPmBasicTxTotalStatsBinTxFramesPerSec OBJECT-TYPE
     SYNTAX      Counter64
     MAX-ACCESS  read-only
     STATUS      current
     DESCRIPTION "The number of frames transmitted per second on this PM
                  instance."
     ::= { cienaCesPmBasicTxTotalStatisticsBinEntry 5 }


   --
   -- PM Instance Index Xref tables.
   --
   cienaCesPmInstanceIndexXrefAutoTable OBJECT-TYPE
     SYNTAX     SEQUENCE OF CienaCesPmInstanceIndexXrefAutoEntry
     MAX-ACCESS not-accessible
     STATUS     current
     DESCRIPTION
            "The (conceptual) table listing the cienaCesPmInstanceIndex values for each
             row as identified by its unique combination of indexes, as specified by:
             cienaCesPmInstanceInterfaceType, cienaCesPmInstanceInterfaceId,
             cienaCesPmInstanceInterfaceId2, and cienaCesPmInstanceProfileType.
             
             This table allows for direct lookup of a cienaCesPmInstanceIndex by
             for each PM Instance that has been created automatically by the system.
             This table provides lookup for PM Instances which are defined in the
             cienaCesPmInstanceTable with a cienaCesPmInstanceConfigurationMode
             value of auto.

             By providing this direct method of determining a PM Instance index for
             a given interface and profile type, an agent can more rapidly perform a
             subsequent query of the applicable table underneath the cienaCesPmStatistics
             branch to directly query statistics for the given interface and profile type."
     ::= { cienaCesPmInstanceIndexXrefAuto 1 }
                
   cienaCesPmInstanceIndexXrefAutoEntry OBJECT-TYPE
     SYNTAX      CienaCesPmInstanceIndexXrefAutoEntry
     MAX-ACCESS  not-accessible
     STATUS      current
     DESCRIPTION
           "An entry (conceptual row) in the cienaCesPmInstanceIndexXrefAutoTable."
     INDEX { cienaCesPmInstanceInterfaceType,
             cienaCesPmInstanceInterfaceId,
             cienaCesPmInstanceInterfaceId2,
             cienaCesPmInstanceProfileType }
     ::= { cienaCesPmInstanceIndexXrefAutoTable 1 }
        
   CienaCesPmInstanceIndexXrefAutoEntry ::=  SEQUENCE {               
     cienaCesPmInstanceIndexXrefAutoValue                      Unsigned32
   }

   cienaCesPmInstanceIndexXrefAutoValue OBJECT-TYPE
     SYNTAX      Unsigned32
     MAX-ACCESS  read-only
     STATUS      current
     DESCRIPTION
             "The value returned by this object represents the cienaCesPmInstanceIndex
              for the single auto-created PM Instance associated with the given indexes.

              The value may be used as a subsequent index into any tables which are
              indexed by the cienaCesPmInstanceIndex object, in order to obtain further
              information about the PM Interface."
     ::= { cienaCesPmInstanceIndexXrefAutoEntry 1 } 

   --
   -- PM Interval Profile Table
   --
   cienaCesPmIntervalProfileNextIndex OBJECT-TYPE
     SYNTAX      Unsigned32(0..2147483647)
     MAX-ACCESS  read-only
     STATUS      current
     DESCRIPTION "This object contains an unused value for
                  cienaCesPmIntervalProfileIndex, or zero to indicate that no
                  index is available (table full).  When creating an interval
                  profile in the cienaCesPmIntervalProfileTable, this object
                  may be used to determine an appropriate value for the
                  cienaCesPmIntervalProfileIndex object."
     ::= { cienaCesPmIntervalProfile 1 }

   cienaCesPmIntervalProfileTable OBJECT-TYPE
     SYNTAX      SEQUENCE OF CienaCesPmIntervalProfileEntry
     MAX-ACCESS  not-accessible
     STATUS      current
     DESCRIPTION
            "The (conceptual) table listing the configuration
             parameters for the PM interval profile table.
            
             To create an entry in this table, values are required
             for cienaCesPmIntervalProfileName,
             cienaCesPmIntervalProfileSampleInterval, and
             cienaCesPmIntervalProfileRowStatus must be set to createAndGo."
     ::= { cienaCesPmIntervalProfile 2 }

   cienaCesPmIntervalProfileEntry OBJECT-TYPE
     SYNTAX      CienaCesPmIntervalProfileEntry
     MAX-ACCESS  not-accessible
     STATUS      current
     DESCRIPTION
           "An entry (conceptual row) in the cienaCesPmIntervalProfileTable."
     INDEX { cienaCesPmIntervalProfileIndex }
     ::= { cienaCesPmIntervalProfileTable 1 }

   CienaCesPmIntervalProfileEntry ::=  SEQUENCE {
     cienaCesPmIntervalProfileIndex                          Unsigned32,
     cienaCesPmIntervalProfileName                           DisplayString,
     cienaCesPmIntervalProfileSampleInterval                 INTEGER,
     cienaCesPmIntervalProfileCfgAttrsInUse                  PmTcaIntProfCfgAttrs,
     cienaCesPmIntervalProfileCfgAttrsUnset                  PmTcaIntProfCfgAttrs,
     cienaCesPmIntervalProfileAdjustmentInterval             Unsigned32,
     cienaCesPmIntervalProfileAdjustmentThreshold            Unsigned32,
     cienaCesPmIntervalProfileAdjustmentThresholdPercentage  Unsigned32,
     cienaCesPmIntervalProfileOverflowThreshold              Unsigned32,
     cienaCesPmIntervalProfileOverflowThresholdPercentage    Unsigned32,
     cienaCesPmIntervalProfileOverflowCount                  Unsigned32,
     cienaCesPmIntervalProfileUnderflowThreshold             Unsigned32,
     cienaCesPmIntervalProfileUnderflowThresholdPercentage   Unsigned32,
     cienaCesPmIntervalProfileUnderflowCount                 Unsigned32,
     cienaCesPmIntervalProfileAlertInterval                  Unsigned32,
     cienaCesPmIntervalProfileAlertThresholdPercentage       Unsigned32,
     cienaCesPmIntervalProfileRowStatus                      RowStatus
   }

   cienaCesPmIntervalProfileIndex OBJECT-TYPE
     SYNTAX      Unsigned32(1..2147483647)
     MAX-ACCESS  not-accessible
     STATUS      current
     DESCRIPTION "A unique identifier for the PM interval profile entry."
     ::= { cienaCesPmIntervalProfileEntry 1 }

   cienaCesPmIntervalProfileName OBJECT-TYPE
     SYNTAX      DisplayString (SIZE (1..31))
     MAX-ACCESS  read-create
     STATUS      current
     DESCRIPTION "Name for the PM interval profile."
     ::= { cienaCesPmIntervalProfileEntry 2 }

   cienaCesPmIntervalProfileSampleInterval OBJECT-TYPE
     SYNTAX      INTEGER {
                           other(1),
                           minutes1(2),
                           minutes5(3),
                           minutes10(4),
                           minutes15(5),
                           minutes30(6),
                           minutes60(7),
                           hours24(8)
                 }
     MAX-ACCESS	 read-create
     STATUS      current
     DESCRIPTION "The period of time for each sample interval.  Value returned
                  should by one of the time periods supported by the system."
     ::= { cienaCesPmIntervalProfileEntry 3 }

   cienaCesPmIntervalProfileCfgAttrsInUse OBJECT-TYPE
     SYNTAX      PmTcaIntProfCfgAttrs
     MAX-ACCESS	 read-only
     STATUS      current
     DESCRIPTION
            "This object indicates the row entries with active configuration.
             Corresponding rows with a set bit indicated by this object will be
             used by the PM instances which are associated with this profile.
             This object is automatically populated based on the row objects
             which are successfully included during a row creation or are
             successfully set or unset after a row has been created.

             Each named bit in this object corresponds to the row object in this
             table representing the same configuration attribute."
     ::= { cienaCesPmIntervalProfileEntry 4 }

   cienaCesPmIntervalProfileCfgAttrsUnset OBJECT-TYPE
     SYNTAX      PmTcaIntProfCfgAttrs
     MAX-ACCESS	 read-create
     STATUS      current
     DESCRIPTION
            "This object may be used to unset attributes, effectively disabling
             the feature for which the attribute is used.  When this object is
             set, the indiciated configuration items will be unset which may
             disable the feature which uses the specified configuration
             attribute.  Such changes will automatically apply to all PM
             instances associated with the specified interval profile.

             This object may only be set on an existing row.  Attempts to
             include this object during a row creation will be rejected.

             This object will always return all bits zero.

             Each named bit in this object corresponds to the row object in this
             table representing the same configuration attribute."
     ::= { cienaCesPmIntervalProfileEntry 5 }

   cienaCesPmIntervalProfileAdjustmentInterval OBJECT-TYPE
     SYNTAX      Unsigned32(0..2592000)
     UNITS       "seconds"
     MAX-ACCESS  read-create
     STATUS      current
     DESCRIPTION "The adjustment interval used by the Adjustment TCA feature.
                  The specified value must conform to the following criteria:
                   -Evenly divisible by the specified sample interval.
                   -Equal or greater than the sample interval.
                   -No more than a 1 month period (30 days).
                  Value 0 is used when the attribute is not in use, after having
                  been unset.  Value 0 may not be set directly.  The set request
                  will be rejected if the specified value does not conform to
                  the critera established for this attribute."
     ::= { cienaCesPmIntervalProfileEntry 6 }

   cienaCesPmIntervalProfileAdjustmentThreshold OBJECT-TYPE
     SYNTAX      Unsigned32(0..2147483647)
     MAX-ACCESS  read-create
     STATUS      current
     DESCRIPTION "The threshold value which is applied against the adjustment
                  basis value maintained by the PM instance associated with this
                  interval profile.  Sample values that are within this
                  threshold value (above and below) the basis value are
                  considered normal and not subject to causing an Adjustment
                  TCA event."
     ::= { cienaCesPmIntervalProfileEntry 7 }

   cienaCesPmIntervalProfileAdjustmentThresholdPercentage OBJECT-TYPE
     SYNTAX      Unsigned32(0..100)
     MAX-ACCESS  read-create
     STATUS      current
     DESCRIPTION "The percentage amount of the adjustment basis which defines
                  the range of normal values (above and below) the basis.
                  Sample values which are outside this range are subject to
                  causing an Adjustment TCA event."
     ::= { cienaCesPmIntervalProfileEntry 8 }

   cienaCesPmIntervalProfileOverflowThreshold OBJECT-TYPE
     SYNTAX      Unsigned32(0..2147483647)
     MAX-ACCESS  read-create
     STATUS      current
     DESCRIPTION "The threshold value which is applied against the adjustment
                  basis value maintained by the PM instance associated with this
                  interval profile.  Sample values that are within this
                  threshold value (above) the basis value are considered normal
                  and not subject to causing an Overflow condition.  Values that
                  exceed this range will cause an overflow condition to occur
                  at the end of the sample interval, which may cause an
                  Adjustment TCA if the overflow count has been reached."
     ::= { cienaCesPmIntervalProfileEntry 9 }

   cienaCesPmIntervalProfileOverflowThresholdPercentage OBJECT-TYPE
     SYNTAX      Unsigned32(0..100)
     MAX-ACCESS  read-create
     STATUS      current
     DESCRIPTION "The percentage amount of the adjustment basis which defines
                  the range of normal values (above) the basis.  Sample values
                  that are within this threshold (above) the basis value are
                  considered normal and not subject to causing an Overflow
                  condition."
     ::= { cienaCesPmIntervalProfileEntry 10 }

   cienaCesPmIntervalProfileOverflowCount OBJECT-TYPE
     SYNTAX      Unsigned32(0..2147483647)
     MAX-ACCESS  read-create
     STATUS      current
     DESCRIPTION "The number of consecutive sample intervals, all of which are
                  in overflow condition, before an Adjustment TCA occurs due to
                  overflow.  Value 0 is used when the attribute is not in use,
                  after having been unset.  Value 0 may not be set directly."
     ::= { cienaCesPmIntervalProfileEntry 11 }

   cienaCesPmIntervalProfileUnderflowThreshold OBJECT-TYPE
     SYNTAX      Unsigned32(0..2147483647)
     MAX-ACCESS  read-create
     STATUS      current
     DESCRIPTION "The threshold value which is applied against the adjustment
                  basis value maintained by the PM instance associated with this
                  interval profile.  Sample values that are within this
                  threshold value (below) the basis value are considered normal
                  and not subject to causing an underflow condition.  Values
                  that precede this range will cause an underflow condition to
                  occur at the end of the sample interval, which may cause an
                  Adjustment TCA if the underflow count has been reached."
     ::= { cienaCesPmIntervalProfileEntry 12 } 

   cienaCesPmIntervalProfileUnderflowThresholdPercentage OBJECT-TYPE
     SYNTAX      Unsigned32(0..100)
     MAX-ACCESS  read-create
     STATUS      current
     DESCRIPTION "The percentage amount of the adjustment basis which defines
                  the range of normal values (below) the basis.  Sample values
                  that are within this threshold (below) the basis value are
                  considered normal and not subject to causing an underflow
                  condition."
     ::= { cienaCesPmIntervalProfileEntry 13 } 

   cienaCesPmIntervalProfileUnderflowCount OBJECT-TYPE
     SYNTAX      Unsigned32(0..2147483647)
     MAX-ACCESS  read-create
     STATUS      current
     DESCRIPTION "The number of consecutive sample intervals, all of which are
                  in underflow condition, before an adjustment TCA occurs due to
                  underflow.  Value 0 may not be set directly.  Value 0 may not
                  be set directly."
     ::= { cienaCesPmIntervalProfileEntry 14 } 

   cienaCesPmIntervalProfileAlertInterval OBJECT-TYPE
     SYNTAX      Unsigned32(0..2592000)
     UNITS       "seconds"
     MAX-ACCESS  read-create
     STATUS      current
     DESCRIPTION "The alert interval used by the Alert TCA feature.
                  The specified value must conform to the following criteria:
                   -Evenly divisible by the specified sample interval.
                   -Equal or greater than the sample interval.
                   -No more than a 1 month period (30 days).
                  Value 0 is used when the attribute is not in use, after having
                  been unset.  Value 0 may not be set directly.  The set request
                  will be rejected if the specified value does not conform to
                  the critera established for this attribute."
     ::= { cienaCesPmIntervalProfileEntry 15 }

   cienaCesPmIntervalProfileAlertThresholdPercentage OBJECT-TYPE
     SYNTAX      Unsigned32(0..100)
     MAX-ACCESS  read-create
     STATUS      current
     DESCRIPTION "The percentage amount of the alert basis which defines the
                  level below the basis at which point a sample reading is
                  subject to causing an Alert TCA at the end of the alert
                  interval."
     ::= { cienaCesPmIntervalProfileEntry 16 }

   cienaCesPmIntervalProfileRowStatus OBJECT-TYPE
     SYNTAX      RowStatus
     MAX-ACCESS  read-create
     STATUS      current
     DESCRIPTION
             "Used to manage the creation and deletion of the conceptual rows in
              this table.  Row deletion will not be allowed if the interval
              profile is presently associated with one or more PM instances.

              To create a row in this table, set this object to 'createAndGo'.
              To delete a row in this table, set this object to 'destroy'."
     ::= { cienaCesPmIntervalProfileEntry 17 }

   cienaCesPmIntervalProfileUsageTable OBJECT-TYPE
     SYNTAX      SEQUENCE OF CienaCesPmIntervalProfileUsageEntry
     MAX-ACCESS  not-accessible
     STATUS      current
     DESCRIPTION
            "The (conceptual) table providing a list of the PM instances which
             are configured to use each PM interval profile.

             This table utilizes a dual indexing scheme allowing rows to
             exist representing the present configuration of the interval
             profiles and pm instances.

             For each interval profile (primary index) there are zero or more
             PM instances which are configured (secondary index).  If an
             interval profile has no PM Instances, there will be zero rows in
             this table with the interval profile primary index."
     ::= { cienaCesPmIntervalProfile 3 }

   cienaCesPmIntervalProfileUsageEntry OBJECT-TYPE
     SYNTAX      CienaCesPmIntervalProfileUsageEntry
     MAX-ACCESS  not-accessible
     STATUS      current
     DESCRIPTION
           "An entry (conceptual row) in the cienaCesPmIntervalProfileUsageTable."
     INDEX { cienaCesPmIntervalProfileIndex,
             cienaCesPmInstanceIndex }
     ::= { cienaCesPmIntervalProfileUsageTable 1 }

   CienaCesPmIntervalProfileUsageEntry ::=  SEQUENCE {
     cienaCesPmIntervalProfileInstanceOperState                      CienaGlobalState
   }

   cienaCesPmIntervalProfileInstanceOperState OBJECT-TYPE
     SYNTAX      CienaGlobalState
     MAX-ACCESS  read-only
     STATUS      current
     DESCRIPTION
             "Operational state for the PM instance identified by the second
              index of this table entry.  This object provides a way to rapidly
              determine the operational state of the PM instance(s) associated
              with the interval profile, as identified by the primary index of
              this table entry, in lieu of directly accessing or walking the
              cienaCesPmInstanceOperState object."
     ::= { cienaCesPmIntervalProfileUsageEntry 1 }

   --
   -- PM Instance Threshold Table
   --
   cienaCesPmInstanceThresholdTable OBJECT-TYPE
     SYNTAX      SEQUENCE OF CienaCesPmInstanceThresholdEntry
     MAX-ACCESS  not-accessible
     STATUS      current
     DESCRIPTION
            "The (conceptual) table listing parameters for the PM instance
             table which are applicable to the PM Threshold feature."
     ::= { cienaCesPmInstanceThreshold 1 }

   cienaCesPmInstanceThresholdEntry OBJECT-TYPE
     SYNTAX      CienaCesPmInstanceThresholdEntry
     MAX-ACCESS  not-accessible
     STATUS      current
     DESCRIPTION
           "An entry (conceptual row) in the cienaCesPmInstanceThresholdTable.
            This table serves as an extension of the cienaCesPmInstanceTable,
            representing configuration parameters for each PM instance,
            specific to the PM Threshold feature(s)."
     AUGMENTS { cienaCesPmInstanceEntry }
     ::= { cienaCesPmInstanceThresholdTable 1 }

   CienaCesPmInstanceThresholdEntry ::=  SEQUENCE {
     cienaCesPmInstanceIntervalProfileIndex                 Unsigned32,
     cienaCesPmInstanceTcaStatisticsClear                   CienaStatsClear,
     cienaCesPmInstanceTcaHistoryClear                      CienaStatsClear
   }

   cienaCesPmInstanceIntervalProfileIndex OBJECT-TYPE
     SYNTAX      Unsigned32(0..2147483647)
     MAX-ACCESS  read-create
     STATUS      current
     DESCRIPTION "This object indicates the interval profile associated with the
                  PM instance which will be used by the PM Threshold features
                  corresponding to a row in the cienaCesPmIntervalProfileTable
                  with a cienaCesPmIntervalProfileIndex of matching value.

                  When value is zero, the PM instance is not associated with any
                  interval profile and will not participate in the PM Threshold
                  features."
     ::= { cienaCesPmInstanceThresholdEntry 1 }

   cienaCesPmInstanceTcaStatisticsClear OBJECT-TYPE
     SYNTAX      CienaStatsClear
     MAX-ACCESS  read-create
     STATUS      current
     DESCRIPTION "Setting this object to clear(1) will clear the statistics that
                  track the operation of the PM TCA feature on the PM instance.
                  This will clear the various counters associated with the
                  Adjustment TCA and Alert TCA mechanism such as number of TCA
                  events and samples collected on behalf of the PM instance."
     ::= { cienaCesPmInstanceThresholdEntry 2 }

   cienaCesPmInstanceTcaHistoryClear OBJECT-TYPE
     SYNTAX      CienaStatsClear
     MAX-ACCESS  read-create
     STATUS      current
     DESCRIPTION "Setting this object to clear(1) will clear the history records
                  related to the operation of the PM TCA feature on the PM
                  instance.  This will clear all records of the last Adjustment
                  TCA events and the last Alert TCA event that have occurred on
                  the PM instance."
     ::= { cienaCesPmInstanceThresholdEntry 3 }

   --
   -- PM Instance Adjustment TCA Table
   --
   cienaCesPmInstanceAdjustmentTcaTable OBJECT-TYPE
     SYNTAX      SEQUENCE OF CienaCesPmInstanceAdjustmentTcaEntry
     MAX-ACCESS  not-accessible
     STATUS      current
     DESCRIPTION
            "The (conceptual) table listing data for the PM instance table which
             is applicable to the PM Threshold Adjustment TCA feature."
     ::= { cienaCesPmInstanceAdjustmentTca 1 }

   cienaCesPmInstanceAdjustmentTcaEntry OBJECT-TYPE
     SYNTAX      CienaCesPmInstanceAdjustmentTcaEntry
     MAX-ACCESS  not-accessible
     STATUS      current
     DESCRIPTION
           "An entry (conceptual row) in the
            cienaCesPmInstanceAdjustmentTcaTable.
            This table serves as an extension of the cienaCesPmInstanceTable,
            representing operational data for each PM instance, specific to the
            PM Threshold Adjustment TCA feature."
     AUGMENTS { cienaCesPmInstanceEntry }
     ::= { cienaCesPmInstanceAdjustmentTcaTable 1 }

   CienaCesPmInstanceAdjustmentTcaEntry ::=  SEQUENCE {
     cienaCesPmAdjustmentTcaUnits                           PmTcaUnits,
     cienaCesPmAdjustmentTcaScheme                          PmTcaScheme,
     cienaCesPmAdjustmentTcaStats                           PmStatBitmap,
     cienaCesPmAdjustmentTcaBasisValue                      PmTcaUnsigned64,
     cienaCesPmAdjustmentTcaBasisValueMin                   PmTcaUnsigned64,
     cienaCesPmAdjustmentTcaBasisValueMax                   PmTcaUnsigned64,
     cienaCesPmAdjustmentTcaConfigStatus                    PmTcaConfigStatus,
     cienaCesPmAdjustmentTcaUpperBoundaryValue              PmTcaUnsigned64,
     cienaCesPmAdjustmentTcaLowerBoundaryValue              PmTcaUnsigned64,
     cienaCesPmAdjustmentTcaIntervalStartTime               PmTimeDate,
     cienaCesPmAdjustmentTcaIntervalEndTime                 PmTimeDate,
     cienaCesPmAdjustmentTcaSampleStartTime                 PmTimeDate,
     cienaCesPmAdjustmentTcaSampleEndTime                   PmTimeDate,
     cienaCesPmAdjustmentTcaHighWatermarkTime               PmTimeDate,
     cienaCesPmAdjustmentTcaHighWatermarkStats              PmStatBitmap,
     cienaCesPmAdjustmentTcaHighWatermarkValue              PmTcaUnsigned64,
     cienaCesPmAdjustmentTcaOverflowConfigStatus            PmTcaConfigStatus,
     cienaCesPmAdjustmentTcaOverflowBoundaryValue           PmTcaUnsigned64,
     cienaCesPmAdjustmentTcaOverflowCurrentCount            Unsigned32,
     cienaCesPmAdjustmentTcaOverflowHighWatermarkTime       PmTimeDate,
     cienaCesPmAdjustmentTcaOverflowHighWatermarkStats      PmStatBitmap,
     cienaCesPmAdjustmentTcaOverflowHighWatermarkValue      PmTcaUnsigned64,
     cienaCesPmAdjustmentTcaUnderflowConfigStatus           PmTcaConfigStatus,
     cienaCesPmAdjustmentTcaUnderflowBoundaryValue          PmTcaUnsigned64,
     cienaCesPmAdjustmentTcaUnderflowCurrentCount           Unsigned32,
     cienaCesPmAdjustmentTcaUnderflowHighWatermarkTime      PmTimeDate,
     cienaCesPmAdjustmentTcaUnderflowHighWatermarkStats     PmStatBitmap,
     cienaCesPmAdjustmentTcaUnderflowHighWatermarkValue     PmTcaUnsigned64,
     cienaCesPmAdjustmentTcaEventsTotal                     Unsigned32,
     cienaCesPmAdjustmentTcaEventsIntervalEndUpperBoundary  Unsigned32,
     cienaCesPmAdjustmentTcaEventsIntervalEndLowerBoundary  Unsigned32,
     cienaCesPmAdjustmentTcaEventsOverflowCountReached      Unsigned32,
     cienaCesPmAdjustmentTcaEventsUnderflowCountReached     Unsigned32,
     cienaCesPmAdjustmentTcaSamplesProcessedTotal           Unsigned32,
     cienaCesPmAdjustmentTcaSamplesDiscardedTotal           Unsigned32,
     cienaCesPmAdjustmentTcaSamplesProcessedCurrentInterval Unsigned32,
     cienaCesPmAdjustmentTcaSamplesDiscardedCurrentInterval Unsigned32,
     cienaCesPmAdjustmentTcaLastIntvlEndTcaTime             PmTimeDate,
     cienaCesPmAdjustmentTcaLastIntvlEndTcaUnits            PmTcaUnits,
     cienaCesPmAdjustmentTcaLastIntvlEndTcaScheme           PmTcaScheme,
     cienaCesPmAdjustmentTcaLastIntvlEndTcaBasisValue       PmTcaUnsigned64,
     cienaCesPmAdjustmentTcaLastIntvlEndTcaBasisValueMin    PmTcaUnsigned64,
     cienaCesPmAdjustmentTcaLastIntvlEndTcaBasisValueMax    PmTcaUnsigned64,
     cienaCesPmAdjustmentTcaLastIntvlEndTcaThresholdType    PmTcaThresholdType,
     cienaCesPmAdjustmentTcaLastIntvlEndTcaThresholdValue   Unsigned32,
     cienaCesPmAdjustmentTcaLastIntvlEndTcaBoundaryValue    PmTcaUnsigned64,
     cienaCesPmAdjustmentTcaLastIntvlEndTcaWatermarkTime    PmTimeDate,
     cienaCesPmAdjustmentTcaLastIntvlEndTcaWatermarkType    PmTcaWatermarkType,
     cienaCesPmAdjustmentTcaLastIntvlEndTcaWatermarkStats   PmStatBitmap,
     cienaCesPmAdjustmentTcaLastIntvlEndTcaWatermarkValue   PmTcaUnsigned64,
     cienaCesPmAdjustmentTcaLastOverflowTcaTime             PmTimeDate,
     cienaCesPmAdjustmentTcaLastOverflowTcaUnits            PmTcaUnits,
     cienaCesPmAdjustmentTcaLastOverflowTcaScheme           PmTcaScheme,
     cienaCesPmAdjustmentTcaLastOverflowTcaBasisValue       PmTcaUnsigned64,
     cienaCesPmAdjustmentTcaLastOverflowTcaBasisValueMin    PmTcaUnsigned64,
     cienaCesPmAdjustmentTcaLastOverflowTcaBasisValueMax    PmTcaUnsigned64,
     cienaCesPmAdjustmentTcaLastOverflowTcaThresholdType    PmTcaThresholdType,
     cienaCesPmAdjustmentTcaLastOverflowTcaThresholdValue   Unsigned32,
     cienaCesPmAdjustmentTcaLastOverflowTcaBoundaryValue    PmTcaUnsigned64,
     cienaCesPmAdjustmentTcaLastOverflowTcaWatermarkTime    PmTimeDate,
     cienaCesPmAdjustmentTcaLastOverflowTcaWatermarkType    PmTcaWatermarkType,
     cienaCesPmAdjustmentTcaLastOverflowTcaWatermarkStats   PmStatBitmap,
     cienaCesPmAdjustmentTcaLastOverflowTcaWatermarkValue   PmTcaUnsigned64,
     cienaCesPmAdjustmentTcaLastOverflowTcaCount            Unsigned32,
     cienaCesPmAdjustmentTcaLastUnderflowTcaTime            PmTimeDate,
     cienaCesPmAdjustmentTcaLastUnderflowTcaUnits           PmTcaUnits,
     cienaCesPmAdjustmentTcaLastUnderflowTcaScheme          PmTcaScheme,
     cienaCesPmAdjustmentTcaLastUnderflowTcaBasisValue      PmTcaUnsigned64,
     cienaCesPmAdjustmentTcaLastUnderflowTcaBasisValueMin   PmTcaUnsigned64,
     cienaCesPmAdjustmentTcaLastUnderflowTcaBasisValueMax   PmTcaUnsigned64,
     cienaCesPmAdjustmentTcaLastUnderflowTcaThresholdType   PmTcaThresholdType,
     cienaCesPmAdjustmentTcaLastUnderflowTcaThresholdValue  Unsigned32,
     cienaCesPmAdjustmentTcaLastUnderflowTcaBoundaryValue   PmTcaUnsigned64,
     cienaCesPmAdjustmentTcaLastUnderflowTcaWatermarkTime   PmTimeDate,
     cienaCesPmAdjustmentTcaLastUnderflowTcaWatermarkType   PmTcaWatermarkType,
     cienaCesPmAdjustmentTcaLastUnderflowTcaWatermarkStats  PmStatBitmap,
     cienaCesPmAdjustmentTcaLastUnderflowTcaWatermarkValue  PmTcaUnsigned64,
     cienaCesPmAdjustmentTcaLastUnderflowTcaCount           Unsigned32
   }

   cienaCesPmAdjustmentTcaUnits OBJECT-TYPE
     SYNTAX      PmTcaUnits
     MAX-ACCESS  read-only
     STATUS      current
     DESCRIPTION "This object defines the way in which the data is used by the
                  Adjustment TCA feature for the PM instance.  This specifies
                  the way in which the statistics samples are handled and the
                  way in which the adjustment basis and threshold values are
                  interpreted.

                  When bitsPerSecond is specified, the data is intended to
                  represent a throughput as a rate of data in bits per second.
                  When analyzing samples for the Adjustment TCA feature, the
                  statistic value is internally adjusted so that it represents a
                  number of bits.  For example a statistic that represents a
                  number of bytes is multiplied by 8 to determine the bit count.
                  The statistic value representing bits is then compared to the
                  boundary value(s) derived from the adjustment basis and
                  threshold value(s).  The adjustment basis and threshold values
                  are considered to be values representing data in
                  bits-per-second and are not subjected to adjustment."
     ::= { cienaCesPmInstanceAdjustmentTcaEntry 1 }

   cienaCesPmAdjustmentTcaScheme OBJECT-TYPE
     SYNTAX      PmTcaScheme
     MAX-ACCESS  read-only
     STATUS      current
     DESCRIPTION "This object specifies the way in which the statistics, as
                  identified by cienaCesPmAdjustmentTcaStatistics object, are
                  used by the Adjustment TCA feature for the PM instance."
     ::= { cienaCesPmInstanceAdjustmentTcaEntry 2 }

   cienaCesPmAdjustmentTcaStats OBJECT-TYPE
     SYNTAX      PmStatBitmap
     MAX-ACCESS  read-only
     STATUS      current
     DESCRIPTION "The statistic(s) used by the PM instance, subject to the
                  Adjustment TCA feature.  The PM profile is identified by the
                  cienaCesPmInstanceProfileType object in this same table row.
                  The PM profile table underneath the cienaCesPmStatistics
                  branch representing the Current Bin for the PM profile is
                  used by the Adjustment TCA feature for the PM instance.  The
                  identified statistics are used by the Adjustment TCA feature
                  to determine new watermark values and to determine if overflow
                  or underflow conditions exist."
     ::= { cienaCesPmInstanceAdjustmentTcaEntry 3 }

   cienaCesPmAdjustmentTcaBasisValue OBJECT-TYPE
     SYNTAX      PmTcaUnsigned64
     MAX-ACCESS  read-only
     STATUS      current
     DESCRIPTION "Base value against which the adjustment threshold is applied
                  to determine the boundary value(s) that trigger an Adjustment
                  TCA event.  Value is provided to PM from the component which
                  manages the entity being monitored by the PM instance."
     ::= { cienaCesPmInstanceAdjustmentTcaEntry 4 }

   cienaCesPmAdjustmentTcaBasisValueMin OBJECT-TYPE
     SYNTAX      PmTcaUnsigned64
     MAX-ACCESS  read-only
     STATUS      current
     DESCRIPTION "Lowest value which the adjustment basis value will be allowed
                  to reach.  May be used by PM to inhibit Adjustment TCA events
                  once the limit has been reached.  Value is provided to PM from
                  the component which manages the entity being monitored by the
                  PM instance."
     ::= { cienaCesPmInstanceAdjustmentTcaEntry 5 }

   cienaCesPmAdjustmentTcaBasisValueMax OBJECT-TYPE
     SYNTAX      PmTcaUnsigned64
     MAX-ACCESS  read-only
     STATUS      current
     DESCRIPTION "Highest value which the adjustment basis value will be allowed
                  to reach.  May be used by PM to inhibit Adjustment TCA events
                  once the limit has been reached.  Value is provided to PM from
                  the component which manages the entity being monitored by the
                  PM instance."
     ::= { cienaCesPmInstanceAdjustmentTcaEntry 6 }

   cienaCesPmAdjustmentTcaConfigStatus OBJECT-TYPE
     SYNTAX      PmTcaConfigStatus
     MAX-ACCESS  read-only
     STATUS      current
     DESCRIPTION "This object indicates whether the Adjustment TCA configuration
                  attributes are configured in a way for periodic Adjustment TCA
                  events to occur on behalf of the PM Instance.  This status
                  refers to the Adjustment TCA functionality comprising of the
                  following necessary configuration attributes:
                    1. cienaCesPmIntervalProfileAdjustmentInterval
                    2. cienaCesPmIntervalProfileAdjustmentThreshold or
                        cienaCesPmIntervalProfileAdjustmentThresholdPercentage

                  noProfile indicates there is no interval profile configured
                  for the PM Instance.

                  notConfigured indicates the PM instance is configured with a
                  particular interval profile, however none of the necessary
                  configuration attributes for the Adjustment TCA feature are
                  configured.

                  partiallyConfigured indicates the PM instance is configured
                  with a particular interval profile and that some, but not all,
                  of the necessary configuration attributes for the Adjustment
                  TCA feature are configured.

                  configured indicates the PM instance is configured with a
                  particular interval profile and that all of the necessary
                  configuration attributes for the Adjustment TCA feature are
                  configured."
     ::= { cienaCesPmInstanceAdjustmentTcaEntry 7 }

   cienaCesPmAdjustmentTcaUpperBoundaryValue OBJECT-TYPE
     SYNTAX      PmTcaUnsigned64
     MAX-ACCESS  read-only
     STATUS      current
     DESCRIPTION "Upper boundary established by adding the value represented as
                  the adjustment threshold to the adjustment basis.  Statistic
                  readings which are equal or greater than this boundary are
                  subject to causing an Adjustment TCA event at the end of the
                  adjustment interval."
     ::= { cienaCesPmInstanceAdjustmentTcaEntry 8 }

   cienaCesPmAdjustmentTcaLowerBoundaryValue OBJECT-TYPE
     SYNTAX      PmTcaUnsigned64
     MAX-ACCESS  read-only
     STATUS      current
     DESCRIPTION "Lower boundary established by subtracting the value
                  represented as the adjustment threshold from the adjustment
                  basis.  Statistic readings which are equal or less than this
                  boundary are subject to causing an Adjustment TCA event at the
                  end of the adjustment interval."
     ::= { cienaCesPmInstanceAdjustmentTcaEntry 9 }

   cienaCesPmAdjustmentTcaIntervalStartTime OBJECT-TYPE
     SYNTAX      PmTimeDate
     MAX-ACCESS  read-only
     STATUS      current
     DESCRIPTION "The time and date representing when the current Adjustment
                  Interval has started.  This value will update whenever the
                  operational state of the pm instance changes and whenever
                  the adjustment interval period has elapsed."
     ::= { cienaCesPmInstanceAdjustmentTcaEntry 10 }

   cienaCesPmAdjustmentTcaIntervalEndTime OBJECT-TYPE
     SYNTAX      PmTimeDate
     MAX-ACCESS  read-only
     STATUS      current
     DESCRIPTION "The time and date representing when the current Adjustment
                  Interval will end.  This value will update whenever the
                  interval start time changes."
     ::= { cienaCesPmInstanceAdjustmentTcaEntry 11 }

   cienaCesPmAdjustmentTcaSampleStartTime OBJECT-TYPE
     SYNTAX      PmTimeDate
     MAX-ACCESS  read-only
     STATUS      current
     DESCRIPTION "The time and date representing when the current sample
                  interval has started."
     ::= { cienaCesPmInstanceAdjustmentTcaEntry 12 }

   cienaCesPmAdjustmentTcaSampleEndTime OBJECT-TYPE
     SYNTAX      PmTimeDate
     MAX-ACCESS  read-only
     STATUS      current
     DESCRIPTION "The time and date representing when the current sample
                  interval will end."
     ::= { cienaCesPmInstanceAdjustmentTcaEntry 13 }

   cienaCesPmAdjustmentTcaHighWatermarkTime OBJECT-TYPE
     SYNTAX      PmTimeDate
     MAX-ACCESS  read-only
     STATUS      current
     DESCRIPTION "The time and date representing when the high watermark value
                  was established.  An empty string is returned if no high
                  watermark has been determined."
     ::= { cienaCesPmInstanceAdjustmentTcaEntry 14 }

   cienaCesPmAdjustmentTcaHighWatermarkStats OBJECT-TYPE
     SYNTAX      PmStatBitmap
     MAX-ACCESS  read-only
     STATUS      current
     DESCRIPTION "The statistic(s) which were used by the Adjustment TCA feature
                  to establish the watermark value identified by the
                  cienaCesPmAdjustmentTcaHighWatermarkValue object.  Depending
                  on the value indicated by cienaCesPmAdjustmentTcaScheme, this
                  may be the same or a subset of the statistics identified by
                  the cienaCesPmAdjustmentTcaStats object."
     ::= { cienaCesPmInstanceAdjustmentTcaEntry 15 }

   cienaCesPmAdjustmentTcaHighWatermarkValue OBJECT-TYPE
     SYNTAX      PmTcaUnsigned64
     MAX-ACCESS  read-only
     STATUS      current
     DESCRIPTION "Highest sample interval reading during the current adjustment
                  interval.  This value resets to zero at the start of each
                  adjustment interval."
     ::= { cienaCesPmInstanceAdjustmentTcaEntry 16 }

   cienaCesPmAdjustmentTcaOverflowConfigStatus OBJECT-TYPE
     SYNTAX      PmTcaConfigStatus
     MAX-ACCESS  read-only
     STATUS      current
     DESCRIPTION "This object indicates whether the Overflow component of the
                  Adjustment TCA feature configuration attributes are configured
                  in a way for preemptive Adjustment TCA events to occur on
                  behalf of the PM Instance due to overflow condition.  This
                  status refers to the Adjustment TCA functionality comprising
                  of the following necessary configuration attributes:
                    1. cienaCesPmIntervalProfileAdjustmentInterval, and
                    2. cienaCesPmIntervalProfileAdjustmentThreshold or
                        cienaCesPmIntervalProfileAdjustmentThresholdPercentage
                    3. cienaCesPmIntervalProfileOverflowThreshold or
                        cienaCesPmIntervalProfileOverflowThresholdPercentage
                    4. cienaCesPmIntervalProfileOverflowCount

                  The Overflow component of the Adjustment TCA requires the
                  regular periodic Adjustment TCA feature to be configured.
                  For this reason, adjustment interval and threshold
                  configuration attributes are necessary before the overflow
                  component is deemed configured (attributes 1 and 2).

                  noProfile indicates there is no interval profile configured
                  for the PM Instance.

                  notConfigured indicates the PM instance is configured with a
                  particular interval profile, however none of the necessary
                  configuration attributes for the Overflow component of the
                  Adjustment TCA feature are configured.

                  partiallyConfigured indicates the PM instance is configured
                  with a particular interval profile and that some, but not all,
                  of the necessary configuration attributes for the Overflow
                  component of the Adjustment TCA feature are configured.

                  configured indicates the PM instance is configured with a
                  particular interval profile and that all of the necessary
                  configuration attributes for the Overflow component of the
                  Adjustment TCA feature are configured."
     ::= { cienaCesPmInstanceAdjustmentTcaEntry 17 }

   cienaCesPmAdjustmentTcaOverflowBoundaryValue OBJECT-TYPE
     SYNTAX      PmTcaUnsigned64
     MAX-ACCESS  read-only
     STATUS      current
     DESCRIPTION "Boundary established by adding the value represented as the
                  overflow threshold to the adjustment basis.  Statistic
                  readings which are equal or greater than this boundary at the
                  end of a sample interval represent an overflow condition and
                  are subject to causing the overflow current count to increment
                  which may lead to an Adjustment TCA when the configured
                  overflow count is reached."
     ::= { cienaCesPmInstanceAdjustmentTcaEntry 18 }

   cienaCesPmAdjustmentTcaOverflowCurrentCount OBJECT-TYPE
     SYNTAX      Unsigned32
     MAX-ACCESS  read-only
     STATUS      current
     DESCRIPTION "Current number of consecutive overflow conditions that have
                  occurred.  A non-zero value indicates the PM instance is
                  presently in an overflow condition which may result in an
                  Adjustment TCA event when the count reaches the overflow count
                  configured in the PM instance's interval profile."
     ::= { cienaCesPmInstanceAdjustmentTcaEntry 19 }

   cienaCesPmAdjustmentTcaOverflowHighWatermarkTime OBJECT-TYPE
     SYNTAX      PmTimeDate
     MAX-ACCESS  read-only
     STATUS      current
     DESCRIPTION "The time and date representing when the overflow high
                  watermark value was established.  An empty string is returned
                  if no overflow high watermark has been determined."
     ::= { cienaCesPmInstanceAdjustmentTcaEntry 20 }

   cienaCesPmAdjustmentTcaOverflowHighWatermarkStats OBJECT-TYPE
     SYNTAX      PmStatBitmap
     MAX-ACCESS  read-only
     STATUS      current
     DESCRIPTION "The statistic(s) which were used by the Adjustment TCA feature
                  to establish the watermark value identified by the
                  cienaCesPmAdjustmentTcaOverflowHighWatermarkValue object.
                  Depending on the value indicated by
                  cienaCesPmAdjustmentTcaScheme, this may be the same or a
                  subset of the statistics identified by the
                  cienaCesPmAdjustmentTcaStats object."
     ::= { cienaCesPmInstanceAdjustmentTcaEntry 21 }

   cienaCesPmAdjustmentTcaOverflowHighWatermarkValue OBJECT-TYPE
     SYNTAX      PmTcaUnsigned64
     MAX-ACCESS  read-only
     STATUS      current
     DESCRIPTION "Highest sample interval reading during the current series of
                  samples which qualify for declaring an overflow condition.
                  This value resets to zero at the start of each adjustment
                  interval."
     ::= { cienaCesPmInstanceAdjustmentTcaEntry 22 }

   cienaCesPmAdjustmentTcaUnderflowConfigStatus OBJECT-TYPE
     SYNTAX      PmTcaConfigStatus
     MAX-ACCESS  read-only
     STATUS      current
     DESCRIPTION "This object indicates whether the Underflow component of the
                  Adjustment TCA feature configuration attributes are configured
                  in a way for preemptive Adjustment TCA events to occur on
                  behalf of the PM Instance due to underflow condition.  This
                  status refers to the Adjustment TCA functionality comprising
                  of the following necessary configuration attributes:
                    1. cienaCesPmIntervalProfileAdjustmentInterval, and
                    2. cienaCesPmIntervalProfileAdjustmentThreshold or
                        cienaCesPmIntervalProfileAdjustmentThresholdPercentage
                    3. cienaCesPmIntervalProfileUnderflowThreshold or
                        cienaCesPmIntervalProfileUnderflowThresholdPercentage
                    4. cienaCesPmIntervalProfileUnderflowCount

                  The Underflow component of the Adjustment TCA requires the
                  regular periodic Adjustment TCA feature to be configured.
                  For this reason, adjustment interval and threshold
                  configuration attributes are necessary before the underflow
                  component is deemed configured (attributes 1 and 2).

                  noProfile indicates there is no interval profile configured
                  for the PM Instance.

                  notConfigured indicates the PM instance is configured with a
                  particular interval profile, however none of the necessary
                  configuration attributes for the Underflow component of the
                  Adjustment TCA feature are configured.

                  partiallyConfigured indicates the PM instance is configured
                  with a particular interval profile and that some, but not all,
                  of the necessary configuration attributes for the Underflow
                  component of the Adjustment TCA feature are configured.

                  configured indicates the PM instance is configured with a
                  particular interval profile and that all of the necessary
                  configuration attributes for the Underflow component of the
                  Adjustment TCA feature are configured."
     ::= { cienaCesPmInstanceAdjustmentTcaEntry 23 }

   cienaCesPmAdjustmentTcaUnderflowBoundaryValue OBJECT-TYPE
     SYNTAX      PmTcaUnsigned64
     MAX-ACCESS  read-only
     STATUS      current
     DESCRIPTION "Boundary established by subtracting the value represented as
                  the underflow threshold from the adjustment basis.  Statistic
                  readings which are equal or less than this boundary at the end
                  of a sample interval represent an underflow condition and are
                  subject to causing the underflow current count to increment
                  which may lead to an Adjustment TCA when the configured
                  underflow count is reached."
     ::= { cienaCesPmInstanceAdjustmentTcaEntry 24 }

   cienaCesPmAdjustmentTcaUnderflowCurrentCount OBJECT-TYPE
     SYNTAX      Unsigned32
     MAX-ACCESS  read-only
     STATUS      current
     DESCRIPTION "Current number of consecutive underflow conditions that have
                  occurred.  A non-zero value indicates the PM instance is
                  presently in an underflow condition which may result in an
                  Adjustment TCA event when the count reaches the underflow
                  count configured in the PM instance's interval profile."
     ::= { cienaCesPmInstanceAdjustmentTcaEntry 25 }

   cienaCesPmAdjustmentTcaUnderflowHighWatermarkTime OBJECT-TYPE
     SYNTAX      PmTimeDate
     MAX-ACCESS  read-only
     STATUS      current
     DESCRIPTION "The time and date representing when the underflow high
                  watermark value was established.  An empty string is returned
                  if no underflow high watermark has been determined."
     ::= { cienaCesPmInstanceAdjustmentTcaEntry 26 }

   cienaCesPmAdjustmentTcaUnderflowHighWatermarkStats OBJECT-TYPE
     SYNTAX      PmStatBitmap
     MAX-ACCESS  read-only
     STATUS      current
     DESCRIPTION "The statistic(s) which were used by the Adjustment TCA feature
                  to establish the watermark value identified by the
                  cienaCesPmAdjustmentTcaUnderflowHighWatermarkValue object.
                  Depending on the value indicated by
                  cienaCesPmAdjustmentTcaScheme, this may be the same or a
                  subset of the statistics identified by the
                  cienaCesPmAdjustmentTcaStats object."
     ::= { cienaCesPmInstanceAdjustmentTcaEntry 27 }

   cienaCesPmAdjustmentTcaUnderflowHighWatermarkValue OBJECT-TYPE
     SYNTAX      PmTcaUnsigned64
     MAX-ACCESS  read-only
     STATUS      current
     DESCRIPTION "Highest sample interval reading during the current series of
                  samples which qualify for declaring an underflow condition.
                  This value resets to zero at the start of each adjustment
                  interval."
     ::= { cienaCesPmInstanceAdjustmentTcaEntry 28 }

   cienaCesPmAdjustmentTcaEventsTotal OBJECT-TYPE
     SYNTAX      Unsigned32
     MAX-ACCESS  read-only
     STATUS      current
     DESCRIPTION "Total number of Adjustment TCA events that have occurred for
                  the PM instance."
     ::= { cienaCesPmInstanceAdjustmentTcaEntry 29 }

   cienaCesPmAdjustmentTcaEventsIntervalEndUpperBoundary OBJECT-TYPE
     SYNTAX      Unsigned32
     MAX-ACCESS  read-only
     STATUS      current
     DESCRIPTION "Number of Adjustment TCA events that have occurred for the PM
                  instance which occurred due to the end of Adjustment Interval
                  having been reached and the high watermark for the interval is
                  a value greater or equal to the upper boundary value."
     ::= { cienaCesPmInstanceAdjustmentTcaEntry 30 }

   cienaCesPmAdjustmentTcaEventsIntervalEndLowerBoundary OBJECT-TYPE
     SYNTAX      Unsigned32
     MAX-ACCESS  read-only
     STATUS      current
     DESCRIPTION "Number of Adjustment TCA events that have occurred for the PM
                  instance which occurred due to the end of Adjustment Interval
                  having been reached and the high watermark for the interval is
                  a value less than or equal to the lower boundary value."
     ::= { cienaCesPmInstanceAdjustmentTcaEntry 31 }

   cienaCesPmAdjustmentTcaEventsOverflowCountReached OBJECT-TYPE
     SYNTAX      Unsigned32
     MAX-ACCESS  read-only
     STATUS      current
     DESCRIPTION "Number of Adjustment TCA events that have occurred for the PM
                  instance which occurred due to a sample collection resulting
                  in an increment of the overflow current count value and the
                  overflow current count value reaching the configured overflow
                  count value."
     ::= { cienaCesPmInstanceAdjustmentTcaEntry 32 }

   cienaCesPmAdjustmentTcaEventsUnderflowCountReached OBJECT-TYPE
     SYNTAX      Unsigned32
     MAX-ACCESS  read-only
     STATUS      current
     DESCRIPTION "Number of Adjustment TCA events that have occurred for the PM
                  instance which occurred due to a sample collection resulting
                  in an increment of the underflow current count value and the
                  underflow current count value reaching the configured
                  underflow count value."
     ::= { cienaCesPmInstanceAdjustmentTcaEntry 33 }

   cienaCesPmAdjustmentTcaSamplesProcessedTotal OBJECT-TYPE
     SYNTAX      Unsigned32
     MAX-ACCESS  read-only
     STATUS      current
     DESCRIPTION "Total Number of valid samples that have been collected used by
                  the Adjustment TCA feature on the PM instance."
     ::= { cienaCesPmInstanceAdjustmentTcaEntry 34 }

   cienaCesPmAdjustmentTcaSamplesDiscardedTotal OBJECT-TYPE
     SYNTAX      Unsigned32
     MAX-ACCESS  read-only
     STATUS      current
     DESCRIPTION "Total Number of samples that have been collected but not used
                  by the Adjustment TCA feature on the PM instance."
     ::= { cienaCesPmInstanceAdjustmentTcaEntry 35 }

   cienaCesPmAdjustmentTcaSamplesProcessedCurrentInterval OBJECT-TYPE
     SYNTAX      Unsigned32
     MAX-ACCESS  read-only
     STATUS      current
     DESCRIPTION "Number of valid samples that have been collected during the
                  current Adjustment Interval and used by the Adjustment TCA
                  feature on the PM instance."
     ::= { cienaCesPmInstanceAdjustmentTcaEntry 36 }

   cienaCesPmAdjustmentTcaSamplesDiscardedCurrentInterval OBJECT-TYPE
     SYNTAX      Unsigned32
     MAX-ACCESS  read-only
     STATUS      current
     DESCRIPTION "Number of samples that have been collected during the current
                  Adjustment Interval but not used by the Adjustment TCA feature
                  on the PM instance."
     ::= { cienaCesPmInstanceAdjustmentTcaEntry 37 }

   cienaCesPmAdjustmentTcaLastIntvlEndTcaTime OBJECT-TYPE
     SYNTAX      PmTimeDate
     MAX-ACCESS  read-only
     STATUS      current
     DESCRIPTION "The time and date of the last (most recent) Adjustment TCA
                  which occurred on behalf of the PM instance due to end of
                  Adjustment Interval high watermark value being outside of the
                  upper and lower boundary region.  An empty string is returned
                  if no such Adjustment TCA has occurred."
     ::= { cienaCesPmInstanceAdjustmentTcaEntry 38 }

   cienaCesPmAdjustmentTcaLastIntvlEndTcaUnits OBJECT-TYPE
     SYNTAX      PmTcaUnits
     MAX-ACCESS  read-only
     STATUS      current
     DESCRIPTION "The value of cienaCesPmAdjustmentTcaUnits that was in use
                  during the last Adjustment TCA which occurred on behalf of the
                  PM instance due to end of Adjustment Interval high watermark
                  value being outside of the upper and lower boundary region."
     ::= { cienaCesPmInstanceAdjustmentTcaEntry 39 }

   cienaCesPmAdjustmentTcaLastIntvlEndTcaScheme OBJECT-TYPE
     SYNTAX      PmTcaScheme
     MAX-ACCESS  read-only
     STATUS      current
     DESCRIPTION "The value of cienaCesPmAdjustmentTcaScheme that was in use
                  during the last Adjustment TCA which occurred on behalf of the
                  PM instance due to end of Adjustment Interval high watermark
                  value being outside of the upper and lower boundary region."
     ::= { cienaCesPmInstanceAdjustmentTcaEntry 40 }

   cienaCesPmAdjustmentTcaLastIntvlEndTcaBasisValue OBJECT-TYPE
     SYNTAX      PmTcaUnsigned64
     MAX-ACCESS  read-only
     STATUS      current
     DESCRIPTION "The adjustment basis value that was in place when the last
                  Adjustment TCA occurred on behalf of the PM instance due to
                  end of Adjustment Interval high watermark value being outside
                  of the upper and lower boundary region.  This refers to the
                  value of cienaCesPmAdjustmentTcaBasisValue when such
                  Adjustment TCA occurred."
     ::= { cienaCesPmInstanceAdjustmentTcaEntry 41 }

   cienaCesPmAdjustmentTcaLastIntvlEndTcaBasisValueMin OBJECT-TYPE
     SYNTAX      PmTcaUnsigned64
     MAX-ACCESS  read-only
     STATUS      current
     DESCRIPTION "The adjustment basis minimum value that was in place when the
                  last Adjustment TCA occurred on behalf of the PM instance due
                  to end of Adjustment Interval high watermark value being
                  outside of the upper and lower boundary region.  This refers
                  to the value of cienaCesPmAdjustmentTcaBasisValueMin when such
                  Adjustment TCA occurred."
     ::= { cienaCesPmInstanceAdjustmentTcaEntry 42 }

   cienaCesPmAdjustmentTcaLastIntvlEndTcaBasisValueMax OBJECT-TYPE
     SYNTAX      PmTcaUnsigned64
     MAX-ACCESS  read-only
     STATUS      current
     DESCRIPTION "The adjustment basis maximum value that was in place when the
                  last Adjustment TCA occurred on behalf of the PM instance due
                  to end of Adjustment Interval high watermark value being
                  outside of the upper and lower boundary region.  This refers
                  to the value of cienaCesPmAdjustmentTcaBasisValueMax when such
                  Adjustment TCA occurred."
     ::= { cienaCesPmInstanceAdjustmentTcaEntry 43 }

   cienaCesPmAdjustmentTcaLastIntvlEndTcaThresholdType OBJECT-TYPE
     SYNTAX      PmTcaThresholdType
     MAX-ACCESS  read-only
     STATUS      current
     DESCRIPTION "This object defines the way in which the value returned for
                  cienaCesPmAdjustmentTcaLastIntvlEndTcaThresholdValue should be
                  interpreted."
     ::= { cienaCesPmInstanceAdjustmentTcaEntry 44 }

   cienaCesPmAdjustmentTcaLastIntvlEndTcaThresholdValue OBJECT-TYPE
     SYNTAX      Unsigned32
     MAX-ACCESS  read-only
     STATUS      current
     DESCRIPTION "The threshold value that was used in the last Adjustment TCA
                  which occurred on behalf of the PM instance due to end of
                  Adjustment Interval high watermark value being outside of the
                  upper and lower boundary region.  For such Adjustment TCA,
                  this refers to the value of the configured adjustment
                  threshold as specified in the interval profile associated with
                  the PM instance when the Adjustment TCA occurred."
     ::= { cienaCesPmInstanceAdjustmentTcaEntry 45 }

   cienaCesPmAdjustmentTcaLastIntvlEndTcaBoundaryValue OBJECT-TYPE
     SYNTAX      PmTcaUnsigned64
     MAX-ACCESS  read-only
     STATUS      current
     DESCRIPTION "The threshold boundary value which was reached, exceeded, or
                  preceeded, causing the last Adjustment TCA which occurred on
                  behalf of the PM instance due to end of Adjustment Interval
                  high watermark value being outside of the upper and lower
                  boundary region.  For such Adjustment TCA, this can refer to
                  the value of cienaCesPmAdjustmentTcaUpperBoundaryValue or
                  cienaCesPmAdjustmentTcaLowerBoundaryValue at the time of the
                  Adjustment TCA."
     ::= { cienaCesPmInstanceAdjustmentTcaEntry 46 }

   cienaCesPmAdjustmentTcaLastIntvlEndTcaWatermarkTime OBJECT-TYPE
     SYNTAX      PmTimeDate
     MAX-ACCESS  read-only
     STATUS      current
     DESCRIPTION "The time and date that the watermark value used in the last
                  Adjustment TCA which occurred on behalf of the PM instance
                  due to end of Adjustment Interval high watermark value being
                  outside of the  upper and lower boundary region was derived.
                  An empty string is returned if no such Adjustment TCA has
                  occurred for the PM instance."
     ::= { cienaCesPmInstanceAdjustmentTcaEntry 47 }

   cienaCesPmAdjustmentTcaLastIntvlEndTcaWatermarkType OBJECT-TYPE
     SYNTAX      PmTcaWatermarkType
     MAX-ACCESS  read-only
     STATUS      current
     DESCRIPTION "The type of watermark that was used in the logic that caused
                  the last Adjustment TCA which occurred on behalf of the PM
                  instance due to end of Adjustment Interval high watermark
                  value being outside of the upper and lower boundary region.
                  This refers to the watermark value reported by the
                  cienaCesPmAdjustmentTcaLastIntvlEndTcaWatermarkValue object."
     ::= { cienaCesPmInstanceAdjustmentTcaEntry 48 }

   cienaCesPmAdjustmentTcaLastIntvlEndTcaWatermarkStats OBJECT-TYPE
     SYNTAX      PmStatBitmap
     MAX-ACCESS  read-only
     STATUS      current
     DESCRIPTION "The statistic(s) which were used by the Adjustment TCA feature
                  to establish the watermark value identified by the
                  cienaCesPmAdjustmentTcaLastIntvlEndTcaWatermarkValue object.
                  Since this object applies to the last Adjustment TCA which
                  occurred on behalf of the PM instance due to end of Adjustment
                  Interval high watermark value being outside of the upper and
                  lower boundary region, this object represents the value of
                  cienaCesPmAdjustmentTcaHighWatermarkStats at the time of such
                  Adjustment TCA."
     ::= { cienaCesPmInstanceAdjustmentTcaEntry 49 }

   cienaCesPmAdjustmentTcaLastIntvlEndTcaWatermarkValue OBJECT-TYPE
     SYNTAX      PmTcaUnsigned64
     MAX-ACCESS  read-only
     STATUS      current
     DESCRIPTION "The watermark value that was used in the logic that caused the
                  last Adjustment TCA to occur on behalf of the PM instance due
                  to end of Adjustment Interval high watermark value being
                  outside of the upper and lower boundary region.  For such
                  Adjustment TCA, this object represents the value of
                  cienaCesPmAdjustmentTcaHighWatermarkValue at the time the
                  Adjustment TCA."
     ::= { cienaCesPmInstanceAdjustmentTcaEntry 50 }

   cienaCesPmAdjustmentTcaLastOverflowTcaTime OBJECT-TYPE
     SYNTAX      PmTimeDate
     MAX-ACCESS  read-only
     STATUS      current
     DESCRIPTION "The time and date of the last (most recent) Adjustment TCA
                  which occurred on behalf of the PM instance due to end of
                  Sample Interval incrementing the current overflow count to
                  reach the configured overflow count associated with the
                  interval profile associated with the PM instance.  An empty
                  string is returned if no such Adjustment TCA has occurred."
     ::= { cienaCesPmInstanceAdjustmentTcaEntry 51 }

   cienaCesPmAdjustmentTcaLastOverflowTcaUnits OBJECT-TYPE
     SYNTAX      PmTcaUnits
     MAX-ACCESS  read-only
     STATUS      current
     DESCRIPTION "The value of cienaCesPmAdjustmentTcaUnits that was in use
                  during the last Adjustment TCA which occurred on behalf of the
                  PM instance due to end of Sample Interval incrementing the
                  current overflow count to reach the configured overflow count
                  associated with the interval profile associated with the PM
                  instance."
     ::= { cienaCesPmInstanceAdjustmentTcaEntry 52 }

   cienaCesPmAdjustmentTcaLastOverflowTcaScheme OBJECT-TYPE
     SYNTAX      PmTcaScheme
     MAX-ACCESS  read-only
     STATUS      current
     DESCRIPTION "The value of cienaCesPmAdjustmentTcaScheme that was in use
                  during the last Adjustment TCA which occurred on behalf of the
                  PM instance due to end of Sample Interval incrementing the
                  current overflow count to reach the configured overflow count
                  associated with the interval profile associated with the PM
                  instance."
     ::= { cienaCesPmInstanceAdjustmentTcaEntry 53 }

   cienaCesPmAdjustmentTcaLastOverflowTcaBasisValue OBJECT-TYPE
     SYNTAX      PmTcaUnsigned64
     MAX-ACCESS  read-only
     STATUS      current
     DESCRIPTION "The adjustment basis value that was in place when the last
                  Adjustment TCA occurred on behalf of the PM instance due to
                  end of Sample Interval incrementing the current overflow count
                  to reach the configured overflow count associated with the
                  interval profile associated with the PM instance.  This refers
                  to the value of cienaCesPmAdjustmentTcaBasisValue when such
                  Adjustment TCA occurred."
     ::= { cienaCesPmInstanceAdjustmentTcaEntry 54 }

   cienaCesPmAdjustmentTcaLastOverflowTcaBasisValueMin OBJECT-TYPE
     SYNTAX      PmTcaUnsigned64
     MAX-ACCESS  read-only
     STATUS      current
     DESCRIPTION "The adjustment basis minimum value that was in place when the
                  last Adjustment TCA occurred on behalf of the PM instance due
                  to end of Sample Interval incrementing the current overflow
                  count to reach the configured overflow count associated with
                  the interval profile associated with the PM instance.  This
                  refers to the value of cienaCesPmAdjustmentTcaBasisValueMin
                  when such Adjustment TCA occurred."
     ::= { cienaCesPmInstanceAdjustmentTcaEntry 55 }

   cienaCesPmAdjustmentTcaLastOverflowTcaBasisValueMax OBJECT-TYPE
     SYNTAX      PmTcaUnsigned64
     MAX-ACCESS  read-only
     STATUS      current
     DESCRIPTION "The adjustment basis maximum value that was in place when the
                  last Adjustment TCA occurred on behalf of the PM instance due
                  to end of Sample Interval incrementing the current overflow
                  count to reach the configured overflow count associated with
                  the interval profile associated with the PM instance.  This
                  refers to the value of cienaCesPmAdjustmentTcaBasisValueMax
                  when such Adjustment TCA occurred."
     ::= { cienaCesPmInstanceAdjustmentTcaEntry 56 }

   cienaCesPmAdjustmentTcaLastOverflowTcaThresholdType OBJECT-TYPE
     SYNTAX      PmTcaThresholdType
     MAX-ACCESS  read-only
     STATUS      current
     DESCRIPTION "This object defines the way in which the value returned for
                  cienaCesPmAdjustmentTcaLastOverflowTcaThresholdValue should be
                  interpreted."
     ::= { cienaCesPmInstanceAdjustmentTcaEntry 57 }

   cienaCesPmAdjustmentTcaLastOverflowTcaThresholdValue OBJECT-TYPE
     SYNTAX      Unsigned32
     MAX-ACCESS  read-only
     STATUS      current
     DESCRIPTION "The threshold value that was used in the last Adjustment TCA
                  which occurred on behalf of the PM instance due to end of
                  Sample Interval incrementing the current overflow count to
                  reach the configured overflow count associated with the
                  interval profile associated with the PM instance.  For such
                  Adjustment TCA, this refers to the value of the configured
                  overflow threshold as specified in the interval profile
                  associated with the PM instance when the Adjustment TCA
                  occurred."
     ::= { cienaCesPmInstanceAdjustmentTcaEntry 58 }

   cienaCesPmAdjustmentTcaLastOverflowTcaBoundaryValue OBJECT-TYPE
     SYNTAX      PmTcaUnsigned64
     MAX-ACCESS  read-only
     STATUS      current
     DESCRIPTION "The threshold boundary value which was reached or exceeded,
                  causing the last Adjustment TCA which occurred on behalf of
                  the PM instance due to end of Sample Interval incrementing the
                  current overflow count to reach the configured overflow count
                  associated with the interval profile associated with the PM
                  instance.  For such Adjustment TCA, this refers to the value
                  of cienaCesPmAdjustmentTcaOverflowBoundaryValue at the time of
                  the Adjustment TCA."
     ::= { cienaCesPmInstanceAdjustmentTcaEntry 59 }

   cienaCesPmAdjustmentTcaLastOverflowTcaWatermarkTime OBJECT-TYPE
     SYNTAX      PmTimeDate
     MAX-ACCESS  read-only
     STATUS      current
     DESCRIPTION "The time and date that the watermark value used in the last
                  Adjustment TCA which occurred on behalf of the PM instance
                  due to end of Sample Interval incrementing the current
                  overflow count to reach the configured overflow count
                  associated with the interval profile associated with the PM
                  instance was derived.  An empty string is returned if no such
                  Adjustment TCA has occurred for the PM instance."
     ::= { cienaCesPmInstanceAdjustmentTcaEntry 60 }

   cienaCesPmAdjustmentTcaLastOverflowTcaWatermarkType OBJECT-TYPE
     SYNTAX      PmTcaWatermarkType
     MAX-ACCESS  read-only
     STATUS      current
     DESCRIPTION "The type of watermark that was used in the logic that caused
                  the last Adjustment TCA which occurred on behalf of the PM
                  instance due to end of Sample Interval incrementing the
                  current overflow count to reach the configured overflow count
                  associated with the interval profile associated with the PM
                  instance.  This refers to the watermark value reported by the
                  cienaCesPmAdjustmentTcaLastOverflowTcaWatermarkValue object."
     ::= { cienaCesPmInstanceAdjustmentTcaEntry 61 }

   cienaCesPmAdjustmentTcaLastOverflowTcaWatermarkStats OBJECT-TYPE
     SYNTAX      PmStatBitmap
     MAX-ACCESS  read-only
     STATUS      current
     DESCRIPTION "The statistic(s) which were used by the Adjustment TCA feature
                  to establish the watermark value identified by the
                  cienaCesPmAdjustmentTcaLastOverflowTcaWatermarkValue object.
                  Since this object applies to the last Adjustment TCA which
                  occurred on behalf of the PM instance due to end of Sample
                  Interval incrementing the current overflow count to reach the
                  configured overflow count associated with the interval profile
                  associated with the PM instance, this object represents the
                  value of cienaCesPmAdjustmentTcaOverflowHighWatermarkStats at
                  the time of such Adjustment TCA."
     ::= { cienaCesPmInstanceAdjustmentTcaEntry 62 }

   cienaCesPmAdjustmentTcaLastOverflowTcaWatermarkValue OBJECT-TYPE
     SYNTAX      PmTcaUnsigned64
     MAX-ACCESS  read-only
     STATUS      current
     DESCRIPTION "The watermark value that was used in the logic that caused the
                  last Adjustment TCA to occur on behalf of the PM instance due
                  to end of Sample Interval incrementing the current overflow
                  count to reach the configured overflow count associated with
                  the interval profile associated with the PM instance.  For
                  such Adjustment TCA, this object represents the value of
                  cienaCesPmAdjustmentTcaOverflowHighWatermarkValue at the time
                  of the Adjustment TCA."
     ::= { cienaCesPmInstanceAdjustmentTcaEntry 63 }

   cienaCesPmAdjustmentTcaLastOverflowTcaCount OBJECT-TYPE
     SYNTAX      Unsigned32
     MAX-ACCESS  read-only
     STATUS      current
     DESCRIPTION "The overflow count that was used in the last Adjustment TCA
                  which occurred on behalf of the PM instance due to end of
                  Sample Interval incrementing the current overflow count to
                  reach the configured overflow count associated with the
                  interval profile associated with the PM instance.  Since such
                  Adjustment TCA happened when the current count reaches the
                  configured overflow count, this object will effectively
                  report the configured overflow count that was in use at the
                  time the Adjustment TCA."
     ::= { cienaCesPmInstanceAdjustmentTcaEntry 64 }

   cienaCesPmAdjustmentTcaLastUnderflowTcaTime OBJECT-TYPE
     SYNTAX      PmTimeDate
     MAX-ACCESS  read-only
     STATUS      current
     DESCRIPTION "The time and date of the last (most recent) Adjustment TCA
                  which occurred on behalf of the PM instance due to end of
                  Sample Interval incrementing the current underflow count to
                  reach the configured underflow count associated with the
                  interval profile associated with the PM instance.  An empty
                  string is returned if no such Adjustment TCA has occurred."
     ::= { cienaCesPmInstanceAdjustmentTcaEntry 65 }

   cienaCesPmAdjustmentTcaLastUnderflowTcaUnits OBJECT-TYPE
     SYNTAX      PmTcaUnits
     MAX-ACCESS  read-only
     STATUS      current
     DESCRIPTION "The value of cienaCesPmAdjustmentTcaUnits that was in use
                  during the last Adjustment TCA which occurred on behalf of the
                  PM instance due to end of Sample Interval incrementing the
                  current underflow count to reach the configured underflow
                  count associated with the interval profile associated with the
                  PM instance."
     ::= { cienaCesPmInstanceAdjustmentTcaEntry 66 }

   cienaCesPmAdjustmentTcaLastUnderflowTcaScheme OBJECT-TYPE
     SYNTAX      PmTcaScheme
     MAX-ACCESS  read-only
     STATUS      current
     DESCRIPTION "The value of cienaCesPmAdjustmentTcaScheme that was in use
                  during the last Adjustment TCA which occurred on behalf of the
                  PM instance due to end of Sample Interval incrementing the
                  current underflow count to reach the configured underflow
                  count associated with the interval profile associated with the
                  PM instance."
     ::= { cienaCesPmInstanceAdjustmentTcaEntry 67 }

   cienaCesPmAdjustmentTcaLastUnderflowTcaBasisValue OBJECT-TYPE
     SYNTAX      PmTcaUnsigned64
     MAX-ACCESS  read-only
     STATUS      current
     DESCRIPTION "The adjustment basis value that was in place when the last
                  Adjustment TCA occurred on behalf of the PM instance due to
                  end of Sample Interval incrementing the current underflow count
                  to reach the configured underflow count associated with the
                  interval profile associated with the PM instance.  This refers
                  to the value of cienaCesPmAdjustmentTcaBasisValue when such
                  Adjustment TCA occurred."
     ::= { cienaCesPmInstanceAdjustmentTcaEntry 68 }

   cienaCesPmAdjustmentTcaLastUnderflowTcaBasisValueMin OBJECT-TYPE
     SYNTAX      PmTcaUnsigned64
     MAX-ACCESS  read-only
     STATUS      current
     DESCRIPTION "The adjustment basis minimum value that was in place when the
                  last Adjustment TCA occurred on behalf of the PM instance due
                  to end of Sample Interval incrementing the current underflow
                  count to reach the configured underflow count associated with
                  the interval profile associated with the PM instance.  This
                  refers to the value of cienaCesPmAdjustmentTcaBasisValueMin
                  when such Adjustment TCA occurred."
     ::= { cienaCesPmInstanceAdjustmentTcaEntry 69 }

   cienaCesPmAdjustmentTcaLastUnderflowTcaBasisValueMax OBJECT-TYPE
     SYNTAX      PmTcaUnsigned64
     MAX-ACCESS  read-only
     STATUS      current
     DESCRIPTION "The adjustment basis maximum value that was in place when the
                  last Adjustment TCA occurred on behalf of the PM instance due
                  to end of Sample Interval incrementing the current underflow
                  count to reach the configured underflow count associated with
                  the interval profile associated with the PM instance.  This
                  refers to the value of cienaCesPmAdjustmentTcaBasisValueMax
                  when such Adjustment TCA occurred."
     ::= { cienaCesPmInstanceAdjustmentTcaEntry 70 }

   cienaCesPmAdjustmentTcaLastUnderflowTcaThresholdType OBJECT-TYPE
     SYNTAX      PmTcaThresholdType
     MAX-ACCESS  read-only
     STATUS      current
     DESCRIPTION "This object defines the way in which the value returned for
                  cienaCesPmAdjustmentTcaLastUnderflowTcaThresholdValue should be
                  interpreted."
     ::= { cienaCesPmInstanceAdjustmentTcaEntry 71 }

   cienaCesPmAdjustmentTcaLastUnderflowTcaThresholdValue OBJECT-TYPE
     SYNTAX      Unsigned32
     MAX-ACCESS  read-only
     STATUS      current
     DESCRIPTION "The threshold value that was used in the last Adjustment TCA
                  which occurred on behalf of the PM instance due to end of
                  Sample Interval incrementing the current underflow count to
                  reach the configured underflow count associated with the
                  interval profile associated with the PM instance.  For such
                  Adjustment TCA, this refers to the value of the configured
                  underflow threshold as specified in the interval profile
                  associated with the PM instance when the Adjustment TCA
                  occurred."
     ::= { cienaCesPmInstanceAdjustmentTcaEntry 72 }

   cienaCesPmAdjustmentTcaLastUnderflowTcaBoundaryValue OBJECT-TYPE
     SYNTAX      PmTcaUnsigned64
     MAX-ACCESS  read-only
     STATUS      current
     DESCRIPTION "The threshold boundary value which was reached or exceeded,
                  causing the last Adjustment TCA which occurred on behalf of
                  the PM instance due to end of Sample Interval incrementing the
                  current underflow count to reach the configured underflow count
                  associated with the interval profile associated with the PM
                  instance.  For such Adjustment TCA, this refers to the value
                  of cienaCesPmAdjustmentTcaUnderflowBoundaryValue at the time
                  of the Adjustment TCA."
     ::= { cienaCesPmInstanceAdjustmentTcaEntry 73 }

   cienaCesPmAdjustmentTcaLastUnderflowTcaWatermarkTime OBJECT-TYPE
     SYNTAX      PmTimeDate
     MAX-ACCESS  read-only
     STATUS      current
     DESCRIPTION "The time and date that the watermark value used in the last
                  Adjustment TCA which occurred on behalf of the PM instance
                  due to end of Sample Interval incrementing the current
                  underflow count to reach the configured underflow count
                  associated with the interval profile associated with the PM
                  instance was derived.  An empty string is returned if no such
                  Adjustment TCA has occurred for the PM instance."
     ::= { cienaCesPmInstanceAdjustmentTcaEntry 74 }

   cienaCesPmAdjustmentTcaLastUnderflowTcaWatermarkType OBJECT-TYPE
     SYNTAX      PmTcaWatermarkType
     MAX-ACCESS  read-only
     STATUS      current
     DESCRIPTION "The type of watermark that was used in the logic that caused
                  the last Adjustment TCA which occurred on behalf of the PM
                  instance due to end of Sample Interval incrementing the
                  current underflow count to reach the configured underflow
                  count associated with the interval profile associated with the
                  PM instance.  This refers to the watermark value reported by
                  the cienaCesPmAdjustmentTcaLastUnderflowTcaWatermarkValue
                  object."
     ::= { cienaCesPmInstanceAdjustmentTcaEntry 75 }

   cienaCesPmAdjustmentTcaLastUnderflowTcaWatermarkStats OBJECT-TYPE
     SYNTAX      PmStatBitmap
     MAX-ACCESS  read-only
     STATUS      current
     DESCRIPTION "The statistic(s) which were used by the Adjustment TCA feature
                  to establish the watermark value identified by the
                  cienaCesPmAdjustmentTcaLastUnderflowTcaWatermarkValue object.
                  Since this object applies to the last Adjustment TCA which
                  occurred on behalf of the PM instance due to end of Sample
                  Interval incrementing the current underflow count to reach the
                  configured underflow count associated with the interval
                  profile associated with the PM instance, this object
                  represents the value of
                  cienaCesPmAdjustmentTcaUnderflowHighWatermarkStats at the time
                  of such Adjustment TCA."
     ::= { cienaCesPmInstanceAdjustmentTcaEntry 76 }

   cienaCesPmAdjustmentTcaLastUnderflowTcaWatermarkValue OBJECT-TYPE
     SYNTAX      PmTcaUnsigned64
     MAX-ACCESS  read-only
     STATUS      current
     DESCRIPTION "The watermark value that was used in the logic that caused the
                  last Adjustment TCA to occur on behalf of the PM instance due
                  to end of Sample Interval incrementing the current underflow
                  count to reach the configured underflow count associated with
                  the interval profile associated with the PM instance.  For
                  such Adjustment TCA, this object represents the value of
                  cienaCesPmAdjustmentTcaUnderflowHighWatermarkValue at the time
                  of the Adjustment TCA."
     ::= { cienaCesPmInstanceAdjustmentTcaEntry 77 }

   cienaCesPmAdjustmentTcaLastUnderflowTcaCount OBJECT-TYPE
     SYNTAX      Unsigned32
     MAX-ACCESS  read-only
     STATUS      current
     DESCRIPTION "The underflow count that was used in the last Adjustment TCA
                  which occurred on behalf of the PM instance due to end of
                  Sample Interval incrementing the current underflow count to
                  reach the configured underflow count associated with the
                  interval profile associated with the PM instance.  Since such
                  Adjustment TCA happened when the current count reaches the
                  configured underflow count, this object will effectively
                  report the configured underflow count that was in use at the
                  time the Adjustment TCA."
     ::= { cienaCesPmInstanceAdjustmentTcaEntry 78 }

   --
   -- PM Instance Alert TCA Table
   --
   cienaCesPmInstanceAlertTcaTable OBJECT-TYPE
     SYNTAX      SEQUENCE OF CienaCesPmInstanceAlertTcaEntry
     MAX-ACCESS  not-accessible
     STATUS      current
     DESCRIPTION
            "The (conceptual) table listing data for the PM instance table which
             is applicable to the PM Threshold Alert TCA feature."
     ::= { cienaCesPmInstanceAlertTca 1 }

   cienaCesPmInstanceAlertTcaEntry OBJECT-TYPE
     SYNTAX      CienaCesPmInstanceAlertTcaEntry
     MAX-ACCESS  not-accessible
     STATUS      current
     DESCRIPTION
           "An entry (conceptual row) in the cienaCesPmInstanceAlertTcaTable.
            This table serves as an extension of the cienaCesPmInstanceTable,
            representing operational data for each PM instance, specific to the
            PM Threshold Alert TCA feature."
     AUGMENTS { cienaCesPmInstanceEntry }
     ::= { cienaCesPmInstanceAlertTcaTable 1 }

   CienaCesPmInstanceAlertTcaEntry ::=  SEQUENCE {
     cienaCesPmAlertTcaUnits                                PmTcaUnits,
     cienaCesPmAlertTcaScheme                               PmTcaScheme,
     cienaCesPmAlertTcaStats                                PmStatBitmap,
     cienaCesPmAlertTcaBasisValue                           PmTcaUnsigned64,
     cienaCesPmAlertTcaConfigStatus                         PmTcaConfigStatus,
     cienaCesPmAlertTcaBoundaryValue                        PmTcaUnsigned64,
     cienaCesPmAlertTcaIntervalStartTime                    PmTimeDate,
     cienaCesPmAlertTcaIntervalEndTime                      PmTimeDate,
     cienaCesPmAlertTcaSampleStartTime                      PmTimeDate,
     cienaCesPmAlertTcaSampleEndTime                        PmTimeDate,
     cienaCesPmAlertTcaHighWatermarkTime                    PmTimeDate,
     cienaCesPmAlertTcaHighWatermarkStats                   PmStatBitmap,
     cienaCesPmAlertTcaHighWatermarkValue                   PmTcaUnsigned64,
     cienaCesPmAlertTcaState                                PmTcaAlertState,
     cienaCesPmAlertTcaEventsTotal                          Unsigned32,
     cienaCesPmAlertTcaSamplesProcessedTotal                Unsigned32,
     cienaCesPmAlertTcaSamplesDiscardedTotal                Unsigned32,
     cienaCesPmAlertTcaSamplesProcessedCurrentInterval      Unsigned32,
     cienaCesPmAlertTcaSamplesDiscardedCurrentInterval      Unsigned32,
     cienaCesPmAlertTcaLastTcaTime                          PmTimeDate,
     cienaCesPmAlertTcaLastTcaUnits                         PmTcaUnits,
     cienaCesPmAlertTcaLastTcaScheme                        PmTcaScheme,
     cienaCesPmAlertTcaLastTcaBasisValue                    PmTcaUnsigned64,
     cienaCesPmAlertTcaLastTcaThresholdType                 PmTcaThresholdType,
     cienaCesPmAlertTcaLastTcaThresholdValue                Unsigned32,
     cienaCesPmAlertTcaLastTcaBoundaryValue                 PmTcaUnsigned64,
     cienaCesPmAlertTcaLastTcaWatermarkTime                 PmTimeDate,
     cienaCesPmAlertTcaLastTcaWatermarkType                 PmTcaWatermarkType,
     cienaCesPmAlertTcaLastTcaWatermarkStats                PmStatBitmap,
     cienaCesPmAlertTcaLastTcaWatermarkValue                PmTcaUnsigned64,
     cienaCesPmAlertTcaLastTcaState                         PmTcaAlertState
   }

   cienaCesPmAlertTcaUnits OBJECT-TYPE
     SYNTAX      PmTcaUnits
     MAX-ACCESS  read-only
     STATUS      current
     DESCRIPTION "This object defines the way in which the data is used by the
                  Alert TCA feature for the PM instance.  This specifies the way
                  in which the statistics samples are handled and the way in
                  which the alert basis and threshold values are interpreted.

                  When bitsPerSecond is specified, the data is intended to
                  represent a throughput as a rate of data in bits per second.
                  When analyzing samples for the Alert TCA feature, the
                  statistic value is internally adjusted so that it represents a
                  number of bits.  For example a statistic that represents a
                  number of bytes is multiplied by 8 to determine the bit count.
                  The statistic value representing bits is then compared to the
                  boundary value derived from the alert basis and threshold
                  values.  The alert basis and threshold values are considered
                  to be values representing data in bits-per-second and are not
                  subjected to adjustment."
     ::= { cienaCesPmInstanceAlertTcaEntry 1 }

   cienaCesPmAlertTcaScheme OBJECT-TYPE
     SYNTAX      PmTcaScheme
     MAX-ACCESS  read-only
     STATUS      current
     DESCRIPTION "This object specifies the way in which the statistics, as
                  identified by cienaCesPmAlertTcaStatistics object, are used by
                  the Alert TCA feature for the PM instance."
     ::= { cienaCesPmInstanceAlertTcaEntry 2 }

   cienaCesPmAlertTcaStats OBJECT-TYPE
     SYNTAX      PmStatBitmap
     MAX-ACCESS  read-only
     STATUS      current
     DESCRIPTION "The statistic(s) used by the PM instance, subject to the
                  Alert TCA feature.  The PM profile is identified by the
                  cienaCesPmInstanceProfileType object in this same table row.
                  The PM profile table underneath the cienaCesPmStatistics
                  branch representing the Current Bin for the PM profile is
                  used by the Alert TCA feature for the PM instance.  The
                  identified statistics are used by the Alert TCA feature to
                  determine a new watermark value."
     ::= { cienaCesPmInstanceAlertTcaEntry 3 }

   cienaCesPmAlertTcaConfigStatus OBJECT-TYPE
     SYNTAX      PmTcaConfigStatus
     MAX-ACCESS  read-only
     STATUS      current
     DESCRIPTION "This object indicates whether the Alert TCA configuration
                  attributes are configured in a way for periodic Alert TCA
                  state monitoring and reporting to occur on behalf of the PM
                  Instance.  This status refers to the Alert TCA functionality
                  comprising of the following necessary configuration
                  attributes:
                    1. cienaCesPmIntervalProfileAlertInterval
                    2. cienaCesPmIntervalProfileAlertThresholdPercentage

                  noProfile indicates there is no interval profile configured
                  for the PM Instance.

                  notConfigured indicates the PM instance is configured with a
                  particular interval profile, however none of the necessary
                  configuration attributes for the Alert TCA feature are
                  configured.

                  partiallyConfigured indicates the PM instance is configured
                  with a particular interval profile and that some, but not all,
                  of the necessary configuration attributes for the Alert TCA
                  feature are configured.

                  configured indicates the PM instance is configured with a
                  particular interval profile and that all of the necessary
                  configuration attributes for the Alert TCA feature are
                  configured."
     ::= { cienaCesPmInstanceAlertTcaEntry 4 }

   cienaCesPmAlertTcaBasisValue OBJECT-TYPE
     SYNTAX      PmTcaUnsigned64
     MAX-ACCESS  read-only
     STATUS      current
     DESCRIPTION "Base value against which the alert threshold is applied to
                  determine the boundary value that triggers an Alert TCA event.
                  Value is provided to PM from the component which manages the
                  entity being monitored by the PM instance."
     ::= { cienaCesPmInstanceAlertTcaEntry 5 }

   cienaCesPmAlertTcaBoundaryValue OBJECT-TYPE
     SYNTAX      PmTcaUnsigned64
     MAX-ACCESS  read-only
     STATUS      current
     DESCRIPTION "Boundary established by subtracting the value represented as
                  the alert threshold from the alert basis.  Statistic readings
                  which are equal or greater than this boundary are subject to
                  causing an Alert TCA event at the end of the alert interval."
     ::= { cienaCesPmInstanceAlertTcaEntry 6 }

   cienaCesPmAlertTcaIntervalStartTime OBJECT-TYPE
     SYNTAX      PmTimeDate
     MAX-ACCESS  read-only
     STATUS      current
     DESCRIPTION "The time and date representing when the current Alert Interval
                  has started.  This value will update whenever the operational
                  state of the pm instance changes and whenever the alert
                  interval period has elapsed."
     ::= { cienaCesPmInstanceAlertTcaEntry 7 }

   cienaCesPmAlertTcaIntervalEndTime OBJECT-TYPE
     SYNTAX      PmTimeDate
     MAX-ACCESS  read-only
     STATUS      current
     DESCRIPTION "The time and date representing when the current Alert Interval
                  will end.  This value will update whenever the interval start
                  time changes."
     ::= { cienaCesPmInstanceAlertTcaEntry 8 }

   cienaCesPmAlertTcaSampleStartTime OBJECT-TYPE
     SYNTAX      PmTimeDate
     MAX-ACCESS  read-only
     STATUS      current
     DESCRIPTION "The time and date representing when the current sample
                  interval has started."
     ::= { cienaCesPmInstanceAlertTcaEntry 9 }

   cienaCesPmAlertTcaSampleEndTime OBJECT-TYPE
     SYNTAX      PmTimeDate
     MAX-ACCESS  read-only
     STATUS      current
     DESCRIPTION "The time and date representing when the current sample
                  interval will end."
     ::= { cienaCesPmInstanceAlertTcaEntry 10 }

   cienaCesPmAlertTcaHighWatermarkTime OBJECT-TYPE
     SYNTAX      PmTimeDate
     MAX-ACCESS  read-only
     STATUS      current
     DESCRIPTION "The time and date representing when the high watermark value
                  was established.  An empty string is returned if no high
                  watermark has been determined."
     ::= { cienaCesPmInstanceAlertTcaEntry 11 }

   cienaCesPmAlertTcaHighWatermarkStats OBJECT-TYPE
     SYNTAX      PmStatBitmap
     MAX-ACCESS  read-only
     STATUS      current
     DESCRIPTION "The statistic(s) which were used by the Alert TCA feature to
                  establish the watermark value identified by the
                  cienaCesPmAlertTcaHighWatermarkValue object.  Depending on the
                  value indicated by cienaCesPmAlertTcaScheme, this may be the
                  same or a subset of the statistics identified by the
                  cienaCesPmAlertTcaStats object."
     ::= { cienaCesPmInstanceAlertTcaEntry 12 }

   cienaCesPmAlertTcaHighWatermarkValue OBJECT-TYPE
     SYNTAX      PmTcaUnsigned64
     MAX-ACCESS  read-only
     STATUS      current
     DESCRIPTION "Highest sample interval reading during the current alert
                  interval.  This value resets to zero at the start of each
                  alert interval."
     ::= { cienaCesPmInstanceAlertTcaEntry 13 }

   cienaCesPmAlertTcaState OBJECT-TYPE
     SYNTAX      PmTcaAlertState
     MAX-ACCESS  read-only
     STATUS      current
     DESCRIPTION "The current alert state of the PM instance.  At the end of
                  each alert interval, the alert high watermark is compared to
                  the alert boundary value to determine if the current Alert TCA
                  state is normal or alert.  This object indicates the state that
                  was determined at the end of the most recent alert interval.
                  This object will indicate a value of unspecified if an alert
                  interval has yet to end for the PM instance."
     ::= { cienaCesPmInstanceAlertTcaEntry 14 }

   cienaCesPmAlertTcaEventsTotal OBJECT-TYPE
     SYNTAX      Unsigned32
     MAX-ACCESS  read-only
     STATUS      current
     DESCRIPTION "Total number of Alert TCA events that have occurred for the PM
                  instance."
     ::= { cienaCesPmInstanceAlertTcaEntry 15 }

   cienaCesPmAlertTcaSamplesProcessedTotal OBJECT-TYPE
     SYNTAX      Unsigned32
     MAX-ACCESS  read-only
     STATUS      current
     DESCRIPTION "Total Number of valid samples that have been collected used by
                  the Alert TCA feature on the PM instance."
     ::= { cienaCesPmInstanceAlertTcaEntry 16 }

   cienaCesPmAlertTcaSamplesDiscardedTotal OBJECT-TYPE
     SYNTAX      Unsigned32
     MAX-ACCESS  read-only
     STATUS      current
     DESCRIPTION "Total Number of samples that have been collected but not used
                  by the Alert TCA feature on the PM instance."
     ::= { cienaCesPmInstanceAlertTcaEntry 17 }

   cienaCesPmAlertTcaSamplesProcessedCurrentInterval OBJECT-TYPE
     SYNTAX      Unsigned32
     MAX-ACCESS  read-only
     STATUS      current
     DESCRIPTION "Number of valid samples that have been collected during the
                  current Alert Interval and used by the Alert TCA feature on
                  the PM instance."
     ::= { cienaCesPmInstanceAlertTcaEntry 18 }

   cienaCesPmAlertTcaSamplesDiscardedCurrentInterval OBJECT-TYPE
     SYNTAX      Unsigned32
     MAX-ACCESS  read-only
     STATUS      current
     DESCRIPTION "Number of samples that have been collected during the current
                  Alert Interval but not used by the Alert TCA feature on the PM
                  instance."
     ::= { cienaCesPmInstanceAlertTcaEntry 19 }

   cienaCesPmAlertTcaLastTcaTime OBJECT-TYPE
     SYNTAX      PmTimeDate
     MAX-ACCESS  read-only
     STATUS      current
     DESCRIPTION "The time and date of the last Alert TCA for the PM instance.
                  An empty string is returned if no Alert TCAs have occurred for
                  the PM instance."
     ::= { cienaCesPmInstanceAlertTcaEntry 20 }

   cienaCesPmAlertTcaLastTcaUnits OBJECT-TYPE
     SYNTAX      PmTcaUnits
     MAX-ACCESS  read-only
     STATUS      current
     DESCRIPTION "The value of cienaCesPmAlertTcaUnits that was in use during
                  the last Alert TCA for the PM instance."
     ::= { cienaCesPmInstanceAlertTcaEntry 21 }

   cienaCesPmAlertTcaLastTcaScheme OBJECT-TYPE
     SYNTAX      PmTcaScheme
     MAX-ACCESS  read-only
     STATUS      current
     DESCRIPTION "The value of cienaCesPmAlertTcaScheme that was in use during
                  the last Alert TCA for the PM instance."
     ::= { cienaCesPmInstanceAlertTcaEntry 22 }

   cienaCesPmAlertTcaLastTcaBasisValue OBJECT-TYPE
     SYNTAX      PmTcaUnsigned64
     MAX-ACCESS  read-only
     STATUS      current
     DESCRIPTION "The alert basis value that was in place when the last Alert
                  TCA event occurred.  This refers to the value of
                  cienaCesPmAlertTcaBasis when the last Alert TCA occurred."
     ::= { cienaCesPmInstanceAlertTcaEntry 23 }

   cienaCesPmAlertTcaLastTcaThresholdType OBJECT-TYPE
     SYNTAX      PmTcaThresholdType
     MAX-ACCESS  read-only
     STATUS      current
     DESCRIPTION "This object defines the way in which the value returned for
                  cienaCesPmAlertTcaLastTcaThresholdValue should be
                  interpreted."
     ::= { cienaCesPmInstanceAlertTcaEntry 24 }

   cienaCesPmAlertTcaLastTcaThresholdValue OBJECT-TYPE
     SYNTAX      Unsigned32
     MAX-ACCESS  read-only
     STATUS      current
     DESCRIPTION "The threshold value that was used in the last Alert TCA event.
                  This refers to the configured alert threshold as specified in
                  the interval profile associated with the PM instance when the
                  last Alert TCA occurred."
     ::= { cienaCesPmInstanceAlertTcaEntry 25 }

   cienaCesPmAlertTcaLastTcaBoundaryValue OBJECT-TYPE
     SYNTAX      PmTcaUnsigned64
     MAX-ACCESS  read-only
     STATUS      current
     DESCRIPTION "The threshold boundary value which was reached or exceeded,
                  causing the last Alert TCA.  This refers to the value of
                  cienaCesPmAlertTcaBoundaryValue when the last Alert TCA
                  occurred."
     ::= { cienaCesPmInstanceAlertTcaEntry 26 }

   cienaCesPmAlertTcaLastTcaWatermarkTime OBJECT-TYPE
     SYNTAX      PmTimeDate
     MAX-ACCESS  read-only
     STATUS      current
     DESCRIPTION "The time and date that the watermark value used in the last
                  Alert TCA was derived.  An empty string is returned if no
                  Alert TCAs have occurred for the PM instance."
     ::= { cienaCesPmInstanceAlertTcaEntry 27 }

   cienaCesPmAlertTcaLastTcaWatermarkType OBJECT-TYPE
     SYNTAX      PmTcaWatermarkType
     MAX-ACCESS  read-only
     STATUS      current
     DESCRIPTION "The type of watermark that was used in the logic that caused
                  the last Alert TCA event for the PM instance.  This refers to
                  the watermark value reported by the
                  cienaCesPmAlertTcaLastTcaWatermarkValue object."
     ::= { cienaCesPmInstanceAlertTcaEntry 28 }

   cienaCesPmAlertTcaLastTcaWatermarkStats OBJECT-TYPE
     SYNTAX      PmStatBitmap
     MAX-ACCESS  read-only
     STATUS      current
     DESCRIPTION "The statistic(s) which were used by the Alert TCA feature to
                  establish the watermark value identified by the
                  cienaCesPmAlertTcaLastTcaWatermarkValue object.  This refers
                  to the value of cienaCesPmAlertTcaHighWatermarkStats when the
                  Alert TCA occurred."
     ::= { cienaCesPmInstanceAlertTcaEntry 29 }

   cienaCesPmAlertTcaLastTcaWatermarkValue OBJECT-TYPE
     SYNTAX      PmTcaUnsigned64
     MAX-ACCESS  read-only
     STATUS      current
     DESCRIPTION "The watermark value that was used in the logic that caused the
                  last Alert TCA event for the PM instance.  This refers to the
                  value of cienaCesPmAlertTcaHighWatermarkValue when the last
                  Alert TCA occurred."
     ::= { cienaCesPmInstanceAlertTcaEntry 30 }

   cienaCesPmAlertTcaLastTcaState OBJECT-TYPE
     SYNTAX      PmTcaAlertState
     MAX-ACCESS  read-only
     STATUS      current
     DESCRIPTION "The alert state that was in place during the last Alert TCA.
                  Alert TCA events occur whenever there are changes to the Alert
                  TCA state of the PM Instance.  This object indicates whether
                  the last Alert TCA represented the PM instance having entered
                  the Alert TCA state by indicating a value of alert.  This
                  object indicates whether the last Alert TCA represented the PM
                  instance having exited the Alert TCA state by indicating a
                  value of normal."
     ::= { cienaCesPmInstanceAlertTcaEntry 31 }


   --
   -- PM Notifications
   --
   cienaCesPmAlertTcaNotification NOTIFICATION-TYPE
     OBJECTS     {
                 cienaGlobalSeverity,
                 cienaGlobalMacAddress,
                 cienaCesPmInstanceName,
                 cienaCesPmInstanceInterfaceType,
                 cienaCesPmInstanceInterfaceName,
                 cienaCesPmAlertTcaLastTcaUnits,
                 cienaCesPmAlertTcaLastTcaBasisValue,
                 cienaCesPmAlertTcaLastTcaBoundaryValue,
                 cienaCesPmAlertTcaLastTcaWatermarkType,
                 cienaCesPmAlertTcaLastTcaWatermarkStats,
                 cienaCesPmAlertTcaLastTcaWatermarkValue,
                 cienaCesPmAlertTcaLastTcaState
                 }
     STATUS      current
     DESCRIPTION "This notification is sent when the device reports an Alert
                  Threshold Crossing Alert (TCA) event."
     ::= { cienaCesPmMIBNotifications 1 }

   END
