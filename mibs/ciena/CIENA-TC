-- This file was included in WWP MIB release 04-16-00-0047


CIENA-TC DEFINITIONS ::= BEGIN

             
	IMPORTS                
   MacAddress
   		FROM SNMPv2-TC;               

-- definition of textual conventions

-- TEXTUAL-CONVENTION MACRO ::= 
-- 
-- 
-- BEGIN
--     TYPE NOTATION ::=
--                   DisplayPart
--                   "STATUS" Status
--                   "DESCRIPTION" Text
--                   ReferPart
--                   "SYNTAX" Syntax
-- 
--     VALUE NOTATION ::=
--                    value(VALUE Syntax)      // adapted ASN.1
-- 
--     DisplayPart ::=
--                   "DISPLAY-HINT" Text
--                 | empty
-- 
--     Status ::=
--                   "current"
--                 | "deprecated"
--                 | "obsolete"
-- 
--     ReferPart ::=
--                   "REFERENCE" Text
--                 | empty
-- 
--     // a character string as defined in [2]
--     Text ::= value(IA5String)
-- 
--     Syntax ::=   // Must be one of the following:
--                        // a base type (or its refinement), or
--                        // a BITS pseudo-type
--                   type
--                 | "BITS" "{" NamedBits "}"
-- 
--     NamedBits ::= NamedBit
--                 | NamedBits "," NamedBit
-- 
--     NamedBit ::=  identifier "(" number ")" // number is nonnegative
-- 
-- END

--Textual conventions
--

CienaGlobalState  ::=  TEXTUAL-CONVENTION
     STATUS  current
     DESCRIPTION
         "This textual convention enumerates the administrative and operational state."
     SYNTAX  INTEGER {                                                 
     					enabled(1),
     					disabled(2)
     				}                  
     				
  CienaGlobalSeverity ::= TEXTUAL-CONVENTION
		STATUS	current
		DESCRIPTION
			"This textual convention enumerates the severity levels."
		SYNTAX	INTEGER {
					   none       (0), 
                       cleared           (1), 
                       intermediate      (2), 
                       critical           (3),  
                       major         (4),  
                       minor          (5),
                       warning			(6), 
                       config			(7),
                       info            (8),  -- informational
                       debug           (9),  -- debug-level messages
                       internal           (10)  -- None of the above
					}

  CienaStatsClear ::= TEXTUAL-CONVENTION
	STATUS current
	DESCRIPTION
		"This textual convention enumerates the statistics clear operation if the value is set to 1."
	SYNTAX	INTEGER {		
					none(0),
     				clear(1)
     			}  
 CienaMacAddress ::= TEXTUAL-CONVENTION
 	STATUS current
 	DESCRIPTION
 		"This textual convention denotes a MAC address."
 	SYNTAX MacAddress 
 	
END
