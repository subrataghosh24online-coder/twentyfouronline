STORMSHIELD-VPNSA-MIB DEFINITIONS ::= BEGIN

   IMPORTS
      MODULE-IDENTITY, OBJECT-TYPE, Integer32,
         Unsigned32, Counter64                FROM SNMPv2-SMI
      DisplayString                           FROM RFC1213-MIB
      stormshieldMIB                          FROM STORMSHIELD-SMI-MIB;

   snsVPN MODULE-IDENTITY
      LAST-UPDATED  "201702200000Z"
      ORGANIZATION  "Stormshield"
      CONTACT-INFO
         "Customer Support

         22 rue du Gouverneur General Eboue
         92130 Issy-les-Moulineaux
         FRANCE

         Tel: +33 (0)9 69 32 96 29
         E-mail: support@stormshield.eu
         http://www.stormshield.eu"
      DESCRIPTION   "stormshield VPN MIBS"
      REVISION      "201702200000Z"
      DESCRIPTION   "Initial"
      ::= { stormshieldMIB 1 }

   snsVPNSATable OBJECT-TYPE
      SYNTAX SEQUENCE OF SnsVPNSAEntry
      MAX-ACCESS  not-accessible
      STATUS  current
      DESCRIPTION
         "List of Security Association"
      ::= { snsVPN 1 }

   snsVPNSAEntry OBJECT-TYPE
      SYNTAX  SnsVPNSAEntry
      MAX-ACCESS  not-accessible
      STATUS  current
      DESCRIPTION
         "Each entry in the snsVPNSATable holds a set of parameters."
      INDEX   { snsVPNSAIndex }
      ::= { snsVPNSATable 1 }

   SnsVPNSAEntry ::= SEQUENCE {
      snsVPNSAIndex        INTEGER,
      snsVPNIPSrc          DisplayString,
      snsVPNIPDst          DisplayString,
      snsVPNType           INTEGER,
      snsVPNMode           INTEGER,
      snsVPNSpi            Unsigned32,
      snsVPNPeerSpi        Unsigned32,
      snsVPNReqID          Integer32,
      snsVPNEnc            DisplayString,
      snsVPNAuth           INTEGER,
      snsVPNState          INTEGER,
      snsVPNLifetime       Counter64,
      snsVPNBytes          Counter64,
      snsVPNMaxLifetime    Counter64,
      snsVPNMaxBytes       Counter64
   }

   snsVPNSAIndex OBJECT-TYPE
      SYNTAX  INTEGER  (1..65535)
      MAX-ACCESS  read-only
      STATUS  current
      DESCRIPTION
         "A unique value for phase one table.  Its value
         ranges between 1 and 65535 and may not be contigous.
         the index has no other meaning but a pure index"
      ::= { snsVPNSAEntry 1 }

   snsVPNIPSrc OBJECT-TYPE
      SYNTAX DisplayString
      MAX-ACCESS read-only
      STATUS current
      DESCRIPTION
         "IP source"
      ::= { snsVPNSAEntry 2 }

   snsVPNIPDst OBJECT-TYPE
      SYNTAX DisplayString
      MAX-ACCESS read-only
      STATUS current
      DESCRIPTION
         "IP destination"
      ::= { snsVPNSAEntry 3 }

   snsVPNType OBJECT-TYPE
      SYNTAX INTEGER {
         unspec(0),
         unknown(1),
         ah(2),
         esp(3),
         rsvp(4),
         ospfv2(5),
         ripv2(6),
         mip(7),
         ipcomp(8)
      }
      MAX-ACCESS read-only
      STATUS current
      DESCRIPTION
         "Type"
      ::= { snsVPNSAEntry 4 }

   snsVPNMode OBJECT-TYPE
      SYNTAX INTEGER {
         any(0),
         transport(1),
         tunnel(2)
      }
      MAX-ACCESS read-only
      STATUS current
      DESCRIPTION
         "Mode"
      ::= { snsVPNSAEntry 5 }

   snsVPNSpi OBJECT-TYPE
      SYNTAX Unsigned32
      MAX-ACCESS read-only
      STATUS current
      DESCRIPTION
         "Secure property index"
      ::= { snsVPNSAEntry 6 }

   snsVPNPeerSpi OBJECT-TYPE
      SYNTAX Unsigned32
      MAX-ACCESS read-only
      STATUS current
      DESCRIPTION
         "Secure property index of the peer"
      ::= { snsVPNSAEntry 7 }

   snsVPNReqID OBJECT-TYPE
      SYNTAX Integer32
      MAX-ACCESS read-only
      STATUS current
      DESCRIPTION
         "ReqID"
      ::= { snsVPNSAEntry 8 }

   snsVPNEnc OBJECT-TYPE
      SYNTAX DisplayString
      MAX-ACCESS read-only
      STATUS current
      DESCRIPTION
         "Enc"
      ::= { snsVPNSAEntry 9 }

   snsVPNAuth OBJECT-TYPE
      SYNTAX INTEGER {
         none(0),
         hmac-md5(2),
         hmac-sha1(3),
         hmac-sha256(5),
         hmac-sha384(6),
         hmac-sha512(7),
         md5(249),
         sha(250),
         null(251)
      }
      MAX-ACCESS read-only
      STATUS current
      DESCRIPTION
         "Auth"
      ::= { snsVPNSAEntry 10 }

   snsVPNState OBJECT-TYPE
      SYNTAX INTEGER {
         larval(0),
         mature(1),
         dying(2),
         dead(3)
      }
      MAX-ACCESS read-only
      STATUS current
      DESCRIPTION
         "VPN State"
      ::= { snsVPNSAEntry 11 }

   snsVPNLifetime OBJECT-TYPE
      SYNTAX Counter64
      MAX-ACCESS read-only
      STATUS current
      DESCRIPTION
         "Lifetime"
      ::= { snsVPNSAEntry 12 }

   snsVPNBytes OBJECT-TYPE
      SYNTAX Counter64
      MAX-ACCESS read-only
      STATUS current
      DESCRIPTION
         "Bytes"
      ::= { snsVPNSAEntry 13 }

   snsVPNMaxLifetime OBJECT-TYPE
      SYNTAX Counter64
      MAX-ACCESS read-only
      STATUS current
      DESCRIPTION
         "MaxLifetime"
      ::= { snsVPNSAEntry 14 }

   snsVPNMaxBytes OBJECT-TYPE
      SYNTAX Counter64
      MAX-ACCESS read-only
      STATUS current
      DESCRIPTION
         "MaxBytes"
      ::= { snsVPNSAEntry 15 }

END
