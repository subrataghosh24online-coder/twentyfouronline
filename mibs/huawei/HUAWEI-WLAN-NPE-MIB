--
-- HUAWEI-WLAN-NPE-MIB.mib
-- MIB generated by MG-SOFT Visual MIB Builder Version 4.0 Build 341
-- Thursday, March 05, 2015 at 17:40:04
--

--  ============================================================================
-- Copyright (C) 2015 by  HUAWEI TECHNOLOGIES. All rights reserved.
-- Description:  This mib file is used for management of huawei Class Based 
--                NPE information.
-- Reference: 
-- Version: V1.00
-- History:             
--              v1.00 yuxingbiao  suxunjin

-- ============================================================================
-- Module definition

	HUAWEI-WLAN-NPE-MIB DEFINITIONS ::= BEGIN
 
		IMPORTS
			hwWlan			
				FROM HUAWEI-WLAN-MIB			
			OBJECT-GROUP, MODULE-COMPLIANCE			
				FROM SNMPv2-CONF			
			Integer32, Unsigned32, Counter64, OBJECT-TYPE, MODULE-IDENTITY			
				FROM SNMPv2-SMI			
			MacAddress, RowStatus, DateAndTime			
				FROM SNMPv2-TC;
	
	
-- 1.3.6.1.4.1.2011.6.139.21
		-- 1.3.6.1.4.1.2011.6.139.21
		hwWlanNpe MODULE-IDENTITY 
			LAST-UPDATED "201506191725Z"
			ORGANIZATION 
				"Huawei Technologies Co.,Ltd."
			CONTACT-INFO 
				"Huawei Industrial Base 
				Bantian, Longgang 
				Shenzhen 518129 
				People's Republic of China 
				Website: http://www.huawei.com Email: support@huawei.com
				"
			DESCRIPTION 
				"Description."
				
		       REVISION "201506191725Z"
                       DESCRIPTION
                       "V1.00, Inital version. "
	  	
			::= { hwWlan 21 }

	
-- Node definitions
-- 
-- 1.3.6.1.4.1.2011.6.139.21.1
		-- 1.3.6.1.4.1.2011.6.139.21.1
		hwWlanNpeObjects OBJECT IDENTIFIER ::= { hwWlanNpe 1 }

		
-- 1.3.6.1.4.1.2011.6.139.21.1.1
		-- 1.3.6.1.4.1.2011.6.139.21.1.1
		hwWlanConnectProfileTable OBJECT-TYPE
			SYNTAX SEQUENCE OF HwWlanConnectProfileEntry
			MAX-ACCESS not-accessible
			STATUS current
			DESCRIPTION
				"Description."
			::= { hwWlanNpeObjects 1 }

		
-- 1.3.6.1.4.1.2011.6.139.21.1.1.1
		-- 1.3.6.1.4.1.2011.6.139.21.1.1.1
		hwWlanConnectProfileEntry OBJECT-TYPE
			SYNTAX HwWlanConnectProfileEntry
			MAX-ACCESS not-accessible
			STATUS current
			DESCRIPTION
				"Description."
			INDEX { hwWlanConnectProfileName }
			::= { hwWlanConnectProfileTable 1 }

		
		HwWlanConnectProfileEntry ::=
			SEQUENCE { 
				hwWlanConnectProfileName
					OCTET STRING,
				hwWlanConnectSsid
					OCTET STRING,
				hwWlanConnectPeerMac
					MacAddress,
				hwWlanConnectPSKPassPhase
					OCTET STRING,
				hwWlanConnectProfileActived
					Integer32,
				hwWlanConnectProfileRowStatus
					RowStatus
			 }

-- 1.3.6.1.4.1.2011.6.139.21.1.1.1.1
		-- 1.3.6.1.4.1.2011.6.139.21.1.1.1.1
		hwWlanConnectProfileName OBJECT-TYPE
			SYNTAX OCTET STRING
			MAX-ACCESS not-accessible
			STATUS current
			DESCRIPTION
				"Description."
			::= { hwWlanConnectProfileEntry 1 }

		
-- 1.3.6.1.4.1.2011.6.139.21.1.1.1.2
		-- 1.3.6.1.4.1.2011.6.139.21.1.1.1.2
		hwWlanConnectSsid OBJECT-TYPE
			SYNTAX OCTET STRING
			MAX-ACCESS read-write
			STATUS current
			DESCRIPTION
				"Description."
			::= { hwWlanConnectProfileEntry 2 }

		
-- 1.3.6.1.4.1.2011.6.139.21.1.1.1.3
		-- 1.3.6.1.4.1.2011.6.139.21.1.1.1.3
		hwWlanConnectPeerMac OBJECT-TYPE
			SYNTAX MacAddress
			MAX-ACCESS read-write
			STATUS current
			DESCRIPTION
				"Description."
			::= { hwWlanConnectProfileEntry 3 }

		
-- 1.3.6.1.4.1.2011.6.139.21.1.1.1.4
		-- 1.3.6.1.4.1.2011.6.139.21.1.1.1.4
		hwWlanConnectPSKPassPhase OBJECT-TYPE
			SYNTAX OCTET STRING
			MAX-ACCESS read-write
			STATUS current
			DESCRIPTION
				"Description."
			::= { hwWlanConnectProfileEntry 4 }

		
-- 1.3.6.1.4.1.2011.6.139.21.1.1.1.5
		-- 1.3.6.1.4.1.2011.6.139.21.1.1.1.5
		hwWlanConnectProfileActived OBJECT-TYPE
			SYNTAX Integer32
			MAX-ACCESS read-write
			STATUS current
			DESCRIPTION
				"Description."
			::= { hwWlanConnectProfileEntry 5 }

		
-- 1.3.6.1.4.1.2011.6.139.21.1.1.1.6
		-- 1.3.6.1.4.1.2011.6.139.21.1.1.1.6
		hwWlanConnectProfileRowStatus OBJECT-TYPE
			SYNTAX RowStatus
			MAX-ACCESS read-write
			STATUS current
			DESCRIPTION
				"Description."
			::= { hwWlanConnectProfileEntry 6 }

		
-- 1.3.6.1.4.1.2011.6.139.21.1.2
		-- 1.3.6.1.4.1.2011.6.139.21.1.2
		hwWlanRadioBasicSettingTable OBJECT-TYPE
			SYNTAX SEQUENCE OF HwWlanRadioBasicSettingEntry
			MAX-ACCESS not-accessible
			STATUS current
			DESCRIPTION
				"Description."
			::= { hwWlanNpeObjects 2 }

		
-- 1.3.6.1.4.1.2011.6.139.21.1.2.1
		-- 1.3.6.1.4.1.2011.6.139.21.1.2.1
		hwWlanRadioBasicSettingEntry OBJECT-TYPE
			SYNTAX HwWlanRadioBasicSettingEntry
			MAX-ACCESS not-accessible
			STATUS current
			DESCRIPTION
				"Description."
			INDEX { hwWlanNpeRadioID }
			::= { hwWlanRadioBasicSettingTable 1 }

		
		HwWlanRadioBasicSettingEntry ::=
			SEQUENCE { 
				hwWlanNpeRadioID
					Integer32,
				hwWlanNpeRadioTxPower
					Integer32,
				hwWlanNpeRadioRtsThreshold
					Integer32
			 }

-- 1.3.6.1.4.1.2011.6.139.21.1.2.1.1
		-- 1.3.6.1.4.1.2011.6.139.21.1.2.1.1
		hwWlanNpeRadioID OBJECT-TYPE
			SYNTAX Integer32
			MAX-ACCESS not-accessible
			STATUS current
			DESCRIPTION
				"Description."
			::= { hwWlanRadioBasicSettingEntry 1 }

		
-- 1.3.6.1.4.1.2011.6.139.21.1.2.1.2
		-- 1.3.6.1.4.1.2011.6.139.21.1.2.1.2
		hwWlanNpeRadioTxPower OBJECT-TYPE
			SYNTAX Integer32
			MAX-ACCESS read-write
			STATUS current
			DESCRIPTION
				"Description."
			::= { hwWlanRadioBasicSettingEntry 2 }

		
-- 1.3.6.1.4.1.2011.6.139.21.1.2.1.3
		-- 1.3.6.1.4.1.2011.6.139.21.1.2.1.3
		hwWlanNpeRadioRtsThreshold OBJECT-TYPE
			SYNTAX Integer32
			MAX-ACCESS read-write
			STATUS current
			DESCRIPTION
				"Description."
			::= { hwWlanRadioBasicSettingEntry 3 }

		
-- 1.3.6.1.4.1.2011.6.139.21.1.3
		-- 1.3.6.1.4.1.2011.6.139.21.1.3
		hwWlanConnectStatusTable OBJECT-TYPE
			SYNTAX SEQUENCE OF HwWlanConnectStatusEntry
			MAX-ACCESS not-accessible
			STATUS current
			DESCRIPTION
				"Description."
			::= { hwWlanNpeObjects 3 }

		
-- 1.3.6.1.4.1.2011.6.139.21.1.3.1
		-- 1.3.6.1.4.1.2011.6.139.21.1.3.1
		hwWlanConnectStatusEntry OBJECT-TYPE
			SYNTAX HwWlanConnectStatusEntry
			MAX-ACCESS not-accessible
			STATUS current
			DESCRIPTION
				"Description."
			INDEX { hwWlanConnectStatusPeerMac }
			::= { hwWlanConnectStatusTable 1 }

		
		HwWlanConnectStatusEntry ::=
			SEQUENCE { 
				hwWlanConnectStatusPeerMac
					MacAddress,
				hwWlanConnectStatusSsid
					OCTET STRING,
				hwWlanConnectStatus
					INTEGER,
				hwWlanConnectStatusSNR
					Integer32,
				hwWlanConnectStatusNoiseFloor
					Integer32,
				hwWlanConnectStatusChannel
					Integer32,
				hwWlanConnectStatusActualTxPower
					Integer32,
				hwWlanConnectStatusBeaconInterval
					Integer32,
				hwWlanConnectStatusCurrentRate
					Integer32,
				hwWlanConnectStatusTxBeamforming
					Integer32,
				hwWlanConnectStatusActualCountryCode
					Integer32,
				hwWlanConnectStatusDistance
					Integer32,
				hwWlanConnectStatusCurrentRateKbps
					Integer32,
				hwWlanConnectStatusHtMode
					INTEGER,
				hwWlanConnectStatusGIMode
					INTEGER
			 }

-- 1.3.6.1.4.1.2011.6.139.21.1.3.1.1
		-- 1.3.6.1.4.1.2011.6.139.21.1.3.1.1
		hwWlanConnectStatusPeerMac OBJECT-TYPE
			SYNTAX MacAddress
			MAX-ACCESS not-accessible
			STATUS current
			DESCRIPTION
				"Description."
			::= { hwWlanConnectStatusEntry 1 }

		
-- 1.3.6.1.4.1.2011.6.139.21.1.3.1.2
		-- 1.3.6.1.4.1.2011.6.139.21.1.3.1.2
		hwWlanConnectStatusSsid OBJECT-TYPE
			SYNTAX OCTET STRING
			MAX-ACCESS read-only
			STATUS current
			DESCRIPTION
				"Description."
			::= { hwWlanConnectStatusEntry 2 }

		
-- 1.3.6.1.4.1.2011.6.139.21.1.3.1.3
		-- 1.3.6.1.4.1.2011.6.139.21.1.3.1.3
		hwWlanConnectStatus OBJECT-TYPE
			SYNTAX INTEGER
				{
				disconnect(1),
				connect(2)
				}
			MAX-ACCESS read-only
			STATUS current
			DESCRIPTION
				"Description."
			::= { hwWlanConnectStatusEntry 3 }

		
-- 1.3.6.1.4.1.2011.6.139.21.1.3.1.4
		-- 1.3.6.1.4.1.2011.6.139.21.1.3.1.4
		hwWlanConnectStatusSNR OBJECT-TYPE
			SYNTAX Integer32
			MAX-ACCESS read-only
			STATUS current
			DESCRIPTION
				"Description."
			::= { hwWlanConnectStatusEntry 4 }

		
-- 1.3.6.1.4.1.2011.6.139.21.1.3.1.5
		-- 1.3.6.1.4.1.2011.6.139.21.1.3.1.5
		hwWlanConnectStatusNoiseFloor OBJECT-TYPE
			SYNTAX Integer32
			MAX-ACCESS read-only
			STATUS current
			DESCRIPTION
				"Description."
			::= { hwWlanConnectStatusEntry 5 }

		
-- 1.3.6.1.4.1.2011.6.139.21.1.3.1.6
		-- 1.3.6.1.4.1.2011.6.139.21.1.3.1.6
		hwWlanConnectStatusChannel OBJECT-TYPE
			SYNTAX Integer32
			MAX-ACCESS read-only
			STATUS current
			DESCRIPTION
				"Description."
			::= { hwWlanConnectStatusEntry 6 }

		
-- 1.3.6.1.4.1.2011.6.139.21.1.3.1.7
		-- 1.3.6.1.4.1.2011.6.139.21.1.3.1.7
		hwWlanConnectStatusActualTxPower OBJECT-TYPE
			SYNTAX Integer32
			MAX-ACCESS read-only
			STATUS current
			DESCRIPTION
				"Description."
			::= { hwWlanConnectStatusEntry 7 }

		
-- 1.3.6.1.4.1.2011.6.139.21.1.3.1.8
		-- 1.3.6.1.4.1.2011.6.139.21.1.3.1.8
		hwWlanConnectStatusBeaconInterval OBJECT-TYPE
			SYNTAX Integer32
			MAX-ACCESS read-only
			STATUS current
			DESCRIPTION
				"Description."
			::= { hwWlanConnectStatusEntry 8 }

		
-- 1.3.6.1.4.1.2011.6.139.21.1.3.1.9
		-- 1.3.6.1.4.1.2011.6.139.21.1.3.1.9
		hwWlanConnectStatusCurrentRate OBJECT-TYPE
			SYNTAX Integer32
			MAX-ACCESS read-only
			STATUS current
			DESCRIPTION
				"Description."
			::= { hwWlanConnectStatusEntry 9 }

		
-- 1.3.6.1.4.1.2011.6.139.21.1.3.1.10
		-- 1.3.6.1.4.1.2011.6.139.21.1.3.1.10
		hwWlanConnectStatusTxBeamforming OBJECT-TYPE
			SYNTAX Integer32
			MAX-ACCESS read-only
			STATUS current
			DESCRIPTION
				"Description."
			::= { hwWlanConnectStatusEntry 10 }

		
-- 1.3.6.1.4.1.2011.6.139.21.1.3.1.11
		-- 1.3.6.1.4.1.2011.6.139.21.1.3.1.11
		hwWlanConnectStatusActualCountryCode OBJECT-TYPE
			SYNTAX Integer32
			MAX-ACCESS read-only
			STATUS current
			DESCRIPTION
				"Description."
			::= { hwWlanConnectStatusEntry 11 }

		
-- 1.3.6.1.4.1.2011.6.139.21.1.3.1.12
		-- 1.3.6.1.4.1.2011.6.139.21.1.3.1.12
		hwWlanConnectStatusDistance OBJECT-TYPE
			SYNTAX Integer32
			MAX-ACCESS read-only
			STATUS current
			DESCRIPTION
				"Description."
			::= { hwWlanConnectStatusEntry 12 }

		
--  1.3.6.1.4.1.2011.6.139.21.1.3.1.13
		-- 1.3.6.1.4.1.2011.6.139.21.1.3.1.13
		hwWlanConnectStatusCurrentRateKbps OBJECT-TYPE
			SYNTAX Integer32
			MAX-ACCESS read-only
			STATUS current
			DESCRIPTION
				"An object is used to display the rate of current link, the unit is Kbps."
			::= { hwWlanConnectStatusEntry 13 }

		
--  1.3.6.1.4.1.2011.6.139.21.1.3.1.14
		-- 1.3.6.1.4.1.2011.6.139.21.1.3.1.14
		hwWlanConnectStatusHtMode OBJECT-TYPE
			SYNTAX INTEGER
				{
				ht20(1),
				ht40(2)
				}
			MAX-ACCESS read-only
			STATUS current
			DESCRIPTION
				"An object is used to display the HT mode of current link."
			::= { hwWlanConnectStatusEntry 14 }

		
--  1.3.6.1.4.1.2011.6.139.21.1.3.1.15
		-- 1.3.6.1.4.1.2011.6.139.21.1.3.1.15
		hwWlanConnectStatusGIMode OBJECT-TYPE
			SYNTAX INTEGER
				{
				normal(1),
				short(2)
				}
			MAX-ACCESS read-only
			STATUS current
			DESCRIPTION
				"An object is used to display the GI mode of current link."
			::= { hwWlanConnectStatusEntry 15 }

		
-- 1.3.6.1.4.1.2011.6.139.21.1.4
		-- 1.3.6.1.4.1.2011.6.139.21.1.4
		hwWlanConnectStatisticsTable OBJECT-TYPE
			SYNTAX SEQUENCE OF HwWlanConnectStatisticsEntry
			MAX-ACCESS not-accessible
			STATUS current
			DESCRIPTION
				"Description."
			::= { hwWlanNpeObjects 4 }

		
-- 1.3.6.1.4.1.2011.6.139.21.1.4.1
		-- 1.3.6.1.4.1.2011.6.139.21.1.4.1
		hwWlanConnectStatisticsEntry OBJECT-TYPE
			SYNTAX HwWlanConnectStatisticsEntry
			MAX-ACCESS not-accessible
			STATUS current
			DESCRIPTION
				"Description."
			INDEX { hwWlanConnectStatisticsPeerMac }
			::= { hwWlanConnectStatisticsTable 1 }

		
		HwWlanConnectStatisticsEntry ::=
			SEQUENCE { 
				hwWlanConnectStatisticsPeerMac
					MacAddress,
				hwWlanConnectRxOkUcastDataFrames
					Counter64,
				hwWlanConnectRxOkUcastDataBytes
					Counter64,
				hwWlanConnectTxOkUcastDataFrames
					Counter64,
				hwWlanConnectTxOkUcastDataBytes
					Counter64,
				hwWlanConnectRxThroughput
					Unsigned32,
				hwWlanConnectTxThroughput
					Unsigned32,
				hwWlanConnectRxErrFrames
					Counter64,
				hwWlanConnectTxErrUcastDataFrames
					Counter64,
				hwWlanConnectUcastDataFrameTxRetryRatio
					Unsigned32,
				hwWlanConnectOnlineTime
					Unsigned32,
				hwWlanConnectStatisticsReset
					INTEGER
			 }

-- 1.3.6.1.4.1.2011.6.139.21.1.4.1.1
		-- 1.3.6.1.4.1.2011.6.139.21.1.4.1.1
		hwWlanConnectStatisticsPeerMac OBJECT-TYPE
			SYNTAX MacAddress
			MAX-ACCESS not-accessible
			STATUS current
			DESCRIPTION
				"Description."
			::= { hwWlanConnectStatisticsEntry 1 }

		
-- 1.3.6.1.4.1.2011.6.139.21.1.4.1.2
		-- 1.3.6.1.4.1.2011.6.139.21.1.4.1.2
		hwWlanConnectRxOkUcastDataFrames OBJECT-TYPE
			SYNTAX Counter64
			MAX-ACCESS read-only
			STATUS current
			DESCRIPTION
				"Description."
			::= { hwWlanConnectStatisticsEntry 2 }

		
-- 1.3.6.1.4.1.2011.6.139.21.1.4.1.3
		-- 1.3.6.1.4.1.2011.6.139.21.1.4.1.3
		hwWlanConnectRxOkUcastDataBytes OBJECT-TYPE
			SYNTAX Counter64
			MAX-ACCESS read-only
			STATUS current
			DESCRIPTION
				"Description."
			::= { hwWlanConnectStatisticsEntry 3 }

		
-- 1.3.6.1.4.1.2011.6.139.21.1.4.1.4
		-- 1.3.6.1.4.1.2011.6.139.21.1.4.1.4
		hwWlanConnectTxOkUcastDataFrames OBJECT-TYPE
			SYNTAX Counter64
			MAX-ACCESS read-only
			STATUS current
			DESCRIPTION
				"Description."
			::= { hwWlanConnectStatisticsEntry 4 }

		
-- 1.3.6.1.4.1.2011.6.139.21.1.4.1.5
		-- 1.3.6.1.4.1.2011.6.139.21.1.4.1.5
		hwWlanConnectTxOkUcastDataBytes OBJECT-TYPE
			SYNTAX Counter64
			MAX-ACCESS read-only
			STATUS current
			DESCRIPTION
				"Description."
			::= { hwWlanConnectStatisticsEntry 5 }

		
-- 1.3.6.1.4.1.2011.6.139.21.1.4.1.6
		-- 1.3.6.1.4.1.2011.6.139.21.1.4.1.6
		hwWlanConnectRxThroughput OBJECT-TYPE
			SYNTAX Unsigned32
			MAX-ACCESS read-only
			STATUS current
			DESCRIPTION
				"Description."
			::= { hwWlanConnectStatisticsEntry 6 }

		
-- 1.3.6.1.4.1.2011.6.139.21.1.4.1.7
		-- 1.3.6.1.4.1.2011.6.139.21.1.4.1.7
		hwWlanConnectTxThroughput OBJECT-TYPE
			SYNTAX Unsigned32
			MAX-ACCESS read-only
			STATUS current
			DESCRIPTION
				"Description."
			::= { hwWlanConnectStatisticsEntry 7 }

		
-- 1.3.6.1.4.1.2011.6.139.21.1.4.1.8
		-- 1.3.6.1.4.1.2011.6.139.21.1.4.1.8
		hwWlanConnectRxErrFrames OBJECT-TYPE
			SYNTAX Counter64
			MAX-ACCESS read-only
			STATUS current
			DESCRIPTION
				"Description."
			::= { hwWlanConnectStatisticsEntry 8 }

		
-- 1.3.6.1.4.1.2011.6.139.21.1.4.1.9
		-- 1.3.6.1.4.1.2011.6.139.21.1.4.1.9
		hwWlanConnectTxErrUcastDataFrames OBJECT-TYPE
			SYNTAX Counter64
			MAX-ACCESS read-only
			STATUS current
			DESCRIPTION
				"Description."
			::= { hwWlanConnectStatisticsEntry 9 }

		
-- 1.3.6.1.4.1.2011.6.139.21.1.4.1.10
		-- 1.3.6.1.4.1.2011.6.139.21.1.4.1.10
		hwWlanConnectUcastDataFrameTxRetryRatio OBJECT-TYPE
			SYNTAX Unsigned32
			MAX-ACCESS read-only
			STATUS current
			DESCRIPTION
				"Description."
			::= { hwWlanConnectStatisticsEntry 10 }

		
-- 1.3.6.1.4.1.2011.6.139.21.1.4.1.11
		-- 1.3.6.1.4.1.2011.6.139.21.1.4.1.11
		hwWlanConnectOnlineTime OBJECT-TYPE
			SYNTAX Unsigned32
			MAX-ACCESS read-only
			STATUS current
			DESCRIPTION
				"Description."
			::= { hwWlanConnectStatisticsEntry 11 }

		
-- 1.3.6.1.4.1.2011.6.139.21.1.4.1.12
		-- 1.3.6.1.4.1.2011.6.139.21.1.4.1.12
		hwWlanConnectStatisticsReset OBJECT-TYPE
			SYNTAX INTEGER { reset(1) }
			MAX-ACCESS read-write
			STATUS current
			DESCRIPTION
				"Description."
			::= { hwWlanConnectStatisticsEntry 12 }

		
-- 1.3.6.1.4.1.2011.6.139.21.1.5
		-- 1.3.6.1.4.1.2011.6.139.21.1.5
		hwWlanConnectRateHistogramTable OBJECT-TYPE
			SYNTAX SEQUENCE OF HwWlanConnectRateHistogramEntry
			MAX-ACCESS not-accessible
			STATUS current
			DESCRIPTION
				"Description."
			::= { hwWlanNpeObjects 5 }

		
-- 1.3.6.1.4.1.2011.6.139.21.1.5.1
		-- 1.3.6.1.4.1.2011.6.139.21.1.5.1
		hwWlanConnectRateHistogramEntry OBJECT-TYPE
			SYNTAX HwWlanConnectRateHistogramEntry
			MAX-ACCESS not-accessible
			STATUS current
			DESCRIPTION
				"Description."
			INDEX { hwWlanConnectRateStatDirection, hwWlanConnectRateStatRange }
			::= { hwWlanConnectRateHistogramTable 1 }

		
		HwWlanConnectRateHistogramEntry ::=
			SEQUENCE { 
				hwWlanConnectRateStatDirection
					INTEGER,
				hwWlanConnectRateStatRange
					Integer32,
				hwWlanConnectRateStatUcastDataFrames
					Counter64
			 }

-- 1.3.6.1.4.1.2011.6.139.21.1.5.1.1
		-- 1.3.6.1.4.1.2011.6.139.21.1.5.1.1
		hwWlanConnectRateStatDirection OBJECT-TYPE
			SYNTAX INTEGER
				{
				tx(1),
				rx(2)
				}
			MAX-ACCESS not-accessible
			STATUS current
			DESCRIPTION
				"Description."
			::= { hwWlanConnectRateHistogramEntry 1 }

		
-- 1.3.6.1.4.1.2011.6.139.21.1.5.1.2
		-- 1.3.6.1.4.1.2011.6.139.21.1.5.1.2
		hwWlanConnectRateStatRange OBJECT-TYPE
			SYNTAX Integer32
			MAX-ACCESS not-accessible
			STATUS current
			DESCRIPTION
				"Description."
			::= { hwWlanConnectRateHistogramEntry 2 }

		
-- 1.3.6.1.4.1.2011.6.139.21.1.5.1.3
		-- 1.3.6.1.4.1.2011.6.139.21.1.5.1.3
		hwWlanConnectRateStatUcastDataFrames OBJECT-TYPE
			SYNTAX Counter64
			MAX-ACCESS read-only
			STATUS current
			DESCRIPTION
				"Description."
			::= { hwWlanConnectRateHistogramEntry 3 }

		
-- 1.3.6.1.4.1.2011.6.139.21.1.6
		-- 1.3.6.1.4.1.2011.6.139.21.1.6
		hwWlanConnectAMPDUHistogramTable OBJECT-TYPE
			SYNTAX SEQUENCE OF HwWlanConnectAMPDUHistogramEntry
			MAX-ACCESS not-accessible
			STATUS current
			DESCRIPTION
				"Description."
			::= { hwWlanNpeObjects 6 }

		
-- 1.3.6.1.4.1.2011.6.139.21.1.6.1
		-- 1.3.6.1.4.1.2011.6.139.21.1.6.1
		hwWlanConnectAMPDUHistogramEntry OBJECT-TYPE
			SYNTAX HwWlanConnectAMPDUHistogramEntry
			MAX-ACCESS not-accessible
			STATUS current
			DESCRIPTION
				"Description."
			INDEX { hwWlanConnectAMPDUStatDirection, hwWlanConnectAMPDUStatRange }
			::= { hwWlanConnectAMPDUHistogramTable 1 }

		
		HwWlanConnectAMPDUHistogramEntry ::=
			SEQUENCE { 
				hwWlanConnectAMPDUStatDirection
					INTEGER,
				hwWlanConnectAMPDUStatRange
					Integer32,
				hwWlanConnectAMPDUStatUcastDataFrames
					Counter64
			 }

-- 1.3.6.1.4.1.2011.6.139.21.1.6.1.1
		-- 1.3.6.1.4.1.2011.6.139.21.1.6.1.1
		hwWlanConnectAMPDUStatDirection OBJECT-TYPE
			SYNTAX INTEGER
				{
				tx(1),
				rx(2)
				}
			MAX-ACCESS not-accessible
			STATUS current
			DESCRIPTION
				"Description."
			::= { hwWlanConnectAMPDUHistogramEntry 1 }

		
-- 1.3.6.1.4.1.2011.6.139.21.1.6.1.2
		-- 1.3.6.1.4.1.2011.6.139.21.1.6.1.2
		hwWlanConnectAMPDUStatRange OBJECT-TYPE
			SYNTAX Integer32
			MAX-ACCESS not-accessible
			STATUS current
			DESCRIPTION
				"Description."
			::= { hwWlanConnectAMPDUHistogramEntry 2 }

		
-- 1.3.6.1.4.1.2011.6.139.21.1.6.1.3
		-- 1.3.6.1.4.1.2011.6.139.21.1.6.1.3
		hwWlanConnectAMPDUStatUcastDataFrames OBJECT-TYPE
			SYNTAX Counter64
			MAX-ACCESS read-only
			STATUS current
			DESCRIPTION
				"Description."
			::= { hwWlanConnectAMPDUHistogramEntry 3 }

		
-- 1.3.6.1.4.1.2011.6.139.21.1.7
		-- 1.3.6.1.4.1.2011.6.139.21.1.7
		hwWlanConnectLenHistogramTable OBJECT-TYPE
			SYNTAX SEQUENCE OF HwWlanConnectLenHistogramEntry
			MAX-ACCESS not-accessible
			STATUS current
			DESCRIPTION
				"Description."
			::= { hwWlanNpeObjects 7 }

		
-- 1.3.6.1.4.1.2011.6.139.21.1.7.1
		-- 1.3.6.1.4.1.2011.6.139.21.1.7.1
		hwWlanConnectLenHistogramEntry OBJECT-TYPE
			SYNTAX HwWlanConnectLenHistogramEntry
			MAX-ACCESS not-accessible
			STATUS current
			DESCRIPTION
				"Description."
			INDEX { hwWlanConnectDataLenStatDirection, hwWlanConnectDataLenStatLength }
			::= { hwWlanConnectLenHistogramTable 1 }

		
		HwWlanConnectLenHistogramEntry ::=
			SEQUENCE { 
				hwWlanConnectDataLenStatDirection
					INTEGER,
				hwWlanConnectDataLenStatLength
					Integer32,
				hwWlanConnectDataLenStatFrameCounts
					Counter64
			 }

-- 1.3.6.1.4.1.2011.6.139.21.1.7.1.1
		-- 1.3.6.1.4.1.2011.6.139.21.1.7.1.1
		hwWlanConnectDataLenStatDirection OBJECT-TYPE
			SYNTAX INTEGER
				{
				tx(1),
				rx(2)
				}
			MAX-ACCESS not-accessible
			STATUS current
			DESCRIPTION
				"Description."
			::= { hwWlanConnectLenHistogramEntry 1 }

		
-- 1.3.6.1.4.1.2011.6.139.21.1.7.1.2
		-- 1.3.6.1.4.1.2011.6.139.21.1.7.1.2
		hwWlanConnectDataLenStatLength OBJECT-TYPE
			SYNTAX Integer32
			MAX-ACCESS not-accessible
			STATUS current
			DESCRIPTION
				"Description."
			::= { hwWlanConnectLenHistogramEntry 2 }

		
-- 1.3.6.1.4.1.2011.6.139.21.1.7.1.3
		-- 1.3.6.1.4.1.2011.6.139.21.1.7.1.3
		hwWlanConnectDataLenStatFrameCounts OBJECT-TYPE
			SYNTAX Counter64
			MAX-ACCESS read-only
			STATUS current
			DESCRIPTION
				"Description."
			::= { hwWlanConnectLenHistogramEntry 3 }

		
-- 1.3.6.1.4.1.2011.6.139.21.1.8
		-- 1.3.6.1.4.1.2011.6.139.21.1.8
		hwWlanConnectMaxSnrTable OBJECT-TYPE
			SYNTAX SEQUENCE OF HwWlanConnectMaxSnrEntry
			MAX-ACCESS not-accessible
			STATUS current
			DESCRIPTION
				"Description."
			::= { hwWlanNpeObjects 8 }

		
-- 1.3.6.1.4.1.2011.6.139.21.1.8.1
		-- 1.3.6.1.4.1.2011.6.139.21.1.8.1
		hwWlanConnectMaxSnrEntry OBJECT-TYPE
			SYNTAX HwWlanConnectMaxSnrEntry
			MAX-ACCESS not-accessible
			STATUS current
			DESCRIPTION
				"Description."
			INDEX { hwWlanConnectMaxSnrPeerMAC }
			::= { hwWlanConnectMaxSnrTable 1 }

		
		HwWlanConnectMaxSnrEntry ::=
			SEQUENCE { 
				hwWlanConnectMaxSnrPeerMAC
					MacAddress,
				hwWlanConnectMaxSnrValue
					Integer32,
				hwWlanConnectMaxSnrNoiseFloor
					Integer32,
				hwWlanConnectMaxSnrSSID
					OCTET STRING,
				hwWlanConnectMaxSnrTime
					DateAndTime
			 }

-- 1.3.6.1.4.1.2011.6.139.21.1.8.1.1
		-- 1.3.6.1.4.1.2011.6.139.21.1.8.1.1
		hwWlanConnectMaxSnrPeerMAC OBJECT-TYPE
			SYNTAX MacAddress
			MAX-ACCESS not-accessible
			STATUS current
			DESCRIPTION
				"Description."
			::= { hwWlanConnectMaxSnrEntry 1 }

		
-- 1.3.6.1.4.1.2011.6.139.21.1.8.1.2
		-- 1.3.6.1.4.1.2011.6.139.21.1.8.1.2
		hwWlanConnectMaxSnrValue OBJECT-TYPE
			SYNTAX Integer32
			MAX-ACCESS read-only
			STATUS current
			DESCRIPTION
				"Description."
			::= { hwWlanConnectMaxSnrEntry 2 }

		
-- 1.3.6.1.4.1.2011.6.139.21.1.8.1.3
		-- 1.3.6.1.4.1.2011.6.139.21.1.8.1.3
		hwWlanConnectMaxSnrNoiseFloor OBJECT-TYPE
			SYNTAX Integer32
			MAX-ACCESS read-only
			STATUS current
			DESCRIPTION
				"Description."
			::= { hwWlanConnectMaxSnrEntry 3 }

		
-- 1.3.6.1.4.1.2011.6.139.21.1.8.1.4
		-- 1.3.6.1.4.1.2011.6.139.21.1.8.1.4
		hwWlanConnectMaxSnrSSID OBJECT-TYPE
			SYNTAX OCTET STRING
			MAX-ACCESS read-only
			STATUS current
			DESCRIPTION
				"Description."
			::= { hwWlanConnectMaxSnrEntry 4 }

		
-- 1.3.6.1.4.1.2011.6.139.21.1.8.1.5
		-- 1.3.6.1.4.1.2011.6.139.21.1.8.1.5
		hwWlanConnectMaxSnrTime OBJECT-TYPE
			SYNTAX DateAndTime
			MAX-ACCESS read-only
			STATUS current
			DESCRIPTION
				"Description."
			::= { hwWlanConnectMaxSnrEntry 5 }

		
--  1.3.6.1.4.1.2011.6.139.21.1.9
		-- 1.3.6.1.4.1.2011.6.139.21.1.9
		hwWlanNpeSysPara OBJECT IDENTIFIER ::= { hwWlanNpeObjects 9 }

		
--  1.3.6.1.4.1.2011.6.139.21.1.9.1
		-- 1.3.6.1.4.1.2011.6.139.21.1.9.1
		hwWlanNpeCountryCode OBJECT-TYPE
			SYNTAX OCTET STRING
			MAX-ACCESS read-write
			STATUS current
			DESCRIPTION
				"Description."
			::= { hwWlanNpeSysPara 1 }

		
		-- 1.3.6.1.4.1.2011.6.139.21.1.10
		hwWlanDot11eCarCfgInfoTable OBJECT-TYPE
			SYNTAX SEQUENCE OF HwWlanDot11eCarCfgInfoEntry
			MAX-ACCESS not-accessible
			STATUS current
			DESCRIPTION
				"A table of 80211E CAR feature configuration information."
			::= { hwWlanNpeObjects 10 }

		
		-- 1.3.6.1.4.1.2011.6.139.21.1.10.1
		hwWlanDot11eCarCfgInfoEntry OBJECT-TYPE
			SYNTAX HwWlanDot11eCarCfgInfoEntry
			MAX-ACCESS not-accessible
			STATUS current
			DESCRIPTION
				"8021E CAR Configuration Information Entry."
			INDEX { hwWlanDot11eCarIndex }
			::= { hwWlanDot11eCarCfgInfoTable 1 }

		
		HwWlanDot11eCarCfgInfoEntry ::=
			SEQUENCE { 
				hwWlanDot11eCarIndex
					Integer32,
				hwWlanDot11eCarCir
					Unsigned32,
				hwWlanDot11eCarCbs
					Unsigned32,
				hwWlanDot11eCarPir
					Unsigned32,
				hwWlanDot11eCarPbs
					Unsigned32,
				hwWlanDot11eCarDot11eValue
					OCTET STRING,
				hwWlanDot11eCarRowStatus
					RowStatus
			 }

		-- 1.3.6.1.4.1.2011.6.139.21.1.10.1.1
		hwWlanDot11eCarIndex OBJECT-TYPE
			SYNTAX Integer32 (1..8)
			MAX-ACCESS read-only
			STATUS current
			DESCRIPTION
				"Every Command Index ID."
			::= { hwWlanDot11eCarCfgInfoEntry 1 }

		
		-- 1.3.6.1.4.1.2011.6.139.21.1.10.1.2
		hwWlanDot11eCarCir OBJECT-TYPE
			SYNTAX Unsigned32 (64..4294967295)
			MAX-ACCESS read-create
			STATUS current
			DESCRIPTION
				"Committed Information Rate. Unit: kbps.
     		 	Unsigned32<64-4294967295>."
			::= { hwWlanDot11eCarCfgInfoEntry 2 }

		
		-- 1.3.6.1.4.1.2011.6.139.21.1.10.1.3
		hwWlanDot11eCarCbs OBJECT-TYPE
			SYNTAX Unsigned32 (1500..4294967295)
			MAX-ACCESS read-create
			STATUS current
			DESCRIPTION
				"Committed Burst Size. Unit: byte.
     		 Unsigned32<1500-4294967295>."
			::= { hwWlanDot11eCarCfgInfoEntry 3 }

		
		-- 1.3.6.1.4.1.2011.6.139.21.1.10.1.4
		hwWlanDot11eCarPir OBJECT-TYPE
			SYNTAX Unsigned32 (64..4294967295)
			MAX-ACCESS read-create
			STATUS current
			DESCRIPTION
				"Peak Information Rate. Unit: kbps.
		 Unsigned32<64-4294967295>."
			::= { hwWlanDot11eCarCfgInfoEntry 4 }

		
		-- 1.3.6.1.4.1.2011.6.139.21.1.10.1.5
		hwWlanDot11eCarPbs OBJECT-TYPE
			SYNTAX Unsigned32 (1500..4294967295)
			MAX-ACCESS read-create
			STATUS current
			DESCRIPTION
				"Peak Burst Size. Unit: byte.
 	         Unsigned32<1500-4294967295>."
			::= { hwWlanDot11eCarCfgInfoEntry 5 }

		
		-- 1.3.6.1.4.1.2011.6.139.21.1.10.1.6
		hwWlanDot11eCarDot11eValue OBJECT-TYPE
			SYNTAX OCTET STRING (SIZE (0..31))
			MAX-ACCESS read-create
			STATUS current
			DESCRIPTION
				"802.11e value.
		 STRING<0-7>."
			::= { hwWlanDot11eCarCfgInfoEntry 6 }

		
		-- 1.3.6.1.4.1.2011.6.139.21.1.10.1.7
		hwWlanDot11eCarRowStatus OBJECT-TYPE
			SYNTAX RowStatus
			MAX-ACCESS read-create
			STATUS current
			DESCRIPTION
				"RowStatus. Three actions are used: active(1),
	     	 createAndGo(4), destroy(6)."
			::= { hwWlanDot11eCarCfgInfoEntry 7 }

		
-- 1.3.6.1.4.1.2011.6.139.21.2
		-- 1.3.6.1.4.1.2011.6.139.21.2
		hwWlanNpeConformance OBJECT IDENTIFIER ::= { hwWlanNpe 2 }

		
-- 1.3.6.1.4.1.2011.6.139.21.2.1
		-- 1.3.6.1.4.1.2011.6.139.21.2.1
		hwWlanNpeCompliances OBJECT IDENTIFIER ::= { hwWlanNpeConformance 1 }

		
-- 1.3.6.1.4.1.2011.6.139.21.2.1.1
		-- 1.3.6.1.4.1.2011.6.139.21.2.1.1
		hwWlanNpeCompliance MODULE-COMPLIANCE
			STATUS current
			DESCRIPTION 
				"Description."
			MODULE -- this module
			::= { hwWlanNpeCompliances 1 }

		
-- 1.3.6.1.4.1.2011.6.139.21.2.2
		-- 1.3.6.1.4.1.2011.6.139.21.2.2
		hwWlanNpeObjectGroups OBJECT IDENTIFIER ::= { hwWlanNpeConformance 2 }

		
-- 1.3.6.1.4.1.2011.6.139.21.2.2.1
		-- 1.3.6.1.4.1.2011.6.139.21.2.2.1
		hwWlanNpeConnectProfileGroup OBJECT-GROUP
			OBJECTS { hwWlanConnectSsid, hwWlanConnectPeerMac, hwWlanConnectPSKPassPhase, hwWlanConnectProfileActived, 
				hwWlanConnectProfileRowStatus }
			STATUS current
			DESCRIPTION 
				"Description."
			::= { hwWlanNpeObjectGroups 1 }

		
-- 1.3.6.1.4.1.2011.6.139.21.2.2.2
		-- 1.3.6.1.4.1.2011.6.139.21.2.2.2
		hwWlanRadioBasicSettingGroup OBJECT-GROUP
			OBJECTS { hwWlanNpeRadioTxPower, hwWlanNpeRadioRtsThreshold }
			STATUS current
			DESCRIPTION 
				"Description."
			::= { hwWlanNpeObjectGroups 2 }

		
-- 1.3.6.1.4.1.2011.6.139.21.2.2.3
		-- 1.3.6.1.4.1.2011.6.139.21.2.2.3
		hwWlanConnectStatusGroup OBJECT-GROUP
			OBJECTS { hwWlanConnectStatusBeaconInterval, hwWlanConnectStatusCurrentRate, hwWlanConnectStatusTxBeamforming, hwWlanConnectStatusActualCountryCode, hwWlanConnectStatusDistance, 
				hwWlanConnectStatus, hwWlanConnectStatusSNR, hwWlanConnectStatusNoiseFloor, hwWlanConnectStatusChannel, hwWlanConnectStatusActualTxPower, 
				hwWlanConnectStatusSsid, hwWlanConnectStatusCurrentRateKbps, hwWlanConnectStatusHtMode, hwWlanConnectStatusGIMode }
			STATUS current
			DESCRIPTION 
				"Description."
			::= { hwWlanNpeObjectGroups 3 }

		
-- 1.3.6.1.4.1.2011.6.139.21.2.2.4
		-- 1.3.6.1.4.1.2011.6.139.21.2.2.4
		hwWlanConnectStatisticsGroup OBJECT-GROUP
			OBJECTS { hwWlanConnectRxOkUcastDataFrames, hwWlanConnectRxOkUcastDataBytes, hwWlanConnectTxOkUcastDataFrames, hwWlanConnectTxOkUcastDataBytes, 
				hwWlanConnectRxThroughput, hwWlanConnectTxThroughput, hwWlanConnectRxErrFrames, hwWlanConnectTxErrUcastDataFrames, hwWlanConnectUcastDataFrameTxRetryRatio, 
				hwWlanConnectOnlineTime, hwWlanConnectStatisticsReset }
			STATUS current
			DESCRIPTION 
				"Description."
			::= { hwWlanNpeObjectGroups 4 }

		
-- 1.3.6.1.4.1.2011.6.139.21.2.2.5
		-- 1.3.6.1.4.1.2011.6.139.21.2.2.5
		hwWlanConnectRateHistogramGroup OBJECT-GROUP
			OBJECTS { hwWlanConnectRateStatUcastDataFrames }
			STATUS current
			DESCRIPTION 
				"Description."
			::= { hwWlanNpeObjectGroups 5 }

		
-- 1.3.6.1.4.1.2011.6.139.21.2.2.6
		-- 1.3.6.1.4.1.2011.6.139.21.2.2.6
		hwWlanConnectAMPDUHistogramGroup OBJECT-GROUP
			OBJECTS { hwWlanConnectAMPDUStatUcastDataFrames }
			STATUS current
			DESCRIPTION 
				"Description."
			::= { hwWlanNpeObjectGroups 6 }

		
-- 1.3.6.1.4.1.2011.6.139.21.2.2.7
		-- 1.3.6.1.4.1.2011.6.139.21.2.2.7
		hwWlanConnectLenHistogramGroup OBJECT-GROUP
			OBJECTS { hwWlanConnectDataLenStatFrameCounts }
			STATUS current
			DESCRIPTION 
				"Description."
			::= { hwWlanNpeObjectGroups 7 }

		
-- 1.3.6.1.4.1.2011.6.139.21.2.2.8
		-- 1.3.6.1.4.1.2011.6.139.21.2.2.8
		hwWlanConnectMaxSnrGroup OBJECT-GROUP
			OBJECTS { hwWlanConnectMaxSnrValue, hwWlanConnectMaxSnrNoiseFloor, hwWlanConnectMaxSnrSSID, hwWlanConnectMaxSnrTime
				 }
			STATUS current
			DESCRIPTION 
				"Description."
			::= { hwWlanNpeObjectGroups 8 }

		
--  1.3.6.1.4.1.2011.6.139.21.2.2.9
		-- 1.3.6.1.4.1.2011.6.139.21.2.2.9
		hwWnpeSysParaGroup OBJECT-GROUP
			OBJECTS { hwWlanNpeCountryCode }
			STATUS current
			DESCRIPTION 
				"Description."
			::= { hwWlanNpeObjectGroups 9 }

		
		-- 1.3.6.1.4.1.2011.6.139.21.2.2.10
		hwWlanDot11eCarGroup OBJECT-GROUP
			OBJECTS { hwWlanDot11eCarIndex, hwWlanDot11eCarCir, hwWlanDot11eCarCbs, hwWlanDot11eCarPir, hwWlanDot11eCarPbs, 
				hwWlanDot11eCarDot11eValue, hwWlanDot11eCarRowStatus }
			STATUS current
			DESCRIPTION 
				"Description."
			::= { hwWlanNpeObjectGroups 10 }

		
	
	END

--
-- HUAWEI-WLAN-NPE-MIB.mib
--
