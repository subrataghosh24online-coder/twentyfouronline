--
-- HUAWEI-STORAGE-SPACE-MIB.mib
-- MIB generated by MG-SOFT Visual MIB Builder Version 4.0 Build 347
-- Wednesday, October 15, 2014 at 11:21:02
--

	HUAWEI-STORAGE-SPACE-MIB DEFINITIONS ::= BEGIN
 
		IMPORTS
			OBJECT-GROUP, MODULE-COMPLIANCE			
				FROM SNMPv2-CONF			
			enterprises, Unsigned32, Counter64, OBJECT-TYPE, 
			MODULE-IDENTITY			
				FROM SNMPv2-SMI			
			TEXTUAL-CONVENTION			
				FROM SNMPv2-TC;
	
	
		hwStorage MODULE-IDENTITY 
			LAST-UPDATED "201008111239Z"		-- August 11, 2010 at 12:39 GMT
			ORGANIZATION 
				"Huawei Technologies Co.,Ltd."
			CONTACT-INFO 
				"Huawei Industrial Base
				Bantian, Longgang
				Shenzhen 518129
				People's Republic of China
				Website: http://www.huawei.com
				Email: support@huawei.com"
			DESCRIPTION 
				"Description."
			REVISION "201304061354Z"		-- April 06, 2013 at 13:54 GMT
			DESCRIPTION 
				" "
			::= { huaweistorage 4 }

		
	
--
-- Textual conventions
--
	
--  August 11, 2010 at 12:39 GMT
-- April 06, 2013 at 13:54 GMT
-- 
-- Textual conventions
-- 
		NodeCodeString ::= TEXTUAL-CONVENTION
			DISPLAY-HINT 
				"255a"
			STATUS current
			DESCRIPTION 
				"characters in length."
			SYNTAX OCTET STRING (SIZE (15..17))

	
--
-- Node definitions
--
	
--  Node definitions
-- 
		huaweistorage OBJECT IDENTIFIER ::= { enterprises 34774 }

		
		hwISM OBJECT IDENTIFIER ::= { hwStorage 1 }

		
		hwStorageDevice OBJECT IDENTIFIER ::= { hwISM 23 }

		
		hwSpaceInfo OBJECT IDENTIFIER ::= { hwStorageDevice 4 }

		
		hwInfoDiskDomainTable OBJECT-TYPE
			SYNTAX SEQUENCE OF HwInfoDiskDomainEntry
			MAX-ACCESS not-accessible
			STATUS current
			DESCRIPTION
				" "
			::= { hwSpaceInfo 1 }

		
		hwInfoDiskDomainEntry OBJECT-TYPE
			SYNTAX HwInfoDiskDomainEntry
			MAX-ACCESS not-accessible
			STATUS current
			DESCRIPTION
				"  "
			INDEX { hwInfoDiskDomainID }
			::= { hwInfoDiskDomainTable 1 }

		
		HwInfoDiskDomainEntry ::=
			SEQUENCE { 
				hwInfoDiskDomainID
					OCTET STRING,
				hwInfoDiskDomainName
					OCTET STRING,
				hwInfoDiskDomainHealthStatus
					Unsigned32,
				hwInfoDiskDomainRunningStatus
					Unsigned32,
				hwInfoDiskDomainTotalCapacity
					Counter64,
				hwInfoDiskDomainFreeCapacity
					Counter64,
				hwInfoDiskDomainHotSpareCapacity
					Counter64,
				hwInfoDiskDomainUsedHotSpareCapacity
					Counter64,
				hwInfoDiskDomainTier0DiskNumber
					Unsigned32,
				hwInfoDiskDomainTier0TotalCapacity
					Counter64,
				hwInfoDiskDomainTier0FreeCapacity
					Counter64,
				hwInfoDiskDomainTier0HotSpareCapacity
					Counter64,
				hwInfoDiskDomainTier0UsedHotSpareCapacity
					Counter64,
				hwInfoDiskDomainTier0HotSpareStrategy
					Unsigned32,
				hwInfoDiskDomainTier1DiskNumber
					Unsigned32,
				hwInfoDiskDomainTier1TotalCapacity
					Counter64,
				hwInfoDiskDomainTier1FreeCapacity
					Counter64,
				hwInfoDiskDomainTier1HotSpareCapacity
					Counter64,
				hwInfoDiskDomainTier1UsedHotSpareCapacity
					Counter64,
				hwInfoDiskDomainTier1HotSpareStrategy
					Unsigned32,
				hwInfoDiskDomainTier2DiskNumber
					Unsigned32,
				hwInfoDiskDomainTier2TotalCapacity
					Counter64,
				hwInfoDiskDomainTier2FreeCapacity
					Counter64,
				hwInfoDiskDomainTier2HotSpareCapacity
					Counter64,
				hwInfoDiskDomainTier2UsedHotSpareCapacity
					Counter64,
				hwInfoDiskDomainTier2HotSpareStrategy
					Unsigned32
			 }

		hwInfoDiskDomainID OBJECT-TYPE
			SYNTAX OCTET STRING
			MAX-ACCESS read-only
			STATUS current
			DESCRIPTION
				"  "
			::= { hwInfoDiskDomainEntry 1 }

		
		hwInfoDiskDomainName OBJECT-TYPE
			SYNTAX OCTET STRING
			MAX-ACCESS read-only
			STATUS current
			DESCRIPTION
				"  "
			::= { hwInfoDiskDomainEntry 2 }

		
		hwInfoDiskDomainHealthStatus OBJECT-TYPE
			SYNTAX Unsigned32
			MAX-ACCESS read-only
			STATUS current
			DESCRIPTION
				"  "
			::= { hwInfoDiskDomainEntry 3 }

		
		hwInfoDiskDomainRunningStatus OBJECT-TYPE
			SYNTAX Unsigned32
			MAX-ACCESS read-only
			STATUS current
			DESCRIPTION
				"  "
			::= { hwInfoDiskDomainEntry 4 }

		
		hwInfoDiskDomainTotalCapacity OBJECT-TYPE
			SYNTAX Counter64
			MAX-ACCESS read-only
			STATUS current
			DESCRIPTION
				"  "
			::= { hwInfoDiskDomainEntry 5 }

		
		hwInfoDiskDomainFreeCapacity OBJECT-TYPE
			SYNTAX Counter64
			MAX-ACCESS read-only
			STATUS current
			DESCRIPTION
				"  "
			::= { hwInfoDiskDomainEntry 6 }

		
		hwInfoDiskDomainHotSpareCapacity OBJECT-TYPE
			SYNTAX Counter64
			MAX-ACCESS read-only
			STATUS current
			DESCRIPTION
				"  "
			::= { hwInfoDiskDomainEntry 7 }

		
		hwInfoDiskDomainUsedHotSpareCapacity OBJECT-TYPE
			SYNTAX Counter64
			MAX-ACCESS read-only
			STATUS current
			DESCRIPTION
				"  "
			::= { hwInfoDiskDomainEntry 8 }

		
		hwInfoDiskDomainTier0DiskNumber OBJECT-TYPE
			SYNTAX Unsigned32
			MAX-ACCESS read-only
			STATUS current
			DESCRIPTION
				"  "
			::= { hwInfoDiskDomainEntry 9 }

		
		hwInfoDiskDomainTier0TotalCapacity OBJECT-TYPE
			SYNTAX Counter64
			MAX-ACCESS read-only
			STATUS current
			DESCRIPTION
				"  "
			::= { hwInfoDiskDomainEntry 10 }

		
		hwInfoDiskDomainTier0FreeCapacity OBJECT-TYPE
			SYNTAX Counter64
			MAX-ACCESS read-only
			STATUS current
			DESCRIPTION
				"  "
			::= { hwInfoDiskDomainEntry 11 }

		
		hwInfoDiskDomainTier0HotSpareCapacity OBJECT-TYPE
			SYNTAX Counter64
			MAX-ACCESS read-only
			STATUS current
			DESCRIPTION
				"  "
			::= { hwInfoDiskDomainEntry 12 }

		
		hwInfoDiskDomainTier0UsedHotSpareCapacity OBJECT-TYPE
			SYNTAX Counter64
			MAX-ACCESS read-only
			STATUS current
			DESCRIPTION
				"  "
			::= { hwInfoDiskDomainEntry 13 }

		
		hwInfoDiskDomainTier0HotSpareStrategy OBJECT-TYPE
			SYNTAX Unsigned32
			MAX-ACCESS read-only
			STATUS current
			DESCRIPTION
				"  "
			::= { hwInfoDiskDomainEntry 14 }

		
		hwInfoDiskDomainTier1DiskNumber OBJECT-TYPE
			SYNTAX Unsigned32
			MAX-ACCESS read-only
			STATUS current
			DESCRIPTION
				"  "
			::= { hwInfoDiskDomainEntry 15 }

		
		hwInfoDiskDomainTier1TotalCapacity OBJECT-TYPE
			SYNTAX Counter64
			MAX-ACCESS read-only
			STATUS current
			DESCRIPTION
				"  "
			::= { hwInfoDiskDomainEntry 16 }

		
		hwInfoDiskDomainTier1FreeCapacity OBJECT-TYPE
			SYNTAX Counter64
			MAX-ACCESS read-only
			STATUS current
			DESCRIPTION
				"  "
			::= { hwInfoDiskDomainEntry 17 }

		
		hwInfoDiskDomainTier1HotSpareCapacity OBJECT-TYPE
			SYNTAX Counter64
			MAX-ACCESS read-only
			STATUS current
			DESCRIPTION
				"  "
			::= { hwInfoDiskDomainEntry 18 }

		
		hwInfoDiskDomainTier1UsedHotSpareCapacity OBJECT-TYPE
			SYNTAX Counter64
			MAX-ACCESS read-only
			STATUS current
			DESCRIPTION
				"  "
			::= { hwInfoDiskDomainEntry 19 }

		
		hwInfoDiskDomainTier1HotSpareStrategy OBJECT-TYPE
			SYNTAX Unsigned32
			MAX-ACCESS read-only
			STATUS current
			DESCRIPTION
				"  "
			::= { hwInfoDiskDomainEntry 20 }

		
		hwInfoDiskDomainTier2DiskNumber OBJECT-TYPE
			SYNTAX Unsigned32
			MAX-ACCESS read-only
			STATUS current
			DESCRIPTION
				"  "
			::= { hwInfoDiskDomainEntry 21 }

		
		hwInfoDiskDomainTier2TotalCapacity OBJECT-TYPE
			SYNTAX Counter64
			MAX-ACCESS read-only
			STATUS current
			DESCRIPTION
				"  "
			::= { hwInfoDiskDomainEntry 22 }

		
		hwInfoDiskDomainTier2FreeCapacity OBJECT-TYPE
			SYNTAX Counter64
			MAX-ACCESS read-only
			STATUS current
			DESCRIPTION
				"  "
			::= { hwInfoDiskDomainEntry 23 }

		
		hwInfoDiskDomainTier2HotSpareCapacity OBJECT-TYPE
			SYNTAX Counter64
			MAX-ACCESS read-only
			STATUS current
			DESCRIPTION
				"  "
			::= { hwInfoDiskDomainEntry 24 }

		
		hwInfoDiskDomainTier2UsedHotSpareCapacity OBJECT-TYPE
			SYNTAX Counter64
			MAX-ACCESS read-only
			STATUS current
			DESCRIPTION
				"  "
			::= { hwInfoDiskDomainEntry 25 }

		
		hwInfoDiskDomainTier2HotSpareStrategy OBJECT-TYPE
			SYNTAX Unsigned32
			MAX-ACCESS read-only
			STATUS current
			DESCRIPTION
				"  "
			::= { hwInfoDiskDomainEntry 26 }

		
		hwInfoStoragePoolTable OBJECT-TYPE
			SYNTAX SEQUENCE OF HwInfoStoragePoolEntry
			MAX-ACCESS not-accessible
			STATUS current
			DESCRIPTION
				"  "
			::= { hwSpaceInfo 2 }

		
		hwInfoStoragePoolEntry OBJECT-TYPE
			SYNTAX HwInfoStoragePoolEntry
			MAX-ACCESS not-accessible
			STATUS current
			DESCRIPTION
				"  "
			INDEX { hwInfoStoragePoolID }
			::= { hwInfoStoragePoolTable 1 }

		
		HwInfoStoragePoolEntry ::=
			SEQUENCE { 
				hwInfoStoragePoolID
					OCTET STRING,
				hwInfoStoragePoolName
					OCTET STRING,
				hwInfoStoragePoolDiskDomainID
					OCTET STRING,
				hwInfoStoragePoolDiskDomainName
					OCTET STRING,
				hwInfoStoragePoolHealthStatus
					Unsigned32,
				hwInfoStoragePoolRunningStatus
					Unsigned32,
				hwInfoStoragePoolTotalCapacity
					Counter64,
				hwInfoStoragePoolSubscribedCapacity
					Counter64,
				hwInfoStoragePoolFreeCapacity
					Counter64,
				hwInfoStoragePoolProtectionCapacity
					Counter64,
				hwInfoStoragePoolTier0Capacity
					Counter64,
				hwInfoStoragePoolTier1Capacity
					Counter64,
				hwInfoStoragePoolTier2Capacity
					Counter64,
				hwInfoStoragePoolFullThreshold
					Unsigned32,
				hwInfoStoragePoolExtentSize
					Unsigned32,
				hwInfoStoragePoolSmartTierFeatureStatus
					Unsigned32,
				hwInfoStoragePoolRelocationStatus
					Unsigned32,
				hwInfoStoragePoolRelocationTriggerMode
					Unsigned32,
				hwInfoStoragePoolRelocationPaused
					Unsigned32,
				hwInfoStoragePoolEstimatedMoveUpData
					Counter64,
				hwInfoStoragePoolEstimatedMoveDownData
					Counter64,
				hwInfoStoragePoolEstimatedDataRelocationDuration
					Counter64
			 }

		hwInfoStoragePoolID OBJECT-TYPE
			SYNTAX OCTET STRING
			MAX-ACCESS read-only
			STATUS current
			DESCRIPTION
				"  "
			::= { hwInfoStoragePoolEntry 1 }

		
		hwInfoStoragePoolName OBJECT-TYPE
			SYNTAX OCTET STRING
			MAX-ACCESS read-only
			STATUS current
			DESCRIPTION
				"  "
			::= { hwInfoStoragePoolEntry 2 }

		
		hwInfoStoragePoolDiskDomainID OBJECT-TYPE
			SYNTAX OCTET STRING
			MAX-ACCESS read-only
			STATUS current
			DESCRIPTION
				"  "
			::= { hwInfoStoragePoolEntry 3 }

		
		hwInfoStoragePoolDiskDomainName OBJECT-TYPE
			SYNTAX OCTET STRING
			MAX-ACCESS read-only
			STATUS current
			DESCRIPTION
				"  "
			::= { hwInfoStoragePoolEntry 4 }

		
		hwInfoStoragePoolHealthStatus OBJECT-TYPE
			SYNTAX Unsigned32
			MAX-ACCESS read-only
			STATUS current
			DESCRIPTION
				"  "
			::= { hwInfoStoragePoolEntry 5 }

		
		hwInfoStoragePoolRunningStatus OBJECT-TYPE
			SYNTAX Unsigned32
			MAX-ACCESS read-only
			STATUS current
			DESCRIPTION
				"  "
			::= { hwInfoStoragePoolEntry 6 }

		
		hwInfoStoragePoolTotalCapacity OBJECT-TYPE
			SYNTAX Counter64
			MAX-ACCESS read-only
			STATUS current
			DESCRIPTION
				"  "
			::= { hwInfoStoragePoolEntry 7 }

		
		hwInfoStoragePoolSubscribedCapacity OBJECT-TYPE
			SYNTAX Counter64
			MAX-ACCESS read-only
			STATUS current
			DESCRIPTION
				"  "
			::= { hwInfoStoragePoolEntry 8 }

		
		hwInfoStoragePoolFreeCapacity OBJECT-TYPE
			SYNTAX Counter64
			MAX-ACCESS read-only
			STATUS current
			DESCRIPTION
				"  "
			::= { hwInfoStoragePoolEntry 9 }

		
		hwInfoStoragePoolProtectionCapacity OBJECT-TYPE
			SYNTAX Counter64
			MAX-ACCESS read-only
			STATUS current
			DESCRIPTION
				"  "
			::= { hwInfoStoragePoolEntry 10 }

		
		hwInfoStoragePoolTier0Capacity OBJECT-TYPE
			SYNTAX Counter64
			MAX-ACCESS read-only
			STATUS current
			DESCRIPTION
				"  "
			::= { hwInfoStoragePoolEntry 11 }

		
		hwInfoStoragePoolTier1Capacity OBJECT-TYPE
			SYNTAX Counter64
			MAX-ACCESS read-only
			STATUS current
			DESCRIPTION
				"  "
			::= { hwInfoStoragePoolEntry 12 }

		
		hwInfoStoragePoolTier2Capacity OBJECT-TYPE
			SYNTAX Counter64
			MAX-ACCESS read-only
			STATUS current
			DESCRIPTION
				"  "
			::= { hwInfoStoragePoolEntry 13 }

		
		hwInfoStoragePoolFullThreshold OBJECT-TYPE
			SYNTAX Unsigned32
			MAX-ACCESS read-only
			STATUS current
			DESCRIPTION
				"  "
			::= { hwInfoStoragePoolEntry 14 }

		
		hwInfoStoragePoolExtentSize OBJECT-TYPE
			SYNTAX Unsigned32
			MAX-ACCESS read-only
			STATUS current
			DESCRIPTION
				"  "
			::= { hwInfoStoragePoolEntry 15 }

		
		hwInfoStoragePoolSmartTierFeatureStatus OBJECT-TYPE
			SYNTAX Unsigned32
			MAX-ACCESS read-only
			STATUS current
			DESCRIPTION
				"  "
			::= { hwInfoStoragePoolEntry 16 }

		
		hwInfoStoragePoolRelocationStatus OBJECT-TYPE
			SYNTAX Unsigned32
			MAX-ACCESS read-only
			STATUS current
			DESCRIPTION
				"  "
			::= { hwInfoStoragePoolEntry 17 }

		
		hwInfoStoragePoolRelocationTriggerMode OBJECT-TYPE
			SYNTAX Unsigned32
			MAX-ACCESS read-only
			STATUS current
			DESCRIPTION
				"  "
			::= { hwInfoStoragePoolEntry 18 }

		
		hwInfoStoragePoolRelocationPaused OBJECT-TYPE
			SYNTAX Unsigned32
			MAX-ACCESS read-only
			STATUS current
			DESCRIPTION
				"  "
			::= { hwInfoStoragePoolEntry 19 }

		
		hwInfoStoragePoolEstimatedMoveUpData OBJECT-TYPE
			SYNTAX Counter64
			MAX-ACCESS read-only
			STATUS current
			DESCRIPTION
				"  "
			::= { hwInfoStoragePoolEntry 20 }

		
		hwInfoStoragePoolEstimatedMoveDownData OBJECT-TYPE
			SYNTAX Counter64
			MAX-ACCESS read-only
			STATUS current
			DESCRIPTION
				"  "
			::= { hwInfoStoragePoolEntry 21 }

		
		hwInfoStoragePoolEstimatedDataRelocationDuration OBJECT-TYPE
			SYNTAX Counter64
			MAX-ACCESS read-only
			STATUS current
			DESCRIPTION
				"  "
			::= { hwInfoStoragePoolEntry 22 }

		
		hwInfoStorageTierTable OBJECT-TYPE
			SYNTAX SEQUENCE OF HwInfoStorageTierEntry
			MAX-ACCESS not-accessible
			STATUS current
			DESCRIPTION
				"  "
			::= { hwSpaceInfo 3 }

		
		hwInfoStorageTierEntry OBJECT-TYPE
			SYNTAX HwInfoStorageTierEntry
			MAX-ACCESS not-accessible
			STATUS current
			DESCRIPTION
				"  "
			INDEX { hwInfoStorageTierID }
			::= { hwInfoStorageTierTable 1 }

		
		HwInfoStorageTierEntry ::=
			SEQUENCE { 
				hwInfoStorageTierID
					OCTET STRING,
				hwInfoStorageTierName
					OCTET STRING,
				hwInfoStorageTierPoolID
					OCTET STRING,
				hwInfoStorageTierHealthStatus
					Unsigned32,
				hwInfoStorageTierRunningStatus
					Unsigned32,
				hwInfoStorageTierCapacity
					Counter64,
				hwInfoStorageTierAllocatedCapacity
					Counter64,
				hwInfoStorageTierFreeCapacity
					Counter64,
				hwInfoStorageTierRAIDLevel
					Unsigned32,
				hwInfoStorageTierRAIDDiskNumber
					Unsigned32,
				hwInfoStorageTierEstimatedMoveUpData
					Counter64,
				hwInfoStorageTierEstimatedMoveDownData
					Counter64
			 }

		hwInfoStorageTierID OBJECT-TYPE
			SYNTAX OCTET STRING
			MAX-ACCESS read-only
			STATUS current
			DESCRIPTION
				"  "
			::= { hwInfoStorageTierEntry 1 }

		
		hwInfoStorageTierName OBJECT-TYPE
			SYNTAX OCTET STRING
			MAX-ACCESS read-only
			STATUS current
			DESCRIPTION
				"  "
			::= { hwInfoStorageTierEntry 2 }

		
		hwInfoStorageTierPoolID OBJECT-TYPE
			SYNTAX OCTET STRING
			MAX-ACCESS read-only
			STATUS current
			DESCRIPTION
				"  "
			::= { hwInfoStorageTierEntry 3 }

		
		hwInfoStorageTierHealthStatus OBJECT-TYPE
			SYNTAX Unsigned32
			MAX-ACCESS read-only
			STATUS current
			DESCRIPTION
				"  "
			::= { hwInfoStorageTierEntry 4 }

		
		hwInfoStorageTierRunningStatus OBJECT-TYPE
			SYNTAX Unsigned32
			MAX-ACCESS read-only
			STATUS current
			DESCRIPTION
				"  "
			::= { hwInfoStorageTierEntry 5 }

		
		hwInfoStorageTierCapacity OBJECT-TYPE
			SYNTAX Counter64
			MAX-ACCESS read-only
			STATUS current
			DESCRIPTION
				"  "
			::= { hwInfoStorageTierEntry 6 }

		
		hwInfoStorageTierAllocatedCapacity OBJECT-TYPE
			SYNTAX Counter64
			MAX-ACCESS read-only
			STATUS current
			DESCRIPTION
				"  "
			::= { hwInfoStorageTierEntry 7 }

		
		hwInfoStorageTierFreeCapacity OBJECT-TYPE
			SYNTAX Counter64
			MAX-ACCESS read-only
			STATUS current
			DESCRIPTION
				"  "
			::= { hwInfoStorageTierEntry 8 }

		
		hwInfoStorageTierRAIDLevel OBJECT-TYPE
			SYNTAX Unsigned32
			MAX-ACCESS read-only
			STATUS current
			DESCRIPTION
				"  "
			::= { hwInfoStorageTierEntry 9 }

		
		hwInfoStorageTierRAIDDiskNumber OBJECT-TYPE
			SYNTAX Unsigned32
			MAX-ACCESS read-only
			STATUS current
			DESCRIPTION
				"  "
			::= { hwInfoStorageTierEntry 10 }

		
		hwInfoStorageTierEstimatedMoveUpData OBJECT-TYPE
			SYNTAX Counter64
			MAX-ACCESS read-only
			STATUS current
			DESCRIPTION
				"  "
			::= { hwInfoStorageTierEntry 11 }

		
		hwInfoStorageTierEstimatedMoveDownData OBJECT-TYPE
			SYNTAX Counter64
			MAX-ACCESS read-only
			STATUS current
			DESCRIPTION
				"  "
			::= { hwInfoStorageTierEntry 12 }

		
		hwInfoPortGroupTable OBJECT-TYPE
			SYNTAX SEQUENCE OF HwInfoPortGroupEntry
			MAX-ACCESS not-accessible
			STATUS current
			DESCRIPTION
				"  "
			::= { hwSpaceInfo 4 }

		
		hwInfoPortGroupEntry OBJECT-TYPE
			SYNTAX HwInfoPortGroupEntry
			MAX-ACCESS not-accessible
			STATUS current
			DESCRIPTION
				"  "
			INDEX { hwInfoPortGroupID }
			::= { hwInfoPortGroupTable 1 }

		
		HwInfoPortGroupEntry ::=
			SEQUENCE { 
				hwInfoPortGroupID
					OCTET STRING,
				hwInfoPortGroupName
					OCTET STRING,
				hwInfoPortGroupPortList
					OCTET STRING
			 }

		hwInfoPortGroupID OBJECT-TYPE
			SYNTAX OCTET STRING
			MAX-ACCESS read-only
			STATUS current
			DESCRIPTION
				"  "
			::= { hwInfoPortGroupEntry 1 }

		
		hwInfoPortGroupName OBJECT-TYPE
			SYNTAX OCTET STRING
			MAX-ACCESS read-only
			STATUS current
			DESCRIPTION
				"  "
			::= { hwInfoPortGroupEntry 2 }

		
		hwInfoPortGroupPortList OBJECT-TYPE
			SYNTAX OCTET STRING
			MAX-ACCESS read-only
			STATUS current
			DESCRIPTION
				"  "
			::= { hwInfoPortGroupEntry 3 }

		
		hwInfoHostTable OBJECT-TYPE
			SYNTAX SEQUENCE OF HwInfoHostEntry
			MAX-ACCESS not-accessible
			STATUS current
			DESCRIPTION
				"  "
			::= { hwSpaceInfo 5 }

		
		hwInfoHostEntry OBJECT-TYPE
			SYNTAX HwInfoHostEntry
			MAX-ACCESS not-accessible
			STATUS current
			DESCRIPTION
				"  "
			INDEX { hwInfoHostID }
			::= { hwInfoHostTable 1 }

		
		HwInfoHostEntry ::=
			SEQUENCE { 
				hwInfoHostID
					OCTET STRING,
				hwInfoHostName
					OCTET STRING,
				hwInfoHostLocation
					OCTET STRING,
				hwInfoHostHealthStatus
					Unsigned32,
				hwInfoHostRunningStatus
					Unsigned32,
				hwInfoHostOperatingSystem
					Unsigned32,
				hwInfoHostIPAddress
					OCTET STRING,
				hwInfoHostNetworkName
					OCTET STRING,
				hwInfoHostModel
					OCTET STRING
			 }

		hwInfoHostID OBJECT-TYPE
			SYNTAX OCTET STRING
			MAX-ACCESS read-only
			STATUS current
			DESCRIPTION
				"  "
			::= { hwInfoHostEntry 1 }

		
		hwInfoHostName OBJECT-TYPE
			SYNTAX OCTET STRING
			MAX-ACCESS read-only
			STATUS current
			DESCRIPTION
				"  "
			::= { hwInfoHostEntry 2 }

		
		hwInfoHostLocation OBJECT-TYPE
			SYNTAX OCTET STRING
			MAX-ACCESS read-only
			STATUS current
			DESCRIPTION
				"  "
			::= { hwInfoHostEntry 3 }

		
		hwInfoHostHealthStatus OBJECT-TYPE
			SYNTAX Unsigned32
			MAX-ACCESS read-only
			STATUS current
			DESCRIPTION
				"  "
			::= { hwInfoHostEntry 4 }

		
		hwInfoHostRunningStatus OBJECT-TYPE
			SYNTAX Unsigned32
			MAX-ACCESS read-only
			STATUS current
			DESCRIPTION
				"  "
			::= { hwInfoHostEntry 5 }

		
		hwInfoHostOperatingSystem OBJECT-TYPE
			SYNTAX Unsigned32
			MAX-ACCESS read-only
			STATUS current
			DESCRIPTION
				"  "
			::= { hwInfoHostEntry 6 }

		
		hwInfoHostIPAddress OBJECT-TYPE
			SYNTAX OCTET STRING
			MAX-ACCESS read-only
			STATUS current
			DESCRIPTION
				"  "
			::= { hwInfoHostEntry 7 }

		
		hwInfoHostNetworkName OBJECT-TYPE
			SYNTAX OCTET STRING
			MAX-ACCESS read-only
			STATUS current
			DESCRIPTION
				"  "
			::= { hwInfoHostEntry 8 }

		
		hwInfoHostModel OBJECT-TYPE
			SYNTAX OCTET STRING
			MAX-ACCESS read-only
			STATUS current
			DESCRIPTION
				"  "
			::= { hwInfoHostEntry 9 }

		
		hwInfoHostGroupTable OBJECT-TYPE
			SYNTAX SEQUENCE OF HwInfoHostGroupEntry
			MAX-ACCESS not-accessible
			STATUS current
			DESCRIPTION
				"  "
			::= { hwSpaceInfo 6 }

		
		hwInfoHostGroupEntry OBJECT-TYPE
			SYNTAX HwInfoHostGroupEntry
			MAX-ACCESS not-accessible
			STATUS current
			DESCRIPTION
				"  "
			INDEX { hwInfoHostGroupID }
			::= { hwInfoHostGroupTable 1 }

		
		HwInfoHostGroupEntry ::=
			SEQUENCE { 
				hwInfoHostGroupID
					OCTET STRING,
				hwInfoHostGroupName
					OCTET STRING,
				hwInfoHostGroupHostList
					OCTET STRING
			 }

		hwInfoHostGroupID OBJECT-TYPE
			SYNTAX OCTET STRING
			MAX-ACCESS read-only
			STATUS current
			DESCRIPTION
				"  "
			::= { hwInfoHostGroupEntry 1 }

		
		hwInfoHostGroupName OBJECT-TYPE
			SYNTAX OCTET STRING
			MAX-ACCESS read-only
			STATUS current
			DESCRIPTION
				"  "
			::= { hwInfoHostGroupEntry 2 }

		
		hwInfoHostGroupHostList OBJECT-TYPE
			SYNTAX OCTET STRING
			MAX-ACCESS read-only
			STATUS current
			DESCRIPTION
				"  "
			::= { hwInfoHostGroupEntry 3 }

		
		hwInfoLunGroupTable OBJECT-TYPE
			SYNTAX SEQUENCE OF HwInfoLunGroupEntry
			MAX-ACCESS not-accessible
			STATUS current
			DESCRIPTION
				"  "
			::= { hwSpaceInfo 7 }

		
		hwInfoLunGroupEntry OBJECT-TYPE
			SYNTAX HwInfoLunGroupEntry
			MAX-ACCESS not-accessible
			STATUS current
			DESCRIPTION
				"  "
			INDEX { hwInfoLunGroupID }
			::= { hwInfoLunGroupTable 1 }

		
		HwInfoLunGroupEntry ::=
			SEQUENCE { 
				hwInfoLunGroupID
					OCTET STRING,
				hwInfoLunGroupName
					OCTET STRING,
				hwInfoLunGroupLunList
					OCTET STRING
			 }

		hwInfoLunGroupID OBJECT-TYPE
			SYNTAX OCTET STRING
			MAX-ACCESS read-only
			STATUS current
			DESCRIPTION
				"  "
			::= { hwInfoLunGroupEntry 1 }

		
		hwInfoLunGroupName OBJECT-TYPE
			SYNTAX OCTET STRING
			MAX-ACCESS read-only
			STATUS current
			DESCRIPTION
				"  "
			::= { hwInfoLunGroupEntry 2 }

		
		hwInfoLunGroupLunList OBJECT-TYPE
			SYNTAX OCTET STRING
			MAX-ACCESS read-only
			STATUS current
			DESCRIPTION
				"  "
			::= { hwInfoLunGroupEntry 3 }

		
		hwInfoLunTable OBJECT-TYPE
			SYNTAX SEQUENCE OF HwInfoLunEntry
			MAX-ACCESS not-accessible
			STATUS current
			DESCRIPTION
				" "
			::= { hwSpaceInfo 8 }

		
		hwInfoLunEntry OBJECT-TYPE
			SYNTAX HwInfoLunEntry
			MAX-ACCESS not-accessible
			STATUS current
			DESCRIPTION
				"  "
			INDEX { hwInfoLunID }
			::= { hwInfoLunTable 1 }

		
		HwInfoLunEntry ::=
			SEQUENCE { 
				hwInfoLunID
					OCTET STRING,
				hwInfoLunName
					OCTET STRING,
				hwInfoLunPoolID
					OCTET STRING,
				hwInfoLunPoolName
					OCTET STRING,
				hwInfoLunCapacity
					Counter64,
				hwInfoLunSubscribedCapacity
					Counter64,
				hwInfoLunProtectionCapacity
					Counter64,
				hwInfoLunSectorSize
					Unsigned32,
				hwInfoLunHealthStatus
					Unsigned32,
				hwInfoLunRunningStatus
					Unsigned32,
				hwInfoLunType
					Unsigned32,
				hwInfoLunIOPriority
					Unsigned32,
				hwInfoLunWWN
					OCTET STRING,
				hwInfoLunExposedToInitiator
					Unsigned32,
				hwInfoLunWritePolicy
					Unsigned32,
				hwInfoLunRunningWritePolicy
					Unsigned32,
				hwInfoLunPrefetchPolicy
					Unsigned32,
				hwInfoLunReadCachePolicy
					Unsigned32,
				hwInfoLunWriteCachePolicy
					Unsigned32,
				hwInfoLunPrefetchValue
					Unsigned32,
				hwInfoLunOwnerController
					OCTET STRING,
				hwInfoLunWorkController
					OCTET STRING,
				hwInfoLunRelocationPolicy
					Unsigned32,
				hwInfoLunIniDistributePolicy
					Unsigned32,
				hwInfoLunIsAddToLunGroup
					Unsigned32,
				hwInfoLunDIFSwitch
					Unsigned32,
				hwInfoLunRemoteLUNWWN
					OCTET STRING,
				hwInfoLunUsageType
					Unsigned32,
				hwInfoLunSmartCacheHitRage
					Unsigned32
			 }

		hwInfoLunID OBJECT-TYPE
			SYNTAX OCTET STRING
			MAX-ACCESS read-only
			STATUS current
			DESCRIPTION
				"  "
			::= { hwInfoLunEntry 1 }

		
		hwInfoLunName OBJECT-TYPE
			SYNTAX OCTET STRING
			MAX-ACCESS read-only
			STATUS current
			DESCRIPTION
				"  "
			::= { hwInfoLunEntry 2 }

		
		hwInfoLunPoolID OBJECT-TYPE
			SYNTAX OCTET STRING
			MAX-ACCESS read-only
			STATUS current
			DESCRIPTION
				"  "
			::= { hwInfoLunEntry 3 }

		
		hwInfoLunPoolName OBJECT-TYPE
			SYNTAX OCTET STRING
			MAX-ACCESS read-only
			STATUS current
			DESCRIPTION
				"  "
			::= { hwInfoLunEntry 4 }

		
		hwInfoLunCapacity OBJECT-TYPE
			SYNTAX Counter64
			MAX-ACCESS read-only
			STATUS current
			DESCRIPTION
				"  "
			::= { hwInfoLunEntry 5 }

		
		hwInfoLunSubscribedCapacity OBJECT-TYPE
			SYNTAX Counter64
			MAX-ACCESS read-only
			STATUS current
			DESCRIPTION
				"  "
			::= { hwInfoLunEntry 6 }

		
		hwInfoLunProtectionCapacity OBJECT-TYPE
			SYNTAX Counter64
			MAX-ACCESS read-only
			STATUS current
			DESCRIPTION
				"  "
			::= { hwInfoLunEntry 7 }

		
		hwInfoLunSectorSize OBJECT-TYPE
			SYNTAX Unsigned32
			MAX-ACCESS read-only
			STATUS current
			DESCRIPTION
				"  "
			::= { hwInfoLunEntry 8 }

		
		hwInfoLunHealthStatus OBJECT-TYPE
			SYNTAX Unsigned32
			MAX-ACCESS read-only
			STATUS current
			DESCRIPTION
				"  "
			::= { hwInfoLunEntry 9 }

		
		hwInfoLunRunningStatus OBJECT-TYPE
			SYNTAX Unsigned32
			MAX-ACCESS read-only
			STATUS current
			DESCRIPTION
				"  "
			::= { hwInfoLunEntry 10 }

		
		hwInfoLunType OBJECT-TYPE
			SYNTAX Unsigned32
			MAX-ACCESS read-only
			STATUS current
			DESCRIPTION
				"  "
			::= { hwInfoLunEntry 11 }

		
		hwInfoLunIOPriority OBJECT-TYPE
			SYNTAX Unsigned32
			MAX-ACCESS read-only
			STATUS current
			DESCRIPTION
				"  "
			::= { hwInfoLunEntry 12 }

		
		hwInfoLunWWN OBJECT-TYPE
			SYNTAX OCTET STRING
			MAX-ACCESS read-only
			STATUS current
			DESCRIPTION
				"  "
			::= { hwInfoLunEntry 13 }

		
		hwInfoLunExposedToInitiator OBJECT-TYPE
			SYNTAX Unsigned32
			MAX-ACCESS read-only
			STATUS current
			DESCRIPTION
				"  "
			::= { hwInfoLunEntry 14 }

		
		hwInfoLunWritePolicy OBJECT-TYPE
			SYNTAX Unsigned32
			MAX-ACCESS read-only
			STATUS current
			DESCRIPTION
				"  "
			::= { hwInfoLunEntry 15 }

		
		hwInfoLunRunningWritePolicy OBJECT-TYPE
			SYNTAX Unsigned32
			MAX-ACCESS read-only
			STATUS current
			DESCRIPTION
				"  "
			::= { hwInfoLunEntry 16 }

		
		hwInfoLunPrefetchPolicy OBJECT-TYPE
			SYNTAX Unsigned32
			MAX-ACCESS read-only
			STATUS current
			DESCRIPTION
				"  "
			::= { hwInfoLunEntry 17 }

		
		hwInfoLunReadCachePolicy OBJECT-TYPE
			SYNTAX Unsigned32
			MAX-ACCESS read-only
			STATUS current
			DESCRIPTION
				"  "
			::= { hwInfoLunEntry 18 }

		
		hwInfoLunWriteCachePolicy OBJECT-TYPE
			SYNTAX Unsigned32
			MAX-ACCESS read-only
			STATUS current
			DESCRIPTION
				"  "
			::= { hwInfoLunEntry 19 }

		
		hwInfoLunPrefetchValue OBJECT-TYPE
			SYNTAX Unsigned32
			MAX-ACCESS read-only
			STATUS current
			DESCRIPTION
				"  "
			::= { hwInfoLunEntry 20 }

		
		hwInfoLunOwnerController OBJECT-TYPE
			SYNTAX OCTET STRING
			MAX-ACCESS read-only
			STATUS current
			DESCRIPTION
				"  "
			::= { hwInfoLunEntry 21 }

		
		hwInfoLunWorkController OBJECT-TYPE
			SYNTAX OCTET STRING
			MAX-ACCESS read-only
			STATUS current
			DESCRIPTION
				"  "
			::= { hwInfoLunEntry 22 }

		
		hwInfoLunRelocationPolicy OBJECT-TYPE
			SYNTAX Unsigned32
			MAX-ACCESS read-only
			STATUS current
			DESCRIPTION
				"  "
			::= { hwInfoLunEntry 23 }

		
		hwInfoLunIniDistributePolicy OBJECT-TYPE
			SYNTAX Unsigned32
			MAX-ACCESS read-only
			STATUS current
			DESCRIPTION
				"  "
			::= { hwInfoLunEntry 24 }

		
		hwInfoLunIsAddToLunGroup OBJECT-TYPE
			SYNTAX Unsigned32
			MAX-ACCESS read-only
			STATUS current
			DESCRIPTION
				"  "
			::= { hwInfoLunEntry 25 }

		
		hwInfoLunDIFSwitch OBJECT-TYPE
			SYNTAX Unsigned32
			MAX-ACCESS read-only
			STATUS current
			DESCRIPTION
				"  "
			::= { hwInfoLunEntry 26 }

		
		hwInfoLunRemoteLUNWWN OBJECT-TYPE
			SYNTAX OCTET STRING
			MAX-ACCESS read-only
			STATUS current
			DESCRIPTION
				"  "
			::= { hwInfoLunEntry 27 }

		
		hwInfoLunUsageType OBJECT-TYPE
			SYNTAX Unsigned32
			MAX-ACCESS read-only
			STATUS current
			DESCRIPTION
				"  "
			::= { hwInfoLunEntry 28 }

		
		hwInfoLunSmartCacheHitRage OBJECT-TYPE
			SYNTAX Unsigned32
			MAX-ACCESS read-only
			STATUS current
			DESCRIPTION
				"  "
			::= { hwInfoLunEntry 29 }

		
		isoConformance OBJECT IDENTIFIER ::= { iso 6 }

		
		isoGroups OBJECT IDENTIFIER ::= { isoConformance 1 }

		
		currentObjectGroup OBJECT-GROUP
			OBJECTS { hwInfoDiskDomainID, hwInfoDiskDomainName, hwInfoDiskDomainHealthStatus, hwInfoDiskDomainRunningStatus, hwInfoDiskDomainTotalCapacity, 
				hwInfoDiskDomainFreeCapacity, hwInfoDiskDomainHotSpareCapacity, hwInfoDiskDomainUsedHotSpareCapacity, hwInfoDiskDomainTier0DiskNumber, hwInfoDiskDomainTier0TotalCapacity, 
				hwInfoDiskDomainTier0FreeCapacity, hwInfoDiskDomainTier0HotSpareCapacity, hwInfoDiskDomainTier0UsedHotSpareCapacity, hwInfoDiskDomainTier0HotSpareStrategy, hwInfoDiskDomainTier1DiskNumber, 
				hwInfoDiskDomainTier1TotalCapacity, hwInfoDiskDomainTier1FreeCapacity, hwInfoDiskDomainTier1HotSpareCapacity, hwInfoDiskDomainTier1UsedHotSpareCapacity, hwInfoDiskDomainTier1HotSpareStrategy, 
				hwInfoDiskDomainTier2DiskNumber, hwInfoDiskDomainTier2TotalCapacity, hwInfoDiskDomainTier2FreeCapacity, hwInfoDiskDomainTier2HotSpareCapacity, hwInfoDiskDomainTier2UsedHotSpareCapacity, 
				hwInfoDiskDomainTier2HotSpareStrategy, hwInfoStoragePoolID, hwInfoStoragePoolName, hwInfoStoragePoolDiskDomainID, hwInfoStoragePoolHealthStatus, 
				hwInfoStoragePoolRunningStatus, hwInfoStoragePoolTotalCapacity, hwInfoStoragePoolSubscribedCapacity, hwInfoStoragePoolFreeCapacity, hwInfoStoragePoolProtectionCapacity, 
				hwInfoStoragePoolTier0Capacity, hwInfoStoragePoolTier1Capacity, hwInfoStoragePoolTier2Capacity, hwInfoStoragePoolFullThreshold, hwInfoStoragePoolExtentSize, 
				hwInfoStoragePoolSmartTierFeatureStatus, hwInfoStoragePoolRelocationStatus, hwInfoStoragePoolRelocationTriggerMode, hwInfoStoragePoolRelocationPaused, hwInfoStoragePoolEstimatedMoveUpData, 
				hwInfoStoragePoolEstimatedMoveDownData, hwInfoStoragePoolEstimatedDataRelocationDuration, hwInfoStorageTierID, hwInfoStorageTierName, hwInfoStorageTierPoolID, 
				hwInfoStorageTierHealthStatus, hwInfoStorageTierRunningStatus, hwInfoStorageTierCapacity, hwInfoStorageTierAllocatedCapacity, hwInfoStorageTierFreeCapacity, 
				hwInfoStorageTierRAIDLevel, hwInfoStorageTierRAIDDiskNumber, hwInfoStorageTierEstimatedMoveUpData, hwInfoHostID, hwInfoHostName, 
				hwInfoHostLocation, hwInfoHostHealthStatus, hwInfoHostRunningStatus, hwInfoHostOperatingSystem, hwInfoHostIPAddress, 
				hwInfoHostModel, hwInfoHostNetworkName, hwInfoHostGroupID, hwInfoHostGroupName, hwInfoLunGroupID, 
				hwInfoLunGroupName, hwInfoLunID, hwInfoLunName, hwInfoLunPoolID, hwInfoLunPoolName, 
				hwInfoLunCapacity, hwInfoLunSubscribedCapacity, hwInfoLunProtectionCapacity, hwInfoLunSectorSize, hwInfoLunHealthStatus, 
				hwInfoLunRunningStatus, hwInfoLunType, hwInfoLunIOPriority, hwInfoLunWWN, hwInfoLunExposedToInitiator, 
				hwInfoLunWritePolicy, hwInfoLunRunningWritePolicy, hwInfoLunPrefetchPolicy, hwInfoLunReadCachePolicy, hwInfoLunWriteCachePolicy, 
				hwInfoLunPrefetchValue, hwInfoLunOwnerController, hwInfoLunWorkController, hwInfoLunRelocationPolicy, hwInfoLunIniDistributePolicy, 
				hwInfoLunIsAddToLunGroup, hwInfoLunDIFSwitch, hwInfoLunRemoteLUNWWN, hwInfoLunSmartCacheHitRage, hwInfoStorageTierEstimatedMoveDownData, 
				hwInfoStoragePoolDiskDomainName, hwInfoPortGroupID, hwInfoPortGroupName, hwInfoPortGroupPortList, hwInfoHostGroupHostList, 
				hwInfoLunGroupLunList, hwInfoLunUsageType }
			STATUS current
			DESCRIPTION 
				"Enter the description of the created OBJECT-GROUP."
			::= { isoGroups 1 }

		
		isoCompliances OBJECT IDENTIFIER ::= { isoConformance 2 }

		
		basicCompliance MODULE-COMPLIANCE
			STATUS current
			DESCRIPTION 
				"Enter the description of the created MODULE-COMPLIANCE."
			MODULE -- this module
				MANDATORY-GROUPS { currentObjectGroup }
			::= { isoCompliances 1 }

		
	
	END

--
-- HUAWEI-STORAGE-SPACE-MIB.mib
--
