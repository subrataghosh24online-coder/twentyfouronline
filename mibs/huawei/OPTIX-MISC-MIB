-- OPTIX-MISC-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-MISC-MIB DEFINITIONS ::= BEGIN
    IMPORTS
        optixProvisionEqpt
            FROM OPTIX-OID-MIB
        OBJECT-GROUP,MODULE-COMPLIANCE
            FROM SNMPv2-CONF
        Unsigned32,OBJECT-TYPE,MODULE-IDENTITY
            FROM SNMPv2-SMI
        ;

    optixMisc MODULE-IDENTITY
        LAST-UPDATED "201204240000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the general configuration information of device"
        REVISION "201204240000Z"
        DESCRIPTION
            "The initial revision of this MIB module."
        REVISION "201204240000Z"
        DESCRIPTION
            "The initial revision of this MIB module."
        ::={ optixProvisionEqpt 39 }

    -- 1.3.6.1.4.1.2011.2.25.4.30.39.1
    optixMiscGroup OBJECT IDENTIFIER ::= { optixMisc 1 }

    -- 1.3.6.1.4.1.2011.2.25.4.30.39.1.1
    optixFanSpeed OBJECT-TYPE
        SYNTAX INTEGER
        {
            stop(4),
            low(1),
            mid(2),
            high(3),
            autolow(5),
            automid(6),
            autohigh(7),
            auto(9)
        }
        MAX-ACCESS read-write
        STATUS current
        DESCRIPTION
            "This object indicates the fan speed. 4: stop, 1: low, 2: mid, 3: high, 5: autolow, 6: automid, 7: autohigh, 9: auto"
        ::= { optixMiscGroup 1 }

    -- 1.3.6.1.4.1.2011.2.25.4.30.39.1.2
    optixFanMinDispersion OBJECT-TYPE
        SYNTAX Unsigned32
        MAX-ACCESS read-only
        STATUS current
        DESCRIPTION
            "This object indicates the minimum temperature difference allowed by the fan. 0: stop, 45: low, 58: mid, 65: high, 58: auto"
        ::= { optixMiscGroup 2 }

    -- 1.3.6.1.4.1.2011.2.25.4.30.39.1.3
    optixEnvironmentTable OBJECT-TYPE
        SYNTAX SEQUENCE OF OptixEnvironmentEntry
        MAX-ACCESS not-accessible
        STATUS current
        DESCRIPTION
            "This table describes the device environmentconfigurations."
        ::= { optixMiscGroup 3 }

    -- 1.3.6.1.4.1.2011.2.25.4.30.39.1.3.1
    optixEnvironmentEntry OBJECT-TYPE
        SYNTAX OptixEnvironmentEntry
        MAX-ACCESS not-accessible
        STATUS current
        DESCRIPTION
            "Thisentry describes the device environment configurations."
        INDEX{ optixEnvironmentBdId }
        ::= { optixEnvironmentTable 1 }

    OptixEnvironmentEntry ::=
        SEQUENCE {
            optixEnvironmentBdId
                Unsigned32,
            optixRelayControlMode
                INTEGER,
            optixRelayNormalAlmState
                INTEGER,
            optixRelaySeriousAlmState
                INTEGER
        }

    -- 1.3.6.1.4.1.2011.2.25.4.30.39.1.3.1.1
    optixEnvironmentBdId OBJECT-TYPE
        SYNTAX Unsigned32
        MAX-ACCESS not-accessible
        STATUS current
        DESCRIPTION
            "This object indicates theslot IDof the board that supports environment configurations."
        ::= { optixEnvironmentEntry 1 }

    -- 1.3.6.1.4.1.2011.2.25.4.30.39.1.3.1.2
    optixRelayControlMode OBJECT-TYPE
        SYNTAX INTEGER
        {
            pmuauto(0),
            pmumanual(1)
        }
        MAX-ACCESS read-write
        STATUS current
        DESCRIPTION
            "This object indicates the relay control mode. 0: pmuauto, 1: pmumanual"
        ::= { optixEnvironmentEntry 2 }

    -- 1.3.6.1.4.1.2011.2.25.4.30.39.1.3.1.3
    optixRelayNormalAlmState OBJECT-TYPE
        SYNTAX INTEGER
        {
            open(1),
            close(0)
        }
        MAX-ACCESS read-write
        STATUS current
        DESCRIPTION
            "This object indicates the general relay alarm status. 0: close, 1: open"
        ::= { optixEnvironmentEntry 3 }

    -- 1.3.6.1.4.1.2011.2.25.4.30.39.1.3.1.4
    optixRelaySeriousAlmState OBJECT-TYPE
        SYNTAX INTEGER
        {
            open(1),
            close(0)
        }
        MAX-ACCESS read-write
        STATUS current
        DESCRIPTION
            "This object indicates theserious relay alarm status. 0: close, 1: open"
        ::= { optixEnvironmentEntry 4 }

    -- 1.3.6.1.4.1.2011.2.25.4.30.39.1.4
    optixRelayTable OBJECT-TYPE
        SYNTAX SEQUENCE OF OptixRelayEntry
        MAX-ACCESS not-accessible
        STATUS current
        DESCRIPTION
            "This table indicates the relay configuration information."
        ::= { optixMiscGroup 4 }

    -- 1.3.6.1.4.1.2011.2.25.4.30.39.1.4.1
    optixRelayEntry OBJECT-TYPE
        SYNTAX OptixRelayEntry
        MAX-ACCESS not-accessible
        STATUS current
        DESCRIPTION
            "Thisentry indicates the relay configuration information."
        INDEX{ optixEnvironmentBdId,optixRelayId }
        ::= { optixRelayTable 1 }

    OptixRelayEntry ::=
        SEQUENCE {
            optixRelayId
                Unsigned32,
            optixRelayUseState
                INTEGER,
            optixRelayAlmSwitchState
                INTEGER,
            optixRelayAlmLevel
                INTEGER,
            optixRelayOutState
                INTEGER
        }

    -- 1.3.6.1.4.1.2011.2.25.4.30.39.1.4.1.1
    optixRelayId OBJECT-TYPE
        SYNTAX Unsigned32
        MAX-ACCESS not-accessible
        STATUS current
        DESCRIPTION
            "This object indicates the ID of the relay connected to each board."
        ::= { optixRelayEntry 1 }

    -- 1.3.6.1.4.1.2011.2.25.4.30.39.1.4.1.2
    optixRelayUseState OBJECT-TYPE
        SYNTAX INTEGER
        {
            enable(1),
            disable(0)
        }
        MAX-ACCESS read-write
        STATUS current
        DESCRIPTION
            "This object indicates the relayusage status. 0: disable, 1: enable"
        ::= { optixRelayEntry 2 }

    -- 1.3.6.1.4.1.2011.2.25.4.30.39.1.4.1.3
    optixRelayAlmSwitchState OBJECT-TYPE
        SYNTAX INTEGER
        {
            open(1),
            close(0)
        }
        MAX-ACCESS read-write
        STATUS current
        DESCRIPTION
            "This object indicates the switch status of relay alarms. 0: close, 1: open"
        ::= { optixRelayEntry 3 }

    -- 1.3.6.1.4.1.2011.2.25.4.30.39.1.4.1.4
    optixRelayAlmLevel OBJECT-TYPE
        SYNTAX INTEGER
        {
            critical(0),
            major(1),
            minor(2),
            ignore(3)
        }
        MAX-ACCESS read-write
        STATUS current
        DESCRIPTION
            "This object indicates the alarm level. 0: critical, 1: major, 2: minor, 3: ignore"
        ::= { optixRelayEntry 4 }

    -- 1.3.6.1.4.1.2011.2.25.4.30.39.1.4.1.5
    optixRelayOutState OBJECT-TYPE
        SYNTAX INTEGER
        {
            close(0),
            open(1)
        }
        MAX-ACCESS read-write
        STATUS current
        DESCRIPTION
            "This object indicates the out state. 0: close, 1: open"
        ::= { optixRelayEntry 5 }

    -- 1.3.6.1.4.1.2011.2.25.4.30.39.1.5
    optixAlmOutputTable OBJECT-TYPE
        SYNTAX SEQUENCE OF OptixAlmOutputEntry
        MAX-ACCESS not-accessible
        STATUS current
        DESCRIPTION
            "This table describes the alarm output information."
        ::= { optixMiscGroup 5 }

    -- 1.3.6.1.4.1.2011.2.25.4.30.39.1.5.1
    optixAlmOutputEntry OBJECT-TYPE
        SYNTAX OptixAlmOutputEntry
        MAX-ACCESS not-accessible
        STATUS current
        DESCRIPTION
            "Thisentry describes the alarm output information."
        INDEX{ optixEnvironmentBdId,optixAlmOutputLevel }
        ::= { optixAlmOutputTable 1 }

    OptixAlmOutputEntry ::=
        SEQUENCE {
            optixAlmOutputLevel
                INTEGER,
            optixAlmOutputNum
                Unsigned32
        }

    -- 1.3.6.1.4.1.2011.2.25.4.30.39.1.5.1.1
    optixAlmOutputLevel OBJECT-TYPE
        SYNTAX INTEGER
        {
            critical(1),
            major(2),
            minor(3),
            ignore(4)
        }
        MAX-ACCESS not-accessible
        STATUS current
        DESCRIPTION
            "This object indicates the alarm output level. 1: critical, 2: major, 3: minor, 4: ignore"
        ::= { optixAlmOutputEntry 1 }

    -- 1.3.6.1.4.1.2011.2.25.4.30.39.1.5.1.2
    optixAlmOutputNum OBJECT-TYPE
        SYNTAX Unsigned32
        MAX-ACCESS read-write
        STATUS current
        DESCRIPTION
            "This object indicates the alarm output channel ID. 1: the first output channel, 2: the second output channel, 3: the third output channel, 4: the forth output channel"
        ::= { optixAlmOutputEntry 2 }

    -- 1.3.6.1.4.1.2011.2.25.4.30.39.1.6
    optixRelayNameTable OBJECT-TYPE
        SYNTAX SEQUENCE OF OptixRelayNameEntry
        MAX-ACCESS not-accessible
        STATUS current
        DESCRIPTION
            "This table describes the relay name."
        ::= { optixMiscGroup 6 }

    -- 1.3.6.1.4.1.2011.2.25.4.30.39.1.6.1
    optixRelayNameEntry OBJECT-TYPE
        SYNTAX OptixRelayNameEntry
        MAX-ACCESS not-accessible
        STATUS current
        DESCRIPTION
            "Thisentry describes the relay name."
        INDEX{ optixEnvironmentBdId,optixRelayId,optixRelayType }
        ::= { optixRelayNameTable 1 }

    OptixRelayNameEntry ::=
        SEQUENCE {
            optixRelayType
                INTEGER,
            optixRelayName
                OCTET STRING
        }

    -- 1.3.6.1.4.1.2011.2.25.4.30.39.1.6.1.1
    optixRelayType OBJECT-TYPE
        SYNTAX INTEGER
        {
            all(0),
            input(1),
            ext(2)
        }
        MAX-ACCESS not-accessible
        STATUS current
        DESCRIPTION
            "This object indicates the relay type. 0: all, 1: input, 2: ext"
        ::= { optixRelayNameEntry 1 }

    -- 1.3.6.1.4.1.2011.2.25.4.30.39.1.6.1.2
    optixRelayName OBJECT-TYPE
        SYNTAX OCTET STRING (SIZE(0..21))
        MAX-ACCESS read-write
        STATUS current
        DESCRIPTION
            "This object indicates the relay name."
        ::= { optixRelayNameEntry 2 }

    -- 1.3.6.1.4.1.2011.2.25.4.30.39.1.7
    optixOamPortMngTable OBJECT-TYPE
        SYNTAX SEQUENCE OF OptixOamPortMngEntry
        MAX-ACCESS not-accessible
        STATUS current
        DESCRIPTION
            "This table describes the OAM port configurations on devices."
        ::= { optixMiscGroup 7 }

    -- 1.3.6.1.4.1.2011.2.25.4.30.39.1.7.1
    optixOamPortMngEntry OBJECT-TYPE
        SYNTAX OptixOamPortMngEntry
        MAX-ACCESS not-accessible
        STATUS current
        DESCRIPTION
            "This entry describes the OAM port configurations on devices."
        INDEX{ optixOamBdId,optixOamSubBdId,optixOamPortId }
        ::= { optixOamPortMngTable 1 }

    OptixOamPortMngEntry ::=
        SEQUENCE {
            optixOamBdId
                Unsigned32,
            optixOamSubBdId
                Unsigned32,
            optixOamPortId
                Unsigned32,
            optixOamPortType
                INTEGER,
            optixOamPortState
                INTEGER
        }

    -- 1.3.6.1.4.1.2011.2.25.4.30.39.1.7.1.1
    optixOamBdId OBJECT-TYPE
        SYNTAX Unsigned32
        MAX-ACCESS not-accessible
        STATUS current
        DESCRIPTION
            "This object indicates the slot ID of the communication board."
        ::= { optixOamPortMngEntry 1 }

    -- 1.3.6.1.4.1.2011.2.25.4.30.39.1.7.1.2
    optixOamSubBdId OBJECT-TYPE
        SYNTAX Unsigned32
        MAX-ACCESS not-accessible
        STATUS current
        DESCRIPTION
            "This object indicates the subboard ID of the communication board. This parameter takes a fixed value of 255."
        ::= { optixOamPortMngEntry 2 }

    -- 1.3.6.1.4.1.2011.2.25.4.30.39.1.7.1.3
    optixOamPortId OBJECT-TYPE
        SYNTAX Unsigned32
        MAX-ACCESS not-accessible
        STATUS current
        DESCRIPTION
            "This object indicates the port number of the communication board."
        ::= { optixOamPortMngEntry 3 }

    -- 1.3.6.1.4.1.2011.2.25.4.30.39.1.7.1.4
    optixOamPortType OBJECT-TYPE
        SYNTAX INTEGER
        {
            all(0),
            com(1),
            eth(2),
            oam(3),
            fF(4),
            ext(5),
            usb(6)
        }
        MAX-ACCESS read-only
        STATUS current
        DESCRIPTION
            "This object indicates the OAM port type. 0: all, 1: com, 2: eth, 3: oam, 4: fF, 5: ext, 6: usb"
        ::= { optixOamPortMngEntry 4 }

    -- 1.3.6.1.4.1.2011.2.25.4.30.39.1.7.1.5
    optixOamPortState OBJECT-TYPE
        SYNTAX INTEGER
        {
            open(1),
            close(0)
        }
        MAX-ACCESS read-write
        STATUS current
        DESCRIPTION
            "This object indicates the OAM port status. 0: close, 1: open"
        ::= { optixOamPortMngEntry 5 }

    -- 1.3.6.1.4.1.2011.2.25.4.30.39.1.8
    optixCommuMngTable OBJECT-TYPE
        SYNTAX SEQUENCE OF OptixCommuMngEntry
        MAX-ACCESS not-accessible
        STATUS current
        DESCRIPTION
            "This table describes the configurations of communication boards on devices."
        ::= { optixMiscGroup 8 }

    -- 1.3.6.1.4.1.2011.2.25.4.30.39.1.8.1
    optixCommuMngEntry OBJECT-TYPE
        SYNTAX OptixCommuMngEntry
        MAX-ACCESS not-accessible
        STATUS current
        DESCRIPTION
            "Thisentry describes the configurations of communication boards on devices."
        INDEX{ optixCommuBdId,optixCommuSubBdId,optixCommuPortId }
        ::= { optixCommuMngTable 1 }

    OptixCommuMngEntry ::=
        SEQUENCE {
            optixCommuBdId
                Unsigned32,
            optixCommuSubBdId
                Unsigned32,
            optixCommuPortId
                Unsigned32,
            optixEthPortAdaptMode
                INTEGER,
            optixEthPortAdaptSpeed
                INTEGER,
            optixEthPortAdaptDuplex
                INTEGER,
            optixCommuRealMode
                INTEGER,
            optixCommuRealSpeed
                INTEGER,
            optixCommuRealDuplex
                INTEGER
        }

    -- 1.3.6.1.4.1.2011.2.25.4.30.39.1.8.1.1
    optixCommuBdId OBJECT-TYPE
        SYNTAX Unsigned32
        MAX-ACCESS not-accessible
        STATUS current
        DESCRIPTION
            "This object indicates the slot ID of the communication board."
        ::= { optixCommuMngEntry 1 }

    -- 1.3.6.1.4.1.2011.2.25.4.30.39.1.8.1.2
    optixCommuSubBdId OBJECT-TYPE
        SYNTAX Unsigned32
        MAX-ACCESS not-accessible
        STATUS current
        DESCRIPTION
            "This object indicates the subboard ID of the communication board. This parameter takes a fixed value of 255."
        ::= { optixCommuMngEntry 2 }

    -- 1.3.6.1.4.1.2011.2.25.4.30.39.1.8.1.3
    optixCommuPortId OBJECT-TYPE
        SYNTAX Unsigned32
        MAX-ACCESS not-accessible
        STATUS current
        DESCRIPTION
            "This object indicates the port number of the communication board."
        ::= { optixCommuMngEntry 3 }

    -- 1.3.6.1.4.1.2011.2.25.4.30.39.1.8.1.4
    optixEthPortAdaptMode OBJECT-TYPE
        SYNTAX INTEGER
        {
            adapt(1),
            fixed(0)
        }
        MAX-ACCESS read-write
        STATUS current
        DESCRIPTION
            "This object indicates the adaptation mode of the ETH port. 0: fixed, 1: adapt"
        ::= { optixCommuMngEntry 4 }

    -- 1.3.6.1.4.1.2011.2.25.4.30.39.1.8.1.5
    optixEthPortAdaptSpeed OBJECT-TYPE
        SYNTAX INTEGER
        {
            snmp100m(1),
            snmp10m(0),
            commufail(254),
            inautonego(255)
        }
        MAX-ACCESS read-write
        STATUS current
        DESCRIPTION
            "This object indicates the speed mode of the ETH port. 1: snmp100m, 0: snmp10m, 254: commufail, 255: inautonego"
        ::= { optixCommuMngEntry 5 }

    -- 1.3.6.1.4.1.2011.2.25.4.30.39.1.8.1.6
    optixEthPortAdaptDuplex OBJECT-TYPE
        SYNTAX INTEGER
        {
            full(1),
            half(0),
            commufail(254),
            inautonego(255)
        }
        MAX-ACCESS read-write
        STATUS current
        DESCRIPTION
            "This object indicates the transmission modeof the ETH port. 1: full, 0: half, 254: commufail, 255: inautonego"
        ::= { optixCommuMngEntry 6 }

    -- 1.3.6.1.4.1.2011.2.25.4.30.39.1.8.1.7
    optixCommuRealMode OBJECT-TYPE
        SYNTAX INTEGER
        {
            fixed(0),
            adapt(1)
        }
        MAX-ACCESS read-only
        STATUS current
        DESCRIPTION
            "This object indicates the real working mode of the ETH port. 0: fixed, 1: adapt"
        ::= { optixCommuMngEntry 7 }

    -- 1.3.6.1.4.1.2011.2.25.4.30.39.1.8.1.8
    optixCommuRealSpeed OBJECT-TYPE
        SYNTAX INTEGER
        {
            snmp10m(0),
            snmp100m(1),
            commufail(254),
            inautonego(255)
        }
        MAX-ACCESS read-only
        STATUS current
        DESCRIPTION
            "This object indicates the real speed mode of the ETH port. 1: snmp100m, 0: snmp10m, 254: commufail, 255: inautonego"
        ::= { optixCommuMngEntry 8 }

    -- 1.3.6.1.4.1.2011.2.25.4.30.39.1.8.1.9
    optixCommuRealDuplex OBJECT-TYPE
        SYNTAX INTEGER
        {
            half(0),
            full(1),
            commufail(254),
            inautonego(255)
        }
        MAX-ACCESS read-only
        STATUS current
        DESCRIPTION
            "This object indicates the real transmission modeof the ETH port. 1: full, 0: half, 254: commufail, 255: inautonego"
        ::= { optixCommuMngEntry 9 }

    -- 1.3.6.1.4.1.2011.2.25.4.30.39.1.9
    optixPowerMonstateTable OBJECT-TYPE
        SYNTAX SEQUENCE OF OptixPowerMonstateEntry
        MAX-ACCESS not-accessible
        STATUS current
        DESCRIPTION
            "This table describes the power input monitoring enable status of the power board."
        ::= { optixMiscGroup 9 }

    -- 1.3.6.1.4.1.2011.2.25.4.30.39.1.9.1
    optixPowerMonstateEntry OBJECT-TYPE
        SYNTAX OptixPowerMonstateEntry
        MAX-ACCESS not-accessible
        STATUS current
        DESCRIPTION
            "This entry describes the power input monitoring enable status of the power board."
        INDEX{ optixPowerMonstateSlotId,optixPowerMonstatePort }
        ::= { optixPowerMonstateTable 1 }

    OptixPowerMonstateEntry ::=
        SEQUENCE {
            optixPowerMonstateSlotId
                Unsigned32,
            optixPowerMonstatePort
                Unsigned32,
            optixPowerMonstateState
                INTEGER
        }

    -- 1.3.6.1.4.1.2011.2.25.4.30.39.1.9.1.1
    optixPowerMonstateSlotId OBJECT-TYPE
        SYNTAX Unsigned32 (0..65536)
        MAX-ACCESS not-accessible
        STATUS current
        DESCRIPTION
            "This parameter indicates the slot ID of the power board."
        ::= { optixPowerMonstateEntry 1 }

    -- 1.3.6.1.4.1.2011.2.25.4.30.39.1.9.1.2
    optixPowerMonstatePort OBJECT-TYPE
        SYNTAX Unsigned32 (1..2)
        MAX-ACCESS not-accessible
        STATUS current
        DESCRIPTION
            "This parameter indicates the power interface. Value range:
1: First power input
2: Second power input"
        ::= { optixPowerMonstateEntry 2 }

    -- 1.3.6.1.4.1.2011.2.25.4.30.39.1.9.1.3
    optixPowerMonstateState OBJECT-TYPE
        SYNTAX INTEGER
        {
            enable(1),
            disable(0)
        }
        MAX-ACCESS read-write
        STATUS current
        DESCRIPTION
            "This parameter indicates the enable status of power input monitoring."
        ::= { optixPowerMonstateEntry 3 }

    -- 1.3.6.1.4.1.2011.2.25.4.30.39.2
    optixMiscextGroup OBJECT IDENTIFIER ::= { optixMisc 2 }

    -- 1.3.6.1.4.1.2011.2.25.4.30.39.2.1
    optixFanSpeedext OBJECT-TYPE
        SYNTAX OCTET STRING (SIZE(0..32))
        MAX-ACCESS read-write
        STATUS current
        DESCRIPTION
            "This object indicates the fan speed."
        ::= { optixMiscextGroup 1 }

END
