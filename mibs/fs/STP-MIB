STP-MIB DEFINITIONS ::= BEGIN

    IMPORTS
        MODULE-IDENTITY, Counter32, TimeTicks, OBJECT-TYPE, Integer32
             FROM SNMPv2-SMI
        MODULE-COMPLIANCE, OBJECT-GROUP
             FROM SNMPv2-CONF
        gbnL2 FROM ADMIN-MASTER-MIB;


    stpMib MODULE-IDENTITY
          LAST-UPDATED "9904230031Z"  -- April 23, 1999
          ORGANIZATION "admin Inc."
          CONTACT-INFO
              "admin
                  E-mail: "

          DESCRIPTION "STP module management."

          REVISION    "9905130000Z" -- May 13, 1999
          DESCRIPTION "Initial Version"

          ::= { gbnL2 3 }

    stpMIBObjects    OBJECT IDENTIFIER ::= { stpMib 1 }
    stpDot1dStp      OBJECT IDENTIFIER ::= { stpMIBObjects 1 }


          -- All representations of MAC addresses in this MIB Module
          -- use, as a textual convention (i.e. this convention does
          -- not affect their encoding), the data type:

          -- MacAddress ::= OCTET STRING (SIZE (6))    a 6 octet address
                                                    -- in the
                                                    -- "canonical"
                                                    -- order
          -- defined by IEEE 802.1a, i.e., as if it were transmitted
          -- least significant bit first, even though 802.5 (in
          -- contrast to other n802.x protocols) requires MAC
          -- addresses to be transmitted most significant bit first.
          --
          -- 16-bit addresses, if needed, are represented by setting
          -- their upper 4 octets to all 0's, i.e., AAFF would be
          -- represented as 00000000AAFF.


          -- Similarly, all representations of Bridge-Id in this MIB
          -- Module use, as a textual convention (i.e. this
          -- convention does not affect their encoding), the data
          -- type:

          BridgeId ::= OCTET STRING (SIZE (8))   -- the
                                                 -- Bridge-Identifier
                                                 -- as used in the
                                                 -- Spanning Tree
          -- Protocol to uniquely identify a bridge.  Its first two
          -- octets (in network byte order) contain a priority
          -- value and its last 6 octets contain the MAC address
          -- used to refer to a bridge in a unique fashion
          -- (typically, the numerically smallest MAC address
          -- of all ports on the bridge).
          -- Several objects in this MIB module represent values of
          -- timers used by the Spanning Tree Protocol.  In this
          -- MIB, these timers have values in units of hundreths of
          -- a second (i.e. 1/100 secs).
          -- These timers, when stored in a Spanning Tree Protocol's
          -- BPDU, are in units of 1/256 seconds.  Note, however,
          -- that 802.1D-1990 specifies a settable granularity of
          -- no more than 1 second for these timers.  To avoid
          -- ambiguity, a data type is defined here as a textual
          -- convention and all representation of these timers
          -- in this MIB module are defined using this data type.  An
          -- algorithm is also defined for converting between the
          -- different units, to ensure a timer's value is not
          -- distorted by multiple conversions.
          -- The data type is:

          Timeout ::= INTEGER -- a STP timer in units of 1/100 seconds

          -- To convert a Timeout value into a value in units of
          -- 1/256 seconds, the following algorithm should be used:
          --
          --      b  = floor( (n * 256) / 100)
          --
          -- where:
          --      floor   =  quotient [ignore remainder]
          --      n is the value in 1/100 second units
          --      b is the value in 1/256 second units
          --
          -- To convert the value from 1/256 second units back to
          -- 1/100 seconds, the following algorithm should be used:
          --
          --      n = ceiling( (b * 100) / 256)
          --
          -- where:
          --      ceiling =  quotient [if remainder is 0], or
          --                 quotient + 1 [if remainder is non-zero]
          --      n is the value in 1/100 second units
          --      b is the value in 1/256 second units
          --
          -- Note: it is important that the arithmetic operations are
          -- done in the order specified (i.e., multiply first, divide
          -- second).
      

          -- the stpDot1dStp group

          -- Implementation of the dot1dStp group is optional.  It is
          -- implemented by those bridges that support the Spanning Tree
          -- Protocol.


          stpDot1dStpProtocolSpecification OBJECT-TYPE
              SYNTAX  INTEGER {
                          unknown(1),
                          decLb100(2),
                          ieee8021d(3)
                      }
              MAX-ACCESS  read-only
              STATUS  current
              DESCRIPTION
                      "An indication of what version of the Spanning
                      Tree Protocol is being run.  The value
                      'decLb100(2)' indicates the DEC LANbridge 100
                      Spanning Tree protocol.  IEEE 802.1d
                      implementations will return 'ieee8021d(3)'.  If
                      future versions of the IEEE Spanning Tree Protocol
                      are released that are incompatible with the
                      current version a new value will be defined."
              ::= { stpDot1dStp 1 }

          stpDot1dStpPriority OBJECT-TYPE
              SYNTAX  INTEGER (0..61440)
              MAX-ACCESS  read-write
              STATUS  current
              DESCRIPTION
                      "DURABLE: { 32768:all }
                      The value of the write-able portion of the Bridge
                      ID, i.e., the first two octets of the (8 octet
                      long) Bridge ID.  The other (last) 6 octets of the
                      Bridge ID are given by the value of
                      dot1dBaseBridgeAddress.The value has to be a multiple
                      of 4096"
              REFERENCE
                      "IEEE 802.1D-1990: Section 4.5.3.7"
              ::= { stpDot1dStp 2 }

          stpDot1dStpTimeSinceTopologyChange OBJECT-TYPE
              SYNTAX  TimeTicks
              MAX-ACCESS  read-only
              STATUS  current
              DESCRIPTION
                      "The time (in hundredths of a second) since the
                      last time a topology change was detected by the
                      bridge entity."
              REFERENCE
                      "IEEE 802.1D-1990: Section 6.8.1.1.3"
              ::= { stpDot1dStp 3 }

          stpDot1dStpTopChanges OBJECT-TYPE
              SYNTAX  Counter32
              MAX-ACCESS  read-only
              STATUS  current
              DESCRIPTION
                      "The total number of topology changes detected by
                      this bridge since the management entity was last
                      reset or initialized."
              REFERENCE
                      "IEEE 802.1D-1990: Section 6.8.1.1.3"
              ::= { stpDot1dStp 4 }

          stpDot1dStpDesignatedRoot OBJECT-TYPE
              SYNTAX  BridgeId
              MAX-ACCESS  read-only
              STATUS  current
              DESCRIPTION
                      "The bridge identifier of the root of the spanning
                      tree as determined by the Spanning Tree Protocol
                      as executed by this node.  This value is used as
                      the Root Identifier parameter in all Configuration
                      Bridge PDUs originated by this node."
              REFERENCE
                      "IEEE 802.1D-1990: Section 4.5.3.1"
              ::= { stpDot1dStp 5 }

          stpDot1dStpRootCost OBJECT-TYPE
              SYNTAX  Integer32
              MAX-ACCESS  read-only
              STATUS  current
              DESCRIPTION
                      "The cost of the path to the root as seen from
                      this bridge."
              REFERENCE
                      "IEEE 802.1D-1990: Section 4.5.3.2"
              ::= { stpDot1dStp 6 }

          stpDot1dStpRootPort OBJECT-TYPE
              SYNTAX  Integer32
              MAX-ACCESS  read-only
              STATUS  current
              DESCRIPTION
                      "The port number of the port which offers the
                      lowest cost path from this bridge to the root
                      bridge."
              REFERENCE
                      "IEEE 802.1D-1990: Section 4.5.3.3"
              ::= { stpDot1dStp 7 }

          stpDot1dStpMaxAge OBJECT-TYPE
              SYNTAX  Timeout (600..4000)
              MAX-ACCESS  read-only
              STATUS  current
              DESCRIPTION
                      "The maximum age of Spanning Tree Protocol
                      information learned from the network on any port
                      before it is discarded, in units of hundredths of
                      a second.  This is the actual value that this
                      bridge is currently using."
              REFERENCE
                      "IEEE 802.1D-1990: Section 4.5.3.4"
              ::= { stpDot1dStp 8 }

          stpDot1dStpHelloTime OBJECT-TYPE
              SYNTAX  Timeout (100..1000)
              MAX-ACCESS  read-only
              STATUS  current
              DESCRIPTION
                      "The amount of time between the transmission of
                      Configuration bridge PDUs by this node on any port
                      when it is the root of the spanning tree or trying
                      to become so, in units of hundredths of a second.
                      This is the actual value that this bridge is
                      currently using."
              REFERENCE
                      "IEEE 802.1D-1990: Section 4.5.3.5"
              ::= { stpDot1dStp 9 }

          stpDot1dStpHoldTime OBJECT-TYPE
              SYNTAX  Integer32
              MAX-ACCESS  read-only
              STATUS  current
              DESCRIPTION
                      "This time value determines the interval length
                      during which no more than two Configuration bridge
                      PDUs shall be transmitted by this node, in units
                      of hundredths of a second."
              REFERENCE
                      "IEEE 802.1D-1990: Section 4.5.3.14"
              ::= { stpDot1dStp 10 }

          stpDot1dStpForwardDelay OBJECT-TYPE
              SYNTAX  Timeout (400..3000)
              MAX-ACCESS  read-only
              STATUS  current
              DESCRIPTION
                      "This time value, measured in units of hundredths
                      of a second, controls how fast a port changes its
                      spanning state when moving towards the Forwarding
                      state.  The value determines how long the port
                      stays in each of the Listening and Learning
                      states, which precede the Forwarding state.  This
                      value is also used, when a topology change has
                      been detected and is underway, to age all dynamic
                      entries in the Forwarding Database.  [Note that
                      this value is the one that this bridge is
                      currently using, in contrast to
                      stpDot1dStpBridgeForwardDelay which is the value that
                      this bridge and all others would start using
                      if/when this bridge were to become the root.]"
              REFERENCE
                      "IEEE 802.1D-1990: Section 4.5.3.6"
              ::= { stpDot1dStp 11 }

          stpDot1dStpBridgeMaxAge OBJECT-TYPE
              SYNTAX  Timeout (600..4000)
              MAX-ACCESS  read-write
              STATUS  current
              DESCRIPTION
                      "DURABLE: { 2000:all }
                      The value that all bridges use for MaxAge when
                      this bridge is acting as the root.  Note that
                      802.1D-1990 specifies that the range for this
                      parameter is related to the value of
                      stpDot1dStpBridgeHelloTime. The granularity of this
                      timer is specified by 802.1D-1990 to be 1 second.
                      An agent may return a badValue error if a set is
                      attempted to a value which is not a whole number
                      of seconds."
              REFERENCE
                      "IEEE 802.1D-1990: Section 4.5.3.8"
              ::= { stpDot1dStp 12 }

          stpDot1dStpBridgeHelloTime OBJECT-TYPE
              SYNTAX  Timeout (100..1000)
              MAX-ACCESS  read-write
              STATUS  current
              DESCRIPTION
                      "DURABLE: { 200:all }
                      The value that all bridges use for HelloTime when
                      this bridge is acting as the root.  The
                      granularity of this timer is specified by 802.1D-
                      1990 to be 1 second.  An agent may return a
                      badValue error if a set is attempted to a value
                      which is not a whole number of seconds."
              REFERENCE
                      "IEEE 802.1D-1990: Section 4.5.3.9"
              ::= { stpDot1dStp 13 }

          stpDot1dStpBridgeForwardDelay OBJECT-TYPE
              SYNTAX  Timeout (400..3000)
              MAX-ACCESS  read-write
              STATUS  current
              DESCRIPTION
                      "DURABLE: { 1500:all }
                      The value that all bridges use for ForwardDelay
                      when this bridge is acting as the root.  Note that
                      802.1D-1990 specifies that the range for this
                      parameter is related to the value of
                      stpDot1dStpBridgeMaxAge.  The granularity of this
                      timer is specified by 802.1D-1990 to be 1 second.
                      An agent may return a badValue error if a set is
                      attempted to a value which is not a whole number
                      of seconds."
              REFERENCE
                      "IEEE 802.1D-1990: Section 4.5.3.10"
              ::= { stpDot1dStp 14 }

          stpPropStpEnable OBJECT-TYPE
              SYNTAX  INTEGER {
                          enabled(1),
                          disabled(2)
                      }
              MAX-ACCESS  read-write
              STATUS  current
              DESCRIPTION
                      "DURABLE: { enabled:all }
                      The enabled/disabled status of STP for the bridge entity."
              ::= { stpDot1dStp 16 }

          -- The Spanning Tree Port Table

          stpDot1dStpPortTable OBJECT-TYPE
              SYNTAX  SEQUENCE OF StpDot1dStpPortEntry
              MAX-ACCESS  not-accessible
              STATUS  current
              DESCRIPTION
                      "A table that contains port-specific information
                      for the Spanning Tree Protocol."
              ::= { stpDot1dStp 15 }

          stpDot1dStpPortEntry OBJECT-TYPE
              SYNTAX  StpDot1dStpPortEntry
              MAX-ACCESS  not-accessible
              STATUS  current
              DESCRIPTION
                      "A list of information maintained by every port
                      about the Spanning Tree Protocol state for that
                      port."
              INDEX   { stpDot1dStpPort }
              ::= { stpDot1dStpPortTable 1 }

          StpDot1dStpPortEntry ::=
              SEQUENCE {
                  stpDot1dStpPort
                      INTEGER,
                  stpDot1dStpPortPriority
                      INTEGER,
                  stpDot1dStpPortState
                      INTEGER,
                  stpDot1dStpPortEnable
                      INTEGER,
                  stpDot1dStpPortPathCost
                      INTEGER,
                  stpDot1dStpPortDesignatedRoot
                      BridgeId,
                  stpDot1dStpPortDesignatedCost
                      Integer32,
                  stpDot1dStpPortDesignatedBridge
                      BridgeId,
                  stpDot1dStpPortDesignatedPort
                      OCTET STRING,
                  stpDot1dStpPortForwardTransitions
                      Counter32,
                  stpDot1dRemoteLoopDetect
                      INTEGER,
                  stpDot1wRstpPortTxHoldCount
                      INTEGER,
                  stpDot1wRstpPortOperP2p
                      INTEGER,
                  stpDot1wRstpPortOperEdge
                      INTEGER,
                  stpDot1wRstpPortMcheck
                      INTEGER,
                  stpDot1wRstpPortTxTcn
                      INTEGER,
                  stpDot1wRstpPortTxConfig
                      INTEGER,
                  stpDot1wRstpPortTxRstp
                      INTEGER,
                  stpDot1wRstpPortRxTcn
                      INTEGER,
                  stpDot1wRstpPortRxConfig
                      INTEGER,
                  stpDot1wRstpPortRxRstp
                      INTEGER,
                  stpDot1wRstpPortClear
                      INTEGER,
                  stpDot1wRstpPortAdminP2p
                      INTEGER,
                  stpDot1wRstpPortAdminEdge
                      INTEGER
              }

          stpDot1dStpPort OBJECT-TYPE
              SYNTAX  INTEGER (1..128)
              MAX-ACCESS  read-only
              STATUS  current
              DESCRIPTION
                      "The port number of the port for which this entry
                      contains Spanning Tree Protocol management
                      information."
              REFERENCE
                      "IEEE 802.1D-1990: Section 6.8.2.1.2"
              ::= { stpDot1dStpPortEntry 1 }

          stpDot1dStpPortPriority OBJECT-TYPE
              SYNTAX  INTEGER (0..240)
              MAX-ACCESS  read-write
              STATUS  current
              DESCRIPTION
                      "DURABLE: { 128:all }
                      The value of the priority field which is
                      contained in the first (in network byte order)
                      octet of the (2 octet long) Port ID.  The other
                      octet of the Port ID is given by the value of
                      stpDot1dStpPort.The value has to be a multiple
                      of 16"
              REFERENCE
                      "IEEE 802.1D-1990: Section 4.5.5.1"
              ::= { stpDot1dStpPortEntry 2 }

          stpDot1dStpPortState OBJECT-TYPE
              SYNTAX  INTEGER {
                          disabled(1),
                          blocking(2),
                          listening(3),
                          learning(4),
                          forwarding(5),
                          broken(6)
                      }
              MAX-ACCESS  read-only
              STATUS  current
              DESCRIPTION
                      "The port's current state as defined by
                      application of the Spanning Tree Protocol.  This
                      state controls what action a port takes on
                      reception of a frame.  If the bridge has detected
                      a port that is malfunctioning it will place that
                      port into the broken(6) state.  For ports which
                      are disabled (see stpDot1dStpPortEnable), this object
                      will have a value of disabled(1)."
              REFERENCE
                      "IEEE 802.1D-1990: Section 4.5.5.2"
              ::= { stpDot1dStpPortEntry 3 }


          stpDot1dStpPortEnable OBJECT-TYPE
              SYNTAX  INTEGER {
                          enabled(1),
                          disabled(2)
                      }
              MAX-ACCESS  read-write
              STATUS  current
              DESCRIPTION
                      "The enabled/disabled status of the port."
              REFERENCE
                      "IEEE 802.1D-1990: Section 4.5.5.2"
              ::= { stpDot1dStpPortEntry 4 }

          stpDot1dStpPortPathCost OBJECT-TYPE
              SYNTAX  INTEGER (1..200000000)
              MAX-ACCESS  read-write
              STATUS  current
              DESCRIPTION
                      "DURABLE: { 10:all }
                      The contribution of this port to the path cost of
                      paths towards the spanning tree root which include
                      this port.  802.1D-1990 recommends that the
                      default value of this parameter be in inverse
                      proportion to the speed of the attached LAN."
              REFERENCE
                      "IEEE 802.1D-1990: Section 4.5.5.3"
              ::= { stpDot1dStpPortEntry 5 }

          stpDot1dStpPortDesignatedRoot OBJECT-TYPE
              SYNTAX  BridgeId
              MAX-ACCESS  read-only
              STATUS  current
              DESCRIPTION
                      "The unique Bridge Identifier of the Bridge
                      recorded as the Root in the Configuration BPDUs
                      transmitted by the Designated Bridge for the
                      segment to which the port is attached."
              REFERENCE
                      "IEEE 802.1D-1990: Section 4.5.5.4"
              ::= { stpDot1dStpPortEntry 6 }

          stpDot1dStpPortDesignatedCost OBJECT-TYPE
              SYNTAX  Integer32
              MAX-ACCESS  read-only
              STATUS  current
              DESCRIPTION
                      "The path cost of the Designated Port of the
                      segment connected to this port.  This value is
                      compared to the Root Path Cost field in received
                      bridge PDUs."
              REFERENCE
                      "IEEE 802.1D-1990: Section 4.5.5.5"
              ::= { stpDot1dStpPortEntry 7 }

          stpDot1dStpPortDesignatedBridge OBJECT-TYPE
              SYNTAX  BridgeId
              MAX-ACCESS  read-only
              STATUS  current
              DESCRIPTION
                      "The Bridge Identifier of the bridge which this
                      port considers to be the Designated Bridge for
                      this port's segment."
              REFERENCE
                      "IEEE 802.1D-1990: Section 4.5.5.6"
              ::= { stpDot1dStpPortEntry 8 }

          stpDot1dStpPortDesignatedPort OBJECT-TYPE
              SYNTAX  OCTET STRING (SIZE (2))
              MAX-ACCESS  read-only
              STATUS  current
              DESCRIPTION
                      "The Port Identifier of the port on the Designated
                      Bridge for this port's segment."
              REFERENCE
                      "IEEE 802.1D-1990: Section 4.5.5.7"
              ::= { stpDot1dStpPortEntry 9 }

          stpDot1dStpPortForwardTransitions OBJECT-TYPE
              SYNTAX  Counter32
              MAX-ACCESS  read-only
              STATUS  current
              DESCRIPTION
                      "The number of times this port has transitioned
                      from the Learning state to the Forwarding state."
              ::= { stpDot1dStpPortEntry 10 }
          
          stpDot1dRemoteLoopDetect OBJECT-TYPE
              SYNTAX  INTEGER {
                          enabled(1),
                          disabled(2)
                      }
              MAX-ACCESS  read-write
              STATUS  current
              DESCRIPTION
                      "The LOOP DETECT status of the port."
              --端口私有生成树的开启/关闭状态
              ::= { stpDot1dStpPortEntry 11 }

          stpDot1wRstpPortTxHoldCount OBJECT-TYPE
              SYNTAX  INTEGER(1..255)
              MAX-ACCESS read-write
              STATUS  current
              DESCRIPTION
                      "Maximum number of BPDUs allowed to be transmitted during per helloTime"
                      --端口在每个helloTime时间内允许发送的最大BPDU数
              ::= { stpDot1dStpPortEntry 12 }
          
          stpDot1wRstpPortOperP2p OBJECT-TYPE
              SYNTAX  INTEGER {
                          true(1),
                          false(2)
                      }
              MAX-ACCESS read-only
              STATUS  current
              DESCRIPTION
                      "The operational point-to-point status of the LAN segment attached to this port"
                    --端口实际工作的点对点链接状态
              ::= { stpDot1dStpPortEntry 13 }
              
          stpDot1wRstpPortOperEdge OBJECT-TYPE
              SYNTAX  INTEGER {
                          true(1),
                          false(2)
                      }
              MAX-ACCESS read-only
              STATUS  current
              DESCRIPTION
                      "The operational value of the Edge Port parameter"
                      --端口实际工作的边界端口状态
              ::= { stpDot1dStpPortEntry 14 }
              
          stpDot1wRstpPortMcheck OBJECT-TYPE
              SYNTAX  INTEGER {
                      enable(1)
              }              
              MAX-ACCESS read-write
              STATUS  current
              DESCRIPTION
                      "force port into transmitting rstp packets"
                      --强制端口发送RSTP报文
              ::= { stpDot1dStpPortEntry 15 }
              
          stpDot1wRstpPortTxTcn OBJECT-TYPE
              SYNTAX  INTEGER
              MAX-ACCESS read-only
              STATUS  current
              DESCRIPTION
                      "Output statistics of TCN packets"
                      --端口发送的TCN报文个数
              ::= { stpDot1dStpPortEntry 16 }
              
          stpDot1wRstpPortTxConfig OBJECT-TYPE
              SYNTAX  INTEGER
              MAX-ACCESS read-only
              STATUS  current
              DESCRIPTION
                      "Output statistics of CONFIG packets"
                      --端口发送的CONFIG报文个数
              ::= { stpDot1dStpPortEntry 17 }
              
          stpDot1wRstpPortTxRstp OBJECT-TYPE
              SYNTAX  INTEGER
              MAX-ACCESS read-only
              STATUS  current
              DESCRIPTION
                      "Output statistics of RSTP packets"
                      --端口发送的RSTP报文个数
              ::= { stpDot1dStpPortEntry 18 }
          
          stpDot1wRstpPortRxTcn OBJECT-TYPE
              SYNTAX  INTEGER
              MAX-ACCESS read-only
              STATUS  current
              DESCRIPTION
                      "Input statistics of TCN packets"
                      --端口接收的TCN报文个数
              ::= { stpDot1dStpPortEntry 19 }
              
          stpDot1wRstpPortRxConfig OBJECT-TYPE
              SYNTAX  INTEGER
              MAX-ACCESS read-only
              STATUS  current
              DESCRIPTION
                      "Input statistics of CONFIG packets"
                      --端口接收的CONFIG报文个数
              ::= { stpDot1dStpPortEntry 20 }
              
          stpDot1wRstpPortRxRstp OBJECT-TYPE
              SYNTAX  INTEGER
              MAX-ACCESS read-only
              STATUS  current
              DESCRIPTION
                      "Input statistics of RSTP packets"
                      --端口接收的RSTP报文个数
              ::= { stpDot1dStpPortEntry 21 }
              
          stpDot1wRstpPortClear OBJECT-TYPE
              SYNTAX  INTEGER{
                          true(1)
                      }
              MAX-ACCESS read-write
              STATUS  current
              DESCRIPTION
                      "Clear port spanning-tree statistics"
                      --清除端口生成树统计信息
              ::= { stpDot1dStpPortEntry 22 }
              
          stpDot1wRstpPortAdminP2p OBJECT-TYPE
              SYNTAX  INTEGER {
                          forceTrue(1),
                          forceFalse(2),
                          auto(3)
                      }
              MAX-ACCESS read-write
              STATUS  current
              DESCRIPTION
                   "The administrative point-to-point status of the LAN segment attached to this port"
                    --配置的端口的点对点链接状态
              ::= { stpDot1dStpPortEntry 23 }

          stpDot1wRstpPortAdminEdge OBJECT-TYPE
              SYNTAX  INTEGER {
                          enable(1),
                          disable(2)
                      }
              MAX-ACCESS read-write
              STATUS  current
              DESCRIPTION
                      "The administrative value of the Edge Port parameter"
                      --配置的边界端口状态
              ::= { stpDot1dStpPortEntry 24 }
              
    spanOnOff OBJECT-TYPE
        SYNTAX INTEGER {
               enable(1),
               disable(2)
        }
        MAX-ACCESS read-write
        STATUS current
        DESCRIPTION
            "DURABLE: { enable }
             Enable/Disable Spanning Tree for the bridge.
             When 'disable(2)', all ports of the device are placed in the
             forwarding mode, regardless of current Spanning Tree state.
             When 'enable(1)', the normal STP state transitions take place."
        ::= { stpDot1dStp 17 }
        
    stpDot1wRstpForceVersion OBJECT-TYPE
        SYNTAX INTEGER {
               ForceStp(0),
               ForceRstp(2),
               ForceMstp(3)
        }
        MAX-ACCESS read-write
        STATUS current
        DESCRIPTION
             "which protocol mode the bridge chooses to execute ,RSTP or STP compatible"
             --桥当前的协议模式，RSTP或者STP兼容模式
        ::= { stpDot1dStp 19 }
        
	stpDot1dStpTrap      OBJECT IDENTIFIER ::= { stpDot1dStp 18 }
        ----------------------------------------------------------------------------------
        --STP TRAP MIB--
        ----------------------------------------------------------------------------------
                    
        stpDot1dStpPortBlocking NOTIFICATION-TYPE
        OBJECTS { stpDot1dStpPortState }
        STATUS  current
        DESCRIPTION
               "Port status is turned from forwarding to blocking."
       	::= { stpDot1dStpTrap 1 }
       	
        stpDot1dStpPortException NOTIFICATION-TYPE
        OBJECTS { stpDot1dStpPort }
        STATUS  current
        DESCRIPTION
               "Port packet flood to CPU rate is too big, port exception happen."
               --如果端口冲击CPU的报文速率太大，则发出端口异常的trap
       	::= { stpDot1dStpTrap 2 }
       	
        stpDot1dStpPortRecover NOTIFICATION-TYPE
        OBJECTS { stpDot1dStpPort }
        STATUS  current
        DESCRIPTION
               "Port recover time pass after port encounter port CAR exception, and Port packet flood to CPU rate is normal, recover port."
               --端口被端口CAR关闭后，过了端口恢复时间，并且该端口下冲击CPU的速率正常，重新打开端口，并发送端口恢复trap
       	::= { stpDot1dStpTrap 3 }

        stpDot1dStpPortRmtLoop NOTIFICATION-TYPE
        OBJECTS { stpDot1dStpPort }
        STATUS  current
        DESCRIPTION
               "Port is blocked because of remote loop."
               --端口因为远端环回而被block
        ::= { stpDot1dStpTrap 4 }

        stpDot1dStpPortRmtLoopFree NOTIFICATION-TYPE
        OBJECTS { stpDot1dStpPort }
        STATUS  current
        DESCRIPTION
               "Port is released from remote loop."
               --端口远端环回解除
        ::= { stpDot1dStpTrap 5 }

        stpDot1dStpNewRoot NOTIFICATION-TYPE
        OBJECTS { stpDot1dStpDesignatedRoot }
        STATUS  current
        DESCRIPTION
               "Root bridge changed for the stp."
        ::= { stpDot1dStpTrap 6 }

        stpDot1dStpPortForwarding NOTIFICATION-TYPE
        OBJECTS { stpDot1dStpPortState }
        STATUS  current
        DESCRIPTION
               "Port status is turned from blocking to forwarding."
        ::= { stpDot1dStpTrap 7 }
-- -----------------------------------------------------------------------------
-- STP MIB - Conformance information
--           Not really necessary other than for strict interpretation of SMIv2
--           (and it doesn't hurt anything)
-- -----------------------------------------------------------------------------
stpMIBConformance OBJECT IDENTIFIER ::= { stpMib 2 }
stpMIBGroups OBJECT IDENTIFIER ::= { stpMIBConformance 1 }
stpMIBCompliances OBJECT IDENTIFIER ::= { stpMIBConformance 2 }

          stpMIBBaseGroup OBJECT-GROUP
             OBJECTS {
                 stpDot1dStpProtocolSpecification,
                 stpDot1dStpPriority,
                 stpDot1dStpTimeSinceTopologyChange,
                 stpDot1dStpTopChanges,
                 stpDot1dStpDesignatedRoot,
                 stpDot1dStpRootCost,
                 stpDot1dStpRootPort,
                 stpDot1dStpMaxAge,
                 stpDot1dStpHelloTime,
                 stpDot1dStpHoldTime,
                 stpDot1dStpForwardDelay,
                 stpDot1dStpBridgeMaxAge,
                 stpDot1dStpBridgeHelloTime,
                 stpDot1dStpBridgeForwardDelay,
                 stpPropStpEnable,
                 stpDot1dStpPort,
                 stpDot1dStpPortPriority,
                 stpDot1dStpPortState,
                 stpDot1dStpPortEnable,
                 stpDot1dStpPortPathCost,
                 stpDot1dStpPortDesignatedRoot,
                 stpDot1dStpPortDesignatedCost,
                 stpDot1dStpPortDesignatedBridge,
                 stpDot1dStpPortDesignatedPort,
                 stpDot1dStpPortForwardTransitions
             }    
             STATUS current
             DESCRIPTION
                    "STP module groups."
             ::= { stpMIBGroups 1 }
    
-- -----------------------------------------------------------------------------
-- STP MIB - Compliance information
-- -----------------------------------------------------------------------------
          stpMIBCompliance MODULE-COMPLIANCE
             STATUS  current
             DESCRIPTION
                    "The compliance statement for STP module."
             MODULE
             MANDATORY-GROUPS {
                 stpMIBBaseGroup
             }
             ::= { stpMIBCompliances 1 }

END
