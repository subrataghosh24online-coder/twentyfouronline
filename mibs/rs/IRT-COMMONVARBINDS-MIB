--
-- IRT-COMMONVARBINDS-MIB.my
-- MIB generated by MG-SOFT Visual MIB Builder Version 6.0  Build 88
-- Thursday, May 03, 2007 at 19:14:24
--

	IRT-COMMONVARBINDS-MIB DEFINITIONS ::= BEGIN
 
		IMPORTS
			common			
				FROM IRT-TRANSMITTER-SMI-MIB			
			OBJECT-GROUP, MODULE-COMPLIANCE			
				FROM SNMPv2-CONF			
			Unsigned32, Counter32, OBJECT-TYPE, MODULE-IDENTITY			
				FROM SNMPv2-SMI			
			DateAndTime			
				FROM SNMPv2-TC;
	
	
		-- 1.3.6.1.4.1.19831.1.1.7.1
		commonVarbinds MODULE-IDENTITY 
			LAST-UPDATED "200705041400Z"		-- May 04, 2007 at 14:00 GMT
			ORGANIZATION 
				"IRT for WORKING-GROUP-TC-MIB"
			CONTACT-INFO 
				"Contact-info:
				
				Andreas Metz
				
				Institut fuer Rundfunktechnik GmbH
				Broadcast Networks and Servers (SN)
				
				Floriansmuehlstr.60
				80939 Munich
				Germany
				
				Phone: +49 89 32399 325
				Fax: +49 89 32399 354
				"
			DESCRIPTION 
				"Description:
				   
				Common values"
			REVISION "200705041400Z"		-- May 04, 2007 at 14:00 GMT
			DESCRIPTION 
				"change MODULE-COMPLIANCE"
			REVISION "200612201400Z"		-- December 20, 2006 at 14:00 GMT
			DESCRIPTION 
				"corrections"
			REVISION "200609211400Z"		-- September 21, 2006 at 14:00 GMT
			DESCRIPTION 
				"Adding Compliance Statement"
			REVISION "200609191400Z"		-- September 19, 2006 at 14:00 GMT
			DESCRIPTION 
				"Channing commonVarbins form 7.2 to 7.1"
			REVISION "200609071400Z"		-- September 07, 2006 at 14:00 GMT
			DESCRIPTION 
				"Relocation of the TC-MIB from the standard OID area at IEC into the private OID area of the IRT"
			::= { common 1 }

		
	
	
--
-- Node definitions
--
	
		-- 1.3.6.1.4.1.19831.1.1.7.1.1
		objectGroup OBJECT-GROUP
			OBJECTS { eventTimeStamp, eventPriority, eventCounter, mibRelease }
			STATUS current
			DESCRIPTION 
				"Description. Common objects"
			::= { commonVarbinds 1 }

		
-- Event timestamp in UTC
		-- 1.3.6.1.4.1.19831.1.1.7.1.2
		eventTimeStamp OBJECT-TYPE
			SYNTAX DateAndTime
			MAX-ACCESS read-only
			STATUS current
			DESCRIPTION
				"Description.Event timestamp in UTC"
			::= { commonVarbinds 2 }

		
-- Event priority level
		-- 1.3.6.1.4.1.19831.1.1.7.1.3
		eventPriority OBJECT-TYPE
			SYNTAX Unsigned32
			MAX-ACCESS read-only
			STATUS current
			DESCRIPTION
				"Description.Event priority level"
			::= { commonVarbinds 3 }

		
-- Event counter
		-- 1.3.6.1.4.1.19831.1.1.7.1.4
		eventCounter OBJECT-TYPE
			SYNTAX Counter32
			MAX-ACCESS read-only
			STATUS current
			DESCRIPTION
				"Description.Event counter"
			::= { commonVarbinds 4 }

		
		-- 1.3.6.1.4.1.19831.1.1.7.1.5
		mibRelease OBJECT-TYPE
			SYNTAX DateAndTime
			MAX-ACCESS read-only
			STATUS current
			DESCRIPTION
				"Description.The current MIB version"
			::= { commonVarbinds 5 }

		
		-- 1.3.6.1.4.1.19831.1.1.7.1.6
		commonVarbindsCompliance MODULE-COMPLIANCE
			STATUS current
			DESCRIPTION 
				"Compliance Statement"
			MODULE -- this module
				MANDATORY-GROUPS { objectGroup }
			::= { commonVarbinds 6 }

		
	
	END

--
-- IRT-COMMONVARBINDS-MIB.my
--
