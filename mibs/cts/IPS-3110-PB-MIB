IPS-3110-PB-MIB DEFINITIONS ::= BEGIN

	IMPORTS
		enterprises, Counter, TimeTicks, Gauge
		                                    FROM RFC1155-SMI
		mib-2, DisplayString                FROM RFC1213-MIB
		TRAP-TYPE                           FROM RFC-1215
		OBJECT-TYPE                         FROM RFC-1212;

	cts OBJECT IDENTIFIER ::= { enterprises 9304 }

	PhysAddress ::=	OCTET STRING

	-- This data type is used to model media addresses.  For many
	-- types of media, this will be in a binary representation.
	-- For example, an ethernet address would be represented as
	-- a string of 6 octets.

	-- All representations of MAC addresses in this MIB Module use,
	-- as a textual convention (i.e., this convention does not affect
	-- their encoding), the data type:

	MacAddress ::= OCTET STRING (SIZE (6))      -- a 6 octet address in
	                                            -- the "canonical" order

	VLANPortMember ::= DisplayString (SIZE (0..27))

	swh
		OBJECT IDENTIFIER ::= { cts 100 }

	ips3110pb
		OBJECT IDENTIFIER ::= { swh 3110 }


-- Main

	swhSystemInformation
		OBJECT IDENTIFIER ::= { ips3110pb 1 }
	swhUserAuthentication
		OBJECT IDENTIFIER ::= { ips3110pb 2 }
	swhNetworkManagement
		OBJECT IDENTIFIER ::= { ips3110pb 3 }
	swhSwitchManagement
		OBJECT IDENTIFIER ::= { ips3110pb 4 }
	swhSwitchMonitor
		OBJECT IDENTIFIER ::= { ips3110pb 5 }
	swhSystemUtility
		OBJECT IDENTIFIER ::= { ips3110pb 6 }
	swhNewBootUpImage OBJECT-TYPE
		SYNTAX    INTEGER { image1(1), image2(2) }
		ACCESS    read-write
		STATUS    mandatory
		DESCRIPTION
			"New Boot Up Image"
		::= { ips3110pb 15 }
	swhSaveConfiguration OBJECT-TYPE
		SYNTAX    INTEGER { normal(0), save(1) }
		ACCESS    write-only
		STATUS    mandatory
		DESCRIPTION
			"Save Configuration to Flash ROM
			 set 1 to execute this function"
		::= { ips3110pb 7 }
	swhResetSystem OBJECT-TYPE
		SYNTAX    INTEGER { normal(0), reset(1) }
		ACCESS    write-only
		STATUS    mandatory
		DESCRIPTION
			"Reset System
			 set 1 to execute this function"
		::= { ips3110pb 8 }
	switchTraps OBJECT IDENTIFIER
		::= { ips3110pb 9 }


-- SystemInformation(1)

	swhCompanyInfo
		OBJECT IDENTIFIER ::= { swhSystemInformation 1 }
	swhHardwareInfo
		OBJECT IDENTIFIER ::= { swhSystemInformation 2 }
--	swhCATVModuleInfo
--		OBJECT IDENTIFIER ::= { swhSystemInformation 5 }
--	swhBatteryModuleInfo
--		OBJECT IDENTIFIER ::= { swhSystemInformation 6 }


-- SystemInformation(1).CompanyInfo(1)

	swhCompanyName OBJECT-TYPE
		SYNTAX    DisplayString (SIZE (0..255))
		ACCESS    read-write
		STATUS    mandatory
		DESCRIPTION
			"Company Name"
		::= { swhCompanyInfo 1 }

	swhDHCPVendorID OBJECT-TYPE
		SYNTAX    DisplayString (SIZE (0..255))
		ACCESS    read-write
		STATUS    mandatory
		DESCRIPTION
			"DHCP Vendor ID"
		::= { swhCompanyInfo 7 }

	swhCLIHostname OBJECT-TYPE
		SYNTAX    DisplayString (SIZE (0..255))
		ACCESS    read-write
		STATUS    mandatory
		DESCRIPTION
			"CLI Hostname"
		::= { swhCompanyInfo 6 }


-- SystemInformation(1).HardwareInfo(2)

	swhModelName OBJECT-TYPE
		SYNTAX    DisplayString (SIZE (0..255))
		ACCESS    read-only
		STATUS    mandatory
		DESCRIPTION
			"Model Name"
		::= { swhHardwareInfo 1 }

	swhBootUpImage OBJECT-TYPE
		SYNTAX    DisplayString
		ACCESS    read-only
		STATUS    mandatory
		DESCRIPTION
			"Boot Up Image"
		::= { swhHardwareInfo 40 }

	swhNextBootUpImage OBJECT-TYPE
		SYNTAX    DisplayString
		ACCESS    read-only
		STATUS    mandatory
		DESCRIPTION
			"Next Boot Up Image"
		::= { swhHardwareInfo 41 }

	swhImage1FirmwareVersion OBJECT-TYPE
		SYNTAX    DisplayString (SIZE (0..255))
		ACCESS    read-only
		STATUS    mandatory
		DESCRIPTION
			"Image1 Firmware Version"
		::= { swhHardwareInfo 45 }

	swhImage2FirmwareVersion OBJECT-TYPE
		SYNTAX    DisplayString (SIZE (0..255))
		ACCESS    read-only
		STATUS    mandatory
		DESCRIPTION
			"Image2 Firmware Version"
		::= { swhHardwareInfo 46 }

	swhGPortNum OBJECT-TYPE
		SYNTAX    INTEGER
		ACCESS    read-only
		STATUS    mandatory
		DESCRIPTION
			"Giga Port Number"
		::= { swhHardwareInfo 6 }

	swhMPortNum OBJECT-TYPE
		SYNTAX    INTEGER
		ACCESS    read-only
		STATUS    mandatory
		DESCRIPTION
			"10/100 Meg Port Number"
		::= { swhHardwareInfo 7 }

	swhMBVersion OBJECT-TYPE
		SYNTAX    DisplayString (SIZE (0..255))
		ACCESS    read-only
		STATUS    mandatory
		DESCRIPTION
			"Main Board Version"
		::= { swhHardwareInfo 9 }

	swhFiber1Type OBJECT-TYPE
		SYNTAX    DisplayString (SIZE (0..255))
		ACCESS    read-only
		STATUS    mandatory
		DESCRIPTION
			"fiber 1 type"
		::= { swhHardwareInfo 10 }

--	swhFiber1WaveLength OBJECT-TYPE
--		SYNTAX    DisplayString (SIZE (0..255))
--		ACCESS    read-only
--		STATUS    mandatory
--		DESCRIPTION
--			"fiber 1 wave length"
--		::= { swhHardwareInfo 11 }

	swhFiber2Type OBJECT-TYPE
		SYNTAX    DisplayString (SIZE (0..255))
		ACCESS    read-only
		STATUS    mandatory
		DESCRIPTION
			"fiber 2 type"
		::= { swhHardwareInfo 12 }

--	swhFiber2WaveLength OBJECT-TYPE
--		SYNTAX    DisplayString (SIZE (0..255))
--		ACCESS    read-only
--		STATUS    mandatory
--		DESCRIPTION
--			"fiber 2 wave length"
--		::= { swhHardwareInfo 13 }

	swhSerialNumber OBJECT-TYPE
		SYNTAX    DisplayString (SIZE (0..255))
		ACCESS    read-only
		STATUS    mandatory
		DESCRIPTION
			"serial number of this device."
		::= { swhHardwareInfo 14 }

	swhDateCode OBJECT-TYPE
		SYNTAX    DisplayString (SIZE (0..255))
		ACCESS    read-only
		STATUS    mandatory
		DESCRIPTION
			"the day of producing this device"
		::= { swhHardwareInfo 15 }

	swhPowerSupply1 OBJECT-TYPE
		SYNTAX    INTEGER { not-installed(2), installed(1), na(0) }
		ACCESS    read-only
		STATUS    mandatory
		DESCRIPTION
			"module a power supply exist or not"
		::= { swhHardwareInfo 24 }

	swhPowerSupply2 OBJECT-TYPE
		SYNTAX    INTEGER { not-installed(2), installed(1), na(0) }
		ACCESS    read-only
		STATUS    mandatory
		DESCRIPTION
			"module b power supply exist or not"
		::= { swhHardwareInfo 28 }

	swhCPUTemperature OBJECT-TYPE
		SYNTAX    DisplayString (SIZE (0..255))
		ACCESS    read-only
		STATUS    mandatory
		DESCRIPTION
			"module b power supply exist or not"
		::= { swhHardwareInfo 56 }

	swhSwitchTemperature OBJECT-TYPE
		SYNTAX    DisplayString (SIZE (0..255))
		ACCESS    read-only
		STATUS    mandatory
		DESCRIPTION
			"module b power supply exist or not"
		::= { swhHardwareInfo 57 }

	swhPowerTemperature OBJECT-TYPE
		SYNTAX    DisplayString (SIZE (0..255))
		ACCESS    read-only
		STATUS    mandatory
		DESCRIPTION
			"module b power supply exist or not"
		::= { swhHardwareInfo 58 }


-- SystemInformation(1).SoftwareInfo(3)


-- SystemInformation(1).CATVModuleInfo(5)


-- SystemInformation(1).BatteryModuleInfo(6)


-- UserAuthentication(2).UserTable(1)

	swhUserTable OBJECT-TYPE
		SYNTAX    SEQUENCE OF SWHUserEntry
		ACCESS    not-accessible
		STATUS    mandatory
		DESCRIPTION
			"Table of user information."
		::= { swhUserAuthentication 1 }

	-- Table Entry
	swhUserEntry OBJECT-TYPE
		SYNTAX    SWHUserEntry
		ACCESS    not-accessible
		STATUS    mandatory
		DESCRIPTION
			"An entry in the table, containing information
			about user.
			Only Administrator can read this table"
		INDEX    { swhUserIndex }
		::= { swhUserTable 1 }

	SWHUserEntry ::=
		SEQUENCE {
			swhUserIndex
				INTEGER,
		--	swhUserValid
		--		INTEGER,
			swhUserEnable
				INTEGER,
			swhUserName
				DisplayString,
			swhUserPassword
				DisplayString,
			swhUserDescription
				DisplayString,
		--	swhUserIPSecurity
		--		INTEGER,
		--	swhUserIPAddr
		--		IpAddress,
		--	swhUserIPTrapDest
		--		IpAddress,
			swhUserConsoleLevel
				INTEGER
		--	swhUserSNMPLevel
		--		INTEGER,
		--	swhUserWebLevel
		--		INTEGER
		}

	swhUserIndex OBJECT-TYPE
		SYNTAX    INTEGER
		ACCESS    read-only
		STATUS    mandatory
		DESCRIPTION
			"user index"
		::= { swhUserEntry 1 }

--	swhUserValid OBJECT-TYPE
--		SYNTAX    INTEGER { valid(1), invalid(0) }
--		ACCESS    read-only
--		STATUS    mandatory
--		DESCRIPTION
--			"Valid"
--		::= { swhUserEntry 2 }

	swhUserEnable OBJECT-TYPE
		SYNTAX    INTEGER { disable(0), enable(1) }
		ACCESS    read-only
		STATUS    mandatory
		DESCRIPTION
			"Enable"
		::= { swhUserEntry 3 }

	swhUserName OBJECT-TYPE
		SYNTAX    DisplayString (SIZE (0..255))
		ACCESS    read-only
		STATUS    mandatory
		DESCRIPTION
			"Name"
		::= { swhUserEntry 4 }

	swhUserPassword OBJECT-TYPE
		SYNTAX    DisplayString (SIZE (0..255))
		ACCESS    read-only
		STATUS    mandatory
		DESCRIPTION
			"Password"
		::= { swhUserEntry 5 }

	swhUserDescription OBJECT-TYPE
		SYNTAX    DisplayString (SIZE (0..255))
		ACCESS    read-only
		STATUS    mandatory
		DESCRIPTION
			"Description"
		::= { swhUserEntry 6 }

	--swhUserIPSecurity OBJECT-TYPE
	--	SYNTAX    INTEGER { disable(0), enable(1) }
	--	ACCESS    read-only
	--	STATUS    mandatory
	--	DESCRIPTION
	--		"IP Security enable,
	--		 only swhUserIPAddr could login console"
	--	::= { swhUserEntry 7 }

	--swhUserIPAddr OBJECT-TYPE
	--	SYNTAX    IpAddress
	--	ACCESS    read-only
	--	STATUS    mandatory
	--	DESCRIPTION
	--		"The IP address from which could login console."
	--	::= { swhUserEntry 8 }

	--swhUserIPTrapDest OBJECT-TYPE
	--	SYNTAX    IpAddress
	--	ACCESS    read-write
	--	STATUS    mandatory
	--	DESCRIPTION
	--		"SNMP trap destination IP address"
	--	::= { swhUserEntry 9 }

	swhUserConsoleLevel OBJECT-TYPE
		SYNTAX    INTEGER { readonly(1), readwrite(2), administrator(3) }
		ACCESS    read-only
		STATUS    mandatory
		DESCRIPTION
			"Console Level"
		::= { swhUserEntry 10 }

	--swhUserSNMPLevel OBJECT-TYPE
	--	SYNTAX    INTEGER { readonly(1), readwrite(2), administrator(3) }
	--	ACCESS    read-write
	--	STATUS    mandatory
	--	DESCRIPTION
	--		"SNMP Level"
	--	::= { swhUserEntry 11 }

	--swhUserWebLevel OBJECT-TYPE
	--	SYNTAX    INTEGER { readonly(1), readwrite(2), administrator(3) }
	--	ACCESS    read-write
	--	STATUS    mandatory
	--	DESCRIPTION
	--		"Web Level"
	--	::= { swhUserEntry 12 }


-- UserAuthentication(2).RADIUSConfiguration(2)

	swhRADIUSConfiguration
		OBJECT IDENTIFIER ::= { swhUserAuthentication 2 }

	swhRADIUSEn OBJECT-TYPE
		SYNTAX    INTEGER { disable(0), enable(1) }
		ACCESS    read-write
		STATUS    mandatory
		DESCRIPTION
			"Enable or disable RADIUS client."
		::= { swhRADIUSConfiguration 1 }

	swhRADIUSSecretKey OBJECT-TYPE
		SYNTAX    DisplayString
		ACCESS    read-write
		STATUS    mandatory
		DESCRIPTION
			"the plain code for encrypting data."
		::= { swhRADIUSConfiguration 2 }

	swhRADIUSPort OBJECT-TYPE
		SYNTAX    INTEGER (1025..65535)
		ACCESS    read-write
		STATUS    mandatory
		DESCRIPTION
			"RADIUS server port."
		::= { swhRADIUSConfiguration 3 }

	swhRADIUSRetry OBJECT-TYPE
		SYNTAX    INTEGER (0..2)
		ACCESS    read-write
		STATUS    mandatory
		DESCRIPTION
			"The retry times of connecting to an unknown RADIUS server."
		::= { swhRADIUSConfiguration 5 }

	swhRADIUSIPAddr OBJECT-TYPE
		SYNTAX    IpAddress 
		ACCESS    read-write
		STATUS    mandatory
		DESCRIPTION
			"RADIUS server ip address."
		::= { swhRADIUSConfiguration 6 }

	swhRADIUSIPAddr2 OBJECT-TYPE
		SYNTAX    IpAddress 
		ACCESS    read-write
		STATUS    mandatory
		DESCRIPTION
			"2th RADIUS server ip address."
		::= { swhRADIUSConfiguration 7 }


-- NetworkManagement(3)

	swhNetworkConfiguration
		OBJECT IDENTIFIER ::= { swhNetworkManagement 1 }
	swhSystemServiceConfiguration
		OBJECT IDENTIFIER ::= { swhNetworkManagement 2 }
	swhRS232TelnetConsoleConfiguration
		OBJECT IDENTIFIER ::= { swhNetworkManagement 3 }
	swhTimeServerConfiguration
		OBJECT IDENTIFIER ::= { swhNetworkManagement 7 }
	swhTimeRange
		OBJECT IDENTIFIER ::= { swhNetworkManagement 10 }
	swhDeviceCommunity
		OBJECT IDENTIFIER ::= { swhNetworkManagement 4 }
	swhTrapDestination
		OBJECT IDENTIFIER ::= { swhNetworkManagement 5 }
	swhTrapConfiguration
		OBJECT IDENTIFIER ::= { swhNetworkManagement 6 }
	swhMalAttemptLogConfiguration
		OBJECT IDENTIFIER ::= { swhNetworkManagement 8 }


-- NetworkManagement(3).NetworkConfiguration(1)

	swhNetMacAddr OBJECT-TYPE
		SYNTAX    MacAddress
		ACCESS    read-only
		STATUS    mandatory
		DESCRIPTION
			"The media-dependent `physical' address."
		::= { swhNetworkConfiguration 1 }

	swhNetType OBJECT-TYPE
		SYNTAX    INTEGER { manual(1), dhcp(0) }
		ACCESS    read-write
		STATUS    mandatory
		DESCRIPTION
			"auto will get ip from DHCP"
		::= { swhNetworkConfiguration 2 }

	swhNetIPAddr OBJECT-TYPE
		SYNTAX    IpAddress
		ACCESS    read-write
		STATUS    mandatory
		DESCRIPTION
			"The IP address to which this entry's addressing
			 information pertains."
		::= { swhNetworkConfiguration 3 }

	swhNetIPMask OBJECT-TYPE
		SYNTAX    IpAddress
		ACCESS    read-write
		STATUS    mandatory
		DESCRIPTION
			"The subnet mask associated with the IP address of
			 this entry.  The value of the mask is an IP
			 address with all the network bits set to 1 and all
			 the hosts bits set to 0."
		::= { swhNetworkConfiguration 4 }

	swhNetGateway OBJECT-TYPE
		SYNTAX    IpAddress
		ACCESS    read-write
		STATUS    mandatory
		DESCRIPTION
			"Gateway"
		::= { swhNetworkConfiguration 5 }

	swhNetCurrentIPAddr OBJECT-TYPE
		SYNTAX    IpAddress
		ACCESS    read-only
		STATUS    mandatory
		DESCRIPTION
			"The Current IP address to which this entry's addressing
			 information pertains."
		::= { swhNetworkConfiguration 10 }

	swhNetCurrentIPMask OBJECT-TYPE
		SYNTAX    IpAddress
		ACCESS    read-only
		STATUS    mandatory
		DESCRIPTION
			"The Current subnet mask associated with the IP address of
			 this entry.  The value of the mask is an IP
			 address with all the network bits set to 1 and all
			 the hosts bits set to 0."
		::= { swhNetworkConfiguration 11 }

	swhNetCurrentGateway OBJECT-TYPE
		SYNTAX    IpAddress
		ACCESS    read-only
		STATUS    mandatory
		DESCRIPTION
			"Current Gateway"
		::= { swhNetworkConfiguration 12 }

--	swhNetIPSourceBinding OBJECT-TYPE
--		SYNTAX    INTEGER { disable(0), enable(1) }
--		ACCESS    read-write
--		STATUS    mandatory
--		DESCRIPTION
--			"Security IP enable or disable"
--		::= { swhNetworkConfiguration 20 }


-- NetworkManagement(3).NetworkConfiguration(1).IPSourceBindingTable(21)

--	swhNetIPSourceBindingTable OBJECT-TYPE
--		SYNTAX    SEQUENCE OF SWHNetIPSourceBindingEntry
--		ACCESS    not-accessible
--		STATUS    mandatory
--		DESCRIPTION
--			"Table of Security IP information."
--		::= { swhNetworkConfiguration 21 }

	-- Table Entry
--	swhNetIPSourceBindingEntry OBJECT-TYPE
--		SYNTAX    SWHNetIPSourceBindingEntry
--		ACCESS    not-accessible
--		STATUS    mandatory
--		DESCRIPTION
--			"An entry in the table, containing information
--			 about SNMP agent.
--			 Only Administrator can read this table"
--		INDEX    { swhNetIPSourceBindingIndex }
--		::= { swhNetIPSourceBindingTable 1 }

--	SWHNetIPSourceBindingEntry ::=
--		SEQUENCE {
--			swhNetIPSourceBindingIndex
--				INTEGER,
--			swhNetIPSourceBindingState
--				INTEGER,
--			swhNetIPSourceBindingIPAddress
--				DisplayString,
--			swhNetIPSourceBindingDelete
--				INTEGER
--		}

--	swhNetIPSourceBindingIndex OBJECT-TYPE
--		SYNTAX    INTEGER 
--		ACCESS    read-only
--		STATUS    mandatory
--		DESCRIPTION
--			"Security IP index"
--		::= { swhNetIPSourceBindingEntry 1 }

--	swhNetIPSourceBindingState OBJECT-TYPE
--		SYNTAX    INTEGER { disable(0), enable(1) }
--		ACCESS    read-write
--		STATUS    mandatory
--		DESCRIPTION
--			"Security IP State"
--		::= { swhNetIPSourceBindingEntry 3 }

--	swhNetIPSourceBindingIPAddress OBJECT-TYPE
--		SYNTAX    DisplayString
--		ACCESS    read-write
--		STATUS    mandatory
--		DESCRIPTION
--			"Security IPv4 Address"
--		::= { swhNetIPSourceBindingEntry 4 }

--	swhNetIPSourceBindingDelete OBJECT-TYPE
--		SYNTAX    INTEGER { normal(0), delete(1) }
--		ACCESS    read-write
--		STATUS    mandatory
--		DESCRIPTION
--			"Delete this entry."
--		::= { swhNetIPSourceBindingEntry 10 }


-- NetworkManagement(3).NetworkConfiguration(1).NetCurrentDNSServerIPorIPv6Addr(28)


-- NetworkManagement(3).NetworkConfiguration(1).NetDNSServerIPv6(30)


-- NetworkManagement(3).NetworkConfiguration(1).NetIPv6(32)


-- NetworkManagement(3).NetworkConfiguration(1).NetCurrentIPv6GlobalAddrTable(45)


-- NetworkManagement(3).SystemServiceConfiguration(2)

	swhServiceTelnetThreadEn OBJECT-TYPE
		SYNTAX    INTEGER { disable(0), enable(1) }
		ACCESS    read-write
		STATUS    mandatory
		DESCRIPTION
			"Enable Telnet Thread,
			 Only Administrator can write this page"
		::= { swhSystemServiceConfiguration 1 }

	swhServiceSSHThreadEn OBJECT-TYPE
		SYNTAX    INTEGER { disable(0), enable(1) }
		ACCESS    read-write
		STATUS    mandatory
		DESCRIPTION
			"Enable SSH Thread,
			 Only Administrator can write this page"
		::= { swhSystemServiceConfiguration 10 }

	swhServiceSNMPThreadEn OBJECT-TYPE
		SYNTAX    INTEGER { disable(0), enable(1) }
		ACCESS    read-write
		STATUS    mandatory
		DESCRIPTION
			"Enable SNMP Thread
			 Only Administrator can write this page"
		::= { swhSystemServiceConfiguration 3 }

	swhServiceWebThreadEn OBJECT-TYPE
		SYNTAX    INTEGER { disable(0), enable(1) }
		ACCESS    read-write
		STATUS    mandatory
		DESCRIPTION
			"Enable Web Thread
			 Only Administrator can write this page"
		::= { swhSystemServiceConfiguration 4 }

--	swhServiceBluetoothThreadEn OBJECT-TYPE
--		SYNTAX    INTEGER { disable(0), enable(1) }
--		ACCESS    read-write
--		STATUS    mandatory
--		DESCRIPTION
--			"Enable Bluetooth Thread
--			 Only Administrator can write this page"
--		::= { swhSystemServiceConfiguration 5 }


-- NetworkManagement(3).RS232TelnetConsoleConfiguration(3)

	swhRS232BaudRate OBJECT-TYPE
		SYNTAX    INTEGER 
		ACCESS    read-only
		STATUS    mandatory
		DESCRIPTION
			"RS232 Baud Rate  (bps)
			9600 14400 19200 38400 57600 115200 are avaivable value
			Only Administrator can write this page"
		::= { swhRS232TelnetConsoleConfiguration 2 }

	swhRS232StopBits OBJECT-TYPE
	--	SYNTAX    INTEGER { "1"(1), "1.5"(2), "2"(3) }
		SYNTAX    INTEGER { x1(1), x1-5(2), x2(3) }
		ACCESS    read-only
		STATUS    mandatory
		DESCRIPTION
			"RS232 Stop Bits
			Only Administrator can write this page"
		::= { swhRS232TelnetConsoleConfiguration 3 }

	swhRS232ParityCheck OBJECT-TYPE
		SYNTAX    INTEGER { none(0), even(1), odd(2), mark(3), space(4) }
		ACCESS    read-only
		STATUS    mandatory
		DESCRIPTION
			"RS232 Parity Check
			Only Administrator can write this page"
		::= { swhRS232TelnetConsoleConfiguration 4 }

	swhRS232WordLength OBJECT-TYPE
		SYNTAX    INTEGER
		ACCESS    read-only
		STATUS    mandatory
		DESCRIPTION
			"RS232 Word Length
			5 6 7 8 are available value
			Only Administrator can write this page"
		::= { swhRS232TelnetConsoleConfiguration 5 }

	swhRS232FlowControl OBJECT-TYPE
		SYNTAX    INTEGER { none(0), hardware(1) }
		ACCESS    read-only
		STATUS    mandatory
		DESCRIPTION
			"RS232 Flow Control
			Only Administrator can write this page"
		::= { swhRS232TelnetConsoleConfiguration 6 }

	swhTelnetPort OBJECT-TYPE
		SYNTAX    INTEGER 
		ACCESS    read-write
		STATUS    mandatory
		DESCRIPTION
			"telnet port 1-65534
			Only Administrator can write this page"
		::= { swhRS232TelnetConsoleConfiguration 8 }

	swhTimeOutTime OBJECT-TYPE
		SYNTAX    INTEGER (1..1440)
		ACCESS    read-write
		STATUS    mandatory
		DESCRIPTION
			"Time out time.
			1-1440 are valid value.
			Only Administrator can write this page"
		::= { swhRS232TelnetConsoleConfiguration 11 }

	swhTimeOutTimeUnit OBJECT-TYPE
		SYNTAX    INTEGER { seconds(0), minutes(1) }
		ACCESS    read-write
		STATUS    mandatory
		DESCRIPTION
			"System Time Out Unit.
			(0 : seconds, 1 : minutes)"
		::= { swhRS232TelnetConsoleConfiguration 12 }

	swhWebTimeOutTime OBJECT-TYPE
		SYNTAX    INTEGER (1..1440)
		ACCESS    read-write
		STATUS    mandatory
		DESCRIPTION
			"Web Time out time.
			1-1440 are valid value."
		::= { swhRS232TelnetConsoleConfiguration 13 }


-- NetworkManagement(3).DeviceCommunity(4)

	swhAgentTable OBJECT-TYPE
		SYNTAX    SEQUENCE OF SWHAgentEntry
		ACCESS    not-accessible
		STATUS    mandatory
		DESCRIPTION
			"Table of Agent information."
		::= { swhDeviceCommunity 1 }

	-- Table Entry
	swhAgentEntry OBJECT-TYPE
		SYNTAX    SWHAgentEntry
		ACCESS    not-accessible
		STATUS    mandatory
		DESCRIPTION
			"An entry in the table, containing information
			 about SNMP agent.
			 Only Administrator can read this table"
		INDEX    { swhAgentIndex }
		::= { swhAgentTable 1 }

	SWHAgentEntry ::=
		SEQUENCE {
			swhAgentIndex
				INTEGER,
			swhAgentValid
				INTEGER,
			swhAgentEnable
				INTEGER,
			swhAgentCommunity
				DisplayString,
		--	swhAgentPassword
		--		DisplayString,
			swhAgentDescription
				DisplayString,
		--	swhAgentIPSecurity
		--		INTEGER,
		--	swhAgentIPAddr
		--		IpAddress,
			swhAgentSNMPLevel
				INTEGER,
			swhAgentDelete
				INTEGER
		}

	swhAgentIndex OBJECT-TYPE
		SYNTAX    INTEGER 
		ACCESS    read-only
		STATUS    mandatory
		DESCRIPTION
			"Agent index"
		::= { swhAgentEntry 1 }

	swhAgentValid OBJECT-TYPE
		SYNTAX    INTEGER { valid(1), invalid(0) }
		ACCESS    read-only
		STATUS    mandatory
		DESCRIPTION
			"Valid"
		::= { swhAgentEntry 2 }

	swhAgentEnable OBJECT-TYPE
		SYNTAX    INTEGER { disable(0), enable(1) }
		ACCESS    read-write
		STATUS    mandatory
		DESCRIPTION
			"Enable"
		::= { swhAgentEntry 3 }

	swhAgentCommunity OBJECT-TYPE
		SYNTAX    DisplayString (SIZE (0..255))
		ACCESS    read-write
		STATUS    mandatory
		DESCRIPTION
			"SNMP community Name"
		::= { swhAgentEntry 4 }

	--swhAgentPassword OBJECT-TYPE
	--	SYNTAX    DisplayString (SIZE (0..255))
	--	ACCESS    read-write
	--	STATUS    mandatory
	--	DESCRIPTION
	--		"Password, this field not used, reserve"
	--	::= { swhAgentEntry 5 }

	swhAgentDescription OBJECT-TYPE
		SYNTAX    DisplayString (SIZE (0..255))
		ACCESS    read-write
		STATUS    mandatory
		DESCRIPTION
			"Description"
		::= { swhAgentEntry 6 }

	--swhAgentIPSecurity OBJECT-TYPE
	--	SYNTAX    INTEGER { disable(0), enable(1) }
	--	ACCESS    read-write
	--	STATUS    mandatory
	--	DESCRIPTION
	--		"IP Security, if enable, 
	--		 only swhAgentIPAddr could walk or set SNMP"
	--	::= { swhAgentEntry 7 }

	--swhAgentIPAddr OBJECT-TYPE
	--	SYNTAX    IpAddress
	--	ACCESS    read-write
	--	STATUS    mandatory
	--	DESCRIPTION
	--		"The IP address from which could walk or set SNMP."
	--	::= { swhAgentEntry 8 }

	swhAgentSNMPLevel OBJECT-TYPE
		SYNTAX    INTEGER { readonly(1), readwrite(2), administrator(3) }
		ACCESS    read-write
		STATUS    mandatory
		DESCRIPTION
			"SNMP Level"
		::= { swhAgentEntry 9 }

	swhAgentDelete OBJECT-TYPE
		SYNTAX    INTEGER { normal(0), delete(1) }
		ACCESS    read-write
		STATUS    mandatory
		DESCRIPTION
			"Delete this entry."
		::= { swhAgentEntry 10 }

	swhSNMPv3AgentTable OBJECT-TYPE
		SYNTAX    SEQUENCE OF SWHSNMPv3AgentEntry
		ACCESS    not-accessible
		STATUS    mandatory
		DESCRIPTION
			"Table of Agent information."
		::= { swhDeviceCommunity 5 }

	-- Table Entry
	swhSNMPv3AgentEntry OBJECT-TYPE
		SYNTAX    SWHSNMPv3AgentEntry
		ACCESS    not-accessible
		STATUS    mandatory
		DESCRIPTION
			"An entry in the table, containing information
			 about SNMP agent.
			 Only Administrator can read this table"
		INDEX    { swhSNMPv3AgentIndex }
		::= { swhSNMPv3AgentTable 1 }

	SWHSNMPv3AgentEntry ::=
		SEQUENCE {
			swhSNMPv3AgentIndex
				INTEGER,
			swhSNMPv3AgentValid
				INTEGER,
		--	swhSNMPv3AgentEnable
		--		INTEGER,
			swhSNMPv3AgentUserName
				DisplayString,
			swhSNMPv3AgentAuthentication
				INTEGER,
			swhSNMPv3AgentAuthPassword
				DisplayString,
			swhSNMPv3AgentPrivate
				INTEGER,
			swhSNMPv3AgentPrivPassword
				DisplayString
		--	swhSNMPv3AgentSNMPLevel
		--		INTEGER
		--	swhAgentDelete
		--		INTEGER
		}

	swhSNMPv3AgentIndex OBJECT-TYPE
		SYNTAX    INTEGER 
		ACCESS    read-only
		STATUS    mandatory
		DESCRIPTION
			"Agent index"
		::= { swhSNMPv3AgentEntry 1 }

	swhSNMPv3AgentValid OBJECT-TYPE
		SYNTAX    INTEGER { valid(1), invalid(0) }
		ACCESS    read-only
		STATUS    mandatory
		DESCRIPTION
			"Valid"
		::= { swhSNMPv3AgentEntry 3 }

--	swhSNMPv3AgentEnable OBJECT-TYPE
--		SYNTAX    INTEGER { disable(0), enable(1) }
--		ACCESS    read-only
--		STATUS    mandatory
--		DESCRIPTION
--			"Enable"
--		::= { swhSNMPv3AgentEntry 5 }

	swhSNMPv3AgentUserName OBJECT-TYPE
		SYNTAX    DisplayString (SIZE (0..255))
		ACCESS    read-only
		STATUS    mandatory
		DESCRIPTION
			"SNMPv3 UserName"
		::= { swhSNMPv3AgentEntry 7 }
		
	swhSNMPv3AgentAuthentication OBJECT-TYPE
		SYNTAX    INTEGER { None(0), MD5(1), SHA(2) }
		ACCESS    read-write
		STATUS    mandatory
		DESCRIPTION
			"Authentication"
		::= { swhSNMPv3AgentEntry 9 }

	swhSNMPv3AgentAuthPassword OBJECT-TYPE
		SYNTAX    DisplayString (SIZE (0..255))
		ACCESS    read-write
		STATUS    mandatory
		DESCRIPTION
			"Authentication Password"
		::= { swhSNMPv3AgentEntry 11 }

	swhSNMPv3AgentPrivate OBJECT-TYPE
		SYNTAX    INTEGER { None(0), DES(1) }
		ACCESS    read-write
		STATUS    mandatory
		DESCRIPTION
			"Authentication"
		::= { swhSNMPv3AgentEntry 12 }

	swhSNMPv3AgentPrivPassword OBJECT-TYPE
		SYNTAX    DisplayString (SIZE (0..255))
		ACCESS    read-write
		STATUS    mandatory
		DESCRIPTION
			"Authentication Password"
		::= { swhSNMPv3AgentEntry 13 }

--	swhSNMPv3AgentSNMPLevel OBJECT-TYPE
--		SYNTAX    INTEGER { None(0), readonly(1), readwrite(2), administrator(3) }
--		ACCESS    read-only
--		STATUS    mandatory
--		DESCRIPTION
--			"SNMPv3 Level"
--		::= { swhSNMPv3AgentEntry 17 }

	SWHSNMPv3AuthEntry ::=
		SEQUENCE {
			swhSNMPv3AgentIndex
				INTEGER,
			swhSNMPv3AgentValid
				INTEGER,
			swhSNMPv3AgentUserName
				DisplayString,
			swhSNMPv3AgentAuthentication
				INTEGER,
			swhSNMPv3AgentAuthPassword
				DisplayString
		}
		
		SWHSNMPv3PrivEntry ::=
		SEQUENCE {
			swhSNMPv3AgentIndex
				INTEGER,
			swhSNMPv3AgentValid
				INTEGER,
			swhSNMPv3AgentUserName
				DisplayString,
			swhSNMPv3AgentPrivate
				INTEGER,
			swhSNMPv3AgentPrivPassword
				DisplayString
		}


-- NetworkManagement(3).TrapDestination(5)

	swhTrapDestTable OBJECT-TYPE
		SYNTAX    SEQUENCE OF SWHTrapDestEntry
		ACCESS    not-accessible
		STATUS    mandatory
		DESCRIPTION
			"Table of Trap destination."
		::= { swhTrapDestination 1 }

	-- Table Entry
	swhTrapDestEntry OBJECT-TYPE
		SYNTAX    SWHTrapDestEntry
		ACCESS    not-accessible
		STATUS    mandatory
		DESCRIPTION
			"An entry in the table, containing information
			 about SNMP Trap Destination.
			 Only Administrator can read this table"
		INDEX    { swhTrapDestIndex }
		::= { swhTrapDestTable 1 }

	SWHTrapDestEntry ::=
		SEQUENCE {
			swhTrapDestIndex
				INTEGER,
		--	swhTrapDestValid
		--		INTEGER,
			swhTrapDestEnable
				INTEGER,
			swhTrapDestIPAddr
				IpAddress,
			swhTrapDestCommunity
				DisplayString
		}

	swhTrapDestIndex OBJECT-TYPE
		SYNTAX    INTEGER
		ACCESS    read-only
		STATUS    mandatory
		DESCRIPTION
			"Trap Destination index"
		::= { swhTrapDestEntry 1 }

	--swhTrapDestValid OBJECT-TYPE
	--	SYNTAX    INTEGER { valid(1), invalid(0) }
	--	ACCESS    read-only
	--	STATUS    mandatory
	--	DESCRIPTION
	--		"Valid"
	--	::= { swhTrapDestEntry 2 }

	swhTrapDestEnable OBJECT-TYPE
		SYNTAX    INTEGER { disable(0), enable(1) }
		ACCESS    read-write
		STATUS    mandatory
		DESCRIPTION
			"Enable"
		::= { swhTrapDestEntry 3 }

	swhTrapDestCommunity OBJECT-TYPE
		SYNTAX    DisplayString (SIZE (0..255))
		ACCESS    read-write
		STATUS    mandatory
		DESCRIPTION
			"SNMP community Name"
		::= { swhTrapDestEntry 4 }

	swhTrapDestIPAddr OBJECT-TYPE
		SYNTAX    IpAddress
		ACCESS    read-write
		STATUS    mandatory
		DESCRIPTION
			"The IP address SNMP TRAP send to"
		::= { swhTrapDestEntry 8 }


-- NetworkManagement(3).TrapConfiguration(6)

	swhTrapColdStart OBJECT-TYPE
		SYNTAX    INTEGER { disable(0), enable(1) }
		ACCESS    read-write
		STATUS    mandatory
		DESCRIPTION
			"cold start trap enable or disable"
		::= { swhTrapConfiguration 1 }

	swhTrapWarmStart OBJECT-TYPE
		SYNTAX    INTEGER { disable(0), enable(1) }
		ACCESS    read-write
		STATUS    mandatory
		DESCRIPTION
			"warm start trap enable or disable"
		::= { swhTrapConfiguration 2 }

	swhTrapAuthenticationFailure OBJECT-TYPE
		SYNTAX    INTEGER { disable(0), enable(1) }
		ACCESS    read-write
		STATUS    mandatory
		DESCRIPTION
			"authentication failure trap enable or disable"
		::= { swhTrapConfiguration 3 }

	swhTrapPortLink OBJECT-TYPE
		SYNTAX    INTEGER { disable(0), enable(1) }
		ACCESS    read-write
		STATUS    mandatory
		DESCRIPTION
			"port link up/down trap enable or disable"
		::= { swhTrapConfiguration 4 }

	swhTrapPowerFailure OBJECT-TYPE
		SYNTAX    INTEGER { disable(0), enable(1) }
		ACCESS    read-write
		STATUS    mandatory
		DESCRIPTION
			"local machine system power down trap enable or disable"
		::= { swhTrapConfiguration 5 }

--	swhTrapBroadcastStorm OBJECT-TYPE
--		SYNTAX    INTEGER { disable(0), enable(1) }
--		ACCESS    read-write
--		STATUS    mandatory
--		DESCRIPTION
--			"Broadcast storm trap enable or disable, when broadcast packets are over upper limit,
--			 broadcast storm trap will be sent."
--		::= { swhTrapConfiguration 6 }

--	swhTrapBroadcastUpperLimit OBJECT-TYPE
--		SYNTAX    INTEGER (0..148810)
--		ACCESS    read-write
--		STATUS    mandatory
--		DESCRIPTION
--			"Broadcast packets upper limit, unit is Packets/Sec."
--		::= { swhTrapConfiguration 7 }

--	swhTrapCATVState OBJECT-TYPE
--		SYNTAX    INTEGER { disable(0), enable(1) }
--		ACCESS    read-write
--		STATUS    mandatory
--		DESCRIPTION
--			"CATV state trap enable or disable."
--		::= { swhTrapConfiguration 8 }

	swhTrapAutoBackup OBJECT-TYPE
		SYNTAX    INTEGER { disable(0), enable(1) }
		ACCESS    read-write
		STATUS    mandatory
		DESCRIPTION
			"auto-backup trap enable or disable"
		::= { swhTrapConfiguration 13 }

	swhTrapFastRedundancy OBJECT-TYPE
		SYNTAX    INTEGER { disable(0), enable(1) }
		ACCESS    read-write
		STATUS    mandatory
		DESCRIPTION
			"Fast Redundancy port link up/down trap enable or disable"
		::= { swhTrapConfiguration 75 }

--	swhTrapBatteryMode OBJECT-TYPE
--		SYNTAX    INTEGER { disable(0), enable(1) }
--		ACCESS    read-write
--		STATUS    mandatory
--		DESCRIPTION
--			"Battery mode trap enable or disable"
--		::= { swhTrapConfiguration 56 }


-- NetworkManagement(3).TimeServerConfiguration(7)

	swhTimeSync OBJECT-TYPE
		SYNTAX    INTEGER { disable(0), enable(1) }
		ACCESS    read-write
		STATUS    mandatory
		DESCRIPTION
			"Time Synchronization"
		::= { swhTimeServerConfiguration 1 }

	swhTimeServerIPAddr OBJECT-TYPE
		SYNTAX    IpAddress
		ACCESS    read-write
		STATUS    mandatory
		DESCRIPTION
			"time server ip address."
		::= { swhTimeServerConfiguration 2 }

	swhTimeServerIPAddr2 OBJECT-TYPE
		SYNTAX    IpAddress
		ACCESS    read-write
		STATUS    mandatory
		DESCRIPTION
			"2th time server ip address."
		::= { swhTimeServerConfiguration 3 }

	swhTimeSyncInterval OBJECT-TYPE
		SYNTAX    INTEGER { hour1(1),
		                    hour2(2),
		                    hour3(3),
		                    hour4(4),
		                    hour6(5),
		                    hour8(6),
		                    hour12(7),
		                    hour24(8)
		                  }
		ACCESS    read-write
		STATUS    mandatory
		DESCRIPTION
			"Time Synchronization Interval, unit is min."
		::= { swhTimeServerConfiguration 4 }

	swhTimeZoneIndex OBJECT-TYPE
		SYNTAX    INTEGER
		ACCESS    read-write
		STATUS    mandatory
		DESCRIPTION
			"time zone
			 0:   GMT-11:00  Apia
			 1:   GMT-10:00  Honolulu
			 2:   GMT-9:00  Anchorage
			 3:   GMT-8:00  Vancouver
			 4:   GMT-8:00  San Francisco
			 5:   GMT-8:00  Seattle
			 6:   GMT-8:00  Los Angeles
			 7:   GMT-7:00  Phoenix
			 8:   GMT-7:00  Aklavik
			 9:   GMT-7:00  Edmonton
			10:   GMT-7:00  Denver
			11:   GMT-6:00  Guatemala
			12:   GMT-6:00  San Salvador
			13:   GMT-6:00  Tegucigalpa
			14:   GMT-6:00  Managua
			15:   GMT-6:00  Mexico City
			16:   GMT-6:00  Winnipeg
			17:   GMT-6:00  Houston
			18:   GMT-6:00  Minneapolis
			19:   GMT-6:00  St. Paul
			20:   GMT-6:00  New Orleans
			21:   GMT-6:00  Chicago
			22:   GMT-6:00  Montgomery
			23:   GMT-5:00  Indianapolis
			24:   GMT-5:00  Lima
			25:   GMT-5:00  Kingston
			26:   GMT-5:00  Bogota
			27:   GMT-5:00  Atlanta
			28:   GMT-5:00  Detroit
			29:   GMT-5:00  Havana
			30:   GMT-5:00  Toronto
			31:   GMT-5:00  Nassau
			32:   GMT-5:00  Washington DC
			33:   GMT-5:00  Ottawa
			34:   GMT-5:00  Philadelphia
			35:   GMT-5:00  New York
			36:   GMT-5:00  Montreal
			37:   GMT-5:00  Boston
			38:   GMT-4:00  Santo Domingo
			39:   GMT-4:00  La Paz
			40:   GMT-4:00  Caracas
			41:   GMT-4:00  San Juan
			42:   GMT-4:00  Santiago
			43:   GMT-4:00  Halifax
			44:   GMT-4:00  Asuncion
			45:   GMT-3:00  Buenos Aires
			46:   GMT-3:00  Montevideo
			47:   GMT-3:00  Brasilia
			48:   GMT-3:00  Sao Paulo
			49:   GMT-3:00  Rio de Janeiro
			50:   GMT-2:00  Fernando de Noronha
			51:   GMT-1:00  Praia
			52:   GMT       Reykjavik
			53:   GMT       Casablanca
			54:   GMT       Lisbon
			55:   GMT       Dublin
			56:   GMT       London
			57:   GMT+1:00  Lagos
			58:   GMT+1:00  Algiers
			59:   GMT+1:00  Madrid
			60:   GMT+1:00  Barcelona
			61:   GMT+1:00  Paris
			62:   GMT+1:00  Brussels
			63:   GMT+1:00  Amsterdam
			64:   GMT+1:00  Geneva
			65:   GMT+1:00  Zurich
			66:   GMT+1:00  Frankfurt
			67:   GMT+1:00  Oslo
			68:   GMT+1:00  Copenhagen
			69:   GMT+1:00  Rome
			70:   GMT+1:00  Berlin
			71:   GMT+1:00  Prague
			72:   GMT+1:00  Zagreb
			73:   GMT+1:00  Vienna
			74:   GMT+1:00  Stockholm
			75:   GMT+1:00  Cape Town
			76:   GMT+1:00  Budapest
			77:   GMT+1:00  Belgrade
			78:   GMT+1:00  Warsaw
			79:   GMT+2:00  Johannesburg
			80:   GMT+2:00  Harare
			81:   GMT+2:00  Cairo
			82:   GMT+2:00  Jerusalem
			83:   GMT+2:00  Sofia
			84:   GMT+2:00  Athens
			85:   GMT+2:00  Tallinn
			86:   GMT+2:00  Helsinki
			87:   GMT+2:00  Bucharest
			88:   GMT+2:00  Minsk
			89:   GMT+2:00  Istanbul
			90:   GMT+2:00  Kyiv
			91:   GMT+2:00  Odesa
			92:   GMT+2:00  Khartoum
			93:   GMT+2:00  Ankara
			94:   GMT+2:00  Beirut
			95:   GMT+2:00  Amman
			96:   GMT+3:00  Nairobi
			97:   GMT+3:00  Addis Ababa
			98:   GMT+3:00  Baghdad
			99:   GMT+3:00  Aden
			100:  GMT+3:00  Riyadh
			101:  GMT+3:00  Antananarivo
			102:  GMT+3:00  Kuwait City
			103:  GMT+3:00  Moscow
			104:  GMT+4:00  Abu Dhabi
			105:  GMT+5:00  Karachi
			106:  GMT+5:00  Tashkent
			107:  GMT+5:00  Islamabad
			108:  GMT+5:00  Lahore
			109:  GMT+5:30  Mumbai
			110:  GMT+5:30  New Delhi
			111:  GMT+5:30  Kolkata
			112:  GMT+6:00  Dhaka
			113:  GMT+7:00  Bangkok
			114:  GMT+7:00  Hanoi
			115:  GMT+7:00  Jakarta
			116:  GMT+8:00  Kuala Lumpur
			117:  GMT+8:00  Singapore
			118:  GMT+8:00  Hong Kong
			119:  GMT+8:00  Perth
			120:  GMT+8:00  Beijing
			121:  GMT+8:00  Manila
			122:  GMT+8:00  Shanghai
			123:  GMT+8:00  Taipei
			124:  GMT+9:00  Seoul
			125:  GMT+9:00  Tokyo
			126:  GMT+10:00  Melbourne
			127:  GMT+10:00  Canberra
			128:  GMT+10:00  Sydney
			129:  GMT+10:00  Brisbane
			130:  GMT+10:00  Vladivostok
			131:  GMT+11:00  Kolonia
			132:  GMT+12:00  Suva
			133:  GMT+12:00  Kamchatka
			134:  GMT+12:00  Wellington
			135:  GMT+12:00  Anadyr
			"
		::= { swhTimeServerConfiguration 5 }

	swhTimeZone OBJECT-TYPE
		SYNTAX    DisplayString
		ACCESS    read-only
		STATUS    mandatory
		DESCRIPTION
			"TimeZone."
		::= { swhTimeServerConfiguration 6 }

	swhTimeDST OBJECT-TYPE
		SYNTAX    INTEGER { disable(0), recurring(1), data(2)}
		ACCESS    read-write
		STATUS    mandatory
		DESCRIPTION
			"disable or enable Daylight Saving Time."
		::= { swhTimeServerConfiguration 7 }

	swhTimeDSTRange OBJECT-TYPE
		SYNTAX    DisplayString
		ACCESS    read-write
		STATUS    mandatory
		DESCRIPTION
			"time range when Daylight Saving Time (swhTimeDST) is enable"
		::= { swhTimeServerConfiguration 9 }


-- NetworkManagement(3).MalAttemptLogConfiguration(8)

	swhLogServer OBJECT-TYPE
		SYNTAX    INTEGER { disable(0), enable(1) }
		ACCESS    read-write
		STATUS    mandatory
		DESCRIPTION
			"Log Server"
		::= { swhMalAttemptLogConfiguration 1 }

	swhLogSNTPStatus OBJECT-TYPE
		SYNTAX    INTEGER { disable(0), enable(1) }
		ACCESS    read-only
		STATUS    mandatory
		DESCRIPTION
			"SNTP Status"
		::= { swhMalAttemptLogConfiguration 3 }

	swhLogServerIPAddr1 OBJECT-TYPE
		SYNTAX    IpAddress
		ACCESS    read-write
		STATUS    mandatory
		DESCRIPTION
			"log server ip address 1."
		::= { swhMalAttemptLogConfiguration 4 }

	swhLogServerIPAddr2 OBJECT-TYPE
		SYNTAX    IpAddress
		ACCESS    read-write
		STATUS    mandatory
		DESCRIPTION
			"log server ip address 2."
		::= { swhMalAttemptLogConfiguration 5 }

	swhLogServerIPAddr3 OBJECT-TYPE
		SYNTAX    IpAddress
		ACCESS    read-write
		STATUS    mandatory
		DESCRIPTION
			"log server ip address 3."
		::= { swhMalAttemptLogConfiguration 6 }


-- NetworkManagement(3).TimeRange(10)

	swhTimeRangeTable OBJECT-TYPE
		SYNTAX    SEQUENCE OF SWHTimeRangeEntry
		ACCESS    not-accessible
		STATUS    mandatory
		DESCRIPTION
			"Table of time range."
		::= { swhTimeRange 1 }

	-- Table Entry
	swhTimeRangeEntry OBJECT-TYPE
		SYNTAX    SWHTimeRangeEntry
		ACCESS    not-accessible
		STATUS    mandatory
		DESCRIPTION
			"An entry in the table, containing information
			 about time range."
		INDEX    { swhTimeRangeIndex }
		::= { swhTimeRangeTable 1 }

	SWHTimeRangeEntry ::=
		SEQUENCE {
			swhTimeRangeIndex
				INTEGER,
			swhTimeRangeName
				DisplayString,
			swhTimeRangeAbsoluteStartHour
				DisplayString,
			swhTimeRangeAbsoluteStartMinute
				DisplayString,
			swhTimeRangeAbsoluteStartDate
				INTEGER,
			swhTimeRangeAbsoluteStartMonth
				INTEGER,
			swhTimeRangeAbsoluteStartYear
				INTEGER,
			swhTimeRangeAbsoluteStartReset
				INTEGER,
			swhTimeRangeAbsoluteEndHour
				DisplayString,
			swhTimeRangeAbsoluteEndMinute
				DisplayString,
			swhTimeRangeAbsoluteEndDate
				INTEGER,
			swhTimeRangeAbsoluteEndMonth
				INTEGER,
			swhTimeRangeAbsoluteEndYear
				INTEGER,
			swhTimeRangeAbsoluteEndReset
				INTEGER,
			swhTimeRangePeriodic1StartHour
				DisplayString,
			swhTimeRangePeriodic1StartMinute
				DisplayString,
			swhTimeRangePeriodic1StartDay
				INTEGER,
			swhTimeRangePeriodic1EndHour
				DisplayString,
			swhTimeRangePeriodic1EndMinute
				DisplayString,
			swhTimeRangePeriodic1EndDay
				INTEGER,
			swhTimeRangePeriodic1Delete
				INTEGER,
			swhTimeRangePeriodic2StartHour
				DisplayString,
			swhTimeRangePeriodic2StartMinute
				DisplayString,
			swhTimeRangePeriodic2StartDay
				INTEGER,
			swhTimeRangePeriodic2EndHour
				DisplayString,
			swhTimeRangePeriodic2EndMinute
				DisplayString,
			swhTimeRangePeriodic2EndDay
				INTEGER,
			swhTimeRangePeriodic2Delete
				INTEGER,
			swhTimeRangePeriodicList1StartHour
				DisplayString,
			swhTimeRangePeriodicList1StartMinute
				DisplayString,
			swhTimeRangePeriodicList1EndHour
				DisplayString,
			swhTimeRangePeriodicList1EndMinute
				DisplayString,
			swhTimeRangePeriodicList1Sun
				INTEGER,
			swhTimeRangePeriodicList1Mon
				INTEGER,
			swhTimeRangePeriodicList1Tue
				INTEGER,
			swhTimeRangePeriodicList1Wed
				INTEGER,
			swhTimeRangePeriodicList1Thr
				INTEGER,
			swhTimeRangePeriodicList1Fri
				INTEGER,
			swhTimeRangePeriodicList1Sat
				INTEGER,
			swhTimeRangePeriodicList1Delete
				INTEGER,
			swhTimeRangePeriodicList2StartHour
				DisplayString,
			swhTimeRangePeriodicList2StartMinute
				DisplayString,
			swhTimeRangePeriodicList2EndHour
				DisplayString,
			swhTimeRangePeriodicList2EndMinute
				DisplayString,
			swhTimeRangePeriodicList2Sun
				INTEGER,
			swhTimeRangePeriodicList2Mon
				INTEGER,
			swhTimeRangePeriodicList2Tue
				INTEGER,
			swhTimeRangePeriodicList2Wed
				INTEGER,
			swhTimeRangePeriodicList2Thr
				INTEGER,
			swhTimeRangePeriodicList2Fri
				INTEGER,
			swhTimeRangePeriodicList2Sat
				INTEGER,
			swhTimeRangePeriodicList2Delete
				INTEGER,
			swhTimeRangeDelete
				INTEGER
		}

	swhTimeRangeIndex OBJECT-TYPE
		SYNTAX    INTEGER
		ACCESS    read-only
		STATUS    mandatory
		DESCRIPTION
			"time range index"
		::= { swhTimeRangeEntry 1 }

	swhTimeRangeName OBJECT-TYPE
		SYNTAX    DisplayString
		ACCESS    read-write
		STATUS    mandatory
		DESCRIPTION
			"Name(32 characters)"
		::= { swhTimeRangeEntry 3 }

	swhTimeRangeAbsoluteStartHour OBJECT-TYPE
		SYNTAX    DisplayString
		ACCESS    read-write
		STATUS    mandatory
		DESCRIPTION
			"Absolute Start Hour(00-23)"
		::= { swhTimeRangeEntry 4 }

	swhTimeRangeAbsoluteStartMinute OBJECT-TYPE
		SYNTAX    DisplayString
		ACCESS    read-write
		STATUS    mandatory
		DESCRIPTION
			"Absolute Start Minute(00-59)"
		::= { swhTimeRangeEntry 5 }

	swhTimeRangeAbsoluteStartDate OBJECT-TYPE
		SYNTAX    INTEGER
		ACCESS    read-write
		STATUS    mandatory
		DESCRIPTION
			"Absolute Start Date(1-31)"
		::= { swhTimeRangeEntry 6 }

	swhTimeRangeAbsoluteStartMonth OBJECT-TYPE
		SYNTAX    INTEGER { JAN(1), FEB(2), MAR(3), APR(4), MAY(5), JUN(6), JUL(7), AUG(8), SEP(9), OCT(10), NOV(11), DEC(12) }
		ACCESS    read-write
		STATUS    mandatory
		DESCRIPTION
			"Absolute Start Month(1-12)"
		::= { swhTimeRangeEntry 7 }

	swhTimeRangeAbsoluteStartYear OBJECT-TYPE
		SYNTAX    INTEGER
		ACCESS    read-write
		STATUS    mandatory
		DESCRIPTION
			"Absolute Start Year(2xxx)"
		::= { swhTimeRangeEntry 8 }

	swhTimeRangeAbsoluteStartReset OBJECT-TYPE
		SYNTAX    INTEGER { normal(0), reset(1) }
		ACCESS    read-write
		STATUS    mandatory
		DESCRIPTION
			"Absolute Start Reset"
		::= { swhTimeRangeEntry 9 }

	swhTimeRangeAbsoluteEndHour OBJECT-TYPE
		SYNTAX    DisplayString
		ACCESS    read-write
		STATUS    mandatory
		DESCRIPTION
			"Absolute End Hour(00-23)"
		::= { swhTimeRangeEntry 10 }

	swhTimeRangeAbsoluteEndMinute OBJECT-TYPE
		SYNTAX    DisplayString
		ACCESS    read-write
		STATUS    mandatory
		DESCRIPTION
			"Absolute End Minute(00-59)"
		::= { swhTimeRangeEntry 11 }

	swhTimeRangeAbsoluteEndDate OBJECT-TYPE
		SYNTAX    INTEGER
		ACCESS    read-write
		STATUS    mandatory
		DESCRIPTION
			"Absolute End Date(1-31)"
		::= { swhTimeRangeEntry 12 }

	swhTimeRangeAbsoluteEndMonth OBJECT-TYPE
		SYNTAX    INTEGER { JAN(1), FEB(2), MAR(3), APR(4), MAY(5), JUN(6), JUL(7), AUG(8), SEP(9), OCT(10), NOV(11), DEC(12) }
		ACCESS    read-write
		STATUS    mandatory
		DESCRIPTION
			"Absolute End Month(1-12)"
		::= { swhTimeRangeEntry 13 }

	swhTimeRangeAbsoluteEndYear OBJECT-TYPE
		SYNTAX    INTEGER
		ACCESS    read-write
		STATUS    mandatory
		DESCRIPTION
			"Absolute End Year(2xxx)"
		::= { swhTimeRangeEntry 14 }

	swhTimeRangeAbsoluteEndReset OBJECT-TYPE
		SYNTAX    INTEGER { normal(0), reset(1) }
		ACCESS    read-write
		STATUS    mandatory
		DESCRIPTION
			"Absolute End Reset"
		::= { swhTimeRangeEntry 15 }

	swhTimeRangePeriodic1StartHour OBJECT-TYPE
		SYNTAX    DisplayString
		ACCESS    read-write
		STATUS    mandatory
		DESCRIPTION
			"Periodic1 Start Hour(00-23)"
		::= { swhTimeRangeEntry 16 }

	swhTimeRangePeriodic1StartMinute OBJECT-TYPE
		SYNTAX    DisplayString
		ACCESS    read-write
		STATUS    mandatory
		DESCRIPTION
			"Periodic1 Start Minute(00-59)"
		::= { swhTimeRangeEntry 17 }

	swhTimeRangePeriodic1StartDay OBJECT-TYPE
		SYNTAX    INTEGER { Sun(0), Mon(1), Tue(2), Wed(3), Thu(4), Fri(5), Sat(6) }
		ACCESS    read-write
		STATUS    mandatory
		DESCRIPTION
			"Periodic1 Start Day(Sun, Mon, Tue, Wed, Thu, Fri, Sat)"
		::= { swhTimeRangeEntry 18 }

	swhTimeRangePeriodic1EndHour OBJECT-TYPE
		SYNTAX    DisplayString
		ACCESS    read-write
		STATUS    mandatory
		DESCRIPTION
			"Periodic1 End Hour(00-23)"
		::= { swhTimeRangeEntry 19 }

	swhTimeRangePeriodic1EndMinute OBJECT-TYPE
		SYNTAX    DisplayString
		ACCESS    read-write
		STATUS    mandatory
		DESCRIPTION
			"Periodic1 End Minute(00-59)"
		::= { swhTimeRangeEntry 20 }

	swhTimeRangePeriodic1EndDay OBJECT-TYPE
		SYNTAX    INTEGER { Sun(0), Mon(1), Tue(2), Wed(3), Thu(4), Fri(5), Sat(6) }
		ACCESS    read-write
		STATUS    mandatory
		DESCRIPTION
			"Periodic1 End Day(Sun, Mon, Tue, Wed, Thu, Fri, Sat)"
		::= { swhTimeRangeEntry 21 }

	swhTimeRangePeriodic1Delete OBJECT-TYPE
		SYNTAX    INTEGER { normal(0), delete(1) }
		ACCESS    read-write
		STATUS    mandatory
		DESCRIPTION
			"Periodic1 Delete"
		::= { swhTimeRangeEntry 22 }

	swhTimeRangePeriodic2StartHour OBJECT-TYPE
		SYNTAX    DisplayString
		ACCESS    read-write
		STATUS    mandatory
		DESCRIPTION
			"Periodic2 Start Hour(00-23)"
		::= { swhTimeRangeEntry 23 }

	swhTimeRangePeriodic2StartMinute OBJECT-TYPE
		SYNTAX    DisplayString
		ACCESS    read-write
		STATUS    mandatory
		DESCRIPTION
			"Periodic2 Start Minute(00-59)"
		::= { swhTimeRangeEntry 24 }

	swhTimeRangePeriodic2StartDay OBJECT-TYPE
		SYNTAX    INTEGER { Sun(0), Mon(1), Tue(2), Wed(3), Thu(4), Fri(5), Sat(6) }
		ACCESS    read-write
		STATUS    mandatory
		DESCRIPTION
			"Periodic2 Start Day(Sun, Mon, Tue, Wed, Thu, Fri, Sat)"
		::= { swhTimeRangeEntry 25 }

	swhTimeRangePeriodic2EndHour OBJECT-TYPE
		SYNTAX    DisplayString
		ACCESS    read-write
		STATUS    mandatory
		DESCRIPTION
			"Periodic2 End Hour(00-23)"
		::= { swhTimeRangeEntry 26 }

	swhTimeRangePeriodic2EndMinute OBJECT-TYPE
		SYNTAX    DisplayString
		ACCESS    read-write
		STATUS    mandatory
		DESCRIPTION
			"Periodic2 End Minute(00-59)"
		::= { swhTimeRangeEntry 27 }

	swhTimeRangePeriodic2EndDay OBJECT-TYPE
		SYNTAX    INTEGER { Sun(0), Mon(1), Tue(2), Wed(3), Thu(4), Fri(5), Sat(6) }
		ACCESS    read-write
		STATUS    mandatory
		DESCRIPTION
			"Periodic2 End Day(Sun, Mon, Tue, Wed, Thu, Fri, Sat)"
		::= { swhTimeRangeEntry 28 }

	swhTimeRangePeriodic2Delete OBJECT-TYPE
		SYNTAX    INTEGER { normal(0), delete(1) }
		ACCESS    read-write
		STATUS    mandatory
		DESCRIPTION
			"Periodic1 Delete"
		::= { swhTimeRangeEntry 29 }

	swhTimeRangePeriodicList1StartHour OBJECT-TYPE
		SYNTAX    DisplayString
		ACCESS    read-write
		STATUS    mandatory
		DESCRIPTION
			"Periodic List1 Start Hour(00-23)"
		::= { swhTimeRangeEntry 30 }

	swhTimeRangePeriodicList1StartMinute OBJECT-TYPE
		SYNTAX    DisplayString
		ACCESS    read-write
		STATUS    mandatory
		DESCRIPTION
			"Periodic List1 Start Minute(00-59)"
		::= { swhTimeRangeEntry 31 }

	swhTimeRangePeriodicList1EndHour OBJECT-TYPE
		SYNTAX    DisplayString
		ACCESS    read-write
		STATUS    mandatory
		DESCRIPTION
			"Periodic1 End Hour(00-23)"
		::= { swhTimeRangeEntry 32 }

	swhTimeRangePeriodicList1EndMinute OBJECT-TYPE
		SYNTAX    DisplayString
		ACCESS    read-write
		STATUS    mandatory
		DESCRIPTION
			"Periodic1 End Minute(00-59)"
		::= { swhTimeRangeEntry 33 }

	swhTimeRangePeriodicList1Sun OBJECT-TYPE
		SYNTAX    INTEGER { b(0), v(1) }
		ACCESS    read-write
		STATUS    mandatory
		DESCRIPTION
			"b:Blocked  v:Member"
		::= { swhTimeRangeEntry 34 }

	swhTimeRangePeriodicList1Mon OBJECT-TYPE
		SYNTAX    INTEGER { b(0), v(1) }
		ACCESS    read-write
		STATUS    mandatory
		DESCRIPTION
			"b:Blocked  v:Member"
		::= { swhTimeRangeEntry 35 }

	swhTimeRangePeriodicList1Tue OBJECT-TYPE
		SYNTAX    INTEGER { b(0), v(1) }
		ACCESS    read-write
		STATUS    mandatory
		DESCRIPTION
			"b:Blocked  v:Member"
		::= { swhTimeRangeEntry 36 }

	swhTimeRangePeriodicList1Wed OBJECT-TYPE
		SYNTAX    INTEGER { b(0), v(1) }
		ACCESS    read-write
		STATUS    mandatory
		DESCRIPTION
			"b:Blocked  v:Member"
		::= { swhTimeRangeEntry 37 }

	swhTimeRangePeriodicList1Thr OBJECT-TYPE
		SYNTAX    INTEGER { b(0), v(1) }
		ACCESS    read-write
		STATUS    mandatory
		DESCRIPTION
			"b:Blocked  v:Member"
		::= { swhTimeRangeEntry 38 }

	swhTimeRangePeriodicList1Fri OBJECT-TYPE
		SYNTAX    INTEGER { b(0), v(1) }
		ACCESS    read-write
		STATUS    mandatory
		DESCRIPTION
			"b:Blocked  v:Member"
		::= { swhTimeRangeEntry 39 }

	swhTimeRangePeriodicList1Sat OBJECT-TYPE
		SYNTAX    INTEGER { b(0), v(1) }
		ACCESS    read-write
		STATUS    mandatory
		DESCRIPTION
			"b:Blocked  v:Member"
		::= { swhTimeRangeEntry 40 }

	swhTimeRangePeriodicList1Delete OBJECT-TYPE
		SYNTAX    INTEGER { normal(0), delete(1) }
		ACCESS    read-write
		STATUS    mandatory
		DESCRIPTION
			"Periodic1 Delete"
		::= { swhTimeRangeEntry 41 }

	swhTimeRangePeriodicList2StartHour OBJECT-TYPE
		SYNTAX    DisplayString
		ACCESS    read-write
		STATUS    mandatory
		DESCRIPTION
			"Periodic List2 Start Hour(00-23)"
		::= { swhTimeRangeEntry 42 }

	swhTimeRangePeriodicList2StartMinute OBJECT-TYPE
		SYNTAX    DisplayString
		ACCESS    read-write
		STATUS    mandatory
		DESCRIPTION
			"Periodic List2 Start Minute(00-59)"
		::= { swhTimeRangeEntry 43 }

	swhTimeRangePeriodicList2EndHour OBJECT-TYPE
		SYNTAX    DisplayString
		ACCESS    read-write
		STATUS    mandatory
		DESCRIPTION
			"Periodic List2 End Hour(00-23)"
		::= { swhTimeRangeEntry 44 }

	swhTimeRangePeriodicList2EndMinute OBJECT-TYPE
		SYNTAX    DisplayString
		ACCESS    read-write
		STATUS    mandatory
		DESCRIPTION
			"Periodic List2 End Minute(00-59)"
		::= { swhTimeRangeEntry 45 }

	swhTimeRangePeriodicList2Sun OBJECT-TYPE
		SYNTAX    INTEGER { b(0), v(1) }
		ACCESS    read-write
		STATUS    mandatory
		DESCRIPTION
			"b:Blocked  v:Member"
		::= { swhTimeRangeEntry 46 }

	swhTimeRangePeriodicList2Mon OBJECT-TYPE
		SYNTAX    INTEGER { b(0), v(1) }
		ACCESS    read-write
		STATUS    mandatory
		DESCRIPTION
			"b:Blocked  v:Member"
		::= { swhTimeRangeEntry 47 }

	swhTimeRangePeriodicList2Tue OBJECT-TYPE
		SYNTAX    INTEGER { b(0), v(1) }
		ACCESS    read-write
		STATUS    mandatory
		DESCRIPTION
			"b:Blocked  v:Member"
		::= { swhTimeRangeEntry 48 }

	swhTimeRangePeriodicList2Wed OBJECT-TYPE
		SYNTAX    INTEGER { b(0), v(1) }
		ACCESS    read-write
		STATUS    mandatory
		DESCRIPTION
			"b:Blocked  v:Member"
		::= { swhTimeRangeEntry 49 }

	swhTimeRangePeriodicList2Thr OBJECT-TYPE
		SYNTAX    INTEGER { b(0), v(1) }
		ACCESS    read-write
		STATUS    mandatory
		DESCRIPTION
			"b:Blocked  v:Member"
		::= { swhTimeRangeEntry 50 }

	swhTimeRangePeriodicList2Fri OBJECT-TYPE
		SYNTAX    INTEGER { b(0), v(1) }
		ACCESS    read-write
		STATUS    mandatory
		DESCRIPTION
			"b:Blocked  v:Member"
		::= { swhTimeRangeEntry 51 }

	swhTimeRangePeriodicList2Sat OBJECT-TYPE
		SYNTAX    INTEGER { b(0), v(1) }
		ACCESS    read-write
		STATUS    mandatory
		DESCRIPTION
			"b:Blocked  v:Member"
		::= { swhTimeRangeEntry 52 }

	swhTimeRangePeriodicList2Delete OBJECT-TYPE
		SYNTAX    INTEGER { normal(0), delete(1) }
		ACCESS    read-write
		STATUS    mandatory
		DESCRIPTION
			"Periodic List2 Delete"
		::= { swhTimeRangeEntry 53 }

	swhTimeRangeDelete OBJECT-TYPE
		SYNTAX    INTEGER { normal(0), delete(1) }
		ACCESS    read-write
		STATUS    mandatory
		DESCRIPTION
			"Time range Delete"
		::= { swhTimeRangeEntry 56 }


-- SwitchManagement(4)

	swhSwitchConfiguration
		OBJECT IDENTIFIER ::= { swhSwitchManagement 1 }
	swhBroadcastStormControl
		OBJECT IDENTIFIER ::= { swhSwitchManagement 16 }
	swhPortConfiguration
		OBJECT IDENTIFIER ::= { swhSwitchManagement 2 }
	swhRateLimiting
		OBJECT IDENTIFIER ::= { swhSwitchManagement 10 }
	swhQoSPriority
		OBJECT IDENTIFIER ::= { swhSwitchManagement 30 }
	swhLinkAggregation
		OBJECT IDENTIFIER ::= { swhSwitchManagement 45 }
	swhRapidSpanningTree
		OBJECT IDENTIFIER ::= { swhSwitchManagement 40 }
	swh8021XConfiguration
		OBJECT IDENTIFIER ::= { swhSwitchManagement 55 }
	swhMacAddressManagement
		OBJECT IDENTIFIER ::= { swhSwitchManagement 35 }
	swhVLANConfiguration
		OBJECT IDENTIFIER ::= { swhSwitchManagement 4 }
	swhMirroringConfiguration
		OBJECT IDENTIFIER ::= { swhSwitchManagement 17 }
	swhIGMPSnooping
		OBJECT IDENTIFIER ::= { swhSwitchManagement 50 }
	swhLLDPConfiguration
		OBJECT IDENTIFIER ::= { swhSwitchManagement 14 }
	swhLoopDetection
		OBJECT IDENTIFIER ::= { swhSwitchManagement 13 }
	swhRingDetection
		OBJECT IDENTIFIER ::= { swhSwitchManagement 24 }
	swhFastRedundancy
		OBJECT IDENTIFIER ::= { swhSwitchManagement 91 }
--	swhDIDOConfiguration
--		OBJECT IDENTIFIER ::= { swhSwitchManagement 22 }
	swhPOEConfiguration
		OBJECT IDENTIFIER ::= { swhSwitchManagement 23 }
	swhSecurityConfiguration
		OBJECT IDENTIFIER ::= { swhSwitchManagement 80 }


-- SwitchManagement(4).SwitchConfiguration(1)

	swhSwitchAgingTime OBJECT-TYPE
		SYNTAX    INTEGER (7..600000)
		ACCESS    read-write
		STATUS    mandatory
		DESCRIPTION
			"Mac address Aging time(7-600000 secs)"
		::= { swhSwitchConfiguration 3 }

--	swhSwitch0180C2000000to0F OBJECT-TYPE
--		SYNTAX    INTEGER { not-filter(0), filter(1) }
--		ACCESS    read-write
--		STATUS    mandatory
--		DESCRIPTION
--			"Filter or not filter destination address 0180C2000000-0F."
--		::= { swhSwitchConfiguration 9 }

--	swhSwitch0180C2000020to2F OBJECT-TYPE
--		SYNTAX    INTEGER { not-filter(0), filter(1) }
--		ACCESS    read-write
--		STATUS    mandatory
--		DESCRIPTION
--			"Filter or not filter destination address 0180C2000020-2F."
--		::= { swhSwitchConfiguration 10 }

--	swhSwitch0180C2000010 OBJECT-TYPE
--		SYNTAX    INTEGER { not-filter(0), filter(1) }
--		ACCESS    read-write
--		STATUS    mandatory
--		DESCRIPTION
--			"Filter or not filter destination address 0180C2000010."
--		::= { swhSwitchConfiguration 11 }

	swhSwitchSFPPolling OBJECT-TYPE
		SYNTAX    INTEGER { disable(0), enable(1) }
		ACCESS    read-write
		STATUS    mandatory
		DESCRIPTION
			"enable or disable SFP Info. and DMI Polling."
		::= { swhSwitchConfiguration 51 }

	swhSwitchStatisticsPolling OBJECT-TYPE
		SYNTAX    INTEGER { disable(0), enable(1) }
		ACCESS    read-write
		STATUS    mandatory
		DESCRIPTION
			"enable or disable Statistics Counter Polling."
		::= { swhSwitchConfiguration 52 }


-- SwitchManagement(4).PortConfiguration(2)

	swhPortConfigTable OBJECT-TYPE
		SYNTAX    SEQUENCE OF SWHPortConfigEntry
		ACCESS    not-accessible
		STATUS    mandatory
		DESCRIPTION
			"Table of Port descriptive and status information."
		::= { swhPortConfiguration 1 }

	--swhSavePortConfiguration OBJECT-TYPE
	--	SYNTAX    INTEGER 
	--	ACCESS    write-only
	--	STATUS    mandatory
	--	DESCRIPTION
	--		"Save Port Configuration to Flash ROM"
	--	::= { swhPortConfiguration 2 }

	-- Table Entry
	swhPortConfigEntry OBJECT-TYPE
		SYNTAX    SWHPortConfigEntry
		ACCESS    not-accessible
		STATUS    mandatory
		DESCRIPTION
			"An entry in the table, containing information
			 about port config."
		INDEX    { swhPortConfigIndex }
		::= { swhPortConfigTable 1 }

	SWHPortConfigEntry ::=
		SEQUENCE {
			swhPortConfigIndex
				INTEGER,
			swhPortConfigMediaType
				INTEGER,
			swhPortConfigState
				INTEGER,
			swhPortConfigType
				INTEGER,
			swhPortConfigSpeed
				INTEGER,
			swhPortConfigDuplex
				INTEGER,
			swhPortConfigFlowControl
				INTEGER,
			swhPortConfigDescription
				DisplayString
		}

	swhPortConfigIndex OBJECT-TYPE
		SYNTAX    INTEGER
		ACCESS    read-only
		STATUS    mandatory
		DESCRIPTION
			"A unique value for each port."
		::= { swhPortConfigEntry 1 }

	swhPortConfigState OBJECT-TYPE
		SYNTAX    INTEGER { disable(0), enable(1) }
		ACCESS    read-write
		STATUS    mandatory
		DESCRIPTION
			"enable or disable port"
		::= { swhPortConfigEntry 2 }

	swhPortConfigType OBJECT-TYPE
		SYNTAX    INTEGER { auto-negotiation(0), manual(1) }
		ACCESS    read-write
		STATUS    mandatory
		DESCRIPTION
			"port type"
		::= { swhPortConfigEntry 3 }

	swhPortConfigSpeed OBJECT-TYPE
		SYNTAX    INTEGER { speed-10M(0), speed-100M(1), speed-1000M(2) }
		ACCESS    read-write
		STATUS    mandatory
		DESCRIPTION
			"port Speed  10 100 1000
			 it's configuration, NOT current speed, 
			 current speed is swhPortStatusSpeed under swhSwitchMonitor"
		::= { swhPortConfigEntry 4 }

	swhPortConfigDuplex OBJECT-TYPE
		SYNTAX    INTEGER { halfDuplex(0), fullDuplex(1) }
		ACCESS    read-write
		STATUS    mandatory
		DESCRIPTION
			"duplex
			 it's configuration, NOT current duplex, 
			 current duplex is swhPortStatusDuplex under swhSwitchMonitor"
		::= { swhPortConfigEntry 5 }

	swhPortConfigFlowControl OBJECT-TYPE
		SYNTAX    INTEGER { off(0), on(1) }
		ACCESS    read-write
		STATUS    mandatory
		DESCRIPTION
			"flow control"
		::= { swhPortConfigEntry 6 }

	swhPortConfigDescription OBJECT-TYPE
		SYNTAX    DisplayString
		ACCESS    read-write
		STATUS    mandatory
		DESCRIPTION
			"Port Description"
		::= { swhPortConfigEntry 7 }

	swhPortConfigMediaType OBJECT-TYPE
		SYNTAX    INTEGER { copper(0), fiber(1), auto-media(3) }
		ACCESS    read-write
		STATUS    mandatory
		DESCRIPTION
			"Port Media Type"
		::= { swhPortConfigEntry 8 }


-- SwitchManagement(4).PriorityAndRateLimitConfiguration(3)


-- SwitchManagement(4).VLANConfiguration(4)

	swhPortVLANConfiguration
		OBJECT IDENTIFIER ::= { swhVLANConfiguration 1 }

	swh8021QVLANConfiguration
		OBJECT IDENTIFIER ::= { swhVLANConfiguration 2 }

--	swhQinQVLANConfiguration
--		OBJECT IDENTIFIER ::= { swhVLANConfiguration 5 }


-- SwitchManagement(4).VLANConfiguration(4).PortVLANConfiguration(1)

	swhPortVLANConfigTable OBJECT-TYPE
		SYNTAX    SEQUENCE OF SWHPortVLANConfigEntry
		ACCESS    not-accessible
		STATUS    mandatory
		DESCRIPTION
			"Table of Port Based VLAN Configuration."
		::= { swhPortVLANConfiguration 1 }

	-- Table Entry
	swhPortVLANConfigEntry OBJECT-TYPE
		SYNTAX    SWHPortVLANConfigEntry
		ACCESS    not-accessible
		STATUS    mandatory
		DESCRIPTION
			"An entry in the table, containing information
			 about port based vlan config."
		INDEX    { swhPortVLANConfigIndex }
		::= { swhPortVLANConfigTable 1 }

	SWHPortVLANConfigEntry ::=
		SEQUENCE {
			swhPortVLANConfigIndex
				INTEGER,
			swhPortVLANConfigValid
				INTEGER,
			swhPortVLANConfigName
				DisplayString,
			swhPortVLANConfigPort1
				INTEGER,
			swhPortVLANConfigPort2
				INTEGER,
			swhPortVLANConfigPort3
				INTEGER,
			swhPortVLANConfigPort4
				INTEGER,
			swhPortVLANConfigPort5
				INTEGER,
			swhPortVLANConfigPort6
				INTEGER,
			swhPortVLANConfigPort7
				INTEGER,
			swhPortVLANConfigPort8
				INTEGER,
			swhPortVLANConfigPort9
				INTEGER,
			swhPortVLANConfigPort10
				INTEGER,
			swhPortVLANConfigCPU
				INTEGER,
			swhPortVLANConfigDelete
				INTEGER
		}

	swhPortVLANConfigIndex OBJECT-TYPE
		SYNTAX    INTEGER 
		ACCESS    read-only
		STATUS    mandatory
		DESCRIPTION
			"A unique value for each vlan."
		::= { swhPortVLANConfigEntry 1 }

	swhPortVLANConfigValid OBJECT-TYPE
		SYNTAX    INTEGER { invalid(0), valid(1) }
		ACCESS    read-only
		STATUS    mandatory
		DESCRIPTION
			"This vlan setting is valid or invalid."
		::= { swhPortVLANConfigEntry 2 }

	swhPortVLANConfigName OBJECT-TYPE
		SYNTAX    DisplayString
		ACCESS    read-write
		STATUS    mandatory
		DESCRIPTION
			"Port based vlan name."
		::= { swhPortVLANConfigEntry 4 }

	swhPortVLANConfigPort1 OBJECT-TYPE
		SYNTAX    INTEGER { b(0), v(1) }
		ACCESS    read-write
		STATUS    mandatory
		DESCRIPTION
			"b:Blocked  v:Member"
		::= { swhPortVLANConfigEntry 5 }

	swhPortVLANConfigPort2 OBJECT-TYPE
		SYNTAX    INTEGER { b(0), v(1) }
		ACCESS    read-write
		STATUS    mandatory
		DESCRIPTION
			"b:Blocked  v:Member"
		::= { swhPortVLANConfigEntry 6 }

	swhPortVLANConfigPort3 OBJECT-TYPE
		SYNTAX    INTEGER { b(0), v(1) }
		ACCESS    read-write
		STATUS    mandatory
		DESCRIPTION
			"b:Blocked  v:Member"
		::= { swhPortVLANConfigEntry 7 }

	swhPortVLANConfigPort4 OBJECT-TYPE
		SYNTAX    INTEGER { b(0), v(1) }
		ACCESS    read-write
		STATUS    mandatory
		DESCRIPTION
			"b:Blocked  v:Member"
		::= { swhPortVLANConfigEntry 8 }

	swhPortVLANConfigPort5 OBJECT-TYPE
		SYNTAX    INTEGER { b(0), v(1) }
		ACCESS    read-write
		STATUS    mandatory
		DESCRIPTION
			"b:Blocked  v:Member"
		::= { swhPortVLANConfigEntry 9 }

	swhPortVLANConfigPort6 OBJECT-TYPE
		SYNTAX    INTEGER { b(0), v(1) }
		ACCESS    read-write
		STATUS    mandatory
		DESCRIPTION
			"b:Blocked  v:Member"
		::= { swhPortVLANConfigEntry 10 }
		
	swhPortVLANConfigPort7 OBJECT-TYPE
		SYNTAX    INTEGER { b(0), v(1) }
		ACCESS    read-write
		STATUS    mandatory
		DESCRIPTION
			"b:Blocked  v:Member"
		::= { swhPortVLANConfigEntry 11 }
		
	swhPortVLANConfigPort8 OBJECT-TYPE
		SYNTAX    INTEGER { b(0), v(1) }
		ACCESS    read-write
		STATUS    mandatory
		DESCRIPTION
			"b:Blocked  v:Member"
		::= { swhPortVLANConfigEntry 12 }
		
	swhPortVLANConfigPort9 OBJECT-TYPE
		SYNTAX    INTEGER { b(0), v(1) }
		ACCESS    read-write
		STATUS    mandatory
		DESCRIPTION
			"b:Blocked  v:Member"
		::= { swhPortVLANConfigEntry 13 }
		
	swhPortVLANConfigPort10 OBJECT-TYPE
		SYNTAX    INTEGER { b(0), v(1) }
		ACCESS    read-write
		STATUS    mandatory
		DESCRIPTION
			"b:Blocked  v:Member"
		::= { swhPortVLANConfigEntry 14 }

	swhPortVLANConfigCPU OBJECT-TYPE
		SYNTAX    INTEGER { b(0), v(1) }
		ACCESS    read-write
		STATUS    mandatory
		DESCRIPTION
			"b:Blocked  v:Member"
		::= { swhPortVLANConfigEntry 55 }

	swhPortVLANConfigDelete OBJECT-TYPE
		SYNTAX    INTEGER { normal(0), delete(1) }
		ACCESS    read-write
		STATUS    mandatory
		DESCRIPTION
			"Delete this vlan setting."
		::= { swhPortVLANConfigEntry 56 }


-- SwitchManagement(4).VLANConfiguration(4).8021QVLANConfiguration(2)

	swh8021QTrunkVLAN
		OBJECT IDENTIFIER ::= { swh8021QVLANConfiguration 1 }

	swh8021QPortVLANConfig
		OBJECT IDENTIFIER ::= { swh8021QVLANConfiguration 2 }

	swh8021QManagementVLANConfig
		OBJECT IDENTIFIER ::= { swh8021QVLANConfiguration 5 }


-- SwitchManagement(4).VLANConfiguration(4).8021QVLANConfiguration(2).8021QTrunkVLAN(1)

	swh8021QTrunkVLANTable OBJECT-TYPE
		SYNTAX    SEQUENCE OF SWH8021QTrunkVLANEntry
		ACCESS    not-accessible
		STATUS    mandatory
		DESCRIPTION
			"Table of 802.1Q Trunk VLAN Configuration."
		::= { swh8021QTrunkVLAN 1 }

	-- Table Entry
	swh8021QTrunkVLANEntry OBJECT-TYPE
		SYNTAX    SWH8021QTrunkVLANEntry
		ACCESS    not-accessible
		STATUS    mandatory
		DESCRIPTION
			"An entry in the table, containing information
			about trunk vlan config."
		INDEX    { swh8021QTrunkVLANIndex }
		::= { swh8021QTrunkVLANTable 1 }

	SWH8021QTrunkVLANEntry ::=
		SEQUENCE {
			swh8021QTrunkVLANIndex
				INTEGER,
			swh8021QTrunkVLANValid
				INTEGER,
			swh8021QTrunkVLANVID
				INTEGER,
			swh8021QTrunkVLANName
				DisplayString,
			swh8021QTrunkVLANPort1
				INTEGER,
			swh8021QTrunkVLANPort2
				INTEGER,
			swh8021QTrunkVLANPort3
				INTEGER,
			swh8021QTrunkVLANPort4
				INTEGER,
			swh8021QTrunkVLANPort5
				INTEGER,
			swh8021QTrunkVLANPort6
				INTEGER,
			swh8021QTrunkVLANPort7
				INTEGER,
			swh8021QTrunkVLANPort8
				INTEGER,
			swh8021QTrunkVLANPort9
				INTEGER,
			swh8021QTrunkVLANPort10
				INTEGER,
			swh8021QTrunkVLANCPU
				INTEGER,
			swh8021QTrunkVLANDelete
				INTEGER
		}

	swh8021QTrunkVLANIndex OBJECT-TYPE
		SYNTAX    INTEGER (0..2147483647)
		ACCESS    read-only
		STATUS    mandatory
		DESCRIPTION
			"A unique value for each vlan."
		::= { swh8021QTrunkVLANEntry 1 }

	swh8021QTrunkVLANValid OBJECT-TYPE
		SYNTAX    INTEGER { invalid(0), valid(1) }
		ACCESS    read-only
		STATUS    mandatory
		DESCRIPTION
			"This vlan setting is valid or invalid."
		::= { swh8021QTrunkVLANEntry 2 }

	swh8021QTrunkVLANVID OBJECT-TYPE
		SYNTAX    INTEGER (1..4094)
		ACCESS    read-write
		STATUS    mandatory
		DESCRIPTION
			"VLAN ID"
		::= { swh8021QTrunkVLANEntry 3 }

	swh8021QTrunkVLANName OBJECT-TYPE
		SYNTAX    DisplayString
		ACCESS    read-write
		STATUS    mandatory
		DESCRIPTION
			"Port based vlan name."
		::= { swh8021QTrunkVLANEntry 4 }

	swh8021QTrunkVLANPort1 OBJECT-TYPE
		SYNTAX    INTEGER { b(0), v(1) }
		ACCESS    read-write
		STATUS    mandatory
		DESCRIPTION
			"b:Blocked  v:Member"
		::= { swh8021QTrunkVLANEntry 5 }

	swh8021QTrunkVLANPort2 OBJECT-TYPE
		SYNTAX    INTEGER { b(0), v(1) }
		ACCESS    read-write
		STATUS    mandatory
		DESCRIPTION
			"b:Blocked  v:Member"
		::= { swh8021QTrunkVLANEntry 6 }

	swh8021QTrunkVLANPort3 OBJECT-TYPE
		SYNTAX    INTEGER { b(0), v(1) }
		ACCESS    read-write
		STATUS    mandatory
		DESCRIPTION
			"b:Blocked  v:Member"
		::= { swh8021QTrunkVLANEntry 7 }

	swh8021QTrunkVLANPort4 OBJECT-TYPE
		SYNTAX    INTEGER { b(0), v(1) }
		ACCESS    read-write
		STATUS    mandatory
		DESCRIPTION
			"b:Blocked  v:Member"
		::= { swh8021QTrunkVLANEntry 8 }

	swh8021QTrunkVLANPort5 OBJECT-TYPE
		SYNTAX    INTEGER { b(0), v(1) }
		ACCESS    read-write
		STATUS    mandatory
		DESCRIPTION
			"b:Blocked  v:Member"
		::= { swh8021QTrunkVLANEntry 9 }

	swh8021QTrunkVLANPort6 OBJECT-TYPE
		SYNTAX    INTEGER { b(0), v(1) }
		ACCESS    read-write
		STATUS    mandatory
		DESCRIPTION
			"b:Blocked  v:Member"
		::= { swh8021QTrunkVLANEntry 10 }
		
	swh8021QTrunkVLANPort7 OBJECT-TYPE
		SYNTAX    INTEGER { b(0), v(1) }
		ACCESS    read-write
		STATUS    mandatory
		DESCRIPTION
			"b:Blocked  v:Member"
		::= { swh8021QTrunkVLANEntry 11 }
		
	swh8021QTrunkVLANPort8 OBJECT-TYPE
		SYNTAX    INTEGER { b(0), v(1) }
		ACCESS    read-write
		STATUS    mandatory
		DESCRIPTION
			"b:Blocked  v:Member"
		::= { swh8021QTrunkVLANEntry 12 }
		
	swh8021QTrunkVLANPort9 OBJECT-TYPE
		SYNTAX    INTEGER { b(0), v(1) }
		ACCESS    read-write
		STATUS    mandatory
		DESCRIPTION
			"b:Blocked  v:Member"
		::= { swh8021QTrunkVLANEntry 13 }
		
	swh8021QTrunkVLANPort10 OBJECT-TYPE
		SYNTAX    INTEGER { b(0), v(1) }
		ACCESS    read-write
		STATUS    mandatory
		DESCRIPTION
			"b:Blocked  v:Member"
		::= { swh8021QTrunkVLANEntry 14 }

	swh8021QTrunkVLANCPU OBJECT-TYPE
		SYNTAX    INTEGER { b(0), v(1) }
		ACCESS    read-only
		STATUS    mandatory
		DESCRIPTION
			"b:Blocked  v:Member"
		::= { swh8021QTrunkVLANEntry 55 }

	swh8021QTrunkVLANDelete OBJECT-TYPE
		SYNTAX    INTEGER { normal(0), delete(1) }
		ACCESS    read-write
		STATUS    mandatory
		DESCRIPTION
			"Delete this vlan setting."
		::= { swh8021QTrunkVLANEntry 56 }


-- SwitchManagement(4).VLANConfiguration(4).8021QVLANConfiguration(2).8021QPortVLANConfig(2)

	swh8021QCPUPVID OBJECT-TYPE
		SYNTAX    INTEGER (1..4094)
		ACCESS    read-only
		STATUS    mandatory
		DESCRIPTION
			"CPU Default Port VLAN ID."
		::= { swh8021QPortVLANConfig 1 }

	swh8021QVLANMode OBJECT-TYPE
		SYNTAX    INTEGER { portbase(1), tagvlan(2) }
		ACCESS    read-write
		STATUS    mandatory
		DESCRIPTION
			"802.1Q Tag VLAN Mode."
		::= { swh8021QPortVLANConfig 3 }

--	swh8021QPortIsolationPortList OBJECT-TYPE
--		SYNTAX    DisplayString (SIZE (0..255))
--		ACCESS    read-write
--		STATUS    mandatory
--		DESCRIPTION
--			"802.1Q Port Isolation Port List."
--		::= { swh8021QPortVLANConfig 6 }

--	swh8021QManagementPriority OBJECT-TYPE
--		SYNTAX    INTEGER (0..7)
--		ACCESS    read-write
--		STATUS    mandatory
--		DESCRIPTION
--			"Specify Management Priority(0-7)."
--		::= { swh8021QPortVLANConfig 11 }


-- SwitchManagement(4).VLANConfiguration(4).8021QVLANConfiguration(2).8021QPortVLANConfig(2).8021QPortVLANConfigTable(2)

	swh8021QPortVLANConfigTable OBJECT-TYPE
		SYNTAX    SEQUENCE OF SWH8021QPortVLANConfigEntry
		ACCESS    not-accessible
		STATUS    mandatory
		DESCRIPTION
			"Table of 802.1q VLAN ID."
		::= { swh8021QPortVLANConfig 2 }

	-- Table Entry
	swh8021QPortVLANConfigEntry OBJECT-TYPE
		SYNTAX    SWH8021QPortVLANConfigEntry
		ACCESS    not-accessible
		STATUS    mandatory
		DESCRIPTION
			"An entry in the table, containing information
			about Port VLAN ID "
		INDEX    { swh8021QPortIndex }
		::= { swh8021QPortVLANConfigTable 1 }

	SWH8021QPortVLANConfigEntry ::=
		SEQUENCE {
			swh8021QPortIndex
				INTEGER,
			swh8021QPortVLANMode
				INTEGER,
			swh8021QPortAccessVLAN
				INTEGER,
			swh8021QPortTrunkVLAN
				DisplayString
		}

	swh8021QPortIndex OBJECT-TYPE
		SYNTAX    INTEGER
		ACCESS    read-only
		STATUS    mandatory
		DESCRIPTION
			"A unique value for port index."
		::= { swh8021QPortVLANConfigEntry 1 }

	swh8021QPortAccessVLAN OBJECT-TYPE
		SYNTAX    INTEGER (1..4094)
		ACCESS    read-write
		STATUS    mandatory
		DESCRIPTION
			"Port Access VLAN ID(1-4094)."
		::= { swh8021QPortVLANConfigEntry 2 }

	swh8021QPortVLANMode OBJECT-TYPE
		SYNTAX    INTEGER { access(0), trunk(1), trunknative(2) }
		ACCESS    read-write
		STATUS    mandatory
		DESCRIPTION
			"Port VLAN mode."
		::= { swh8021QPortVLANConfigEntry 20 }

	swh8021QPortTrunkVLAN OBJECT-TYPE
		SYNTAX    DisplayString
		ACCESS    read-write
		STATUS    mandatory
		DESCRIPTION
			"Port Trunk VLAN ID member(1-4094)."
		::= { swh8021QPortVLANConfigEntry 25 }


-- SwitchManagement(4).VLANConfiguration(4).8021QVLANConfiguration(2).8021QPortVLANConfig(2).8021QVLANTranslation(15)


-- SwitchManagement(4).VLANConfiguration(4).8021QVLANConfiguration(2).8021QPortVLANConfig(3)


-- SwitchManagement(4).VLANConfiguration(4).8021QVLANConfiguration(2).8021QManagementVLANConfig(5)

	swh8021QManagementVLANConfigCPUVID OBJECT-TYPE
		SYNTAX    INTEGER (1..4094) 
		ACCESS    read-write
		STATUS    mandatory
		DESCRIPTION
			"CPU VLAN ID.(1-4094)"
		::= { swh8021QManagementVLANConfig 1 }

	swh8021QManagementVLANConfigVLANMode OBJECT-TYPE
		SYNTAX    INTEGER { access(0), trunk(1), trunknative(2) }
		ACCESS    read-write
		STATUS    mandatory
		DESCRIPTION
			"Aware is disable or enable"
		::= { swh8021QManagementVLANConfig 3 }

	swh8021QManagementVLANConfigPort1 OBJECT-TYPE
		SYNTAX    INTEGER { b(0), v(1) }
		ACCESS    read-write
		STATUS    mandatory
		DESCRIPTION
			"b:Blocked  v:Member"
		::= { swh8021QManagementVLANConfig 5 }

	swh8021QManagementVLANConfigPort2 OBJECT-TYPE
		SYNTAX    INTEGER { b(0), v(1) }
		ACCESS    read-write
		STATUS    mandatory
		DESCRIPTION
			"b:Blocked  v:Member"
		::= { swh8021QManagementVLANConfig 6 }

	swh8021QManagementVLANConfigPort3 OBJECT-TYPE
		SYNTAX    INTEGER { b(0), v(1) }
		ACCESS    read-write
		STATUS    mandatory
		DESCRIPTION
			"b:Blocked  v:Member"
		::= { swh8021QManagementVLANConfig 7 }

	swh8021QManagementVLANConfigPort4 OBJECT-TYPE
		SYNTAX    INTEGER { b(0), v(1) }
		ACCESS    read-write
		STATUS    mandatory
		DESCRIPTION
			"b:Blocked  v:Member"
		::= { swh8021QManagementVLANConfig 8 }

	swh8021QManagementVLANConfigPort5 OBJECT-TYPE
		SYNTAX    INTEGER { b(0), v(1) }
		ACCESS    read-write
		STATUS    mandatory
		DESCRIPTION
			"b:Blocked  v:Member"
		::= { swh8021QManagementVLANConfig 9 }

	swh8021QManagementVLANConfigPort6 OBJECT-TYPE
		SYNTAX    INTEGER { b(0), v(1) }
		ACCESS    read-write
		STATUS    mandatory
		DESCRIPTION
			"b:Blocked  v:Member"
		::= { swh8021QManagementVLANConfig 10 }
		
	swh8021QManagementVLANConfigPort7 OBJECT-TYPE
		SYNTAX    INTEGER { b(0), v(1) }
		ACCESS    read-write
		STATUS    mandatory
		DESCRIPTION
			"b:Blocked  v:Member"
		::= { swh8021QManagementVLANConfig 11 }
		
	swh8021QManagementVLANConfigPort8 OBJECT-TYPE
		SYNTAX    INTEGER { b(0), v(1) }
		ACCESS    read-write
		STATUS    mandatory
		DESCRIPTION
			"b:Blocked  v:Member"
		::= { swh8021QManagementVLANConfig 12 }
		
	swh8021QManagementVLANConfigPort9 OBJECT-TYPE
		SYNTAX    INTEGER { b(0), v(1) }
		ACCESS    read-write
		STATUS    mandatory
		DESCRIPTION
			"b:Blocked  v:Member"
		::= { swh8021QManagementVLANConfig 13 }
		
	swh8021QManagementVLANConfigPort10 OBJECT-TYPE
		SYNTAX    INTEGER { b(0), v(1) }
		ACCESS    read-write
		STATUS    mandatory
		DESCRIPTION
			"b:Blocked  v:Member"
		::= { swh8021QManagementVLANConfig 14 }


-- SwitchManagement(4).VLANConfiguration(4).8021QVLANConfiguration(2).8021QTransVID(8)


-- SwitchManagement(4).VLANConfiguration(4).8021QVLANConfiguration(2).8021QTransVID(8).8021QTransVIDTable(2)


-- SwitchManagement(4).VLANConfiguration(4).QinQVLANConfiguration(5)

--	swhQinQVLANMode OBJECT-TYPE
--		SYNTAX    INTEGER { disable(0), enable(1) }
--		ACCESS    read-write
--		STATUS    mandatory
--		DESCRIPTION
--			"QinQ Mode"
--		::= { swhQinQVLANConfiguration 1 }

--	swhQinQVLANEtherType OBJECT-TYPE
--		SYNTAX    DisplayString
--		ACCESS    read-write
--		STATUS    mandatory
--		DESCRIPTION
--			"QinQ VLAN Ether Type; 0x0000-0xFFFF"
--		::= { swhQinQVLANConfiguration 2 }

--	swhQinQVLANPassThroughMode OBJECT-TYPE
--		SYNTAX    INTEGER { disable(0), enable(1) }
--		ACCESS    read-write
--		STATUS    mandatory
--		DESCRIPTION
--			"QinQ Pass Through Mode"
--		::= { swhQinQVLANConfiguration 57 }

--	swhQinQVLANPassThroughVID OBJECT-TYPE
--		SYNTAX    INTEGER (1..4094)
--		ACCESS    read-write
--		STATUS    mandatory
--		DESCRIPTION
--			"QinQ Pass Through VLAN ID(1-4094)"
--		::= { swhQinQVLANConfiguration 59 }


-- SwitchManagement(4).VLANConfiguration(4).QinQVLANConfiguration(5).QinQVLANConfigTable(60)

--	swhQinQVLANConfigTable OBJECT-TYPE
--		SYNTAX    SEQUENCE OF SWHQinQVLANConfigEntry
--		ACCESS    not-accessible
--		STATUS    mandatory
--		DESCRIPTION
--			"Table of 802.1q VLAN ID."
--		::= { swhQinQVLANConfiguration 60 }

	-- Table Entry
--	swhQinQVLANConfigEntry OBJECT-TYPE
--		SYNTAX    SWHQinQVLANConfigEntry
--		ACCESS    not-accessible
--		STATUS    mandatory
--		DESCRIPTION
--			"An entry in the table, containing information
--			 about QinQ VLAN Config"
--		INDEX    { swhQinQVLANPortIndex }
--		::= { swhQinQVLANConfigTable 1 }

--	SWHQinQVLANConfigEntry ::=
--		SEQUENCE {
--			swhQinQVLANPortIndex
--				INTEGER,
--			swhQinQVLANPortName
--				DisplayString,
--			swhQinQVLANPortStagVID
--				INTEGER,
--			swhQinQVLANPortISPPort
--				INTEGER
--		}

--	swhQinQVLANPortIndex OBJECT-TYPE
--		SYNTAX    INTEGER 
--		ACCESS    read-only
--		STATUS    mandatory
--		DESCRIPTION
--			"A unique value for port index."
--		::= { swhQinQVLANConfigEntry 1 }

--	swhQinQVLANPortName OBJECT-TYPE
--		SYNTAX    DisplayString
--		ACCESS    read-only
--		STATUS    mandatory
--		DESCRIPTION
--			"Port Name"
--		::= { swhQinQVLANConfigEntry 3 }

--	swhQinQVLANPortStagVID OBJECT-TYPE
--		SYNTAX    INTEGER (1..4094)
--		ACCESS    read-write
--		STATUS    mandatory
--		DESCRIPTION
--			"Specify port Stag VLAN ID(1-4094)."
--		::= { swhQinQVLANConfigEntry 6 }

--	swhQinQVLANPortISPPort OBJECT-TYPE
--		SYNTAX    INTEGER { b(0), v(1) }
--		ACCESS    read-write
--		STATUS    mandatory
--		DESCRIPTION
--			"b:Blocked  v:Member"
--		::= { swhQinQVLANConfigEntry 7 }


-- SwitchManagement(4).VLANConfiguration(4).QinQVLANConfiguration(5).QinQVLANManagementStagVID(61)

--	swhQinQVLANManagementStagVID OBJECT-TYPE
--		SYNTAX    INTEGER (1..4094)
--		ACCESS    read-write
--		STATUS    mandatory
--		DESCRIPTION
--			"QinQ Management Stag VLAN ID(1-4094)"
--		::= { swhQinQVLANConfiguration 61 }


-- SwitchManagement(4).SpanningTreeProtocol(9)


-- SwitchManagement(4).RateLimiting(10)

	swhRateLimitingTable OBJECT-TYPE
		SYNTAX    SEQUENCE OF SWHRateLimitingEntry
		ACCESS    not-accessible
		STATUS    mandatory
		DESCRIPTION
			"Table of Rate Limit Configuration."
		::= { swhRateLimiting 2 }

	-- Table Entry
	swhRateLimitingEntry OBJECT-TYPE
		SYNTAX    SWHRateLimitingEntry
		ACCESS    not-accessible
		STATUS    mandatory
		DESCRIPTION
			"An entry in the table, containing information
			about Rate Limit config."
		INDEX    { swhRateLimitingIndex }
		::= { swhRateLimitingTable 1 }

	SWHRateLimitingEntry ::=
		SEQUENCE {
			swhRateLimitingIndex
				INTEGER,
			swhRateLimitingIngress
				INTEGER,
		--	swhRateLimitingIngressBWName
		--		DisplayString,
			swhRateLimitingIngressBW
				INTEGER,
			swhRateLimitingIngressBandwidth
				DisplayString,
			swhRateLimitingEgress
				INTEGER,
		--	swhRateLimitingEgressBWName
		--		DisplayString,
			swhRateLimitingEgressBW
				INTEGER,
			swhRateLimitingEgressBandwidth
				DisplayString
		--	swhRateLimitingEgressQ0BWName
		--		DisplayString,
		--	swhRateLimitingEgressQ0BW
		--	    INTEGER,
		--	swhRateLimitingEgressQ1BWName
		--		DisplayString,
		--	swhRateLimitingEgressQ1BW
		--	    INTEGER,
		--	swhRateLimitingEgressQ2BWName
		--		DisplayString,
		--	swhRateLimitingEgressQ2BW
		--	    INTEGER,
		--	swhRateLimitingEgressQ3BWName
		--		DisplayString,
		--	swhRateLimitingEgressQ3BW
		--	    INTEGER
		}

	swhRateLimitingIndex OBJECT-TYPE
		SYNTAX    INTEGER
		ACCESS    read-only
		STATUS    mandatory
		DESCRIPTION
			"A unique value for each port."
		::= { swhRateLimitingEntry 1 }

	swhRateLimitingIngress OBJECT-TYPE
		SYNTAX    INTEGER { off(0), on(1) }
		ACCESS    read-write
		STATUS    mandatory
		DESCRIPTION
			"Ingress Rate is on or off."
		::= { swhRateLimitingEntry 2 }

--	swhRateLimitingIngressBWName OBJECT-TYPE
--		SYNTAX    DisplayString
--		ACCESS    read-only
--		STATUS    mandatory
--		DESCRIPTION
--			"Ingress Bandwidth Name (bps)."
--		::= { swhRateLimitingEntry 3 }

	swhRateLimitingIngressBW OBJECT-TYPE
		SYNTAX    INTEGER
		ACCESS    read-write
		STATUS    mandatory
		DESCRIPTION
			"Ingress Bandwidth (32-1000000Kbps)"
		::= { swhRateLimitingEntry 4 }

	swhRateLimitingEgress OBJECT-TYPE
		SYNTAX    INTEGER { off(0), on(1) }
		ACCESS    read-write
		STATUS    mandatory
		DESCRIPTION
			"Egress Rate is on or off."
		::= { swhRateLimitingEntry 5 }

--	swhRateLimitingEgressBWName OBJECT-TYPE
--		SYNTAX    DisplayString
--		ACCESS    read-only
--		STATUS    mandatory
--		DESCRIPTION
--			"Egress Bandwidth Name (bps)."
--		::= { swhRateLimitingEntry 6 }

	swhRateLimitingEgressBW OBJECT-TYPE
		SYNTAX    INTEGER
		ACCESS    read-write
		STATUS    mandatory
		DESCRIPTION
			"Egress Bandwidth (32-1000000Kbps)"
		::= { swhRateLimitingEntry 7 }

	-- Queue Rate
--	swhRateLimitingEgressQ0BWName OBJECT-TYPE
--		SYNTAX    DisplayString
--		ACCESS    read-only
--		STATUS    mandatory
--		DESCRIPTION
--			"Egress Q0 Bandwidth Name (bps)."
--		::= { swhRateLimitingEntry 20 }

--	swhRateLimitingEgressQ0BW OBJECT-TYPE
--		SYNTAX    INTEGER
--		ACCESS    read-write
--		STATUS    mandatory
--		DESCRIPTION
--			"Egress Q0 Bandwidth(32-1000000Kbps)"
--		::= { swhRateLimitingEntry 21 }

--	swhRateLimitingEgressQ1BWName OBJECT-TYPE
--		SYNTAX    DisplayString
--		ACCESS    read-only
--		STATUS    mandatory
--		DESCRIPTION
--			"Egress Q1 Bandwidth Name (bps)."
--		::= { swhRateLimitingEntry 22 }

--	swhRateLimitingEgressQ1BW OBJECT-TYPE
--		SYNTAX    INTEGER
--		ACCESS    read-write
--		STATUS    mandatory
--		DESCRIPTION
--			"Egress Q1 Bandwidth(32-1000000Kbps)"
--		::= { swhRateLimitingEntry 23 }

--	swhRateLimitingEgressQ2BWName OBJECT-TYPE
--		SYNTAX    DisplayString
--		ACCESS    read-only
--		STATUS    mandatory
--		DESCRIPTION
--			"Egress Q2 Bandwidth Name (bps)."
--		::= { swhRateLimitingEntry 24 }

--	swhRateLimitingEgressQ2BW OBJECT-TYPE
--		SYNTAX    INTEGER
--		ACCESS    read-write
--		STATUS    mandatory
--		DESCRIPTION
--			"Egress Q2 Bandwidth(32-1000000Kbps)"
--		::= { swhRateLimitingEntry 25 }

--	swhRateLimitingEgressQ3BWName OBJECT-TYPE
--		SYNTAX    DisplayString
--		ACCESS    read-only
--		STATUS    mandatory
--		DESCRIPTION
--			"Egress Q3 Bandwidth Name (bps)."
--		::= { swhRateLimitingEntry 26 }

--	swhRateLimitingEgressQ3BW OBJECT-TYPE
--		SYNTAX    INTEGER
--		ACCESS    read-write
--		STATUS    mandatory
--		DESCRIPTION
--			"Egress Q3 Bandwidth(32-1000000Kbps)"
--		::= { swhRateLimitingEntry 27 }

	-- Bandwidth
	swhRateLimitingIngressBandwidth OBJECT-TYPE
		SYNTAX    DisplayString
		ACCESS    read-only
		STATUS    mandatory
		DESCRIPTION
			"Ingress Bandwidth(bps)."
		::= { swhRateLimitingEntry 40 }

	swhRateLimitingEgressBandwidth OBJECT-TYPE
		SYNTAX    DisplayString
		ACCESS    read-only
		STATUS    mandatory
		DESCRIPTION
			"Egress Bandwidth(bps)."
		::= { swhRateLimitingEntry 41 }


-- SwitchManagement(4).L2ProtocolConverting(11)


-- SwitchManagement(4).CDPConfiguration(12)


-- SwitchManagement(4).LoopDetection(13)

	swhLoopConfigLoopDetection OBJECT-TYPE
		SYNTAX    INTEGER { disable(0), enable(1) }
		ACCESS    read-write
		STATUS    mandatory
		DESCRIPTION
			"Loop Detection is disable or enable."
		::= { swhLoopDetection 60 }

	swhLoopConfigDetectionInterval OBJECT-TYPE
		SYNTAX    INTEGER (1..180)
		ACCESS    read-write
		STATUS    mandatory
		DESCRIPTION
			"Sending Detected Interval(1-180 Secs)"
		::= { swhLoopDetection 63 }
		
	swhLoopConfigUnlockInterval OBJECT-TYPE
		SYNTAX    INTEGER (1..1440)
		ACCESS    read-write
		STATUS    mandatory
		DESCRIPTION
			"Looped port unlock-interval(1-1440 Mins).
			Set the interval to check the port is loop-free or not"
		::= { swhLoopDetection 64 }

	swhLoopConfigAllVLAN OBJECT-TYPE
		SYNTAX    INTEGER { disable(0), enable(1) }
		ACCESS    read-write
		STATUS    mandatory
		DESCRIPTION
			"All VLAN is disable or enable."
		::= { swhLoopDetection 69 }

	swhLoopConfigVLAN1 OBJECT-TYPE
		SYNTAX    INTEGER (1..4096)
		ACCESS    read-write
		STATUS    mandatory
		DESCRIPTION
			"Sending Detected VLAN ID(1-4096)"
		::= { swhLoopDetection 65 }

	swhLoopConfigVLAN2 OBJECT-TYPE
		SYNTAX    INTEGER (1..4096)
		ACCESS    read-write
		STATUS    mandatory
		DESCRIPTION
			"Sending Detected VLAN ID(1-4096)"
		::= { swhLoopDetection 66 }

	swhLoopConfigVLAN3 OBJECT-TYPE
		SYNTAX    INTEGER (1..4096)
		ACCESS    read-write
		STATUS    mandatory
		DESCRIPTION
			"Sending Detected VLAN ID(1-4096)"
		::= { swhLoopDetection 67 }

	swhLoopConfigVLAN4 OBJECT-TYPE
		SYNTAX    INTEGER (1..4096)
		ACCESS    read-write
		STATUS    mandatory
		DESCRIPTION
			"Sending Detected VLAN ID(1-4096)"
		::= { swhLoopDetection 68 }

	swhLoopConfigPort1 OBJECT-TYPE
		SYNTAX    INTEGER { b(0), v(1) }
		ACCESS    read-write
		STATUS    mandatory
		DESCRIPTION
			"b:Blocked  v:Member"
		::= { swhLoopDetection 1 }

	swhLoopConfigPort2 OBJECT-TYPE
		SYNTAX    INTEGER { b(0), v(1) }
		ACCESS    read-write
		STATUS    mandatory
		DESCRIPTION
			"b:Blocked  v:Member"
		::= { swhLoopDetection 2 }

	swhLoopConfigPort3 OBJECT-TYPE
		SYNTAX    INTEGER { b(0), v(1) }
		ACCESS    read-write
		STATUS    mandatory
		DESCRIPTION
			"b:Blocked  v:Member"
		::= { swhLoopDetection 3 }

	swhLoopConfigPort4 OBJECT-TYPE
		SYNTAX    INTEGER { b(0), v(1) }
		ACCESS    read-write
		STATUS    mandatory
		DESCRIPTION
			"b:Blocked  v:Member"
		::= { swhLoopDetection 4 }

	swhLoopConfigPort5 OBJECT-TYPE
		SYNTAX    INTEGER { b(0), v(1) }
		ACCESS    read-write
		STATUS    mandatory
		DESCRIPTION
			"b:Blocked  v:Member"
		::= { swhLoopDetection 5 }

	swhLoopConfigPort6 OBJECT-TYPE
		SYNTAX    INTEGER { b(0), v(1) }
		ACCESS    read-write
		STATUS    mandatory
		DESCRIPTION
			"b:Blocked  v:Member"
		::= { swhLoopDetection 6 }

	swhLoopConfigPort7 OBJECT-TYPE
		SYNTAX    INTEGER { b(0), v(1) }
		ACCESS    read-write
		STATUS    mandatory
		DESCRIPTION
			"b:Blocked  v:Member"
		::= { swhLoopDetection 7 }

	swhLoopConfigPort8 OBJECT-TYPE
		SYNTAX    INTEGER { b(0), v(1) }
		ACCESS    read-write
		STATUS    mandatory
		DESCRIPTION
			"b:Blocked  v:Member"
		::= { swhLoopDetection 8 }

	swhLoopConfigPort9 OBJECT-TYPE
		SYNTAX    INTEGER { b(0), v(1) }
		ACCESS    read-write
		STATUS    mandatory
		DESCRIPTION
			"b:Blocked  v:Member"
		::= { swhLoopDetection 9 }

	swhLoopConfigPort10 OBJECT-TYPE
		SYNTAX    INTEGER { b(0), v(1) }
		ACCESS    read-write
		STATUS    mandatory
		DESCRIPTION
			"b:Blocked  v:Member"
		::= { swhLoopDetection 10 }


-- SwitchManagement(4).LoopDetection(13).LoopConfigTable(80)


-- SwitchManagement(4).LLDPConfiguration(14)

	swhLLDPConfigPort1 OBJECT-TYPE
		SYNTAX    INTEGER { b(0), v(1) }
		ACCESS    read-write
		STATUS    mandatory
		DESCRIPTION
			"b:Blocked  v:Member"
		::= { swhLLDPConfiguration 1 }

	swhLLDPConfigPort2 OBJECT-TYPE
		SYNTAX    INTEGER { b(0), v(1) }
		ACCESS    read-write
		STATUS    mandatory
		DESCRIPTION
			"b:Blocked  v:Member"
		::= { swhLLDPConfiguration 2 }

	swhLLDPConfigPort3 OBJECT-TYPE
		SYNTAX    INTEGER { b(0), v(1) }
		ACCESS    read-write
		STATUS    mandatory
		DESCRIPTION
			"b:Blocked  v:Member"
		::= { swhLLDPConfiguration 3 }

	swhLLDPConfigPort4 OBJECT-TYPE
		SYNTAX    INTEGER { b(0), v(1) }
		ACCESS    read-write
		STATUS    mandatory
		DESCRIPTION
			"b:Blocked  v:Member"
		::= { swhLLDPConfiguration 4 }

	swhLLDPConfigPort5 OBJECT-TYPE
		SYNTAX    INTEGER { b(0), v(1) }
		ACCESS    read-write
		STATUS    mandatory
		DESCRIPTION
			"b:Blocked  v:Member"
		::= { swhLLDPConfiguration 5 }

	swhLLDPConfigPort6 OBJECT-TYPE
		SYNTAX    INTEGER { b(0), v(1) }
		ACCESS    read-write
		STATUS    mandatory
		DESCRIPTION
			"b:Blocked  v:Member"
		::= { swhLLDPConfiguration 6 }

	swhLLDPConfigPort7 OBJECT-TYPE
		SYNTAX    INTEGER { b(0), v(1) }
		ACCESS    read-write
		STATUS    mandatory
		DESCRIPTION
			"b:Blocked  v:Member"
		::= { swhLLDPConfiguration 7 }

	swhLLDPConfigPort8 OBJECT-TYPE
		SYNTAX    INTEGER { b(0), v(1) }
		ACCESS    read-write
		STATUS    mandatory
		DESCRIPTION
			"b:Blocked  v:Member"
		::= { swhLLDPConfiguration 8 }

	swhLLDPConfigPort9 OBJECT-TYPE
		SYNTAX    INTEGER { b(0), v(1) }
		ACCESS    read-write
		STATUS    mandatory
		DESCRIPTION
			"b:Blocked  v:Member"
		::= { swhLLDPConfiguration 9 }

	swhLLDPConfigPort10 OBJECT-TYPE
		SYNTAX    INTEGER { b(0), v(1) }
		ACCESS    read-write
		STATUS    mandatory
		DESCRIPTION
			"b:Blocked  v:Member"
		::= { swhLLDPConfiguration 10 }

	swhLLDPConfigReceiverHoldTime OBJECT-TYPE
		SYNTAX    INTEGER (1..3600)
		ACCESS    read-write
		STATUS    mandatory
		DESCRIPTION
			"Receiver Hold-Time(1-3600 Secs)"
		::= { swhLLDPConfiguration 90 }

	swhLLDPConfigSendingLLDPPacketInterval OBJECT-TYPE
		SYNTAX    INTEGER (1..180)
		ACCESS    read-write
		STATUS    mandatory
		DESCRIPTION
			"Sending LLDP Packet Interval(1-180 Secs)"
		::= { swhLLDPConfiguration 91 }

	swhLLDPConfigSendingLLDPPacketPerDiscover OBJECT-TYPE
		SYNTAX    INTEGER (1..16)
		ACCESS    read-write
		STATUS    mandatory
		DESCRIPTION
			"Sending LLDP Packets Per Discover(1-16 Packet)"
		::= { swhLLDPConfiguration 92 }

	swhLLDPConfigItem OBJECT-TYPE
		SYNTAX    DisplayString
		ACCESS    read-only
		STATUS    mandatory
		DESCRIPTION
			"Selection of LLDP TLVs to send"
		::= { swhLLDPConfiguration 94 }

	swhLLDPConfigPortDescription OBJECT-TYPE
		SYNTAX    INTEGER { disable(0), enable(1) }
		ACCESS    read-write
		STATUS    mandatory
		DESCRIPTION
			"Port Description is On or Off"
		::= { swhLLDPConfiguration 95 }

	swhLLDPConfigSystemName OBJECT-TYPE
		SYNTAX    INTEGER { disable(0), enable(1) }
		ACCESS    read-write
		STATUS    mandatory
		DESCRIPTION
			"System Name is On or Off"
		::= { swhLLDPConfiguration 96 }

	swhLLDPConfigSystemDescription OBJECT-TYPE
		SYNTAX    INTEGER { disable(0), enable(1) }
		ACCESS    read-write
		STATUS    mandatory
		DESCRIPTION
			"System Description is On or Off"
		::= { swhLLDPConfiguration 97 }

	swhLLDPConfigSystemCapabilities OBJECT-TYPE
		SYNTAX    INTEGER { disable(0), enable(1) }
		ACCESS    read-write
		STATUS    mandatory
		DESCRIPTION
			"System Capabilities is On or Off"
		::= { swhLLDPConfiguration 98 }

	swhLLDPConfigManagementAddress OBJECT-TYPE
		SYNTAX    INTEGER { disable(0), enable(1) }
		ACCESS    read-write
		STATUS    mandatory
		DESCRIPTION
			"Management Address is On or Off"
		::= { swhLLDPConfiguration 99 }


-- SwitchManagement(4).PortMirroring(15)


-- SwitchManagement(4).PortMirroring(15).PortMirrorSourcePortConfigTable(1)


-- SwitchManagement(4).StormControl(16)

	swhBroadcastStormControlMode OBJECT-TYPE
		SYNTAX    INTEGER { disable(0), enable(1) }
		ACCESS    read-write
		STATUS    mandatory
		DESCRIPTION
			"Storm Control"
		::= { swhBroadcastStormControl 20 }

	swhBroadcastStormControlRates OBJECT-TYPE
		SYNTAX    INTEGER (32..1000000)
		ACCESS    read-write
		STATUS    mandatory
		DESCRIPTION
			"Storm Rates (32-1000000Kbps)"
		::= { swhBroadcastStormControl 21 }

	swhBroadcastStormControlRatesBandwidth OBJECT-TYPE
		SYNTAX    DisplayString
		ACCESS    read-only
		STATUS    mandatory
		DESCRIPTION
			"Storm Rates Bandwidth(bps)."
		::= { swhBroadcastStormControl 22 }


-- SwitchManagement(4).MirroringConfiguration(17)

	swhMirrorConfigMode OBJECT-TYPE
		SYNTAX    INTEGER { disable(0),
		                    by-port(1)
		                    }
		ACCESS    read-write
		STATUS    mandatory
		DESCRIPTION
			"Mirror Mode"
		::= { swhMirroringConfiguration 1 }

	swhMirrorConfigDestinationPort OBJECT-TYPE
		SYNTAX    INTEGER { port01(0),
		                    port02(1),
		                    port03(2),
		                    port04(3),
		                    port05(4),
		                    port06(5),
							port07(6),
		                    port08(7),
		                    port09(8),
		                    port10(9)
		                    }
		ACCESS    read-write
		STATUS    mandatory
		DESCRIPTION
			"Destination Port"
		::= { swhMirroringConfiguration 2 }


-- SwitchManagement(4).MirroringConfiguration(17).MirrorSourcePortConfigTable(10)

	swhMirrorSourcePortConfigTable OBJECT-TYPE
		SYNTAX    SEQUENCE OF SWHMirrorSourcePortConfigEntry
		ACCESS    not-accessible
		STATUS    mandatory
		DESCRIPTION
			"Table of Source Port Configuration."
		::= { swhMirroringConfiguration 10 }

	-- Table Entry
	swhMirrorSourcePortConfigEntry OBJECT-TYPE
		SYNTAX    SWHMirrorSourcePortConfigEntry
		ACCESS    not-accessible
		STATUS    mandatory
		DESCRIPTION
			"An entry in the table, containing information
			about Source Port Config."
		INDEX    { swhMirrorSourcePortConfigIndex }
		::= { swhMirrorSourcePortConfigTable 1 }

	SWHMirrorSourcePortConfigEntry ::=
		SEQUENCE {
			swhMirrorSourcePortConfigIndex
				INTEGER,
			swhMirrorSourcePortConfigMember
				INTEGER
		}

	swhMirrorSourcePortConfigIndex OBJECT-TYPE
		SYNTAX    INTEGER
		ACCESS    read-only
		STATUS    mandatory
		DESCRIPTION
			"A unique value for each port."
		::= { swhMirrorSourcePortConfigEntry 1 }

	swhMirrorSourcePortConfigMember OBJECT-TYPE
		SYNTAX    INTEGER { disable(0), enable(1) }
		ACCESS    read-write
		STATUS    mandatory
		DESCRIPTION
			"Source Port Member"
		::= { swhMirrorSourcePortConfigEntry 2 }


-- SwitchManagement(4).MirroringConfiguration(17).MirrorVIDConfigTable(11)


-- SwitchManagement(4).MirroringConfiguration(17).MirrorDestinationIPConfigTable(12)


-- SwitchManagement(4).MirroringConfiguration(17).MirrorSourceIPConfigTable(13)


-- SwitchManagement(4).DIDOConfiguration(22).DIConfigTable(1)

--	swhDIConfigTable OBJECT-TYPE
--		SYNTAX    SEQUENCE OF SWHDIConfigEntry
--		ACCESS    not-accessible
--		STATUS    mandatory
--		DESCRIPTION
--			"Table of digital input config."
--		::= { swhDIDOConfiguration 1 }

	-- Table Entry
--	swhDIConfigEntry OBJECT-TYPE
--		SYNTAX    SWHDIConfigEntry
--		ACCESS    not-accessible
--		STATUS    mandatory
--		DESCRIPTION
--			"An entry in the table, containing information
--			about digital input config."
--		INDEX    { swhDIConfigIndex }
--		::= { swhDIConfigTable 1 }

--	SWHDIConfigEntry ::=
--		SEQUENCE {
--			swhDIConfigIndex
--				INTEGER,
--			swhDIConfigNormal
--				INTEGER
--		}

--	swhDIConfigIndex OBJECT-TYPE
--		SYNTAX    INTEGER
--		ACCESS    read-only
--		STATUS    mandatory
--		DESCRIPTION
--			"A unique value for each digital input."
--		::= { swhDIConfigEntry 1 }

--	swhDIConfigNormal OBJECT-TYPE
--		SYNTAX    INTEGER { close(0), open(1) }
--		ACCESS    read-write
--		STATUS    mandatory
--		DESCRIPTION
--			"digital input normal."
--		::= { swhDIConfigEntry 2 }


-- SwitchManagement(4).DIDOConfiguration(22).DOConfigTable(2)

--	swhDOConfigTable OBJECT-TYPE
--		SYNTAX    SEQUENCE OF SWHDOConfigEntry
--		ACCESS    not-accessible
--		STATUS    mandatory
--		DESCRIPTION
--			"Table of digital output config."
--		::= { swhDIDOConfiguration 2 }

	-- Table Entry
--	swhDOConfigEntry OBJECT-TYPE
--		SYNTAX    SWHDOConfigEntry
--		ACCESS    not-accessible
--		STATUS    mandatory
--		DESCRIPTION
--			"An entry in the table, containing information
--			about digital output config."
--		INDEX    { swhDOConfigIndex }
--		::= { swhDOConfigTable 1 }

--	SWHDOConfigEntry ::=
--		SEQUENCE {
--			swhDOConfigIndex
--				INTEGER,
--			swhDOConfigNormal
--				INTEGER,
--			swhDOConfigEventTrigger
--				INTEGER,
--			swhDOConfigEventDigitalInput1
--				INTEGER,
--			swhDOConfigEventDigitalInput2
--				INTEGER,
--			swhDOConfigEventPower1
--				INTEGER,
--			swhDOConfigEventPower2
--				INTEGER,
--			swhDOConfigEventPortList
--				DisplayString
--		}

--	swhDOConfigIndex OBJECT-TYPE
--		SYNTAX    INTEGER
--		ACCESS    read-only
--		STATUS    mandatory
--		DESCRIPTION
--			"A unique value for each digital output."
--		::= { swhDOConfigEntry 1 }

--	swhDOConfigNormal OBJECT-TYPE
--		SYNTAX    INTEGER { close(0), open(1) }
--		ACCESS    read-write
--		STATUS    mandatory
--		DESCRIPTION
--			"digital output normal."
--		::= { swhDOConfigEntry 2 }

--	swhDOConfigEventTrigger OBJECT-TYPE
--		SYNTAX    INTEGER { disable(0), enable(1) }
--		ACCESS    read-write
--		STATUS    mandatory
--		DESCRIPTION
--			"event trigger."
--		::= { swhDOConfigEntry 3 }

--	swhDOConfigEventDigitalInput1 OBJECT-TYPE
--		SYNTAX    INTEGER { disable(0), enable(1) }
--		ACCESS    read-write
--		STATUS    mandatory
--		DESCRIPTION
--			"event digital input 1."
--		::= { swhDOConfigEntry 4 }

--	swhDOConfigEventDigitalInput2 OBJECT-TYPE
--		SYNTAX    INTEGER { disable(0), enable(1) }
--		ACCESS    read-write
--		STATUS    mandatory
--		DESCRIPTION
--			"event digital input 2."
--		::= { swhDOConfigEntry 5 }

--	swhDOConfigEventPortList OBJECT-TYPE
--		SYNTAX    DisplayString (SIZE (0..255))
--		ACCESS    read-write
--		STATUS    mandatory
--		DESCRIPTION
--			"event port list."
--		::= { swhDOConfigEntry 6 }

--	swhDOConfigEventPower1 OBJECT-TYPE
--		SYNTAX    INTEGER { disable(0), enable(1) }
--		ACCESS    read-write
--		STATUS    mandatory
--		DESCRIPTION
--			"event power 1."
--		::= { swhDOConfigEntry 7 }

--	swhDOConfigEventPower2 OBJECT-TYPE
--		SYNTAX    INTEGER { disable(0), enable(1) }
--		ACCESS    read-write
--		STATUS    mandatory
--		DESCRIPTION
--			"event power 2."
--		::= { swhDOConfigEntry 8 }


-- SwitchManagement(4).POEConfiguration(23)

--	swhPOEConfigEnable OBJECT-TYPE
--		SYNTAX    INTEGER { disable(0), enable(1) }
--		ACCESS    read-write
--		STATUS    mandatory
--		DESCRIPTION
--			"Enable or disable POE config."
--		::= { swhPOEConfiguration 1 }

	swhPOEPortConfigTable OBJECT-TYPE
		SYNTAX    SEQUENCE OF SWHPOEPortConfigEntry
		ACCESS    not-accessible
		STATUS    mandatory
		DESCRIPTION
			"Table of POE port config."
		::= { swhPOEConfiguration 2 }

	swhPOEConfigTotalBudget OBJECT-TYPE
		SYNTAX    INTEGER (30..240)
		ACCESS    read-write
		STATUS    mandatory
		DESCRIPTION
			"POE Total Budget config."
		::= { swhPOEConfiguration 5 }

	-- Table Entry
	swhPOEPortConfigEntry OBJECT-TYPE
		SYNTAX    SWHPOEPortConfigEntry
		ACCESS    not-accessible
		STATUS    mandatory
		DESCRIPTION
			"An entry in the table, containing information
			about POE port config."
		INDEX    { swhPOEPortConfigIndex }
		::= { swhPOEPortConfigTable 1 }

	SWHPOEPortConfigEntry ::=
		SEQUENCE {
			swhPOEPortConfigIndex
				INTEGER,
			swhPOEPortConfigState
				INTEGER,
			swhPOEPortConfigName
				DisplayString,
			swhPOEPortConfigPriority
				INTEGER,
			swhPOEPortConfigTimeRange
				DisplayString,
			swhPOEPortConfigSchedule
				INTEGER
		}

	swhPOEPortConfigIndex OBJECT-TYPE
		SYNTAX    INTEGER
		ACCESS    read-only
		STATUS    mandatory
		DESCRIPTION
			"A unique value for each port config."
		::= { swhPOEPortConfigEntry 1 }

	swhPOEPortConfigState OBJECT-TYPE
		SYNTAX    INTEGER { Shutdown(0), Injector-30Watt(1), Auto-AF-AT(2) }
		ACCESS    read-write
		STATUS    mandatory
		DESCRIPTION
			"Port State."
		::= { swhPOEPortConfigEntry 2 }

	swhPOEPortConfigName OBJECT-TYPE
		SYNTAX    DisplayString (SIZE (0..255))
		ACCESS    read-write
		STATUS    mandatory
		DESCRIPTION
			"Description"
		::= { swhPOEPortConfigEntry 4 }

	swhPOEPortConfigPriority OBJECT-TYPE
		SYNTAX    INTEGER { Critical(0), High(1), Low(2) }
		ACCESS    read-write
		STATUS    mandatory
		DESCRIPTION
			"Port Priority."
		::= { swhPOEPortConfigEntry 7 }

	swhPOEPortConfigTimeRange OBJECT-TYPE
		SYNTAX    DisplayString (SIZE (0..255))
		ACCESS    read-write
		STATUS    mandatory
		DESCRIPTION
			"Time Range"
		::= { swhPOEPortConfigEntry 5 }

	swhPOEPortConfigSchedule OBJECT-TYPE
		SYNTAX    INTEGER { off(0), on(1) }
		ACCESS    read-write
		STATUS    mandatory
		DESCRIPTION
			"Port Schedule."
		::= { swhPOEPortConfigEntry 6 }


-- SwitchManagement(4).RingDetection(24)

	swhRingDetectionEnable OBJECT-TYPE
		SYNTAX    INTEGER { disable(0), enable(1) }
		ACCESS    read-write
		STATUS    mandatory
		DESCRIPTION
			"Specify Ring Detection Enable"
		::= { swhRingDetection 1 }

--	swhRingDetectionAccording OBJECT-TYPE
--		SYNTAX    INTEGER { software(0), hardware(1) }
--		ACCESS    read-write
--		STATUS    mandatory
--		DESCRIPTION
--			"Specify Ring Detection According"
--		::= { swhRingDetection 3 }

	swhRingDetectionSoftwareRole OBJECT-TYPE
		SYNTAX    INTEGER { slave(0), master(1) }
		ACCESS    read-write
		STATUS    mandatory
		DESCRIPTION
			"Specify Ring Detection Software Role"
		::= { swhRingDetection 2 }

	swhRingDetectionPortList OBJECT-TYPE
		SYNTAX    DisplayString
		ACCESS    read-write
		STATUS    mandatory
		DESCRIPTION
			"Specify Ring Detection Port List"
		::= { swhRingDetection 4 }


-- SwitchManagement(4).QoSPriority(30)

	swhQoSMode OBJECT-TYPE
		SYNTAX    INTEGER { disable(0), IEEE8021p(2), dscp(3) }
		ACCESS    read-write
		STATUS    mandatory
		DESCRIPTION
			"Specify QoS mode"
		::= { swhQoSPriority 1 }

	swhQueuingMode OBJECT-TYPE
		SYNTAX    INTEGER { weight(0), strict(1) }
		ACCESS    read-write
		STATUS    mandatory
		DESCRIPTION
			"Specify the egress mode is Strict or Weight"
		::= { swhQoSPriority 2 }

	swhQueueWeighted OBJECT-TYPE
		SYNTAX    DisplayString (SIZE (0..255))
		ACCESS    read-write
		STATUS    mandatory
		DESCRIPTION
			"Specify as weight (Q0:Q1:Q2:Q3:Q4:Q5:Q6:Q7) , Queue is 1~31"
		::= { swhQoSPriority 11 }

	swhManagementPriority OBJECT-TYPE
		SYNTAX    INTEGER (0..7)
		ACCESS    read-write
		STATUS    mandatory
		DESCRIPTION
			"Specify Management Priority(0-7)."
		::= { swhQoSPriority 10 }

	swh8021pRemarking OBJECT-TYPE
		SYNTAX    INTEGER { disable(0), enable(1) }
		ACCESS    read-write
		STATUS    mandatory
		DESCRIPTION
			"Specify 802.1p Remarking"
		::= { swhQoSPriority 30 }

	swhDSCPRemarking OBJECT-TYPE
		SYNTAX    INTEGER { disable(0), enable(1) }
		ACCESS    read-write
		STATUS    mandatory
		DESCRIPTION
			"Specify DSCP Remarking"
		::= { swhQoSPriority 40 }


-- SwitchManagement(4).QoSPriority(30).PortPriorityTable(4)

	swhPortPriorityTable OBJECT-TYPE
		SYNTAX    SEQUENCE OF SWHPortPriorityEntry
		ACCESS    not-accessible
		STATUS    mandatory
		DESCRIPTION
			"Table of Port Priority."
		::= { swhQoSPriority 4 }

	-- Table Entry
	swhPortPriorityEntry OBJECT-TYPE
		SYNTAX    SWHPortPriorityEntry
		ACCESS    not-accessible
		STATUS    mandatory
		DESCRIPTION
			"An entry in the table, containing information
			about Port Priority config."
		INDEX    { swhPortPriorityIndex }
		::= { swhPortPriorityTable 1 }

	SWHPortPriorityEntry ::=
		SEQUENCE {
			swhPortPriorityIndex
				INTEGER,
			swhPortPriorityPort
				INTEGER,
			swhPortPriorityUserPriority
				INTEGER
		}

	swhPortPriorityIndex OBJECT-TYPE
		SYNTAX    INTEGER
		ACCESS    read-only
		STATUS    mandatory
		DESCRIPTION
			"A unique value for each port priority."
		::= { swhPortPriorityEntry 1 }

	swhPortPriorityPort OBJECT-TYPE
		SYNTAX    INTEGER { port01(0),
		                    port02(1),
		                    port03(2),
		                    port04(3),
		                    port05(4),
		                    port06(5),
							port07(6),
							port08(7),
							port09(8),
							port10(9)
		                    }
		ACCESS    read-only
		STATUS    mandatory
		DESCRIPTION
			"Port priority."
		::= { swhPortPriorityEntry 2 }

	swhPortPriorityUserPriority OBJECT-TYPE
		SYNTAX    INTEGER (0..7)
		ACCESS    read-write
		STATUS    mandatory
		DESCRIPTION
			"Port User Priority(0-7)."
		::= { swhPortPriorityEntry 4 }


-- SwitchManagement(4).QoSPriority(30).8021pPriorityTable(5)

	swh8021pPriorityTable OBJECT-TYPE
		SYNTAX    SEQUENCE OF SWH8021pPriorityEntry
		ACCESS    not-accessible
		STATUS    mandatory
		DESCRIPTION
			"Table of 802.1p Priority Map."
		::= { swhQoSPriority 5 }

	-- Table Entry
	swh8021pPriorityEntry OBJECT-TYPE
		SYNTAX    SWH8021pPriorityEntry
		ACCESS    not-accessible
		STATUS    mandatory
		DESCRIPTION
			"An entry in the table, containing information
			about 802.1p Priority config."
		INDEX    { swh8021pPriorityIndex }
		::= { swh8021pPriorityTable 1 }

	SWH8021pPriorityEntry ::=
		SEQUENCE {
			swh8021pPriorityIndex
				INTEGER,
			swh8021pPriorityPriority
				INTEGER,
			swh8021pPriorityQueue
				INTEGER
		}

	swh8021pPriorityIndex OBJECT-TYPE
		SYNTAX    INTEGER
		ACCESS    read-only
		STATUS    mandatory
		DESCRIPTION
			"A unique value for each 802.1p priority."
		::= { swh8021pPriorityEntry 1 }

	swh8021pPriorityPriority OBJECT-TYPE
		SYNTAX    INTEGER { dot1p-0(0),
		                    dot1p-1(1),
		                    dot1p-2(2),
		                    dot1p-3(3),
		                    dot1p-4(4),
		                    dot1p-5(5),
		                    dot1p-6(6),
		                    dot1p-7(7)
		                    } 
		ACCESS    read-only
		STATUS    mandatory
		DESCRIPTION
			"802.1p priority."
		::= { swh8021pPriorityEntry 2 }

	swh8021pPriorityQueue OBJECT-TYPE
		SYNTAX    INTEGER { q0(0), q1(1), q2(2), q3(3), q4(4), q5(5), q6(6), q7(7) }
		ACCESS    read-write
		STATUS    mandatory
		DESCRIPTION
			"Specify 802.1p bit value, Q0 Q1 Q2 Q3 Q4 Q5 Q6 Q7."
		::= { swh8021pPriorityEntry 3 }


-- SwitchManagement(4).QoSPriority(30).DSCPPriorityTable(6)

	swhDSCPPriorityTable OBJECT-TYPE
		SYNTAX    SEQUENCE OF SWHDSCPPriorityEntry
		ACCESS    not-accessible
		STATUS    mandatory
		DESCRIPTION
			"Table of DSCP Priority Map."
		::= { swhQoSPriority 6 }

	-- Table Entry
	swhDSCPPriorityEntry OBJECT-TYPE
		SYNTAX    SWHDSCPPriorityEntry
		ACCESS    not-accessible
		STATUS    mandatory
		DESCRIPTION
			"An entry in the table, containing information
			about DSCP Priority config."
		INDEX    { swhDSCPPriorityIndex }
		::= { swhDSCPPriorityTable 1 }

	SWHDSCPPriorityEntry ::=
		SEQUENCE {
			swhDSCPPriorityIndex
				INTEGER,
			swhDSCPPriorityPriority
				INTEGER,
			swhDSCPPriorityQueue
				INTEGER
		}

	swhDSCPPriorityIndex OBJECT-TYPE
		SYNTAX    INTEGER 
		ACCESS    read-only
		STATUS    mandatory
		DESCRIPTION
			"A unique value for each dscp priority."
		::= { swhDSCPPriorityEntry 1 }

	swhDSCPPriorityPriority OBJECT-TYPE
		SYNTAX    INTEGER { dscp-0(0), dscp-1(1), dscp-2(2), dscp-3(3),
		                    dscp-4(4), dscp-5(5), dscp-6(6), dscp-7(7),
		                    dscp-8(8), dscp-9(9), dscp-10(10), dscp-11(11),
		                    dscp-12(12), dscp-13(13), dscp-14(14), dscp-15(15),
		                    dscp-16(16), dscp-17(17), dscp-18(18), dscp-19(19),
		                    dscp-20(20), dscp-21(21), dscp-22(22), dscp-23(23),
		                    dscp-24(24), dscp-25(25), dscp-26(26), dscp-27(27),
		                    dscp-28(28), dscp-29(29), dscp-30(30), dscp-31(31),
		                    dscp-32(32), dscp-33(33), dscp-34(34), dscp-35(35),
		                    dscp-36(36), dscp-37(37), dscp-38(38), dscp-39(39),
		                    dscp-40(40), dscp-41(41), dscp-42(42), dscp-43(43),
		                    dscp-44(44), dscp-45(45), dscp-46(46), dscp-47(47),
		                    dscp-48(48), dscp-49(49), dscp-50(50), dscp-51(51),
		                    dscp-52(52), dscp-53(53), dscp-54(54), dscp-55(55),
		                    dscp-56(56), dscp-57(57), dscp-58(58), dscp-59(59),
		                    dscp-60(60), dscp-61(61), dscp-62(62), dscp-63(63)
		                    }
		ACCESS    read-only
		STATUS    mandatory
		DESCRIPTION
			"DSCP priority."
		::= { swhDSCPPriorityEntry 2 }

	--swhDSCPPriorityPriority OBJECT-TYPE
	--	SYNTAX    INTEGER { invalid(0),
	--	                    dscp-0(1), dscp-1(2), dscp-2(3), dscp-3(4),
	--	                    dscp-4(5), dscp-5(6), dscp-6(7), dscp-7(8),
	--	                    dscp-8(9), dscp-9(10), dscp-10(11), dscp-11(12),
	--	                    dscp-12(13), dscp-13(14), dscp-14(15), dscp-15(16),
	--	                    dscp-16(17), dscp-17(18), dscp-18(19), dscp-19(20),
	--	                    dscp-20(21), dscp-21(22), dscp-22(23), dscp-23(24),
	--	                    dscp-24(25), dscp-25(26), dscp-26(27), dscp-27(28),
	--	                    dscp-28(29), dscp-29(30), dscp-30(31), dscp-31(32),
	--	                    dscp-32(33), dscp-33(34), dscp-34(35), dscp-35(36),
	--	                    dscp-36(37), dscp-37(38), dscp-38(39), dscp-39(40),
	--	                    dscp-40(41), dscp-41(42), dscp-42(43), dscp-43(44),
	--	                    dscp-44(45), dscp-45(46), dscp-46(47), dscp-47(48),
	--	                    dscp-48(49), dscp-49(50), dscp-50(51), dscp-51(52),
	--	                    dscp-52(53), dscp-53(54), dscp-54(55), dscp-55(56),
	--	                    dscp-56(57), dscp-57(58), dscp-58(59), dscp-59(60),
	--	                    dscp-60(61), dscp-61(62), dscp-62(63), dscp-63(64)
	--	                    }
	--	ACCESS    read-write
	--	STATUS    mandatory
	--	DESCRIPTION
	--		"DSCP priority."
	--	::= { swhDSCPPriorityEntry 2 }

	swhDSCPPriorityQueue OBJECT-TYPE
		SYNTAX    INTEGER { q0(0), q1(1), q2(2), q3(3), q4(4), q5(5), q6(6), q7(7) }
		ACCESS    read-write
		STATUS    mandatory
		DESCRIPTION
			"Specify DSCP bit value, Q0 Q1 Q2 Q3 Q4 Q5 Q6 Q7."
		::= { swhDSCPPriorityEntry 3 }


-- SwitchManagement(4).QoSPriority(30).VLANPriorityTable(25)


-- SwitchManagement(4).QoSPriority(30).VIDRemarkingTable(51)


-- SwitchManagement(4).QoSPriority(30).8021pRemarkingTable(31)

	swh8021pRemarkingTable OBJECT-TYPE
		SYNTAX    SEQUENCE OF SWH8021pRemarkingEntry
		ACCESS    not-accessible
		STATUS    mandatory
		DESCRIPTION
			"Table of 802.1p Remarking Map."
		::= { swhQoSPriority 31 }

	-- Table Entry
	swh8021pRemarkingEntry OBJECT-TYPE
		SYNTAX    SWH8021pRemarkingEntry
		ACCESS    not-accessible
		STATUS    mandatory
		DESCRIPTION
			"An entry in the table, containing information
			about 802.1p Remarking config."
		INDEX    { swh8021pRemarkingIndex }
		::= { swh8021pRemarkingTable 1 }

	SWH8021pRemarkingEntry ::=
		SEQUENCE {
			swh8021pRemarkingIndex
				INTEGER,
			swh8021pRemarkingState
				INTEGER,
			swh8021pRemarkingRx8021p
				INTEGER,
			swh8021pRemarkingNew8021p
				INTEGER
		}

	swh8021pRemarkingIndex OBJECT-TYPE
		SYNTAX    INTEGER
		ACCESS    read-only
		STATUS    mandatory
		DESCRIPTION
			"A unique value for each 802.1p remarking index."
		::= { swh8021pRemarkingEntry 1 }

	swh8021pRemarkingNew8021p OBJECT-TYPE
		SYNTAX    INTEGER { dot1p-0(0),
		                    dot1p-1(1),
		                    dot1p-2(2),
		                    dot1p-3(3),
		                    dot1p-4(4),
		                    dot1p-5(5),
		                    dot1p-6(6),
		                    dot1p-7(7)
		                    } 
		ACCESS    read-write
		STATUS    mandatory
		DESCRIPTION
			"New-802.1p(0-7)."
		::= { swh8021pRemarkingEntry 3 }

	swh8021pRemarkingState OBJECT-TYPE
		SYNTAX    INTEGER { disable(0), enable(1) }
		ACCESS    read-write
		STATUS    mandatory
		DESCRIPTION
			"disable or enable 802.1p remarking priority"
		::= { swh8021pRemarkingEntry 4 }

	swh8021pRemarkingRx8021p OBJECT-TYPE
		SYNTAX    INTEGER (0..7)
		ACCESS    read-write
		STATUS    mandatory
		DESCRIPTION
			"Rx-802.1p(0-7)."
		::= { swh8021pRemarkingEntry 5 }


-- SwitchManagement(4).QoSPriority(30).8021pRemarkingDSCPTable(32)


-- SwitchManagement(4).QoSPriority(30).DSCPRemarkingTable(41)

	swhDSCPRemarkingTable OBJECT-TYPE
		SYNTAX    SEQUENCE OF SWHDSCPRemarkingEntry
		ACCESS    not-accessible
		STATUS    mandatory
		DESCRIPTION
			"Table of DSCP Remarking Map."
		::= { swhQoSPriority 41 }

	-- Table Entry
	swhDSCPRemarkingEntry OBJECT-TYPE
		SYNTAX    SWHDSCPRemarkingEntry
		ACCESS    not-accessible
		STATUS    mandatory
		DESCRIPTION
			"An entry in the table, containing information
			about DSCP Remarking config."
		INDEX    { swhDSCPRemarkingIndex }
		::= { swhDSCPRemarkingTable 1 }

	SWHDSCPRemarkingEntry ::=
		SEQUENCE {
			swhDSCPRemarkingIndex
				INTEGER,
			swhDSCPRemarkingState
				INTEGER,
			swhDSCPRemarkingRxDSCP
				INTEGER,
			swhDSCPRemarkingNewDSCP
				INTEGER
		}

	swhDSCPRemarkingIndex OBJECT-TYPE
		SYNTAX    INTEGER 
		ACCESS    read-only
		STATUS    mandatory
		DESCRIPTION
			"A unique value for each dscp remarking index."
		::= { swhDSCPRemarkingEntry 1 }

	swhDSCPRemarkingNewDSCP OBJECT-TYPE
		SYNTAX    INTEGER (0..63)
		ACCESS    read-write
		STATUS    mandatory
		DESCRIPTION
			"DSCP priority(0-63)."
		::= { swhDSCPRemarkingEntry 3 }

	swhDSCPRemarkingState OBJECT-TYPE
		SYNTAX    INTEGER { disable(0), enable(1) }
		ACCESS    read-write
		STATUS    mandatory
		DESCRIPTION
			"disable or enable DSCP remarking"
		::= { swhDSCPRemarkingEntry 4 }

	swhDSCPRemarkingRxDSCP OBJECT-TYPE
		SYNTAX    INTEGER (0..63)
		ACCESS    read-write
		STATUS    mandatory
		DESCRIPTION
			"DSCP(0-63)."
		::= { swhDSCPRemarkingEntry 5 }


-- SwitchManagement(4).QoSPriority(30).DSCPPortRemarkingTable(42)


-- SwitchManagement(4).QoSPriority(30).VIDRemarkingTable(51)


-- SwitchManagement(4).MacAddressManagement(35)

	swhStaticMACTableConfiguration
		OBJECT IDENTIFIER ::= { swhMacAddressManagement 3 }


-- SwitchManagement(4).MacAddressManagement(35).MACTableLearning(1).MACTableLearningTable(2)


-- SwitchManagement(4).MacAddressManagement(35).StaticMACTableConfiguration(3).StaticForwardTable(2)

	swhStaticForwardTable OBJECT-TYPE
		SYNTAX    SEQUENCE OF SWHStaticForwardEntry
		ACCESS    not-accessible
		STATUS    mandatory
		DESCRIPTION
			"Table of Static Forwarding."
		::= { swhStaticMACTableConfiguration 2 }

 	-- Table Entry
	swhStaticForwardEntry OBJECT-TYPE
		SYNTAX    SWHStaticForwardEntry
		ACCESS    not-accessible
		STATUS    mandatory
		DESCRIPTION
			"An entry in the table, containing information
			about Static Forwarding Configuration"
		INDEX    { swhStaticForwardIndex }
		::= { swhStaticForwardTable 1 }

	SWHStaticForwardEntry ::=
		SEQUENCE {
			swhStaticForwardIndex
				INTEGER,  
			swhStaticForwardValid
				INTEGER,  
			swhStaticForwardMacAddress
				MacAddress, 
			swhStaticForwardVID
				INTEGER,
			swhStaticForwardPort
				INTEGER,
			swhStaticForwardDelete
				INTEGER
		}

	swhStaticForwardIndex OBJECT-TYPE
		SYNTAX    INTEGER 
		ACCESS    read-only
		STATUS    mandatory
		DESCRIPTION
			"A unique value for Static Forwarding index."
		::= { swhStaticForwardEntry 1 }

	swhStaticForwardValid OBJECT-TYPE
		SYNTAX    INTEGER { invalid(0), valid(1) }
		ACCESS    read-only
		STATUS    mandatory
		DESCRIPTION
			"This MAC address is valid or invalid."
		::= { swhStaticForwardEntry 2 }

	swhStaticForwardMacAddress OBJECT-TYPE
		SYNTAX    MacAddress
		ACCESS    read-write
		STATUS    mandatory
		DESCRIPTION
			"MAC Address"
		::= { swhStaticForwardEntry 3 }

	swhStaticForwardVID OBJECT-TYPE
		SYNTAX    INTEGER (1..4094)
		ACCESS    read-write
		STATUS    mandatory
		DESCRIPTION
			"VLAN ID"
		::= { swhStaticForwardEntry 4 }

	swhStaticForwardPort OBJECT-TYPE
		SYNTAX    INTEGER { port01(0),
		                    port02(1),
		                    port03(2),
		                    port04(3),
		                    port05(4),
		                    port06(5),
							port07(6),
							port08(7),
							port09(8),
							port10(9)
		                    }
		ACCESS    read-write
		STATUS    mandatory
		DESCRIPTION
			"Static forward packets to this port."
		::= { swhStaticForwardEntry 5 }

	swhStaticForwardDelete OBJECT-TYPE
		SYNTAX    INTEGER { normal(0), delete(1) }
		ACCESS    read-write
		STATUS    mandatory
		DESCRIPTION
			"Delete this MAC address."
		::= { swhStaticForwardEntry 6 }


-- SwitchManagement(4).RapidSpanningTree(40)

	swhRSTPSwitchSettings
		OBJECT IDENTIFIER ::= { swhRapidSpanningTree 3 }
	swhRSTPAggregatedPortSettings
		OBJECT IDENTIFIER ::= { swhRapidSpanningTree 9 }
	swhRSTPPhysicalPortSettings
		OBJECT IDENTIFIER ::= { swhRapidSpanningTree 12 }


-- SwitchManagement(4).RapidSpanningTree(40).RSTPSwitchSettings(3)

	swhRSTPSwitchSettingsSystemPriority OBJECT-TYPE
		SYNTAX    INTEGER
		ACCESS    read-only
		STATUS    mandatory
		DESCRIPTION
			"System Priority"
		::= { swhRSTPSwitchSettings 6 }

	swhRSTPSwitchSettingsSystemPriorityIndex OBJECT-TYPE
		SYNTAX    INTEGER { option-0(0),
		                    option-1(1),
		                    option-2(2),
		                    option-3(3),
		                    option-4(4),
		                    option-5(5),
		                    option-6(6),
		                    option-7(7),
		                    option-8(8),
		                    option-9(9),
		                    option-10(10),
		                    option-11(11),
		                    option-12(12),
		                    option-13(13),
		                    option-14(14),
		                    option-15(15)
		                    }
		ACCESS    read-write
		STATUS    mandatory
		DESCRIPTION
			"Port Priority 0=0, 1=4096, 2=8192, 3=12288, 4=16384, 5=20480, 6=24576, 7=28672, 8=32768, 9=36864,
			               10=40960, 11=45056, 12=49152, 13=53248, 14=57344, 15=61440"
		::= { swhRSTPSwitchSettings 9 }

	swhRSTPSwitchSettingsMaxAge OBJECT-TYPE
		SYNTAX    INTEGER (6..200)
		ACCESS    read-write
		STATUS    mandatory
		DESCRIPTION
			"Max Age is 6-40 hops"
		::= { swhRSTPSwitchSettings 12 }

	swhRSTPSwitchSettingsHelloTime OBJECT-TYPE
		SYNTAX    INTEGER (1..10)
		ACCESS    read-write
		STATUS    mandatory
		DESCRIPTION
			"Hello Time is 1-10 secs"
		::= { swhRSTPSwitchSettings 15 }

	swhRSTPSwitchSettingsForwardDelay OBJECT-TYPE
		SYNTAX    INTEGER (4..30)
		ACCESS    read-write
		STATUS    mandatory
		DESCRIPTION
			"Forward Delay is 4-30 secs"
		::= { swhRSTPSwitchSettings 18 }

	swhRSTPSwitchSettingsForceVersion OBJECT-TYPE
		SYNTAX    INTEGER { compatible(0), normal(1) }
		ACCESS    read-write
		STATUS    mandatory
		DESCRIPTION
			"Force Version is Normal or Compatible"
		::= { swhRSTPSwitchSettings 21 }


-- SwitchManagement(4).RapidSpanningTree(40).RSTPAggregatedPortSettings(9)

	swhRSTPAggregatedPortSettingsState OBJECT-TYPE
		SYNTAX    INTEGER { disable(0), enable(1) }
		ACCESS    read-write
		STATUS    mandatory
		DESCRIPTION
			"Aggregated State is Disable or Enable"
		::= { swhRSTPAggregatedPortSettings 3 }

	swhRSTPAggregatedPortSettingsCost OBJECT-TYPE
		SYNTAX    INTEGER (1..200000000)
		ACCESS    read-write
		STATUS    mandatory
		DESCRIPTION
			"Aggregated State is Disable or Enable"
		::= { swhRSTPAggregatedPortSettings 6 }

	swhRSTPAggregatedPortSettingsPriority OBJECT-TYPE
		SYNTAX    INTEGER
		ACCESS    read-only
		STATUS    mandatory
		DESCRIPTION
			"Aggregated State is Disable or Enable"
		::= { swhRSTPAggregatedPortSettings 9 }

	swhRSTPAggregatedPortSettingsPriorityIndex OBJECT-TYPE
		SYNTAX    INTEGER { option-0(0),
		                    option-1(1),
		                    option-2(2),
		                    option-3(3),
		                    option-4(4),
		                    option-5(5),
		                    option-6(6),
		                    option-7(7),
		                    option-8(8),
		                    option-9(9),
		                    option-10(10),
		                    option-11(11),
		                    option-12(12),
		                    option-13(13),
		                    option-14(14),
		                    option-15(15)
		                    }
		ACCESS    read-write
		STATUS    mandatory
		DESCRIPTION
			"Port Priority 0=0, 1=16, 2=32, 3=48, 4=64, 5=80, 6=96, 7=112, 8=128,
			               9=144, 10=160, 11=176, 12=192, 13=208, 14=224, 15=240"
		::= { swhRSTPAggregatedPortSettings 12 }

	swhRSTPAggregatedPortSettingsEdge OBJECT-TYPE
		SYNTAX    INTEGER { disable(0), enable(1) }
		ACCESS    read-write
		STATUS    mandatory
		DESCRIPTION
			"Edge Enable"
		::= { swhRSTPAggregatedPortSettings 15 }

	swhRSTPAggregatedPortSettingsPoint2point OBJECT-TYPE
		SYNTAX    INTEGER { forcedtrue(0), forcedfalse(1), auto(2) }
		ACCESS    read-write
		STATUS    mandatory
		DESCRIPTION
			"Point to Point"
		::= { swhRSTPAggregatedPortSettings 18 }


-- SwitchManagement(4).RapidSpanningTree(40).RSTPPhysicalPortSettings(12).RSTPPhysicalPortSettingsTable(3)

	swhRSTPPhysicalPortSettingsTable OBJECT-TYPE
		SYNTAX    SEQUENCE OF SWHRSTPPhysicalPortSettingsEntry
		ACCESS    not-accessible
		STATUS    mandatory
		DESCRIPTION
			"Table of RSTP Physical Port descriptive and status information."
		::= { swhRSTPPhysicalPortSettings 3 }

	-- Table Entry
	swhRSTPPhysicalPortSettingsEntry OBJECT-TYPE
		SYNTAX    SWHRSTPPhysicalPortSettingsEntry
		ACCESS    not-accessible
		STATUS    mandatory
		DESCRIPTION
			"An entry in the table, containing information
			about RSTP Physical Port Settings."
		INDEX    { swhRSTPPhysicalPortSettingsIndex }
		::= { swhRSTPPhysicalPortSettingsTable 1 }

	SWHRSTPPhysicalPortSettingsEntry ::=
		SEQUENCE {  
			swhRSTPPhysicalPortSettingsIndex
				INTEGER,
			swhRSTPPhysicalPortSettingsState
				INTEGER,
			swhRSTPPhysicalPortSettingsPathCost
				INTEGER,
			swhRSTPPhysicalPortSettingsPriority
				INTEGER,
			swhRSTPPhysicalPortSettingsPriorityIndex
				INTEGER,
			swhRSTPPhysicalPortSettingsEdge
				INTEGER,
			swhRSTPPhysicalPortSettingsPoint2point
				INTEGER
		}

	swhRSTPPhysicalPortSettingsIndex OBJECT-TYPE
		SYNTAX    INTEGER 
		ACCESS    read-only
		STATUS    mandatory
		DESCRIPTION
			"A unique value for each port."
		::= { swhRSTPPhysicalPortSettingsEntry 3 }

	swhRSTPPhysicalPortSettingsState OBJECT-TYPE
		SYNTAX    INTEGER { disable(0), enable(1) }
		ACCESS    read-write
		STATUS    mandatory
		DESCRIPTION
			"Port Protocol Enable"
		::= { swhRSTPPhysicalPortSettingsEntry 6 }

	swhRSTPPhysicalPortSettingsEdge OBJECT-TYPE
		SYNTAX    INTEGER { disable(0), enable(1) }
		ACCESS    read-write
		STATUS    mandatory
		DESCRIPTION
			"Edge Enable"
		::= { swhRSTPPhysicalPortSettingsEntry 9 }

	swhRSTPPhysicalPortSettingsPathCost OBJECT-TYPE
		SYNTAX    INTEGER (0..200000000)
		ACCESS    read-write
		STATUS    mandatory
		DESCRIPTION
			"Path Cost is 0-200000000"
		::= { swhRSTPPhysicalPortSettingsEntry 12 }

	swhRSTPPhysicalPortSettingsPriority OBJECT-TYPE
		SYNTAX    INTEGER 
		ACCESS    read-only
		STATUS    mandatory
		DESCRIPTION
			"Priority."
		::= { swhRSTPPhysicalPortSettingsEntry 15 }

	swhRSTPPhysicalPortSettingsPriorityIndex OBJECT-TYPE
		SYNTAX    INTEGER { option-0(0),
		                    option-1(1),
		                    option-2(2),
		                    option-3(3),
		                    option-4(4),
		                    option-5(5),
		                    option-6(6),
		                    option-7(7),
		                    option-8(8),
		                    option-9(9),
		                    option-10(10),
		                    option-11(11),
		                    option-12(12),
		                    option-13(13),
		                    option-14(14),
		                    option-15(15)
		                    }
		ACCESS    read-write
		STATUS    mandatory
		DESCRIPTION
			"Port Priority 0=0, 1=16, 2=32, 3=48, 4=64, 5=80, 6=96, 7=112, 8=128,
			               9=144, 10=160, 11=176, 12=192, 13=208, 14=224, 15=240"
		::= { swhRSTPPhysicalPortSettingsEntry 18 }

	swhRSTPPhysicalPortSettingsPoint2point OBJECT-TYPE
		SYNTAX    INTEGER { forcedtrue(0), forcedfalse(1), auto(2) }
		ACCESS    read-write
		STATUS    mandatory
		DESCRIPTION
			"Point to Point"
		::= { swhRSTPPhysicalPortSettingsEntry 21 }


-- SwitchManagement(4).LinkAggregation(45)

	swhDistributionRule
		OBJECT IDENTIFIER ::= { swhLinkAggregation 1 }
	swhPortTrunkConfiguration
		OBJECT IDENTIFIER ::= { swhLinkAggregation 3 }
	swhLACPPortConfiguration
		OBJECT IDENTIFIER ::= { swhLinkAggregation 6 }


-- SwitchManagement(4).LinkAggregation(45).DistributionRule(1)

--	swhDistributionRuleSourceIPAddress OBJECT-TYPE
--		SYNTAX    INTEGER { disable(0), enable(1) }
--		ACCESS    read-write
--		STATUS    mandatory
--		DESCRIPTION
--			"Source IP Address."
--		::= { swhDistributionRule 1 }

--	swhDistributionRuleDestinationIPAddress OBJECT-TYPE
--		SYNTAX    INTEGER { disable(0), enable(1) }
--		ACCESS    read-write
--		STATUS    mandatory
--		DESCRIPTION
--			"Destination IP Address."
--		::= { swhDistributionRule 2 }

--	swhDistributionRuleSourceMACAddress OBJECT-TYPE
--		SYNTAX    INTEGER { disable(0), enable(1) }
--		ACCESS    read-write
--		STATUS    mandatory
--		DESCRIPTION
--			"Source MAC Address."
--		::= { swhDistributionRule 5 }

--	swhDistributionRuleDestinationMACAddress OBJECT-TYPE
--		SYNTAX    INTEGER { disable(0), enable(1) }
--		ACCESS    read-write
--		STATUS    mandatory
--		DESCRIPTION
--			"Destination MAC Address."
--		::= { swhDistributionRule 6 }

	swhDistributionRuleMACQuotient OBJECT-TYPE
		SYNTAX    INTEGER { disable(0), enable(1) }
		ACCESS    read-write
		STATUS    mandatory
		DESCRIPTION
			"MAC Quotient."
		::= { swhDistributionRule 7 }


-- SwitchManagement(4).LinkAggregation(45).PortTrunkConfiguration(3).PortTrunkConfigTable(6)

	swhPortTrunkConfigTable OBJECT-TYPE
		SYNTAX    SEQUENCE OF SWHPortTrunkConfigEntry
		ACCESS    not-accessible
		STATUS    mandatory
		DESCRIPTION
			"Table of Port Trunk Configuration."
		::= { swhPortTrunkConfiguration 6 }

	-- Table Entry
	swhPortTrunkConfigEntry OBJECT-TYPE
		SYNTAX    SWHPortTrunkConfigEntry
		ACCESS    not-accessible
		STATUS    mandatory
		DESCRIPTION
			"An entry in the table, containing information
			about port trunk config."
		INDEX    { swhPortTrunkConfigIndex }
		::= { swhPortTrunkConfigTable 1 }

	SWHPortTrunkConfigEntry ::=
		SEQUENCE {
			swhPortTrunkConfigIndex
				INTEGER,
			swhPortTrunkConfigValid
				INTEGER,
			swhPortTrunkConfigGroupName
				DisplayString,
			swhPortTrunkConfigPort1
				INTEGER,
			swhPortTrunkConfigPort2
				INTEGER,
			swhPortTrunkConfigPort3
				INTEGER,
			swhPortTrunkConfigPort4
				INTEGER,
			swhPortTrunkConfigPort5
				INTEGER,
			swhPortTrunkConfigPort6
				INTEGER,
			swhPortTrunkConfigPort7
				INTEGER,
			swhPortTrunkConfigPort8
				INTEGER,
			swhPortTrunkConfigPort9
				INTEGER,
			swhPortTrunkConfigPort10
				INTEGER,
			swhPortTrunkConfigDelete
				INTEGER
		}

	swhPortTrunkConfigIndex OBJECT-TYPE
		SYNTAX    INTEGER 
		ACCESS    read-only
		STATUS    mandatory
		DESCRIPTION
			"A unique value for each group."
		::= { swhPortTrunkConfigEntry 1 }

	swhPortTrunkConfigValid OBJECT-TYPE
		SYNTAX    INTEGER { invalid(0), valid(1) }
		ACCESS    read-only
		STATUS    mandatory
		DESCRIPTION
			"This group setting is valid or invalid."
		::= { swhPortTrunkConfigEntry 2 }

	swhPortTrunkConfigGroupName OBJECT-TYPE
		SYNTAX    DisplayString
		ACCESS    read-write
		STATUS    mandatory
		DESCRIPTION
			"Port trunk group name."
		::= { swhPortTrunkConfigEntry 4 }

	swhPortTrunkConfigPort1 OBJECT-TYPE
		SYNTAX    INTEGER { b(0), v(1) }
		ACCESS    read-write
		STATUS    mandatory
		DESCRIPTION
			"b:Blocked  v:Member"
		::= { swhPortTrunkConfigEntry 5 }

	swhPortTrunkConfigPort2 OBJECT-TYPE
		SYNTAX    INTEGER { b(0), v(1) }
		ACCESS    read-write
		STATUS    mandatory
		DESCRIPTION
			"b:Blocked  v:Member"
		::= { swhPortTrunkConfigEntry 6 }

	swhPortTrunkConfigPort3 OBJECT-TYPE
		SYNTAX    INTEGER { b(0), v(1) }
		ACCESS    read-write
		STATUS    mandatory
		DESCRIPTION
			"b:Blocked  v:Member"
		::= { swhPortTrunkConfigEntry 7 }

	swhPortTrunkConfigPort4 OBJECT-TYPE
		SYNTAX    INTEGER { b(0), v(1) }
		ACCESS    read-write
		STATUS    mandatory
		DESCRIPTION
			"b:Blocked  v:Member"
		::= { swhPortTrunkConfigEntry 8 }

	swhPortTrunkConfigPort5 OBJECT-TYPE
		SYNTAX    INTEGER { b(0), v(1) }
		ACCESS    read-write
		STATUS    mandatory
		DESCRIPTION
			"b:Blocked  v:Member"
		::= { swhPortTrunkConfigEntry 9 }

	swhPortTrunkConfigPort6 OBJECT-TYPE
		SYNTAX    INTEGER { b(0), v(1) }
		ACCESS    read-write
		STATUS    mandatory
		DESCRIPTION
			"b:Blocked  v:Member"
		::= { swhPortTrunkConfigEntry 10 }
		
	swhPortTrunkConfigPort7 OBJECT-TYPE
		SYNTAX    INTEGER { b(0), v(1) }
		ACCESS    read-write
		STATUS    mandatory
		DESCRIPTION
			"b:Blocked  v:Member"
		::= { swhPortTrunkConfigEntry 11 }
		
	swhPortTrunkConfigPort8 OBJECT-TYPE
		SYNTAX    INTEGER { b(0), v(1) }
		ACCESS    read-write
		STATUS    mandatory
		DESCRIPTION
			"b:Blocked  v:Member"
		::= { swhPortTrunkConfigEntry 12 }
		
	swhPortTrunkConfigPort9 OBJECT-TYPE
		SYNTAX    INTEGER { b(0), v(1) }
		ACCESS    read-write
		STATUS    mandatory
		DESCRIPTION
			"b:Blocked  v:Member"
		::= { swhPortTrunkConfigEntry 13 }
		
	swhPortTrunkConfigPort10 OBJECT-TYPE
		SYNTAX    INTEGER { b(0), v(1) }
		ACCESS    read-write
		STATUS    mandatory
		DESCRIPTION
			"b:Blocked  v:Member"
		::= { swhPortTrunkConfigEntry 14 }

	swhPortTrunkConfigDelete OBJECT-TYPE
		SYNTAX    INTEGER { normal(0), delete(1) }
		ACCESS    read-write
		STATUS    mandatory
		DESCRIPTION
			"Delete this trunk setting."
		::= { swhPortTrunkConfigEntry 56 }


-- SwitchManagement(4).LinkAggregation(45).LACPPortConfiguration(6)

	swhLACPPortConfigTable OBJECT-TYPE
		SYNTAX    SEQUENCE OF SWHLACPPortConfigEntry
		ACCESS    not-accessible
		STATUS    mandatory
		DESCRIPTION
			"Table of LACP Port descriptive and status information."
		::= { swhLACPPortConfiguration 1 }

	-- Table Entry
	swhLACPPortConfigEntry OBJECT-TYPE
		SYNTAX    SWHLACPPortConfigEntry
		ACCESS    not-accessible
		STATUS    mandatory
		DESCRIPTION
			"An entry in the table, containing information
			about LACP Port Config."
		INDEX    { swhLACPPortConfigIndex }
		::= { swhLACPPortConfigTable 1 }

	SWHLACPPortConfigEntry ::=
		SEQUENCE {
			swhLACPPortConfigIndex
				INTEGER,
			swhLACPPortConfigKeyValue
				INTEGER,
			swhLACPPortConfigRole
				INTEGER
		}

	swhLACPPortConfigIndex OBJECT-TYPE
		SYNTAX    INTEGER 
		ACCESS    read-only
		STATUS    mandatory
		DESCRIPTION
			"A unique value for each port."
		::= { swhLACPPortConfigEntry 3 }

	swhLACPPortConfigKeyValue OBJECT-TYPE
		SYNTAX    INTEGER (0..255)
		ACCESS    read-write
		STATUS    mandatory
		DESCRIPTION
			"Path Cost is 0-255; 0=auto"
		::= { swhLACPPortConfigEntry 9 }

	swhLACPPortConfigRole OBJECT-TYPE
		SYNTAX    INTEGER { disable(0), passive(1), active(2) }
		ACCESS    read-write
		STATUS    mandatory
		DESCRIPTION
			"Role is passive or active"
		::= { swhLACPPortConfigEntry 12 }


-- SwitchManagement(4).IGMPSnooping(50)

	swhIGMPConfiguration
		OBJECT IDENTIFIER ::= { swhIGMPSnooping 1 }


-- SwitchManagement(4).IGMPSnooping(50).IGMPConfiguration(1)

	swhIGMPConfigSnooping OBJECT-TYPE
		SYNTAX    INTEGER { disable(0), enable(1) }
		ACCESS    read-write
		STATUS    mandatory
		DESCRIPTION
			"IGMP Snooping"
		::= { swhIGMPConfiguration 1 }

	swhIGMPConfigAgingTime OBJECT-TYPE
		SYNTAX    INTEGER (1..3000)
		ACCESS    read-write
		STATUS    mandatory
		DESCRIPTION
			"Aging Time (1/10Sec)"
		::= { swhIGMPConfiguration 59 }

	swhIGMPConfigImmediateLeave OBJECT-TYPE
		SYNTAX    INTEGER { disable(0), enable(1) }
		ACCESS    read-write
		STATUS    mandatory
		DESCRIPTION
			"IGMP Immediate Leave"
		::= { swhIGMPConfiguration 2 }

	swhIGMPConfigRouterPort1 OBJECT-TYPE
		SYNTAX    INTEGER { b(0), v(1) }
		ACCESS    read-write
		STATUS    mandatory
		DESCRIPTION
			"b:Blocked  v:Member"
		::= { swhIGMPConfiguration 5 }

	swhIGMPConfigRouterPort2 OBJECT-TYPE
		SYNTAX    INTEGER { b(0), v(1) }
		ACCESS    read-write
		STATUS    mandatory
		DESCRIPTION
			"b:Blocked  v:Member"
		::= { swhIGMPConfiguration 6 }

	swhIGMPConfigRouterPort3 OBJECT-TYPE
		SYNTAX    INTEGER { b(0), v(1) }
		ACCESS    read-write
		STATUS    mandatory
		DESCRIPTION
			"b:Blocked  v:Member"
		::= { swhIGMPConfiguration 7 }

	swhIGMPConfigRouterPort4 OBJECT-TYPE
		SYNTAX    INTEGER { b(0), v(1) }
		ACCESS    read-write
		STATUS    mandatory
		DESCRIPTION
			"b:Blocked  v:Member"
		::= { swhIGMPConfiguration 8 }

	swhIGMPConfigRouterPort5 OBJECT-TYPE
		SYNTAX    INTEGER { b(0), v(1) }
		ACCESS    read-write
		STATUS    mandatory
		DESCRIPTION
			"b:Blocked  v:Member"
		::= { swhIGMPConfiguration 9 }

	swhIGMPConfigRouterPort6 OBJECT-TYPE
		SYNTAX    INTEGER { b(0), v(1) }
		ACCESS    read-write
		STATUS    mandatory
		DESCRIPTION
			"b:Blocked  v:Member"
		::= { swhIGMPConfiguration 10 }
		
	swhIGMPConfigRouterPort7 OBJECT-TYPE
		SYNTAX    INTEGER { b(0), v(1) }
		ACCESS    read-write
		STATUS    mandatory
		DESCRIPTION
			"b:Blocked  v:Member"
		::= { swhIGMPConfiguration 11 }
		
	swhIGMPConfigRouterPort8 OBJECT-TYPE
		SYNTAX    INTEGER { b(0), v(1) }
		ACCESS    read-write
		STATUS    mandatory
		DESCRIPTION
			"b:Blocked  v:Member"
		::= { swhIGMPConfiguration 12 }
		
	swhIGMPConfigRouterPort9 OBJECT-TYPE
		SYNTAX    INTEGER { b(0), v(1) }
		ACCESS    read-write
		STATUS    mandatory
		DESCRIPTION
			"b:Blocked  v:Member"
		::= { swhIGMPConfiguration 13 }
		
	swhIGMPConfigRouterPort10 OBJECT-TYPE
		SYNTAX    INTEGER { b(0), v(1) }
		ACCESS    read-write
		STATUS    mandatory
		DESCRIPTION
			"b:Blocked  v:Member"
		::= { swhIGMPConfiguration 14 }


-- SwitchManagement(4).IGMPSnooping(50).IGMPVIDConfiguration(5).IGMPVIDConfigTable(1)


-- SwitchManagement(4).IGMPSnooping(50).IGMPSettings(6)


-- SwitchManagement(4).IGMPSnooping(50).IPMCSegment(7)


-- SwitchManagement(4).IGMPSnooping(50).IPMCProfile(8)


-- SwitchManagement(4).IGMPSnooping(50).IGMPFiltering(9)


-- SwitchManagement(4).8021XConfiguration(55)

	swh8021XSystemConfig
		OBJECT IDENTIFIER ::= { swh8021XConfiguration 3 }
	swh8021XPortConfig
		OBJECT IDENTIFIER ::= { swh8021XConfiguration 6 }


-- SwitchManagement(4).8021XConfiguration(55).8021XSystemConfig(3)

	swh8021XSystemConfigMode OBJECT-TYPE
		SYNTAX    INTEGER { disable(0), enable(1) }
		ACCESS    read-write
		STATUS    mandatory
		DESCRIPTION
			"Enable or disable RADIUS client."
		::= { swh8021XSystemConfig 1 }

	swh8021XSystemConfigRADIUSIP OBJECT-TYPE
		SYNTAX    DisplayString
		ACCESS    read-write
		STATUS    mandatory
		DESCRIPTION
			"RADIUS server ip address."
		::= { swh8021XSystemConfig 3 }

	swh8021XSystemConfigRADIUSSecret OBJECT-TYPE
		SYNTAX    DisplayString 
		ACCESS    read-write
		STATUS    mandatory
		DESCRIPTION
			"RADIUS Secret."
		::= { swh8021XSystemConfig 5 }

	swh8021XSystemConfigRauthenticationEn OBJECT-TYPE
		SYNTAX    INTEGER { disable(0), enable(1) }
		ACCESS    read-write
		STATUS    mandatory
		DESCRIPTION
			"Enable or disable RADIUS client."
		::= { swh8021XSystemConfig 9 }

	swh8021XSystemConfigRadiusAssignedVLANEn OBJECT-TYPE
		SYNTAX    INTEGER { disable(0), enable(1) }
		ACCESS    read-write
		STATUS    mandatory
		DESCRIPTION
			"Enable or disable RADIUS-Assigned VLAN."
		::= { swh8021XSystemConfig 15 }

--	swh8021XSystemConfigRauthenticationPeriod OBJECT-TYPE
--		SYNTAX    INTEGER (1..3600)
--		ACCESS    read-write
--		STATUS    mandatory
--		DESCRIPTION
--			"Rauthentication Period."
--		::= { swh8021XSystemConfig 11 }

--	swh8021XSystemConfigEAPTimeout OBJECT-TYPE
--		SYNTAX    INTEGER (1..255)
--		ACCESS    read-write
--		STATUS    mandatory
--		DESCRIPTION
--			"EAP Timeout."
--		::= { swh8021XSystemConfig 13 }


-- SwitchManagement(4).8021XConfiguration(55).8021XPortConfig(6).8021XPortConfigTable(1)

	swh8021XPortConfigTable OBJECT-TYPE
		SYNTAX    SEQUENCE OF Swh8021XPortConfigEntry
		ACCESS    not-accessible
		STATUS    mandatory
		DESCRIPTION
			"Table of 802.1X Port Configuration."
		::= { swh8021XPortConfig 1 }

	-- Table Entry
	swh8021XPortConfigEntry OBJECT-TYPE
		SYNTAX    Swh8021XPortConfigEntry
		ACCESS    not-accessible
		STATUS    mandatory
		DESCRIPTION
			"An entry in the table, containing information
			about 802.1X Port Config."
		INDEX    { swh8021XPortConfigIndex }
		::= { swh8021XPortConfigTable 1 }

	Swh8021XPortConfigEntry ::=
		SEQUENCE {
			swh8021XPortConfigIndex
				INTEGER,
			swh8021XPortConfigAdminState
				INTEGER,
			swh8021XPortConfigMAB
				INTEGER,
			swh8021XPortConfigRadiusAssignedVLAN
				INTEGER,
			swh8021XPortConfigreAuthEnable
				INTEGER,
			swh8021XPortConfigreAuthSec
				INTEGER,
			swh8021XPortConfigEAPTimeout
				INTEGER,
			swh8021XPortConfigMaxreq
				INTEGER,
			swh8021XPortConfigReauthenticate
				INTEGER
		}

	swh8021XPortConfigIndex OBJECT-TYPE
		SYNTAX    INTEGER (0..2147483647)
		ACCESS    not-accessible
		STATUS    mandatory
		DESCRIPTION
			"A unique value for each Port."
		::= { swh8021XPortConfigEntry 1 }

	swh8021XPortConfigAdminState OBJECT-TYPE
		SYNTAX    INTEGER { auto(0), authorized(1), unauthorized(2) }
		ACCESS    read-write
		STATUS    mandatory
		DESCRIPTION
			"Admin State setting is auto or authorized or unauthorized."
		::= { swh8021XPortConfigEntry 3 }

	swh8021XPortConfigReauthenticate OBJECT-TYPE
		SYNTAX    INTEGER { disable(0), enable(1) }
		ACCESS    read-write
		STATUS    mandatory
		DESCRIPTION
			"Reauthenticate is Disable or Enable"
		::= { swh8021XPortConfigEntry 5 }

	swh8021XPortConfigRadiusAssignedVLAN OBJECT-TYPE
		SYNTAX    INTEGER { disable(0), enable(1) }
		ACCESS    read-write
		STATUS    mandatory
		DESCRIPTION
			"Radius-Assigned VLAN is Disable or Enable"
		::= { swh8021XPortConfigEntry 7 }

	swh8021XPortConfigMAB OBJECT-TYPE
		SYNTAX    INTEGER { disable(0), enable(1) }
		ACCESS    read-write
		STATUS    mandatory
		DESCRIPTION
			"MAB is Disable or Enable"
		::= { swh8021XPortConfigEntry 9 }

	swh8021XPortConfigreAuthEnable OBJECT-TYPE
		SYNTAX    INTEGER { disable(0), enable(1) }
		ACCESS    read-write
		STATUS    mandatory
		DESCRIPTION
			"reAuth Enable is Disable or Enable"
		::= { swh8021XPortConfigEntry 11 }

	swh8021XPortConfigreAuthSec OBJECT-TYPE
		SYNTAX    INTEGER (1..65535)
		ACCESS    read-write
		STATUS    mandatory
		DESCRIPTION
			"reAuth Sec Per Port"
		::= { swh8021XPortConfigEntry 13 }

	swh8021XPortConfigEAPTimeout OBJECT-TYPE
		SYNTAX    INTEGER (1..255)
		ACCESS    read-write
		STATUS    mandatory
		DESCRIPTION
			"EAP Timeout Per Port"
		::= { swh8021XPortConfigEntry 15 }

	swh8021XPortConfigMaxreq OBJECT-TYPE
		SYNTAX    INTEGER (1..10)
		ACCESS    read-write
		STATUS    mandatory
		DESCRIPTION
			"Maxreq Per Port"
		::= { swh8021XPortConfigEntry 17 }


-- SwitchManagement(4).QoSConfiguration(60)


-- SwitchManagement(4).QoSConfiguration(60).QoSConfigPriority(1)


-- SwitchManagement(4).QoSConfiguration(60).QoSConfigPriority(1).QoSConfig8021pPriorityTable(5)


-- SwitchManagement(4).QoSConfiguration(60).QoSConfigPriority(1).QoSConfigDSCPPriorityTable(6)


-- SwitchManagement(4).QoSConfiguration(60).QoSConfigPriority(1).QoSConfig8021pRemarkingTable(31)


-- SwitchManagement(4).QoSConfiguration(60).QoSConfigPriority(1).QoSConfigDSCPRemarkingTable(41)


-- SwitchManagement(4).QoSConfiguration(60).QoSConfigPortConfig(3).QoSConfigPortConfigTable(1)


-- SwitchManagement(4).QoSConfiguration(60).QoSConfigControlList(6)


-- SwitchManagement(4).QoSConfiguration(60).QoSConfigRateLimiters(9)


-- SwitchManagement(4).QoSConfiguration(60).QoSConfigRateLimiters(9).QoSConfigRateLimitersTable(1)


-- SwitchManagement(4).QoSConfiguration(60).QoSConfigStormControl(12)


-- SwitchManagement(4).DSCPRemark(61)


-- SwitchManagement(4).DSCPRemark(61).PortDSCPRemarking(1)


-- SwitchManagement(4).DSCPRemark(61).Port8021pRemarking(2)


-- SwitchManagement(4).DSCPRemark(61).DSCPQueueMapping(3)


-- SwitchManagement(4).DSCPRemark(61).8021pQueueMapping(4)


-- SwitchManagement(4).DSCPRemarkingvoip(63)


-- SwitchManagement(4).ACLConfiguration(65)


-- SwitchManagement(4).ACLConfiguration(65).ACLPortConfiguration(1)


-- SwitchManagement(4).ACLConfiguration(65).ACLRateLimiters(2)


-- SwitchManagement(4).ACLConfiguration(65).AccessControlList(3)


-- SwitchManagement(4).StaticMulticastConfiguration(70).MulticastTable(1)


-- SwitchManagement(4).MVRConfiguration(75)


-- SwitchManagement(4).MVRConfiguration(75).MVRSettings(1)


-- SwitchManagement(4).MVRConfiguration(75).MVRGroups(2)


-- SwitchManagement(4).SecurityConfiguration(80)

	swhFilterConfiguration
		OBJECT IDENTIFIER ::= { swhSecurityConfiguration 3 }


-- SwitchManagement(4).SecurityConfiguration(80).DHCPOpt82Settings(1)


-- SwitchManagement(4).SecurityConfiguration(80).IPSourceGuardSettings(2)


-- SwitchManagement(4).SecurityConfiguration(80).FilterConfiguration(3)

	swhFilterConfigDHCPSnooping OBJECT-TYPE
		SYNTAX    INTEGER { disable(0), enable(1) }
		ACCESS    read-write
		STATUS    mandatory
		DESCRIPTION
			"Enable or disable DHCP Snooping.
			 When DHCP Snooping is enable, ARP/IPv4 filter will also be enable simultaneously"
		::= { swhFilterConfiguration 1 }

--	swhFilterConfigDefaultDHCPInitiatedTime OBJECT-TYPE
--		SYNTAX    INTEGER (0..9999)
--		ACCESS    read-write
--		STATUS    mandatory
--		DESCRIPTION
--			"Default DHCP Initiated Time. 0-9999"
--		::= { swhFilterConfiguration 2 }

--	swhFilterConfigDefaultDHCPLeasedTime OBJECT-TYPE
--		SYNTAX    INTEGER (180..259200)
--		ACCESS    read-write
--		STATUS    mandatory
--		DESCRIPTION
--			"Default DHCP Leased Time. 180-259200"
--		::= { swhFilterConfiguration 3 }

--	swhFilterConfigPortIsolation OBJECT-TYPE
--		SYNTAX    INTEGER { disable(0), enable(1) }
--		ACCESS    read-write
--		STATUS    mandatory
--		DESCRIPTION
--			"Enable or disable Port Isolation"
--		::= { swhFilterConfiguration 4 }

--	swhFilterConfigIPv6 OBJECT-TYPE
--		SYNTAX    INTEGER { disable(0), enable(1) }
--		ACCESS    read-write
--		STATUS    mandatory
--		DESCRIPTION
--			"Enable or disable IPv6 auto discovery / DHCPv6"
--		::= { swhFilterConfiguration 5 }

--	swhFilterConfigUPnP OBJECT-TYPE
--		SYNTAX    INTEGER { disable(0), enable(1) }
--		ACCESS    read-write
--		STATUS    mandatory
--		DESCRIPTION
--			"Enable or disable UPnP"
--		::= { swhFilterConfiguration 6 }


-- SwitchManagement(4).SecurityConfiguration(80).FilterConfiguration(3).DHCPServerTrustPort(7)

	swhSecurityDHCPServerTrustPort
		OBJECT IDENTIFIER ::= { swhFilterConfiguration 7 }


-- SwitchManagement(4).SecurityConfiguration(80).FilterConfiguration(3).DHCPServerTrustPort(7).DHCPServerTable(1)

	swhSecurityDHCPServerTable OBJECT-TYPE
		SYNTAX    SEQUENCE OF SWHSecurityDHCPServerTableEntry
		ACCESS    not-accessible
		STATUS    mandatory
		DESCRIPTION
			"Table of DHCP Server Trust Port."
		::= { swhSecurityDHCPServerTrustPort 1 }

	-- Table Entry
	SWHSecurityDHCPServerTableEntry OBJECT-TYPE
		SYNTAX    SWHSecurityDHCPServerTableEntry
		ACCESS    not-accessible
		STATUS    mandatory
		DESCRIPTION
			"An entry in the table, containing information
			about DHCP Server Trust Port."
		INDEX     { swhSecurityDHCPServerTableIndex }
		::= { swhSecurityDHCPServerTable 1 }

	SWHSecurityDHCPServerTableEntry ::=
		SEQUENCE {
			swhSecurityDHCPServerTableIndex
				INTEGER,
			swhSecurityDHCPServerTableState
				INTEGER
		}

	swhSecurityDHCPServerTableIndex OBJECT-TYPE
		SYNTAX    INTEGER
		ACCESS    read-only
		STATUS    mandatory
		DESCRIPTION
			"A unique value for each port."
		::= { SWHSecurityDHCPServerTableEntry 1 }

	swhSecurityDHCPServerTableState OBJECT-TYPE
		SYNTAX    INTEGER { disable(0), enable(1) }
		ACCESS    read-write
		STATUS    mandatory
		DESCRIPTION
			"enable or disable port"
		::= { SWHSecurityDHCPServerTableEntry 2 }


-- SwitchManagement(4).SecurityConfiguration(80).FilterConfiguration(3).DHCPServerTrustIP(8)


-- SwitchManagement(4).SecurityConfiguration(80).FilterConfiguration(3).DHCPServerTrustIP(8).DHCPServerIP(1)


-- SwitchManagement(4).SecurityConfiguration(80).FilterConfiguration(3).DHCPServerTrustIP(8).DHCPServerIPTable(2)


-- SwitchManagement(4).SecurityConfiguration(80).StaticIPTableConfiguration(4).StaticIPTable(1)


-- SwitchManagement(4).SecurityConfiguration(80).AntiBcast(6)


-- SwitchManagement(4).SecurityConfiguration(80).DHCPRecordPortSettings(8)


-- SwitchManagement(4).SecurityConfiguration(80).StormControl(12)


-- SwitchManagement(4).FilterConfiguration(83)


-- SwitchManagement(4).FilterConfiguration(83).DHCPServerTrustPort(7)


-- SwitchManagement(4).FilterConfiguration(83).DHCPServerTrustPort(7).DHCPServerTable(1)


-- SwitchManagement(4).HTTPAuthentication(90)


-- SwitchManagement(4).FastRedundancy(91)

	swhFastRedundancyConfigTable OBJECT-TYPE
		SYNTAX    SEQUENCE OF SwhFastRedundancyConfigEntry
		ACCESS    not-accessible
		STATUS    mandatory
		DESCRIPTION
			"Table of digital input config."
		::= { swhFastRedundancy 1 }

	-- Table Entry
	swhFastRedundancyConfigEntry OBJECT-TYPE
		SYNTAX    SwhFastRedundancyConfigEntry
		ACCESS    not-accessible
		STATUS    mandatory
		DESCRIPTION
			"An entry in the table, containing information
			about digital input config."
		INDEX    { swhFastRedundancyConfigIndex }
		::= { swhFastRedundancyConfigTable 1 }

	SwhFastRedundancyConfigEntry ::=
		SEQUENCE {
			swhFastRedundancyConfigIndex
				INTEGER,
			swhFastRedundancyConfigValid
				INTEGER,
			swhFastRedundancyConfigGroupID
				INTEGER,
			swhFastRedundancyConfigDescription
				DisplayString,
			swhFastRedundancyConfigProtocol
				INTEGER,
			swhFastRedundancyConfigEnable
				INTEGER,
			swhFastRedundancyConfigRole
				INTEGER,
			swhFastRedundancyConfigPort1
				INTEGER,
			swhFastRedundancyConfigPort1Role
				INTEGER,
			swhFastRedundancyConfigPort2
				INTEGER,
			swhFastRedundancyConfigPort2Role
				INTEGER,
			swhFastRedundancyConfigDelete
				INTEGER
		}

	swhFastRedundancyConfigIndex OBJECT-TYPE
		SYNTAX    INTEGER (0..2147483647)
		ACCESS    not-accessible
		STATUS    mandatory
		DESCRIPTION
			"A unique value for each digital input."
		::= { swhFastRedundancyConfigEntry 1 }

	swhFastRedundancyConfigValid OBJECT-TYPE
		SYNTAX    INTEGER { invalid(0), valid(1) }
		ACCESS    read-only
		STATUS    mandatory
		DESCRIPTION
			"digital input normal."
		::= { swhFastRedundancyConfigEntry 2 }

	swhFastRedundancyConfigGroupID OBJECT-TYPE
		SYNTAX    INTEGER { id-1(1),
		                    id-2(2)
		                    }
		ACCESS    read-write
		STATUS    mandatory
		DESCRIPTION
			"digital input normal."
		::= { swhFastRedundancyConfigEntry 3 }

	swhFastRedundancyConfigDescription OBJECT-TYPE
		SYNTAX    DisplayString
		ACCESS    read-write
		STATUS    mandatory
		DESCRIPTION
			"Fast Redundancy Description"
		::= { swhFastRedundancyConfigEntry 4 }

	swhFastRedundancyConfigProtocol OBJECT-TYPE
		SYNTAX    INTEGER { fast-ringv2(0), chain(1) }
		ACCESS    read-write
		STATUS    mandatory
		DESCRIPTION
			"Fast Redundancy Enable."
		::= { swhFastRedundancyConfigEntry 5 }

	swhFastRedundancyConfigEnable OBJECT-TYPE
		SYNTAX    INTEGER { disable(0), enable(1) }
		ACCESS    read-write
		STATUS    mandatory
		DESCRIPTION
			"Fast Redundancy Enable."
		::= { swhFastRedundancyConfigEntry 6 }

	swhFastRedundancyConfigRole OBJECT-TYPE
		SYNTAX    INTEGER { disable(-1), slave(0), master(1) }
		ACCESS    read-write
		STATUS    mandatory
		DESCRIPTION
			"Fast Redundancy Role."
		::= { swhFastRedundancyConfigEntry 7 }

	swhFastRedundancyConfigPort1 OBJECT-TYPE
		SYNTAX    INTEGER { disable(0),
		                    port01(1),
		                    port02(2),
		                    port03(3),
		                    port04(4),
		                    port05(5),
		                    port06(6),
		                    port07(7),
		                    port08(8),
		                    port09(9),
		                    port10(10)
		                    }
		ACCESS    read-write
		STATUS    mandatory
		DESCRIPTION
			"Port Number."
		::= { swhFastRedundancyConfigEntry 8 }

	swhFastRedundancyConfigPort1Role OBJECT-TYPE
		SYNTAX    INTEGER { member(0), head(1), tail(2) }
		ACCESS    read-write
		STATUS    mandatory
		DESCRIPTION
			"Fast Redundancy Port1 Role."
		::= { swhFastRedundancyConfigEntry 9 }

	swhFastRedundancyConfigPort2 OBJECT-TYPE
		SYNTAX    INTEGER { disable(0),
		                    port01(1),
		                    port02(2),
		                    port03(3),
		                    port04(4),
		                    port05(5),
		                    port06(6),
		                    port07(7),
		                    port08(8),
		                    port09(9),
		                    port10(10)
		                    }
		ACCESS    read-write
		STATUS    mandatory
		DESCRIPTION
			"Port Number."
		::= { swhFastRedundancyConfigEntry 10 }

	swhFastRedundancyConfigPort2Role OBJECT-TYPE
		SYNTAX    INTEGER { member(0) }
		ACCESS    read-only
		STATUS    mandatory
		DESCRIPTION
			"Fast Redundancy Port2 Role."
		::= { swhFastRedundancyConfigEntry 11 }

	swhFastRedundancyConfigDelete OBJECT-TYPE
		SYNTAX    INTEGER { normal(0), delete(1) }
		ACCESS    read-write
		STATUS    mandatory
		DESCRIPTION
			"Delete this entry."
		::= { swhFastRedundancyConfigEntry 13 }


-- SwitchMonitor(5)

	swhPortStatus
		OBJECT IDENTIFIER ::= { swhSwitchMonitor 1 }
	swhPortCountersRates
		OBJECT IDENTIFIER ::= { swhSwitchMonitor 5 }
	swhPortCountersEvents
		OBJECT IDENTIFIER ::= { swhSwitchMonitor 6 }
	swhSFPInformation
		OBJECT IDENTIFIER ::= { swhSwitchMonitor 34 }
	swh8021QTagVLAN
		OBJECT IDENTIFIER ::= { swhSwitchMonitor 3 }
	swhLACPPortStatus
		OBJECT IDENTIFIER ::= { swhSwitchMonitor 22 }
	swhLACPStatistics
		OBJECT IDENTIFIER ::= { swhSwitchMonitor 24 }
	swhRSTPBridgeOverview
		OBJECT IDENTIFIER ::= { swhSwitchMonitor 10 }
	swhRSTPPortStatus
		OBJECT IDENTIFIER ::= { swhSwitchMonitor 14 }
	swhRSTPStatistics
		OBJECT IDENTIFIER ::= { swhSwitchMonitor 18 }
	swh8021XPortStatus
		OBJECT IDENTIFIER ::= { swhSwitchMonitor 32 }
	swh8021XStatistics
		OBJECT IDENTIFIER ::= { swhSwitchMonitor 33 }
	swhIGMPGroupTable
		OBJECT IDENTIFIER ::= { swhSwitchMonitor 28 }
	swhMacAddressTable
		OBJECT IDENTIFIER ::= { swhSwitchMonitor 7 }
	swhLLDPStatus
		OBJECT IDENTIFIER ::= { swhSwitchMonitor 11 }
	swhLoopDetectionStatus
		OBJECT IDENTIFIER ::= { swhSwitchMonitor 36 }
	swhRingStatus
		OBJECT IDENTIFIER ::= { swhSwitchMonitor 43 }
	swhFastRedundancyStatus
		OBJECT IDENTIFIER ::= { swhSwitchMonitor 52 }
	swhPOEStatus
		OBJECT IDENTIFIER ::= { swhSwitchMonitor 48 }
--	swhDIDOStatus
--		OBJECT IDENTIFIER ::= { swhSwitchMonitor 41 }


-- SwitchMonitor(5).PortState(1)

	swhPortStatusTable OBJECT-TYPE
		SYNTAX    SEQUENCE OF SWHPortStatusEntry
		ACCESS    not-accessible
		STATUS    mandatory
		DESCRIPTION
			"Table of Port State."
		::= { swhPortStatus 1 }

	-- Table Entry
	swhPortStatusEntry OBJECT-TYPE
		SYNTAX    SWHPortStatusEntry
		ACCESS    not-accessible
		STATUS    mandatory
		DESCRIPTION
			"An entry in the table, containing information
			 about Port State."
		INDEX    { swhPortStatusIndex }
		::= { swhPortStatusTable 1 }

	SWHPortStatusEntry ::=
		SEQUENCE {
			swhPortStatusIndex
				INTEGER,
			swhPortStatusPortMedia
				INTEGER,
			swhPortStatusPortState
				INTEGER,
			swhPortStatusPortLink
				INTEGER,
			swhPortStatusPortSpeed
				INTEGER,
			swhPortStatusPortDuplex
				INTEGER,
			swhPortStatusPortFlowCtrl
				INTEGER,
			swhPortStatusDescription
				DisplayString
		}

	swhPortStatusIndex OBJECT-TYPE
		SYNTAX    INTEGER
		ACCESS    read-only
		STATUS    mandatory
		DESCRIPTION
			"A unique value for each port."
		::= { swhPortStatusEntry 1 }

	swhPortStatusDescription OBJECT-TYPE
		SYNTAX    DisplayString
		ACCESS    read-only
		STATUS    mandatory
		DESCRIPTION
			"Port Description"
		::= { swhPortStatusEntry 2 }

	swhPortStatusPortMedia OBJECT-TYPE
		SYNTAX    INTEGER { n2a(-2), na(-1), tx(1), fx(2) }
		ACCESS    read-only
		STATUS    mandatory
		DESCRIPTION
			"Port Media Type"
		::= { swhPortStatusEntry 3 }

	swhPortStatusPortState OBJECT-TYPE
		SYNTAX    INTEGER { na2(-2), na(-1), disable(0), blocking-listening(1), learning(2), forwarding(3) }
		ACCESS    read-only
		STATUS    mandatory
		DESCRIPTION
			"Port State"
		::= { swhPortStatusEntry 4 }

	swhPortStatusPortLink OBJECT-TYPE
		SYNTAX    INTEGER { na2(-2), na(-1), up(1), down(2) }
		ACCESS    read-only
		STATUS    mandatory
		DESCRIPTION
			"Port Link"
		::= { swhPortStatusEntry 5 }

	swhPortStatusPortSpeed OBJECT-TYPE
		SYNTAX    INTEGER { na2(-2), na(-1) }
		ACCESS    read-only
		STATUS    mandatory
		DESCRIPTION
			"Port Speed"
		::= { swhPortStatusEntry 6 }

	swhPortStatusPortDuplex OBJECT-TYPE
		SYNTAX    INTEGER { na(-2), na(-1), full(1), half(2) }
		ACCESS    read-only
		STATUS    mandatory
		DESCRIPTION
			"Port Duplex"
		::= { swhPortStatusEntry 7 }

	swhPortStatusPortFlowCtrl OBJECT-TYPE
		SYNTAX    INTEGER { na2(-2), na(-1), on(1), off(2) }
		ACCESS    read-only
		STATUS    mandatory
		DESCRIPTION
			"Port Flow Control"
		::= { swhPortStatusEntry 8 }


-- SwitchMonitor(5).8021QTagVLAN(3)

	swh8021QTagVLANTable OBJECT-TYPE
		SYNTAX    SEQUENCE OF SWH8021QTagVLANEntry
		ACCESS    not-accessible
		STATUS    mandatory
		DESCRIPTION
			"Table of 802.1Q Tag VLAN Configuration."
		::= { swh8021QTagVLAN 1 }

	-- Table Entry
	swh8021QTagVLANEntry OBJECT-TYPE
		SYNTAX    SWH8021QTagVLANEntry
		ACCESS    not-accessible
		STATUS    mandatory
		DESCRIPTION
			"An entry in the table, containing information
			about tag vlan config."
		INDEX    { swh8021QTagVLANIndex }
		::= { swh8021QTagVLANTable 1 }

	SWH8021QTagVLANEntry ::=
		SEQUENCE {
			swh8021QTagVLANIndex
				INTEGER,
			swh8021QTagVLANVID
				INTEGER,
			swh8021QTagVLANName
				DisplayString,
			swh8021QTagVLANPort1
				INTEGER,
			swh8021QTagVLANPort2
				INTEGER,
			swh8021QTagVLANPort3
				INTEGER,
			swh8021QTagVLANPort4
				INTEGER,
			swh8021QTagVLANPort5
				INTEGER,
			swh8021QTagVLANPort6
				INTEGER,
			swh8021QTagVLANPort7
				INTEGER,
			swh8021QTagVLANPort8
				INTEGER,
			swh8021QTagVLANPort9
				INTEGER,
			swh8021QTagVLANPort10
				INTEGER,
			swh8021QTagVLANCPU
				INTEGER
		}

	swh8021QTagVLANIndex OBJECT-TYPE
		SYNTAX    INTEGER 
		ACCESS    read-only
		STATUS    mandatory
		DESCRIPTION
			"A unique value for each vlan."
		::= { swh8021QTagVLANEntry 1 }

	swh8021QTagVLANVID OBJECT-TYPE
		SYNTAX    INTEGER (1..4094)
		ACCESS    read-only
		STATUS    mandatory
		DESCRIPTION
			"VLAN ID"
		::= { swh8021QTagVLANEntry 3 }

	swh8021QTagVLANName OBJECT-TYPE
		SYNTAX    DisplayString
		ACCESS    read-only
		STATUS    mandatory
		DESCRIPTION
			"Port based vlan name."
		::= { swh8021QTagVLANEntry 4 }

	swh8021QTagVLANPort1 OBJECT-TYPE
		SYNTAX    INTEGER { b(0), t(2), u(3), d(4) }
		ACCESS    read-only
		STATUS    mandatory
		DESCRIPTION
			"b:Blocked  t:Tagged u:Untagged d:Dot1q-Tunnel"
		::= { swh8021QTagVLANEntry 5 }

	swh8021QTagVLANPort2 OBJECT-TYPE
		SYNTAX    INTEGER { b(0), t(2), u(3), d(4) }
		ACCESS    read-only
		STATUS    mandatory
		DESCRIPTION
			"b:Blocked  t:Tagged u:Untagged d:Dot1q-Tunnel"
		::= { swh8021QTagVLANEntry 6 }

	swh8021QTagVLANPort3 OBJECT-TYPE
		SYNTAX    INTEGER { b(0), t(2), u(3), d(4) }
		ACCESS    read-only
		STATUS    mandatory
		DESCRIPTION
			"b:Blocked  t:Tagged u:Untagged d:Dot1q-Tunnel"
		::= { swh8021QTagVLANEntry 7 }

	swh8021QTagVLANPort4 OBJECT-TYPE
		SYNTAX    INTEGER { b(0), t(2), u(3), d(4) }
		ACCESS    read-only
		STATUS    mandatory
		DESCRIPTION
			"b:Blocked  t:Tagged u:Untagged d:Dot1q-Tunnel"
		::= { swh8021QTagVLANEntry 8 }

	swh8021QTagVLANPort5 OBJECT-TYPE
		SYNTAX    INTEGER { b(0), t(2), u(3), d(4) }
		ACCESS    read-only
		STATUS    mandatory
		DESCRIPTION
			"b:Blocked  t:Tagged u:Untagged d:Dot1q-Tunnel"
		::= { swh8021QTagVLANEntry 9 }

	swh8021QTagVLANPort6 OBJECT-TYPE
		SYNTAX    INTEGER { b(0), t(2), u(3), d(4) }
		ACCESS    read-only
		STATUS    mandatory
		DESCRIPTION
			"b:Blocked  t:Tagged u:Untagged d:Dot1q-Tunnel"
		::= { swh8021QTagVLANEntry 10 }
		
	swh8021QTagVLANPort7 OBJECT-TYPE
		SYNTAX    INTEGER { b(0), t(2), u(3), d(4) }
		ACCESS    read-only
		STATUS    mandatory
		DESCRIPTION
			"b:Blocked  t:Tagged u:Untagged d:Dot1q-Tunnel"
		::= { swh8021QTagVLANEntry 11 }
	
	swh8021QTagVLANPort8 OBJECT-TYPE
		SYNTAX    INTEGER { b(0), t(2), u(3), d(4) }
		ACCESS    read-only
		STATUS    mandatory
		DESCRIPTION
			"b:Blocked  t:Tagged u:Untagged d:Dot1q-Tunnel"
		::= { swh8021QTagVLANEntry 12 }
		
	swh8021QTagVLANPort9 OBJECT-TYPE
		SYNTAX    INTEGER { b(0), t(2), u(3), d(4) }
		ACCESS    read-only
		STATUS    mandatory
		DESCRIPTION
			"b:Blocked  t:Tagged u:Untagged d:Dot1q-Tunnel"
		::= { swh8021QTagVLANEntry 13 }
		
	swh8021QTagVLANPort10 OBJECT-TYPE
		SYNTAX    INTEGER { b(0), t(2), u(3), d(4) }
		ACCESS    read-only
		STATUS    mandatory
		DESCRIPTION
			"b:Blocked  t:Tagged u:Untagged d:Dot1q-Tunnel"
		::= { swh8021QTagVLANEntry 14 }

	swh8021QTagVLANCPU OBJECT-TYPE
		SYNTAX    INTEGER { b(0), v(1) }
		ACCESS    read-only
		STATUS    mandatory
		DESCRIPTION
			"b:Blocked  v:Member"
		::= { swh8021QTagVLANEntry 55 }


-- SwitchMonitor(5).PortInformation(4)


-- SwitchMonitor(5).PortCountersRates(5)

	swhCountersRatesTable OBJECT-TYPE
		SYNTAX    SEQUENCE OF SWHCountersRatesEntry
		ACCESS    not-accessible
		STATUS    mandatory
		DESCRIPTION
			"Table of Port counters rates."
		::= { swhPortCountersRates 1 }

	-- Table Entry
	swhCountersRatesEntry OBJECT-TYPE
		SYNTAX    SWHCountersRatesEntry
		ACCESS    not-accessible
		STATUS    mandatory
		DESCRIPTION
			"An entry in the table, containing information
			about Port counters rates mode."
		INDEX    { swhCountersRatesIndex }
		::= { swhCountersRatesTable 1 }

	SWHCountersRatesEntry ::=
		SEQUENCE {
			swhCountersRatesIndex
				INTEGER,
			swhCountersRatesBytesReceived
				Counter32,
			swhCountersRatesFramesReceived
				Counter32,
			swhCountersRatesReceivedUtilization
				DisplayString,
			swhCountersRatesBytesSent
				Counter32,
			swhCountersRatesFramesSent
				Counter32,
			swhCountersRatesSentUtilization
				DisplayString,
			swhCountersRatesTotalBytes
				Counter32,
			swhCountersRatesTotalUtilization
				DisplayString,
		--	swhCountersRatesRxCRCAlignError
		--		Counter32,
			swhCountersRatesRxCRCError
				Counter32,
		--	swhCountersRatesRxAlignError
		--		Counter32,
			swhCountersRatesRxUndersizeFrames
				Counter32,
			swhCountersRatesRxFragments
				Counter32,
		--	swhCountersRatesRxJabbers
		--		Counter32,
		--	swhCountersRatesRxOversizeFrames
		--		Counter32,
		--	swhCountersRatesRxDroppedFrames
		--		Counter32,
		--	swhCountersRatesTxCollision
		--		Counter32,
		--	swhCountersRatesTxDroppedFrames
		--		Counter32,
			swhCountersRatesTotalErrors
				Counter32,
			swhCountersRatesRxFrames64
				Counter32,
			swhCountersRatesRxFrames65to127
				Counter32,
			swhCountersRatesRxFrames128to255
				Counter32,
			swhCountersRatesRxFrames256to511
				Counter32,
			swhCountersRatesRxFrames512to1023
				Counter32,
			swhCountersRatesRxFrames1024to10240
				Counter32,
		--	swhCountersRatesRxFrames1519toMaxSize
		--		Counter32,
			swhCountersRatesTxMulticastFrames
				Counter32,
			swhCountersRatesTxBroadcastFrames
				Counter32,
			swhCountersRatesRxMulticastFrames
				Counter32,
			swhCountersRatesRxBroadcastFrames
				Counter32
		--	swhCountersRatesRxFilteredFrames
		--		Counter32,
		--	swhCountersRatesTxLateCollision
		--		Counter32,
		--	swhCountersRatesTxDeferred
		--		Counter32
		--	swhCountersRatesTxTotalCollision
		--		Counter32,
		--	swhCountersRatesRxFrames1024toMaxSize
		--		Counter32,
		--	swhCountersRatesRxUnicastFrames
		--		Counter32,
		--	swhCountersRatesTxUnicastFrames
		--		Counter32,
		--	swhCountersRatesRxTotalErrors
		--		Counter32,
		--	swhCountersRatesTxTotalErrors
		--		Counter32,
		--	swhCountersRatesTxTotalCollisions
		--		Counter32
		}

	swhCountersRatesIndex OBJECT-TYPE
		SYNTAX    INTEGER
		ACCESS    read-only
		STATUS    mandatory
		DESCRIPTION
			"A unique value for each Port."
		::= { swhCountersRatesEntry 1 }

	swhCountersRatesBytesReceived OBJECT-TYPE
		SYNTAX    Counter32
		ACCESS    read-only
		STATUS    mandatory
		DESCRIPTION
			""
		::= { swhCountersRatesEntry 2 }

	swhCountersRatesFramesReceived OBJECT-TYPE
		SYNTAX    Counter32
		ACCESS    read-only
		STATUS    mandatory
		DESCRIPTION
			""
		::= { swhCountersRatesEntry 3 }

	swhCountersRatesReceivedUtilization OBJECT-TYPE
		SYNTAX    DisplayString
		ACCESS    read-only
		STATUS    mandatory
		DESCRIPTION
			""
		::= { swhCountersRatesEntry 4 }

	swhCountersRatesBytesSent OBJECT-TYPE
		SYNTAX    Counter32
		ACCESS    read-only
		STATUS    mandatory
		DESCRIPTION
			""
		::= { swhCountersRatesEntry 5 }

	swhCountersRatesFramesSent OBJECT-TYPE
		SYNTAX    Counter32
		ACCESS    read-only
		STATUS    mandatory
		DESCRIPTION
			""
		::= { swhCountersRatesEntry 6 }

	swhCountersRatesSentUtilization OBJECT-TYPE
		SYNTAX    DisplayString
		ACCESS    read-only
		STATUS    mandatory
		DESCRIPTION
			""
		::= { swhCountersRatesEntry 7 }

	swhCountersRatesTotalBytes OBJECT-TYPE
		SYNTAX    Counter32
		ACCESS    read-only
		STATUS    mandatory
		DESCRIPTION
			""
		::= { swhCountersRatesEntry 8 }

	swhCountersRatesTotalUtilization OBJECT-TYPE
		SYNTAX    DisplayString
		ACCESS    read-only
		STATUS    mandatory
		DESCRIPTION
			""
		::= { swhCountersRatesEntry 9 }

	swhCountersRatesRxCRCError OBJECT-TYPE
		SYNTAX    Counter32
		ACCESS    read-only
		STATUS    mandatory
		DESCRIPTION
			""
		::= { swhCountersRatesEntry 10 }

	swhCountersRatesRxFragments OBJECT-TYPE
		SYNTAX    Counter32
		ACCESS    read-only
		STATUS    mandatory
		DESCRIPTION
			""
		::= { swhCountersRatesEntry 11 }

--	swhCountersRatesRxFilteredFrames OBJECT-TYPE
--		SYNTAX    Counter32
--		ACCESS    read-only
--		STATUS    mandatory
--		DESCRIPTION
--			""
--		::= { swhCountersRatesEntry 12 }

--	swhCountersRatesRxAlignError OBJECT-TYPE
--		SYNTAX    Counter32
--		ACCESS    read-only
--		STATUS    mandatory
--		DESCRIPTION
--			""
--		::= { swhCountersRatesEntry 13 }

	swhCountersRatesRxUndersizeFrames OBJECT-TYPE
		SYNTAX    Counter32
		ACCESS    read-only
		STATUS    mandatory
		DESCRIPTION
			""
		::= { swhCountersRatesEntry 14 }

--	swhCountersRatesRxOversizeFrames OBJECT-TYPE
--		SYNTAX    Counter32
--		ACCESS    read-only
--		STATUS    mandatory
--		DESCRIPTION
--			""
--		::= { swhCountersRatesEntry 15 }

--	swhCountersRatesRxJabbers OBJECT-TYPE
--		SYNTAX    Counter32
--		ACCESS    read-only
--		STATUS    mandatory
--		DESCRIPTION
--			""
--		::= { swhCountersRatesEntry 16 }

--	swhCountersRatesRxDroppedFrames OBJECT-TYPE
--		SYNTAX    Counter32
--		ACCESS    read-only
--		STATUS    mandatory
--		DESCRIPTION
--			""
--		::= { swhCountersRatesEntry 17 }

--	swhCountersRatesTxDroppedFrames OBJECT-TYPE
--		SYNTAX    Counter32
--		ACCESS    read-only
--		STATUS    mandatory
--		DESCRIPTION
--			""
--		::= { swhCountersRatesEntry 18 }

--	swhCountersRatesTxLateCollision OBJECT-TYPE
--		SYNTAX    Counter32
--		ACCESS    read-only
--		STATUS    mandatory
--		DESCRIPTION
--			""
--		::= { swhCountersRatesEntry 19 }

--	swhCountersRatesTxDeferred OBJECT-TYPE
--		SYNTAX    Counter32
--		ACCESS    read-only
--		STATUS    mandatory
--		DESCRIPTION
--			""
--		::= { swhCountersRatesEntry 20 }

--	swhCountersRatesTxTotalCollision OBJECT-TYPE
--		SYNTAX    Counter32
--		ACCESS    read-only
--		STATUS    mandatory
--		DESCRIPTION
--			""
--		::= { swhCountersRatesEntry 21 }

	swhCountersRatesRxFrames64 OBJECT-TYPE
		SYNTAX    Counter32
		ACCESS    read-only
		STATUS    mandatory
		DESCRIPTION
			""
		::= { swhCountersRatesEntry 22 }

	swhCountersRatesRxFrames65to127 OBJECT-TYPE
		SYNTAX    Counter32
		ACCESS    read-only
		STATUS    mandatory
		DESCRIPTION
			""
		::= { swhCountersRatesEntry 23 }

	swhCountersRatesRxFrames128to255 OBJECT-TYPE
		SYNTAX    Counter32
		ACCESS    read-only
		STATUS    mandatory
		DESCRIPTION
			""
		::= { swhCountersRatesEntry 24 }

	swhCountersRatesRxFrames256to511 OBJECT-TYPE
		SYNTAX    Counter32
		ACCESS    read-only
		STATUS    mandatory
		DESCRIPTION
			""
		::= { swhCountersRatesEntry 25 }

	swhCountersRatesRxFrames512to1023 OBJECT-TYPE
		SYNTAX    Counter32
		ACCESS    read-only
		STATUS    mandatory
		DESCRIPTION
			""
		::= { swhCountersRatesEntry 26 }

--	swhCountersRatesRxFrames1024toMaxSize OBJECT-TYPE
--		SYNTAX    Counter32
--		ACCESS    read-only
--		STATUS    mandatory
--		DESCRIPTION
--			""
--		::= { swhCountersRatesEntry 27 }

--	swhCountersRatesRxUnicastFrames OBJECT-TYPE
--		SYNTAX    Counter32
--		ACCESS    read-only
--		STATUS    mandatory
--		DESCRIPTION
--			""
--		::= { swhCountersRatesEntry 28 }

	swhCountersRatesRxMulticastFrames OBJECT-TYPE
		SYNTAX    Counter32
		ACCESS    read-only
		STATUS    mandatory
		DESCRIPTION
			""
		::= { swhCountersRatesEntry 29 }

	swhCountersRatesRxBroadcastFrames OBJECT-TYPE
		SYNTAX    Counter32
		ACCESS    read-only
		STATUS    mandatory
		DESCRIPTION
			""
		::= { swhCountersRatesEntry 30 }

--	swhCountersRatesTxUnicastFrames OBJECT-TYPE
--		SYNTAX    Counter32
--		ACCESS    read-only
--		STATUS    mandatory
--		DESCRIPTION
--			""
--		::= { swhCountersRatesEntry 31 }

	swhCountersRatesTxMulticastFrames OBJECT-TYPE
		SYNTAX    Counter32
		ACCESS    read-only
		STATUS    mandatory
		DESCRIPTION
			""
		::= { swhCountersRatesEntry 32 }

	swhCountersRatesTxBroadcastFrames OBJECT-TYPE
		SYNTAX    Counter32
		ACCESS    read-only
		STATUS    mandatory
		DESCRIPTION
			""
		::= { swhCountersRatesEntry 33 }

--	swhCountersRatesRxTotalErrors OBJECT-TYPE
--		SYNTAX    Counter32
--		ACCESS    read-only
--		STATUS    mandatory
--		DESCRIPTION
--			""
--		::= { swhCountersRatesEntry 34 }

--	swhCountersRatesTxTotalErrors OBJECT-TYPE
--		SYNTAX    Counter32
--		ACCESS    read-only
--		STATUS    mandatory
--		DESCRIPTION
--			""
--		::= { swhCountersRatesEntry 35 }

--	swhCountersRatesTxTotalCollisions OBJECT-TYPE
--		SYNTAX    Counter32
--		ACCESS    read-only
--		STATUS    mandatory
--		DESCRIPTION
--			""
--		::= { swhCountersRatesEntry 36 }

--	swhCountersRatesRxCRCAlignError OBJECT-TYPE
--		SYNTAX    Counter32
--		ACCESS    read-only
--		STATUS    mandatory
--		DESCRIPTION
--			""
--		::= { swhCountersRatesEntry 37 }

--	swhCountersRatesTxCollision OBJECT-TYPE
--		SYNTAX    Counter32
--		ACCESS    read-only
--		STATUS    mandatory
--		DESCRIPTION
--			""
--		::= { swhCountersRatesEntry 38 }

	swhCountersRatesTotalErrors OBJECT-TYPE
		SYNTAX    Counter32
		ACCESS    read-only
		STATUS    mandatory
		DESCRIPTION
			""
		::= { swhCountersRatesEntry 39 }

	swhCountersRatesRxFrames1024to10240 OBJECT-TYPE
		SYNTAX    Counter32
		ACCESS    read-only
		STATUS    mandatory
		DESCRIPTION
			""
		::= { swhCountersRatesEntry 42 }

--	swhCountersRatesRxFrames1519toMaxSize OBJECT-TYPE
--		SYNTAX    Counter32
--		ACCESS    read-only
--		STATUS    mandatory
--		DESCRIPTION
--			""
--		::= { swhCountersRatesEntry 41 }

--  Counters Rates Traffic

	SWHCountersRatesTraffic ::=
		SEQUENCE {
			swhCountersRatesIndex
				INTEGER,
			swhCountersRatesBytesReceived
				Counter32,
			swhCountersRatesFramesReceived
				Counter32,
			swhCountersRatesReceivedUtilization
				DisplayString,
			swhCountersRatesBytesSent
				Counter32,
			swhCountersRatesFramesSent
				Counter32,
			swhCountersRatesSentUtilization
				DisplayString,
			swhCountersRatesTotalBytes
				Counter32,
			swhCountersRatesTotalUtilization
				DisplayString
		}

--  Counters Rates Error

	SWHCountersRatesError ::=
		SEQUENCE {
			swhCountersRatesIndex
				INTEGER,
		--	swhCountersRatesRxCRCAlignError
		--		Counter32,
			swhCountersRatesRxCRCError
				Counter32,
		--	swhCountersRatesRxAlignError
		--		Counter32,
			swhCountersRatesRxUndersizeFrames
				Counter32,
			swhCountersRatesRxFragments
				Counter32,
		--	swhCountersRatesRxJabbers
		--		Counter32,
		--	swhCountersRatesRxOversizeFrames
		--		Counter32,
		--	swhCountersRatesRxDroppedFrames
		--		Counter32,
		--	swhCountersRatesTxCollision
		--		Counter32,
		--	swhCountersRatesTxDroppedFrames
		--		Counter32,
			swhCountersRatesTotalErrors
				Counter32
		}

--  Counters Rates Analysis

	SWHCountersRatesAnalysis ::=
		SEQUENCE {
			swhCountersRatesIndex
				INTEGER,
			swhCountersRatesRxFrames64
				Counter32,
			swhCountersRatesRxFrames65to127
				Counter32,
			swhCountersRatesRxFrames128to255
				Counter32,
			swhCountersRatesRxFrames256to511
				Counter32,
			swhCountersRatesRxFrames512to1023
				Counter32,
			swhCountersRatesRxFrames1024to10240
				Counter32,
		--	swhCountersRatesRxFrames1519toMaxSize
		--		Counter32,
			swhCountersRatesTxMulticastFrames
				Counter32,
			swhCountersRatesTxBroadcastFrames
				Counter32,
			swhCountersRatesRxMulticastFrames
				Counter32,
			swhCountersRatesRxBroadcastFrames
				Counter32
		}


-- SwitchMonitor(5).PortCountersEvents(6)

	swhCountersEventsTable OBJECT-TYPE
		SYNTAX    SEQUENCE OF SWHCountersEventsEntry
		ACCESS    not-accessible
		STATUS    mandatory
		DESCRIPTION
			"Table of Port counters events."
		::= { swhPortCountersEvents 1 }

	swhCountersEventsClearCountersOfAllPort OBJECT-TYPE
		SYNTAX    INTEGER { normal(0), clear(1) }
		ACCESS    write-only
		STATUS    mandatory
		DESCRIPTION
			"Clear Counters of All Port"
		::= { swhPortCountersEvents 2  }

	-- Table Entry
	swhCountersEventsEntry OBJECT-TYPE
		SYNTAX    SWHCountersEventsEntry
		ACCESS    not-accessible
		STATUS    mandatory
		DESCRIPTION
			"An entry in the table, containing information
			about Port counter events mode."
		INDEX    { swhCountersEventsIndex }
		::= { swhCountersEventsTable 1 }

	SWHCountersEventsEntry ::=
		SEQUENCE {
			swhCountersEventsIndex
				INTEGER,
			swhCountersEventsBytesReceived
				Counter64,
			swhCountersEventsFramesReceived
				Counter64,
			swhCountersEventsBytesSent
				Counter64,
			swhCountersEventsFramesSent
				Counter64,
			swhCountersEventsTotalBytes
				Counter64,
		--	swhCountersEventsRxCRCAlignError
		--		Counter64,
			swhCountersEventsRxCRCError
				Counter64,
		--	swhCountersEventsRxAlignError
		--		Counter64,
			swhCountersEventsRxUndersizeFrames
				Counter64,
			swhCountersEventsRxFragments
				Counter64,
		--	swhCountersEventsRxJabbers
		--		Counter64,
		--	swhCountersEventsRxOversizeFrames
		--		Counter64,
		--	swhCountersEventsRxDroppedFrames
		--		Counter64,
		--	swhCountersEventsTxCollision
		--		Counter64,
		--	swhCountersEventsTxDroppedFrames
		--		Counter64,
			swhCountersEventsRxFrames64
				Counter64,
			swhCountersEventsRxFrames65to127
				Counter64,
			swhCountersEventsRxFrames128to255
				Counter64,
			swhCountersEventsRxFrames256to511
				Counter64,
			swhCountersEventsRxFrames512to1023
				Counter64,
			swhCountersEventsRxFrames1024to10240
				Counter64,
		--	swhCountersEventsRxFrames1519toMaxSize
		--		Counter64,
			swhCountersEventsTxMulticastFrames
				Counter64,
			swhCountersEventsTxBroadcastFrames
				Counter64,
			swhCountersEventsRxMulticastFrames
				Counter64,
			swhCountersEventsRxBroadcastFrames
				Counter64,
		--	swhClearCountersOfThisModule
		--		INTEGER,
			swhCountersEventsTotalErrors
				Counter64
		--	swhCountersEventsRxFilteredFrames
		--		Counter64,
		--	swhCountersEventsTxLateCollision
		--		Counter64,
		--	swhCountersEventsTxDeferred
		--		Counter64
		--	swhCountersEventsTxTotalCollision
		--		Counter64,
		--	swhCountersEventsRxFrames1024toMaxSize
		--		Counter64,
		--	swhCountersEventsRxUnicastFrames
		--		Counter64,
		--	swhCountersEventsTxUnicastFrames
		--		Counter64,
		--	swhCountersEventsRxTotalErrors
		--		Counter64,
		--	swhCountersEventsTxTotalErrors
		--		Counter64,
		--	swhCountersEventsTxTotalCollisions
		--		Counter64
		}

	swhCountersEventsIndex OBJECT-TYPE
		SYNTAX    INTEGER
		ACCESS    read-only
		STATUS    mandatory
		DESCRIPTION
			"A unique value for each Port."
		::= { swhCountersEventsEntry 1 }

	swhCountersEventsBytesReceived OBJECT-TYPE
		SYNTAX    Counter64
		ACCESS    read-only
		STATUS    mandatory
		DESCRIPTION
			""
		::= { swhCountersEventsEntry 2 }

	swhCountersEventsFramesReceived OBJECT-TYPE
		SYNTAX    Counter64
		ACCESS    read-only
		STATUS    mandatory
		DESCRIPTION
			""
		::= { swhCountersEventsEntry 3 }

--	swhCountersEventsReceivedUtilization OBJECT-TYPE
--		SYNTAX    DisplayString
--		ACCESS    read-only
--		STATUS    mandatory
--		DESCRIPTION
--			""
--		::= { swhCountersEventsEntry 4 }

	swhCountersEventsBytesSent OBJECT-TYPE
		SYNTAX    Counter64
		ACCESS    read-only
		STATUS    mandatory
		DESCRIPTION
			""
		::= { swhCountersEventsEntry 5 }

	swhCountersEventsFramesSent OBJECT-TYPE
		SYNTAX    Counter64
		ACCESS    read-only
		STATUS    mandatory
		DESCRIPTION
			""
		::= { swhCountersEventsEntry 6 }

--	swhCountersEventsSentUtilization OBJECT-TYPE
--		SYNTAX    DisplayString
--		ACCESS    read-only
--		STATUS    mandatory
--		DESCRIPTION
--			""
--		::= { swhCountersEventsEntry 7 }

	swhCountersEventsTotalBytes OBJECT-TYPE
		SYNTAX    Counter64
		ACCESS    read-only
		STATUS    mandatory
		DESCRIPTION
			""
		::= { swhCountersEventsEntry 8 }

--	swhCountersEventsTotalUtilization OBJECT-TYPE
--		SYNTAX    DisplayString
--		ACCESS    read-only
--		STATUS    mandatory
--		DESCRIPTION
--			""
--		::= { swhCountersEventsEntry 9 }

	swhCountersEventsRxCRCError OBJECT-TYPE
		SYNTAX    Counter64
		ACCESS    read-only
		STATUS    mandatory
		DESCRIPTION
			""
		::= { swhCountersEventsEntry 10 }

	swhCountersEventsRxFragments OBJECT-TYPE
		SYNTAX    Counter64
		ACCESS    read-only
		STATUS    mandatory
		DESCRIPTION
			""
		::= { swhCountersEventsEntry 11 }

--	swhCountersEventsRxFilteredFrames OBJECT-TYPE
--		SYNTAX    Counter64
--		ACCESS    read-only
--		STATUS    mandatory
--		DESCRIPTION
--			""
--		::= { swhCountersEventsEntry 12 }

--	swhCountersEventsRxAlignError OBJECT-TYPE
--		SYNTAX    Counter64
--		ACCESS    read-only
--		STATUS    mandatory
--		DESCRIPTION
--			""
--		::= { swhCountersEventsEntry 13 }

	swhCountersEventsRxUndersizeFrames OBJECT-TYPE
		SYNTAX    Counter64
		ACCESS    read-only
		STATUS    mandatory
		DESCRIPTION
			""
		::= { swhCountersEventsEntry 14 }

--	swhCountersEventsRxOversizeFrames OBJECT-TYPE
--		SYNTAX    Counter64
--		ACCESS    read-only
--		STATUS    mandatory
--		DESCRIPTION
--			""
--		::= { swhCountersEventsEntry 15 }

--	swhCountersEventsRxJabbers OBJECT-TYPE
--		SYNTAX    Counter64
--		ACCESS    read-only
--		STATUS    mandatory
--		DESCRIPTION
--			""
--		::= { swhCountersEventsEntry 16 }

--	swhCountersEventsRxDroppedFrames OBJECT-TYPE
--		SYNTAX    Counter64
--		ACCESS    read-only
--		STATUS    mandatory
--		DESCRIPTION
--			""
--		::= { swhCountersEventsEntry 17 }

--	swhCountersEventsTxDroppedFrames OBJECT-TYPE
--		SYNTAX    Counter64
--		ACCESS    read-only
--		STATUS    mandatory
--		DESCRIPTION
--			""
--		::= { swhCountersEventsEntry 18 }

--	swhCountersEventsTxLateCollision OBJECT-TYPE
--		SYNTAX    Counter64
--		ACCESS    read-only
--		STATUS    mandatory
--		DESCRIPTION
--			""
--		::= { swhCountersEventsEntry 19 }

--	swhCountersEventsTxDeferred OBJECT-TYPE
--		SYNTAX    Counter64
--		ACCESS    read-only
--		STATUS    mandatory
--		DESCRIPTION
--			""
--		::= { swhCountersEventsEntry 20 }

--	swhCountersEventsTxTotalCollision OBJECT-TYPE
--		SYNTAX    Counter64
--		ACCESS    read-only
--		STATUS    mandatory
--		DESCRIPTION
--			""
--		::= { swhCountersEventsEntry 21 }

	swhCountersEventsRxFrames64 OBJECT-TYPE
		SYNTAX    Counter64
		ACCESS    read-only
		STATUS    mandatory
		DESCRIPTION
			""
		::= { swhCountersEventsEntry 22 }

	swhCountersEventsRxFrames65to127 OBJECT-TYPE
		SYNTAX    Counter64
		ACCESS    read-only
		STATUS    mandatory
		DESCRIPTION
			""
		::= { swhCountersEventsEntry 23 }

	swhCountersEventsRxFrames128to255 OBJECT-TYPE
		SYNTAX    Counter64
		ACCESS    read-only
		STATUS    mandatory
		DESCRIPTION
			""
		::= { swhCountersEventsEntry 24 }

	swhCountersEventsRxFrames256to511 OBJECT-TYPE
		SYNTAX    Counter64
		ACCESS    read-only
		STATUS    mandatory
		DESCRIPTION
			""
		::= { swhCountersEventsEntry 25 }

	swhCountersEventsRxFrames512to1023 OBJECT-TYPE
		SYNTAX    Counter64
		ACCESS    read-only
		STATUS    mandatory
		DESCRIPTION
			""
		::= { swhCountersEventsEntry 26 }

--	swhCountersEventsRxFrames1024toMaxSize OBJECT-TYPE
--		SYNTAX    Counter64
--		ACCESS    read-only
--		STATUS    mandatory
--		DESCRIPTION
--			""
--		::= { swhCountersEventsEntry 27 }

--	swhCountersEventsRxUnicastFrames OBJECT-TYPE
--		SYNTAX    Counter64
--		ACCESS    read-only
--		STATUS    mandatory
--		DESCRIPTION
--			""
--		::= { swhCountersEventsEntry 28 }

	swhCountersEventsRxMulticastFrames OBJECT-TYPE
		SYNTAX    Counter64
		ACCESS    read-only
		STATUS    mandatory
		DESCRIPTION
			""
		::= { swhCountersEventsEntry 29 }

	swhCountersEventsRxBroadcastFrames OBJECT-TYPE
		SYNTAX    Counter64
		ACCESS    read-only
		STATUS    mandatory
		DESCRIPTION
			""
		::= { swhCountersEventsEntry 30 }

--	swhCountersEventsTxUnicastFrames OBJECT-TYPE
--		SYNTAX    Counter64
--		ACCESS    read-only
--		STATUS    mandatory
--		DESCRIPTION
--			""
--		::= { swhCountersEventsEntry 31 }

	swhCountersEventsTxMulticastFrames OBJECT-TYPE
		SYNTAX    Counter64
		ACCESS    read-only
		STATUS    mandatory
		DESCRIPTION
			""
		::= { swhCountersEventsEntry 32 }

	swhCountersEventsTxBroadcastFrames OBJECT-TYPE
		SYNTAX    Counter64
		ACCESS    read-only
		STATUS    mandatory
		DESCRIPTION
			""
		::= { swhCountersEventsEntry 33 }

--	swhClearCountersOfThisModule OBJECT-TYPE
--		SYNTAX    INTEGER { normal(0), clear(1) }
--		ACCESS    write-only
--		STATUS    mandatory
--		DESCRIPTION
--			"Clear Counters of This module"
--		::= { swhCountersEventsEntry 34  }

--	swhCountersEventsRxTotalErrors OBJECT-TYPE
--		SYNTAX    Counter64
--		ACCESS    read-only
--		STATUS    mandatory
--		DESCRIPTION
--			""
--		::= { swhCountersEventsEntry 35 }

--	swhCountersEventsTxTotalErrors OBJECT-TYPE
--		SYNTAX    Counter64
--		ACCESS    read-only
--		STATUS    mandatory
--		DESCRIPTION
--			""
--		::= { swhCountersEventsEntry 36 }

--	swhCountersEventsTxTotalCollisions OBJECT-TYPE
--		SYNTAX    Counter64
--		ACCESS    read-only
--		STATUS    mandatory
--		DESCRIPTION
--			""
--		::= { swhCountersEventsEntry 37 }

--	swhCountersEventsRxCRCAlignError OBJECT-TYPE
--		SYNTAX    Counter64
--		ACCESS    read-only
--		STATUS    mandatory
--		DESCRIPTION
--			""
--		::= { swhCountersEventsEntry 38 }

--	swhCountersEventsTxCollision OBJECT-TYPE
--		SYNTAX    Counter64
--		ACCESS    read-only
--		STATUS    mandatory
--		DESCRIPTION
--			""
--		::= { swhCountersEventsEntry 39 }

	swhCountersEventsRxFrames1024to10240 OBJECT-TYPE
		SYNTAX    Counter64
		ACCESS    read-only
		STATUS    mandatory
		DESCRIPTION
			""
		::= { swhCountersEventsEntry 43 }

--	swhCountersEventsRxFrames1519toMaxSize OBJECT-TYPE
--		SYNTAX    Counter64
--		ACCESS    read-only
--		STATUS    mandatory
--		DESCRIPTION
--			""
--		::= { swhCountersEventsEntry 41 }

	swhCountersEventsTotalErrors  OBJECT-TYPE
		SYNTAX    Counter64
		ACCESS    read-only
		STATUS    mandatory
		DESCRIPTION
			""
		::= { swhCountersEventsEntry 42 }

--  Counters Events Traffic

	SWHCountersEventsTraffic ::=
		SEQUENCE {
			swhCountersEventsIndex
				INTEGER,
			swhCountersEventsBytesReceived
				Counter64,
			swhCountersEventsFramesReceived
				Counter64,
			swhCountersEventsBytesSent
				Counter64,
			swhCountersEventsFramesSent
				Counter64,
			swhCountersEventsTotalBytes
				Counter64
		--	swhClearCountersOfThisModule
		--		INTEGER
		}

--  Counters Events Error

	SWHCountersEventsError ::=
		SEQUENCE {
			swhCountersEventsIndex
				INTEGER,
		--	swhCountersEventsRxCRCAlignError
		--		Counter64,
			swhCountersEventsRxCRCError
				Counter64,
		--	swhCountersEventsRxAlignError
		--		Counter64,
			swhCountersEventsRxUndersizeFrames
				Counter64,
			swhCountersEventsRxFragments
				Counter64,
		--	swhCountersEventsRxJabbers
		--		Counter64,
		--	swhCountersEventsRxOversizeFrames
		--		Counter64,
		--	swhCountersEventsRxDroppedFrames
		--		Counter64,
		--	swhCountersEventsTxCollision
		--		Counter64,
		--	swhCountersEventsTxDroppedFrames
		--		Counter64,
			swhCountersEventsTotalErrors
				Counter64
		--	swhClearCountersOfThisModule
		--		INTEGER
		}

--  Counters Events Analysis

	SWHCountersEventsAnalysis ::=
		SEQUENCE {
			swhCountersEventsIndex
				INTEGER,
			swhCountersEventsRxFrames64
				Counter64,
			swhCountersEventsRxFrames65to127
				Counter64,
			swhCountersEventsRxFrames128to255
				Counter64,
			swhCountersEventsRxFrames256to511
				Counter64,
			swhCountersEventsRxFrames512to1023
				Counter64,
			swhCountersEventsRxFrames1024to10240
				Counter64,
		--	swhCountersEventsRxFrames1519toMaxSize
		--		Counter64,
			swhCountersEventsTxMulticastFrames
				Counter64,
			swhCountersEventsTxBroadcastFrames
				Counter64,
			swhCountersEventsRxMulticastFrames
				Counter64,
			swhCountersEventsRxBroadcastFrames
				Counter64
		--	swhClearCountersOfThisModule
		--		INTEGER
		}


-- SwitchMonitor(5).MacAddressTable(7)

	swhMacAddressPortSelect OBJECT-TYPE
		SYNTAX    INTEGER { all(0),
		                    port01(1),
		                    port02(2),
		                    port03(3),
		                    port04(4),
		                    port05(5),
		                    port06(6),
							port07(7),
							port08(8),
							port09(9),
							port10(10),
		                    cpu(11)
		                    }
		ACCESS    read-write
		STATUS    mandatory
		DESCRIPTION
			"Display mac address of the port which is selected."
		::= { swhMacAddressTable 1 }

--	swhMacAddressClear OBJECT-TYPE
--		SYNTAX    INTEGER { normal(0), clear(1) }
--		ACCESS    read-write
--		STATUS    mandatory
--		DESCRIPTION
--			"Clear mac address table."
--		::= { swhMacAddressTable 2 }

	swhMacAddressTop OBJECT-TYPE
		SYNTAX    INTEGER { normal(0), top(1) }
		ACCESS    read-write
		STATUS    mandatory
		DESCRIPTION
			"Top Mac address table."
		::= { swhMacAddressTable 7 }

	swhMacAddressNext OBJECT-TYPE
		SYNTAX    INTEGER { normal(0), next(1) }
		ACCESS    read-write
		STATUS    mandatory
		DESCRIPTION
			"Next mac address table."
		::= { swhMacAddressTable 8 }

	swhMacAddressTotal OBJECT-TYPE
		SYNTAX    INTEGER
		ACCESS    read-only
		STATUS    mandatory
		DESCRIPTION
			"The amount of total learned mac address."
		::= { swhMacAddressTable 4 }


-- SwitchMonitor(5).MacAddressTable(7).MacTable(6)

	swhMacTable OBJECT-TYPE
		SYNTAX    SEQUENCE OF SWHMacTableEntry
		ACCESS    not-accessible
		STATUS    mandatory
		DESCRIPTION
			"Table of Mac Address."
		::= { swhMacAddressTable 6 }

	-- Table Entry
	swhMacTableEntry OBJECT-TYPE
		SYNTAX    SWHMacTableEntry
		ACCESS    not-accessible
		STATUS    mandatory
		DESCRIPTION
			"An entry in the table, containing information
			about mac address table"
		INDEX    { swhMacTableIndex }
		::= { swhMacTable 1 }

	SWHMacTableEntry ::=
		SEQUENCE {
			swhMacTableIndex
				INTEGER,
			swhMacTableType
				DisplayString,
			swhMacTableAddr
				MacAddress,
			swhMacTableVID
				INTEGER,
			swhMacTablePort
				DisplayString,
			swhMacTableLAGID
				INTEGER
		}

	swhMacTableIndex OBJECT-TYPE
		SYNTAX    INTEGER 
		ACCESS    read-only
		STATUS    mandatory
		DESCRIPTION
			"A unique value for mac address index."
		::= { swhMacTableEntry 1 }

	swhMacTableAddr OBJECT-TYPE
		SYNTAX    MacAddress
		ACCESS    read-only
		STATUS    mandatory
		DESCRIPTION
			"MAC address learned."
		::= { swhMacTableEntry 2 }

	swhMacTableVID OBJECT-TYPE
		SYNTAX    INTEGER 
		ACCESS    read-only
		STATUS    mandatory
		DESCRIPTION
			"MAC address learned from which vlan id."
		::= { swhMacTableEntry 3 }

	swhMacTablePort OBJECT-TYPE
		SYNTAX    DisplayString
		ACCESS    read-only
		STATUS    mandatory
		DESCRIPTION
			"MAC address learned from which port."
		::= { swhMacTableEntry 4 }

	swhMacTableType OBJECT-TYPE
		SYNTAX    DisplayString
		ACCESS    read-only
		STATUS    mandatory
		DESCRIPTION
			"MAC address learning type."
		::= { swhMacTableEntry 5 }

	swhMacTableLAGID OBJECT-TYPE
		SYNTAX    INTEGER 
		ACCESS    read-only
		STATUS    mandatory
		DESCRIPTION
			"MAC address learned from which LAG id."
		::= { swhMacTableEntry 6 }


-- SwitchMonitor(5).RSTPBridgeOverview(10)

	swhRSTPBridgeTable OBJECT-TYPE
		SYNTAX    SEQUENCE OF SWHRSTPBridgeEntry
		ACCESS    not-accessible
		STATUS    mandatory
		DESCRIPTION
			"Table of RSTP Bridge Overview."
		::= { swhRSTPBridgeOverview 7 }

	-- Table Entry
	swhRSTPBridgeEntry OBJECT-TYPE
		SYNTAX    SWHRSTPBridgeEntry
		ACCESS    not-accessible
		STATUS    mandatory
		DESCRIPTION
			"An entry in the table, containing information
			about RSTP Bridge mode."
		INDEX    { swhRSTPBridgeIndex }
		::= { swhRSTPBridgeTable 1 }

	SWHRSTPBridgeEntry ::=
		SEQUENCE {
			swhRSTPBridgeIndex
				INTEGER,
		--	swhRSTPBridgeVLANID
		--		INTEGER,
			swhRSTPBridgeBridgeID
				DisplayString,
			swhRSTPBridgeMaxAge
				INTEGER,
			swhRSTPBridgeHelloTime
				INTEGER,
			swhRSTPBridgeFwdDelay
				INTEGER,
			swhRSTPBridgeTopology
				INTEGER,
		--	swhRSTPBridgeTopologyCount
		--		INTEGER,
		--	swhRSTPBridgeLastTopology
		--		INTEGER,
			swhRSTPBridgeRootID
				DisplayString,
			swhRSTPBridgeRootPort
				INTEGER
		--	swhRSTPBridgeViaGroup
		--		INTEGER,
		--	swhRSTPBridgeViaPort
		--		INTEGER
		}

	swhRSTPBridgeIndex OBJECT-TYPE
		SYNTAX    INTEGER
		ACCESS    read-only
		STATUS    mandatory
		DESCRIPTION
			"A unique value for each Port."
		::= { swhRSTPBridgeEntry 1 }

	--swhRSTPBridgeVLANID OBJECT-TYPE
	--	SYNTAX    INTEGER
	--	ACCESS    read-only
	--	STATUS    mandatory
	--	DESCRIPTION
	--		"VLAN ID"
	--	::= { swhRSTPBridgeEntry 2 }

	swhRSTPBridgeBridgeID OBJECT-TYPE
		SYNTAX    DisplayString
		ACCESS    read-only
		STATUS    mandatory
		DESCRIPTION
			"Bridge ID"
		::= { swhRSTPBridgeEntry 3 }

	swhRSTPBridgeMaxAge OBJECT-TYPE
		SYNTAX    INTEGER
		ACCESS    read-only
		STATUS    mandatory
		DESCRIPTION
			"Max Age"
		::= { swhRSTPBridgeEntry 4 }

	swhRSTPBridgeHelloTime OBJECT-TYPE
		SYNTAX    INTEGER
		ACCESS    read-only
		STATUS    mandatory
		DESCRIPTION
			"Hello Time"
		::= { swhRSTPBridgeEntry 5 }

	swhRSTPBridgeFwdDelay OBJECT-TYPE
		SYNTAX    INTEGER
		ACCESS    read-only
		STATUS    mandatory
		DESCRIPTION
			"Fwd Delay"
		::= { swhRSTPBridgeEntry 6 }

	swhRSTPBridgeTopology OBJECT-TYPE
		SYNTAX    INTEGER { steady(0), changing(1) }
		ACCESS    read-only
		STATUS    mandatory
		DESCRIPTION
			"Topology"
		::= { swhRSTPBridgeEntry 7 }

--	swhRSTPBridgeTopologyCount OBJECT-TYPE
--		SYNTAX    INTEGER
--		ACCESS    read-only
--		STATUS    mandatory
--		DESCRIPTION
--			"Topology Count"
--		::= { swhRSTPBridgeEntry 8 }

--	swhRSTPBridgeLastTopology OBJECT-TYPE
--		SYNTAX    INTEGER
--		ACCESS    read-only
--		STATUS    mandatory
--		DESCRIPTION
--			"Last Topology"
--		::= { swhRSTPBridgeEntry 9 }

	swhRSTPBridgeRootID OBJECT-TYPE
		SYNTAX    DisplayString
		ACCESS    read-only
		STATUS    mandatory
		DESCRIPTION
			"Root ID"
		::= { swhRSTPBridgeEntry 10 }

--	swhRSTPBridgeViaGroup OBJECT-TYPE
--		SYNTAX    INTEGER
--		ACCESS    read-only
--		STATUS    mandatory
--		DESCRIPTION
--			"Via Group"
--		::= { swhRSTPBridgeEntry 11 }

--	swhRSTPBridgeViaPort OBJECT-TYPE
--		SYNTAX    INTEGER
--		ACCESS    read-only
--		STATUS    mandatory
--		DESCRIPTION
--			"Via Port"
--		::= { swhRSTPBridgeEntry 12 }

	swhRSTPBridgeRootPort OBJECT-TYPE
		SYNTAX    INTEGER
		ACCESS    read-only
		STATUS    mandatory
		DESCRIPTION
			"Root Port"
		::= { swhRSTPBridgeEntry 13 }


-- SwitchMonitor(5).LLDPStatus(11)

	swhLLDPStatusTable OBJECT-TYPE
		SYNTAX    SEQUENCE OF SWHLLDPStatusTableEntry
		ACCESS    not-accessible
		STATUS    mandatory
		DESCRIPTION
			"Table of LLDP Status."
		::= { swhLLDPStatus 4 }

	-- Table Entry
	swhLLDPStatusTableEntry OBJECT-TYPE
		SYNTAX    SWHLLDPStatusTableEntry
		ACCESS    not-accessible
		STATUS    mandatory
		DESCRIPTION
			"An entry in the table, containing information
			 about LLDP Status table"
		INDEX    { swhLLDPStatusTableIndex }
		::= { swhLLDPStatusTable 1 }

	SWHLLDPStatusTableEntry ::=
		SEQUENCE {
			swhLLDPStatusTableIndex
				INTEGER,
			swhLLDPStatusTableChassisID
				DisplayString,
			swhLLDPStatusTableRemotePort
				DisplayString,
			swhLLDPStatusTableSystemName
				DisplayString,
			swhLLDPStatusTablePortDescription
				DisplayString,
			swhLLDPStatusTableSystemCapabilities
				DisplayString,
			swhLLDPStatusTableManagement1Address
				DisplayString,
			swhLLDPStatusTableManagement2Address
				DisplayString,
			swhLLDPStatusTableManagement3Address
				DisplayString,
			swhLLDPStatusTableManagement4Address
				DisplayString,
			swhLLDPStatusTableManagement5Address
				DisplayString
		}

	swhLLDPStatusTableIndex OBJECT-TYPE
		SYNTAX    INTEGER
		ACCESS    read-only
		STATUS    mandatory
		DESCRIPTION
			"A unique value for Port index."
		::= { swhLLDPStatusTableEntry 1 }

	swhLLDPStatusTableChassisID OBJECT-TYPE
		SYNTAX    DisplayString
		ACCESS    read-only
		STATUS    mandatory
		DESCRIPTION
			"Chassis ID."
		::= { swhLLDPStatusTableEntry 3 }

	swhLLDPStatusTableRemotePort OBJECT-TYPE
		SYNTAX    DisplayString
		ACCESS    read-only
		STATUS    mandatory
		DESCRIPTION
			"Remote Port."
		::= { swhLLDPStatusTableEntry 4 }

	swhLLDPStatusTableSystemName OBJECT-TYPE
		SYNTAX    DisplayString
		ACCESS    read-only
		STATUS    mandatory
		DESCRIPTION
			"System Name."
		::= { swhLLDPStatusTableEntry 5 }

	swhLLDPStatusTablePortDescription OBJECT-TYPE
		SYNTAX    DisplayString
		ACCESS    read-only
		STATUS    mandatory
		DESCRIPTION
			"Port Description."
		::= { swhLLDPStatusTableEntry 6 }

	swhLLDPStatusTableSystemCapabilities OBJECT-TYPE
		SYNTAX    DisplayString
		ACCESS    read-only
		STATUS    mandatory
		DESCRIPTION
			"System Capabilities."
		::= { swhLLDPStatusTableEntry 7 }

	swhLLDPStatusTableManagement1Address OBJECT-TYPE
		SYNTAX    DisplayString
		ACCESS    read-only
		STATUS    mandatory
		DESCRIPTION
			"Management Address."
		::= { swhLLDPStatusTableEntry 8 }

	swhLLDPStatusTableManagement2Address OBJECT-TYPE
		SYNTAX    DisplayString
		ACCESS    read-only
		STATUS    mandatory
		DESCRIPTION
			"Management Address."
		::= { swhLLDPStatusTableEntry 9 }

	swhLLDPStatusTableManagement3Address OBJECT-TYPE
		SYNTAX    DisplayString
		ACCESS    read-only
		STATUS    mandatory
		DESCRIPTION
			"Management Address."
		::= { swhLLDPStatusTableEntry 10 }

	swhLLDPStatusTableManagement4Address OBJECT-TYPE
		SYNTAX    DisplayString
		ACCESS    read-only
		STATUS    mandatory
		DESCRIPTION
			"Management Address."
		::= { swhLLDPStatusTableEntry 11 }

	swhLLDPStatusTableManagement5Address OBJECT-TYPE
		SYNTAX    DisplayString
		ACCESS    read-only
		STATUS    mandatory
		DESCRIPTION
			"Management Address."
		::= { swhLLDPStatusTableEntry 12 }


-- SwitchMonitor(5).RSTPPortStatus(14).RSTPPortStatusTable(1)

	swhRSTPPortStatusTable OBJECT-TYPE
		SYNTAX    SEQUENCE OF SWHRSTPPortStatusEntry
		ACCESS    not-accessible
		STATUS    mandatory
		DESCRIPTION
			"Table of RSTP Port Status."
		::= { swhRSTPPortStatus 1 }

	-- Table Entry
	swhRSTPPortStatusEntry OBJECT-TYPE
		SYNTAX    SWHRSTPPortStatusEntry
		ACCESS    not-accessible
		STATUS    mandatory
		DESCRIPTION
			"An entry in the table, containing information
			about RSTP Port Status mode."
		INDEX    { swhRSTPPortStatusIndex }
		::= { swhRSTPPortStatusTable 1 }

	SWHRSTPPortStatusEntry ::=
		SEQUENCE {
			swhRSTPPortStatusIndex
				INTEGER,
			swhRSTPPortStatusPort
				DisplayString,
		--	swhRSTPPortStatusVLANID
		--		INTEGER,
			swhRSTPPortStatusPathCost
				INTEGER,
			swhRSTPPortStatusEdgePort
				INTEGER,
			swhRSTPPortStatusP2pPort
				INTEGER,
			swhRSTPPortStatusProtocol
				INTEGER,
			swhRSTPPortStatusRole
				INTEGER,
			swhRSTPPortStatusPortState
				INTEGER
		}

	swhRSTPPortStatusIndex OBJECT-TYPE
		SYNTAX    INTEGER
		ACCESS    read-only
		STATUS    mandatory
		DESCRIPTION
			"A unique value for each Port."
		::= { swhRSTPPortStatusEntry 1 }

	--swhRSTPPortStatusVLANID OBJECT-TYPE
	--	SYNTAX    INTEGER
	--	ACCESS    read-only
	--	STATUS    mandatory
	--	DESCRIPTION
	--		"VLAN ID"
	--	::= { swhRSTPPortStatusEntry 2 }

	swhRSTPPortStatusPathCost OBJECT-TYPE
		SYNTAX    INTEGER
		ACCESS    read-only
		STATUS    mandatory
		DESCRIPTION
			"Path Cost"
		::= { swhRSTPPortStatusEntry 3 }

	swhRSTPPortStatusEdgePort OBJECT-TYPE
		SYNTAX    INTEGER { no(0), yes(1) }
		ACCESS    read-only
		STATUS    mandatory
		DESCRIPTION
			"Edge Port"
		::= { swhRSTPPortStatusEntry 4 }

	swhRSTPPortStatusP2pPort OBJECT-TYPE
		SYNTAX    INTEGER { no(0), yes(1) }
		ACCESS    read-only
		STATUS    mandatory
		DESCRIPTION
			"P2p Port"
		::= { swhRSTPPortStatusEntry 5 }

	swhRSTPPortStatusProtocol OBJECT-TYPE
		SYNTAX    INTEGER { rstp(0), stp(1) }
		ACCESS    read-only
		STATUS    mandatory
		DESCRIPTION
			"Protocol"
		::= { swhRSTPPortStatusEntry 6 }

	swhRSTPPortStatusRole OBJECT-TYPE
		SYNTAX    INTEGER { disable(0), alternate(1), backup(2), root(3), designated(4), non-stp(5) }
		ACCESS    read-only
		STATUS    mandatory
		DESCRIPTION
			"Role"
		::= { swhRSTPPortStatusEntry 7 }

	swhRSTPPortStatusPortState OBJECT-TYPE
		SYNTAX    INTEGER { disable(0), blocking(1), listening(2), learning(3), forwarding(4), non-stp(5) }
		ACCESS    read-only
		STATUS    mandatory
		DESCRIPTION
			"Port State"
		::= { swhRSTPPortStatusEntry 8 }

	swhRSTPPortStatusPort OBJECT-TYPE
		SYNTAX    DisplayString
		ACCESS    read-only
		STATUS    mandatory
		DESCRIPTION
			"Port Name"
		::= { swhRSTPPortStatusEntry 9 }


-- SwitchMonitor(5).RSTPStatistics(18).RSTPStatisticsTable(1)

	swhRSTPStatisticsTable OBJECT-TYPE
		SYNTAX    SEQUENCE OF SWHRSTPStatisticsEntry
		ACCESS    not-accessible
		STATUS    mandatory
		DESCRIPTION
			"Table of RSTP Statistics."
		::= { swhRSTPStatistics 1 }

	-- Table Entry
	swhRSTPStatisticsEntry OBJECT-TYPE
		SYNTAX    SWHRSTPStatisticsEntry
		ACCESS    not-accessible
		STATUS    mandatory
		DESCRIPTION
			"An entry in the table, containing information
			about RSTP Statistics."
		INDEX    { swhRSTPStatisticsIndex }
		::= { swhRSTPStatisticsTable 1 }

	SWHRSTPStatisticsEntry ::=
		SEQUENCE {
			swhRSTPStatisticsIndex
				INTEGER,
			swhRSTPStatisticsPort
				DisplayString,
			swhRSTPStatisticsRSTPTransmitted
				Counter32,
			swhRSTPStatisticsSTPTransmitted
				Counter32,
			swhRSTPStatisticsTCNTransmitted
				Counter32,
			swhRSTPStatisticsRSTPReceived
				Counter32,
			swhRSTPStatisticsSTPReceived
				Counter32,
			swhRSTPStatisticsTCNReceived
				Counter32,
			swhRSTPStatisticsIllegalReceived
				Counter32,
			swhRSTPStatisticsUnknownReceived
				Counter32
		}

	swhRSTPStatisticsIndex OBJECT-TYPE
		SYNTAX    INTEGER
		ACCESS    read-only
		STATUS    mandatory
		DESCRIPTION
			"A unique value for each Port."
		::= { swhRSTPStatisticsEntry 1 }

	swhRSTPStatisticsRSTPTransmitted OBJECT-TYPE
		SYNTAX    Counter32
		ACCESS    read-only
		STATUS    mandatory
		DESCRIPTION
			""
		::= { swhRSTPStatisticsEntry 3 }

	swhRSTPStatisticsSTPTransmitted OBJECT-TYPE
		SYNTAX    Counter32
		ACCESS    read-only
		STATUS    mandatory
		DESCRIPTION
			""
		::= { swhRSTPStatisticsEntry 5 }

	swhRSTPStatisticsTCNTransmitted OBJECT-TYPE
		SYNTAX    Counter32
		ACCESS    read-only
		STATUS    mandatory
		DESCRIPTION
			""
		::= { swhRSTPStatisticsEntry 7 }

	swhRSTPStatisticsRSTPReceived OBJECT-TYPE
		SYNTAX    Counter32
		ACCESS    read-only
		STATUS    mandatory
		DESCRIPTION
			""
		::= { swhRSTPStatisticsEntry 9 }

	swhRSTPStatisticsSTPReceived OBJECT-TYPE
		SYNTAX    Counter32
		ACCESS    read-only
		STATUS    mandatory
		DESCRIPTION
			""
		::= { swhRSTPStatisticsEntry 11 }

	swhRSTPStatisticsTCNReceived OBJECT-TYPE
		SYNTAX    Counter32
		ACCESS    read-only
		STATUS    mandatory
		DESCRIPTION
			""
		::= { swhRSTPStatisticsEntry 13 }

	swhRSTPStatisticsIllegalReceived OBJECT-TYPE
		SYNTAX    Counter32
		ACCESS    read-only
		STATUS    mandatory
		DESCRIPTION
			""
		::= { swhRSTPStatisticsEntry 15 }

	swhRSTPStatisticsUnknownReceived OBJECT-TYPE
		SYNTAX    Counter32
		ACCESS    read-only
		STATUS    mandatory
		DESCRIPTION
			""
		::= { swhRSTPStatisticsEntry 17 }

	swhRSTPStatisticsPort OBJECT-TYPE
		SYNTAX    DisplayString
		ACCESS    read-only
		STATUS    mandatory
		DESCRIPTION
			"Port Name"
		::= { swhRSTPStatisticsEntry 18 }


-- SwitchMonitor(5).LACPPortStatus(22)

	swhLACPPortStatusTable OBJECT-TYPE
		SYNTAX    SEQUENCE OF SWHLACPPortStatusEntry
		ACCESS    not-accessible
		STATUS    mandatory
		DESCRIPTION
			"Table of RSTP VLAN Bridge Overview."
		::= { swhLACPPortStatus 1 }

	-- Table Entry
	swhLACPPortStatusEntry OBJECT-TYPE
		SYNTAX    SWHLACPPortStatusEntry
		ACCESS    not-accessible
		STATUS    mandatory
		DESCRIPTION
			"An entry in the table, containing information
			about RSTP VLAN Bridge mode."
		INDEX    { swhLACPPortStatusIndex }
		::= { swhLACPPortStatusTable 1 }

	SWHLACPPortStatusEntry ::=
		SEQUENCE {
			swhLACPPortStatusIndex
				INTEGER,
			swhLACPPortStatusLACPOperationalState
				INTEGER,
			swhLACPPortStatusKey
				INTEGER,
			swhLACPPortStatusAggrID
				INTEGER,
			swhLACPPortStatusPartnerID
				DisplayString,
			swhLACPPortStatusPartnerPort
				INTEGER
		}

	swhLACPPortStatusIndex OBJECT-TYPE
		SYNTAX    INTEGER
		ACCESS    read-only
		STATUS    mandatory
		DESCRIPTION
			"A unique value for each Port."
		::= { swhLACPPortStatusEntry 1 }

	swhLACPPortStatusPartnerPort OBJECT-TYPE
		SYNTAX    INTEGER
		ACCESS    read-only
		STATUS    mandatory
		DESCRIPTION
			"Partner Port"
		::= { swhLACPPortStatusEntry 3 }

	swhLACPPortStatusLACPOperationalState OBJECT-TYPE
		SYNTAX    INTEGER { no(0), yes(1) }
		ACCESS    read-only
		STATUS    mandatory
		DESCRIPTION
			"LACP Operational State"
		::= { swhLACPPortStatusEntry 4 }

	swhLACPPortStatusKey OBJECT-TYPE
		SYNTAX    INTEGER
		ACCESS    read-only
		STATUS    mandatory
		DESCRIPTION
			"Key"
		::= { swhLACPPortStatusEntry 5 }

	swhLACPPortStatusAggrID OBJECT-TYPE
		SYNTAX    INTEGER
		ACCESS    read-only
		STATUS    mandatory
		DESCRIPTION
			"Key"
		::= { swhLACPPortStatusEntry 6 }

	swhLACPPortStatusPartnerID OBJECT-TYPE
		SYNTAX    DisplayString
		ACCESS    read-only
		STATUS    mandatory
		DESCRIPTION
			"Partner ID"
		::= { swhLACPPortStatusEntry 7 }


-- SwitchMonitor(5).LACPStatistics(24)

	swhLACPStatisticsTable OBJECT-TYPE
		SYNTAX    SEQUENCE OF SWHLACPStatisticsEntry
		ACCESS    not-accessible
		STATUS    mandatory
		DESCRIPTION
			"Table of RSTP Statistics."
		::= { swhLACPStatistics 1 }

	swhLACPStatisticsClearCountersOfAllPort OBJECT-TYPE
		SYNTAX    INTEGER { normal(0), clear(1) }
		ACCESS    write-only
		STATUS    mandatory
		DESCRIPTION
			"Clear Counters of All Port"
		::= { swhLACPStatistics 2  }

	-- Table Entry
	swhLACPStatisticsEntry OBJECT-TYPE
		SYNTAX    SWHLACPStatisticsEntry
		ACCESS    not-accessible
		STATUS    mandatory
		DESCRIPTION
			"An entry in the table, containing information
			about RSTP Statistics."
		INDEX    { swhLACPStatisticsIndex }
		::= { swhLACPStatisticsTable 1 }

	SWHLACPStatisticsEntry ::=
		SEQUENCE {
			swhLACPStatisticsIndex
				INTEGER,
			swhLACPStatisticsLACPTransmitted
				Counter32,
		--	swhLACPStatisticsMarkTransmitted
		--		Counter32,
		--	swhLACPStatisticsRespTransmitted
		--		Counter32,
			swhLACPStatisticsLACPReceived
				Counter32,
		--	swhLACPStatisticsMarkReceived
		--		Counter32,
		--	swhLACPStatisticsRespReceived
		--		Counter32,
			swhLACPStatisticsIllegalReceived
				Counter32,
			swhLACPStatisticsUnknownReceived
				Counter32,
			swhLACPStatisticsClear
				INTEGER
		}

	swhLACPStatisticsIndex OBJECT-TYPE
		SYNTAX    INTEGER
		ACCESS    read-only
		STATUS    mandatory
		DESCRIPTION
			"A unique value for each Port."
		::= { swhLACPStatisticsEntry 1 }

	swhLACPStatisticsLACPTransmitted OBJECT-TYPE
		SYNTAX    Counter32
		ACCESS    read-only
		STATUS    mandatory
		DESCRIPTION
			""
		::= { swhLACPStatisticsEntry 3 }

--	swhLACPStatisticsMarkTransmitted OBJECT-TYPE
--		SYNTAX    Counter32
--		ACCESS    read-only
--		STATUS    mandatory
--		DESCRIPTION
--			""
--		::= { swhLACPStatisticsEntry 5 }

--	swhLACPStatisticsRespTransmitted OBJECT-TYPE
--		SYNTAX    Counter32
--		ACCESS    read-only
--		STATUS    mandatory
--		DESCRIPTION
--			""
--		::= { swhLACPStatisticsEntry 7 }

	swhLACPStatisticsLACPReceived OBJECT-TYPE
		SYNTAX    Counter32
		ACCESS    read-only
		STATUS    mandatory
		DESCRIPTION
			""
		::= { swhLACPStatisticsEntry 9 }

--	swhLACPStatisticsMarkReceived OBJECT-TYPE
--		SYNTAX    Counter32
--		ACCESS    read-only
--		STATUS    mandatory
--		DESCRIPTION
--			""
--		::= { swhLACPStatisticsEntry 11 }

--	swhLACPStatisticsRespReceived OBJECT-TYPE
--		SYNTAX    Counter32
--		ACCESS    read-only
--		STATUS    mandatory
--		DESCRIPTION
--			""
--		::= { swhLACPStatisticsEntry 13 }

	swhLACPStatisticsIllegalReceived OBJECT-TYPE
		SYNTAX    Counter32
		ACCESS    read-only
		STATUS    mandatory
		DESCRIPTION
			""
		::= { swhLACPStatisticsEntry 15 }

	swhLACPStatisticsUnknownReceived OBJECT-TYPE
		SYNTAX    Counter32
		ACCESS    read-only
		STATUS    mandatory
		DESCRIPTION
			""
		::= { swhLACPStatisticsEntry 17 }

	swhLACPStatisticsClear OBJECT-TYPE
		SYNTAX    INTEGER { normal(0), clear(1) }
		ACCESS    write-only
		STATUS    mandatory
		DESCRIPTION
			"Clear Counters of This module"
		::= { swhLACPStatisticsEntry 19 }


-- SwitchMonitor(5).IGMPStatus(26)


-- SwitchMonitor(5).MLDStatus(27)


-- SwitchMonitor(5).IGMPGroupTable(28)

	swhIGMPState OBJECT-TYPE
		SYNTAX    INTEGER { disable(0), enable(1) }
		ACCESS    read-only
		STATUS    mandatory
		DESCRIPTION
			"IGMP Snooping is disable or enable."
		::= { swhIGMPGroupTable 1 }

	swhIGMPTableUpdate OBJECT-TYPE
		SYNTAX    INTEGER { normal(0), update(1) }
		ACCESS    read-write
		STATUS    mandatory
		DESCRIPTION
			"Update IGMP Snooping Group Table."
		::= { swhIGMPGroupTable 3 }

--	swhIGMPTableState OBJECT-TYPE
--		SYNTAX    DisplayString
--		ACCESS    read-only
--		STATUS    mandatory
--		DESCRIPTION
--			"The state of IGMP group table."
--		::= { swhIGMPGroupTable 5 }


-- SwitchMonitor(5).IGMPGroupTable(28).IGMPTable(2)

	swhIGMPTable OBJECT-TYPE
		SYNTAX    SEQUENCE OF SWHIGMPTableEntry
		ACCESS    not-accessible
		STATUS    mandatory
		DESCRIPTION
			"Table of IGMP Group."
		::= { swhIGMPGroupTable 2 }

 	-- Table Entry
	swhIGMPTableEntry OBJECT-TYPE
		SYNTAX    SWHIGMPTableEntry
		ACCESS    not-accessible
		STATUS    mandatory
		DESCRIPTION
			"An entry in the table, containing information
			 about multicast groups, port members, queries, reports, time of aging out."
		INDEX    { swhIGMPGroupTableIndex }
		::= { swhIGMPTable 1 }

	SWHIGMPTableEntry ::=
		SEQUENCE {
			swhIGMPGroupTableIndex
				INTEGER,
			swhIGMPGroupTableMCastGroup
				DisplayString,
			swhIGMPGroupTableVID
				INTEGER,
			swhIGMPGroupTablePort1
				INTEGER,
			swhIGMPGroupTablePort2
				INTEGER,
			swhIGMPGroupTablePort3
				INTEGER,
			swhIGMPGroupTablePort4
				INTEGER,
			swhIGMPGroupTablePort5
				INTEGER,
			swhIGMPGroupTablePort6
				INTEGER,
			swhIGMPGroupTablePort7
				INTEGER,
			swhIGMPGroupTablePort8
				INTEGER,
			swhIGMPGroupTablePort9
				INTEGER,
			swhIGMPGroupTablePort10
				INTEGER
		}

	swhIGMPGroupTableIndex OBJECT-TYPE
		SYNTAX    INTEGER 
		ACCESS    read-only
		STATUS    mandatory
		DESCRIPTION
			"A unique value multicast groups index."
		::= { swhIGMPTableEntry 1 }

	swhIGMPGroupTableMCastGroup OBJECT-TYPE
		SYNTAX    DisplayString (SIZE (0..255))
		ACCESS    read-only
		STATUS    mandatory
		DESCRIPTION
			"Multicast group."
		::= { swhIGMPTableEntry 3 }

	swhIGMPGroupTablePort1 OBJECT-TYPE
		SYNTAX    INTEGER { b(0), v(1) }
		ACCESS    read-only
		STATUS    mandatory
		DESCRIPTION
			"b:Blocked  v:Member"
		::= { swhIGMPTableEntry 5 }

	swhIGMPGroupTablePort2 OBJECT-TYPE
		SYNTAX    INTEGER { b(0), v(1) }
		ACCESS    read-only
		STATUS    mandatory
		DESCRIPTION
			"b:Blocked  v:Member"
		::= { swhIGMPTableEntry 6 }

	swhIGMPGroupTablePort3 OBJECT-TYPE
		SYNTAX    INTEGER { b(0), v(1) }
		ACCESS    read-only
		STATUS    mandatory
		DESCRIPTION
			"b:Blocked  v:Member"
		::= { swhIGMPTableEntry 7 }

	swhIGMPGroupTablePort4 OBJECT-TYPE
		SYNTAX    INTEGER { b(0), v(1) }
		ACCESS    read-only
		STATUS    mandatory
		DESCRIPTION
			"b:Blocked  v:Member"
		::= { swhIGMPTableEntry 8 }

	swhIGMPGroupTablePort5 OBJECT-TYPE
		SYNTAX    INTEGER { b(0), v(1), na(-1), na(-2) }
		ACCESS    read-only
		STATUS    mandatory
		DESCRIPTION
			"b:Blocked  v:Member"
		::= { swhIGMPTableEntry 9 }

	swhIGMPGroupTablePort6 OBJECT-TYPE
		SYNTAX    INTEGER { b(0), v(1) }
		ACCESS    read-only
		STATUS    mandatory
		DESCRIPTION
			"b:Blocked  v:Member"
		::= { swhIGMPTableEntry 10 }
		
	swhIGMPGroupTablePort7 OBJECT-TYPE
		SYNTAX    INTEGER { b(0), v(1) }
		ACCESS    read-only
		STATUS    mandatory
		DESCRIPTION
			"b:Blocked  v:Member"
		::= { swhIGMPTableEntry 11 }
		
	swhIGMPGroupTablePort8 OBJECT-TYPE
		SYNTAX    INTEGER { b(0), v(1) }
		ACCESS    read-only
		STATUS    mandatory
		DESCRIPTION
			"b:Blocked  v:Member"
		::= { swhIGMPTableEntry 12 }
		
	swhIGMPGroupTablePort9 OBJECT-TYPE
		SYNTAX    INTEGER { b(0), v(1) }
		ACCESS    read-only
		STATUS    mandatory
		DESCRIPTION
			"b:Blocked  v:Member"
		::= { swhIGMPTableEntry 13 }
		
	swhIGMPGroupTablePort10 OBJECT-TYPE
		SYNTAX    INTEGER { b(0), v(1) }
		ACCESS    read-only
		STATUS    mandatory
		DESCRIPTION
			"b:Blocked  v:Member"
		::= { swhIGMPTableEntry 14 }

	swhIGMPGroupTableVID OBJECT-TYPE
		SYNTAX    INTEGER
		ACCESS    read-only
		STATUS    mandatory
		DESCRIPTION
			"VLAN ID."
		::= { swhIGMPTableEntry 60 }


-- SwitchMonitor(5).MLDGroupTable(29)


-- SwitchMonitor(5).MLDGroupTable(29).MLDTable(2)


-- SwitchMonitor(5).8021XPortStatus(32)

	swh8021XPortStatusTable OBJECT-TYPE
		SYNTAX    SEQUENCE OF Swh8021XPortStatusEntry
		ACCESS    not-accessible
		STATUS    mandatory
		DESCRIPTION
			"Table of 802.1X Port Status."
		::= { swh8021XPortStatus 1 }

	-- Table Entry
	swh8021XPortStatusEntry OBJECT-TYPE
		SYNTAX    Swh8021XPortStatusEntry
		ACCESS    not-accessible
		STATUS    mandatory
		DESCRIPTION
			"An entry in the table, containing information
			about 802.1X Port Status"
		INDEX    { swh8021XPortStatusIndex }
		::= { swh8021XPortStatusTable 1 }

	Swh8021XPortStatusEntry ::=
		SEQUENCE {
			swh8021XPortStatusIndex
				INTEGER,
			swh8021XPortStatusState
				INTEGER,
			swh8021XPortStatusLastSource
				DisplayString,
			swh8021XPortStatusLastID
				DisplayString,
			swh8021XPortStatusAssignedVLAN
				DisplayString
		}

	swh8021XPortStatusIndex OBJECT-TYPE
		SYNTAX    INTEGER 
		ACCESS    read-only
		STATUS    mandatory
		DESCRIPTION
			"A unique value for vlan id index."
		::= { swh8021XPortStatusEntry 1 }

	swh8021XPortStatusState OBJECT-TYPE
		SYNTAX    INTEGER { linkdown(0), authorized(1), unauthorized(2), disabled(3) }
		ACCESS    read-only
		STATUS    mandatory
		DESCRIPTION
			"VLAN ID"
		::= { swh8021XPortStatusEntry 3 }

	swh8021XPortStatusLastSource OBJECT-TYPE
		SYNTAX    DisplayString
		ACCESS    read-only
		STATUS    mandatory
		DESCRIPTION
			"Multicast Group learned."
		::= { swh8021XPortStatusEntry 5 }

	swh8021XPortStatusLastID OBJECT-TYPE
		SYNTAX    DisplayString
		ACCESS    read-only
		STATUS    mandatory
		DESCRIPTION
			"Port Number"
		::= { swh8021XPortStatusEntry 7 }

	swh8021XPortStatusAssignedVLAN OBJECT-TYPE
		SYNTAX    DisplayString
		ACCESS    read-only
		STATUS    mandatory
		DESCRIPTION
			"VID"
		::= { swh8021XPortStatusEntry 9 }


-- SwitchMonitor(5).8021XStatistics(33)

	swh8021XStatisticsTable OBJECT-TYPE
		SYNTAX    SEQUENCE OF Swh8021XStatisticsEntry
		ACCESS    not-accessible
		STATUS    mandatory
		DESCRIPTION
			"Table of 802.1X Statistics."
		::= { swh8021XStatistics 1 }

	swh8021XStatisticsClearCountersOfAllPort OBJECT-TYPE
		SYNTAX    INTEGER { normal(0), clear(1) }
		ACCESS    write-only
		STATUS    mandatory
		DESCRIPTION
			"Clear Counters of All Port"
		::= { swh8021XStatistics 2 }

	-- Table Entry
	swh8021XStatisticsEntry OBJECT-TYPE
		SYNTAX    Swh8021XStatisticsEntry
		ACCESS    not-accessible
		STATUS    mandatory
		DESCRIPTION
			"An entry in the table, containing information
			about 802.1X Statistics"
		INDEX    { swh8021XStatisticsIndex }
		::= { swh8021XStatisticsTable 1 }

	Swh8021XStatisticsEntry ::=
		SEQUENCE {
			swh8021XStatisticsIndex
				INTEGER,
			swh8021XStatisticsRxTotal
				Counter32,
			swh8021XStatisticsRxResponseID
				Counter32,
			swh8021XStatisticsRxResponse
				Counter32,
			swh8021XStatisticsRxStart
				Counter32,
			swh8021XStatisticsRxLogoff
				Counter32,
			swh8021XStatisticsRxInvalidType
				Counter32,
			swh8021XStatisticsRxInvalidLength
				Counter32,
			swh8021XStatisticsRxAccessChallenges
				Counter32,
			swh8021XStatisticsRxOtherRequests
				Counter32,
			swh8021XStatisticsRxAuthSuccesses
				Counter32,
			swh8021XStatisticsRxAuthFailures
				Counter32,
			swh8021XStatisticsTxTotal
				Counter32,
			swh8021XStatisticsTxRequestID
				Counter32,
			swh8021XStatisticsTxRequest
				Counter32,
			swh8021XStatisticsTxResponses
				Counter32,
			swh8021XStatisticsClear
				INTEGER
		}

	swh8021XStatisticsIndex OBJECT-TYPE
		SYNTAX    INTEGER 
		ACCESS    read-only
		STATUS    mandatory
		DESCRIPTION
			"A unique value for vlan id index."
		::= { swh8021XStatisticsEntry 1 }

	swh8021XStatisticsRxTotal OBJECT-TYPE
		SYNTAX    Counter32
		ACCESS    read-only
		STATUS    mandatory
		DESCRIPTION
			"Rx Total"
		::= { swh8021XStatisticsEntry 2 }

	swh8021XStatisticsRxResponseID OBJECT-TYPE
		SYNTAX    Counter32
		ACCESS    read-only
		STATUS    mandatory
		DESCRIPTION
			"Rx Response ID"
		::= { swh8021XStatisticsEntry 3 }

	swh8021XStatisticsRxResponse OBJECT-TYPE
		SYNTAX    Counter32
		ACCESS    read-only
		STATUS    mandatory
		DESCRIPTION
			"Rx Response"
		::= { swh8021XStatisticsEntry 4 }

	swh8021XStatisticsRxStart OBJECT-TYPE
		SYNTAX    Counter32
		ACCESS    read-only
		STATUS    mandatory
		DESCRIPTION
			"Rx Response"
		::= { swh8021XStatisticsEntry 5 }

	swh8021XStatisticsRxLogoff OBJECT-TYPE
		SYNTAX    Counter32
		ACCESS    read-only
		STATUS    mandatory
		DESCRIPTION
			"Rx Response"
		::= { swh8021XStatisticsEntry 6 }

	swh8021XStatisticsRxInvalidType OBJECT-TYPE
		SYNTAX    Counter32
		ACCESS    read-only
		STATUS    mandatory
		DESCRIPTION
			"Rx Response"
		::= { swh8021XStatisticsEntry 7 }

	swh8021XStatisticsRxInvalidLength OBJECT-TYPE
		SYNTAX    Counter32
		ACCESS    read-only
		STATUS    mandatory
		DESCRIPTION
			"Rx Response"
		::= { swh8021XStatisticsEntry 8 }

	swh8021XStatisticsRxAccessChallenges OBJECT-TYPE
		SYNTAX    Counter32
		ACCESS    read-only
		STATUS    mandatory
		DESCRIPTION
			"Rx Response"
		::= { swh8021XStatisticsEntry 9 }

	swh8021XStatisticsRxOtherRequests OBJECT-TYPE
		SYNTAX    Counter32
		ACCESS    read-only
		STATUS    mandatory
		DESCRIPTION
			"Rx Response"
		::= { swh8021XStatisticsEntry 10 }

	swh8021XStatisticsRxAuthSuccesses OBJECT-TYPE
		SYNTAX    Counter32
		ACCESS    read-only
		STATUS    mandatory
		DESCRIPTION
			"Rx Response"
		::= { swh8021XStatisticsEntry 11 }

	swh8021XStatisticsRxAuthFailures OBJECT-TYPE
		SYNTAX    Counter32
		ACCESS    read-only
		STATUS    mandatory
		DESCRIPTION
			"Rx Response"
		::= { swh8021XStatisticsEntry 12 }

	swh8021XStatisticsTxTotal OBJECT-TYPE
		SYNTAX    Counter32
		ACCESS    read-only
		STATUS    mandatory
		DESCRIPTION
			"Rx Response"
		::= { swh8021XStatisticsEntry 13 }

	swh8021XStatisticsTxRequestID OBJECT-TYPE
		SYNTAX    Counter32
		ACCESS    read-only
		STATUS    mandatory
		DESCRIPTION
			"Rx Response"
		::= { swh8021XStatisticsEntry 14 }

	swh8021XStatisticsTxRequest OBJECT-TYPE
		SYNTAX    Counter32
		ACCESS    read-only
		STATUS    mandatory
		DESCRIPTION
			"Rx Response"
		::= { swh8021XStatisticsEntry 15 }

	swh8021XStatisticsTxResponses OBJECT-TYPE
		SYNTAX    Counter32
		ACCESS    read-only
		STATUS    mandatory
		DESCRIPTION
			"Rx Response"
		::= { swh8021XStatisticsEntry 16 }

	swh8021XStatisticsClear OBJECT-TYPE
		SYNTAX    INTEGER { normal(0), clear(1) }
		ACCESS    write-only
		STATUS    mandatory
		DESCRIPTION
			"Clear Counters of This module"
		::= { swh8021XStatisticsEntry 17  }


-- SwitchMonitor(5).SFPInformation(34)

	swhSFPPortInfo
		OBJECT IDENTIFIER ::= { swhSFPInformation 1 }
	swhSFPPortState
		OBJECT IDENTIFIER ::= { swhSFPInformation 2 }


-- SwitchMonitor(5).SFPInformation(34).SFPPortInfo(1).SFPPortInfoTable(1)

	swhSFPPortInfoTable OBJECT-TYPE
		SYNTAX    SEQUENCE OF SWHSFPPortInfoEntry
		ACCESS    not-accessible
		STATUS    mandatory
		DESCRIPTION
			"Table of SFP Port Info."
		::= { swhSFPPortInfo 1 }

	-- Table Entry
	swhSFPPortInfoEntry OBJECT-TYPE
		SYNTAX    SWHSFPPortInfoEntry
		ACCESS    not-accessible
		STATUS    mandatory
		DESCRIPTION
			"An entry in the table, containing information
			about SFP Port Info."
		INDEX    { swhSFPPortInfoIndex }
		::= { swhSFPPortInfoTable 1 }

	SWHSFPPortInfoEntry ::=
		SEQUENCE {
			swhSFPPortInfoIndex
				INTEGER,
			swhSFPPortInfoPortName
				DisplayString,
			swhSFPPortInfoSpeed
				DisplayString,
			swhSFPPortInfoDistance
				DisplayString,
			swhSFPPortInfoVendorName
				DisplayString,
			swhSFPPortInfoVendorPN
				DisplayString,
			swhSFPPortInfoVendorSN
				DisplayString
		}

	swhSFPPortInfoIndex OBJECT-TYPE
		SYNTAX    INTEGER
		ACCESS    read-only
		STATUS    mandatory
		DESCRIPTION
			"A unique value for each port."
		::= { swhSFPPortInfoEntry 1 }

	swhSFPPortInfoPortName OBJECT-TYPE
		SYNTAX    DisplayString
		ACCESS    read-only
		STATUS    mandatory
		DESCRIPTION
			"Port Name"
		::= { swhSFPPortInfoEntry 3 }

	swhSFPPortInfoSpeed OBJECT-TYPE
		SYNTAX    DisplayString
		ACCESS    read-only
		STATUS    mandatory
		DESCRIPTION
			"Speed"
		::= { swhSFPPortInfoEntry 5 }

	swhSFPPortInfoDistance OBJECT-TYPE
		SYNTAX    DisplayString
		ACCESS    read-only
		STATUS    mandatory
		DESCRIPTION
			"Distance"
		::= { swhSFPPortInfoEntry 7 }

	swhSFPPortInfoVendorName OBJECT-TYPE
		SYNTAX    DisplayString
		ACCESS    read-only
		STATUS    mandatory
		DESCRIPTION
			"Vendor Name"
		::= { swhSFPPortInfoEntry 9 }

	swhSFPPortInfoVendorPN OBJECT-TYPE
		SYNTAX    DisplayString
		ACCESS    read-only
		STATUS    mandatory
		DESCRIPTION
			"Vendor PN"
		::= { swhSFPPortInfoEntry 11 }

	swhSFPPortInfoVendorSN OBJECT-TYPE
		SYNTAX    DisplayString
		ACCESS    read-only
		STATUS    mandatory
		DESCRIPTION
			"Vendor SN"
		::= { swhSFPPortInfoEntry 13 }


-- SwitchMonitor(5).SFPInformation(34).SFPPortState(2).SFPPortStateTable(1)

	swhSFPPortStateTable OBJECT-TYPE
		SYNTAX    SEQUENCE OF SwhSFPPortStateEntry
		ACCESS    not-accessible
		STATUS    mandatory
		DESCRIPTION
			"Table of SFP Port State."
		::= { swhSFPPortState 1 }

	-- Table Entry
	swhSFPPortStateEntry OBJECT-TYPE
		SYNTAX    SwhSFPPortStateEntry
		ACCESS    not-accessible
		STATUS    mandatory
		DESCRIPTION
			"An entry in the table, containing information
			about SFP Port State."
		INDEX    { swhSFPPortStateIndex }
		::= { swhSFPPortStateTable 1 }

	SwhSFPPortStateEntry ::=
		SEQUENCE {
			swhSFPPortStateIndex
				INTEGER,
			swhSFPPortStatePortName
				DisplayString,
			swhSFPPortStateTemperature
				DisplayString,
			swhSFPPortStateVoltage
				DisplayString,
			swhSFPPortStateTXBias
				DisplayString,
			swhSFPPortStateTXPower
				DisplayString,
			swhSFPPortStateRXPower
				DisplayString
		}

	swhSFPPortStateIndex OBJECT-TYPE
		SYNTAX    INTEGER
		ACCESS    read-only
		STATUS    mandatory
		DESCRIPTION
			"A unique value for each port."
		::= { swhSFPPortStateEntry 1 }

	swhSFPPortStatePortName OBJECT-TYPE
		SYNTAX    DisplayString
		ACCESS    read-only
		STATUS    mandatory
		DESCRIPTION
			"Port Name"
		::= { swhSFPPortStateEntry 3 }

	swhSFPPortStateTemperature OBJECT-TYPE
		SYNTAX    DisplayString
		ACCESS    read-only
		STATUS    mandatory
		DESCRIPTION
			"Port Temperature (C)"
		::= { swhSFPPortStateEntry 5 }

	swhSFPPortStateVoltage OBJECT-TYPE
		SYNTAX    DisplayString
		ACCESS    read-only
		STATUS    mandatory
		DESCRIPTION
			"Port Voltage (V)"
		::= { swhSFPPortStateEntry 7 }

	swhSFPPortStateTXBias OBJECT-TYPE
		SYNTAX    DisplayString
		ACCESS    read-only
		STATUS    mandatory
		DESCRIPTION
			"Port TX Bias (mA)"
		::= { swhSFPPortStateEntry 9 }

	swhSFPPortStateTXPower OBJECT-TYPE
		SYNTAX    DisplayString
		ACCESS    read-only
		STATUS    mandatory
		DESCRIPTION
			"Port TX Power (dBm)"
		::= { swhSFPPortStateEntry 11 }

	swhSFPPortStateRXPower OBJECT-TYPE
		SYNTAX    DisplayString
		ACCESS    read-only
		STATUS    mandatory
		DESCRIPTION
			"Port RX Power (dBm)"
		::= { swhSFPPortStateEntry 13 }


-- SwitchMonitor(5).DHCPSnoopingTable(35)


-- SwitchMonitor(5).DHCPSnoopingTable(35).DHCPSnoopingTableTable(7)


-- SwitchMonitor(5).DHCPSnoopingTable(35).DHCPv6SnoopingTableTable(8)


-- SwitchMonitor(5).LoopDetectionStatus(36)


-- SwitchMonitor(5).LoopDetectionStatus(36).LoopDetectionStatusTable(4)

	swhLoopDetectionStatusTable OBJECT-TYPE
		SYNTAX    SEQUENCE OF SWHLoopDetectionStatusEntry
		ACCESS    not-accessible
		STATUS    mandatory
		DESCRIPTION
			"Table of Loop Status."
		::= { swhLoopDetectionStatus 4 }

 	-- Table Entry
	swhLoopDetectionStatusEntry OBJECT-TYPE
		SYNTAX    SWHLoopDetectionStatusEntry
		ACCESS    not-accessible
		STATUS    mandatory
		DESCRIPTION
			"An entry in the table, containing information
			about Loop Status table"
		INDEX    { swhLoopDetectionStatusPort }
		::= { swhLoopDetectionStatusTable 1 }

	SWHLoopDetectionStatusEntry ::=
		SEQUENCE {
			swhLoopDetectionStatusPort
				INTEGER,
			swhLoopDetectionStatusStatus
				INTEGER,
			swhLoopDetectionStatusLockCause
				DisplayString
		}

	swhLoopDetectionStatusPort OBJECT-TYPE
		SYNTAX    INTEGER 
		ACCESS    read-only
		STATUS    mandatory
		DESCRIPTION
			"A unique value for Port index."
		::= { swhLoopDetectionStatusEntry 1 }

	swhLoopDetectionStatusLockCause OBJECT-TYPE
		SYNTAX    DisplayString
		ACCESS    read-only
		STATUS    mandatory
		DESCRIPTION
			"Lock Cause."
		::= { swhLoopDetectionStatusEntry 3 }

	swhLoopDetectionStatusStatus OBJECT-TYPE
		SYNTAX    INTEGER { un-lock(0), lock(1), na(-1), na(-2) }
		ACCESS    read-only
		STATUS    mandatory
		DESCRIPTION
			"Status."
		::= { swhLoopDetectionStatusEntry 4 }


-- SwitchMonitor(5).MacAddressStore(40)


-- SwitchMonitor(5).MacAddressStore(40).MacStoreTable(6)


-- SwitchMonitor(5).DODIStatus(41).DIStatus(1)

--	swhDIStatusTable OBJECT-TYPE
--		SYNTAX    SEQUENCE OF SWHDIStatusEntry
--		ACCESS    not-accessible
--		STATUS    mandatory
--		DESCRIPTION
--			"Table of digital input status."
--		::= { swhDIDOStatus 1 }

	-- Table Entry
--	swhDIStatusEntry OBJECT-TYPE
--		SYNTAX    SWHDIStatusEntry
--		ACCESS    not-accessible
--		STATUS    mandatory
--		DESCRIPTION
--			"An entry in the table, containing information
--			about digital input status"
--		INDEX    { swhDIStatusIndex }
--		::= { swhDIStatusTable 1 }

--	SWHDIStatusEntry ::=
--		SEQUENCE {
--			swhDIStatusIndex
--				INTEGER,
		--	swhDIStatusNormal
		--		INTEGER,
--			swhDIStatusStatus
--				INTEGER,
--			swhDIStatusAlarm
--				INTEGER
--		}

--	swhDIStatusIndex OBJECT-TYPE
--		SYNTAX    INTEGER 
--		ACCESS    read-only
--		STATUS    mandatory
--		DESCRIPTION
--			"A unique value for digital input index."
--		::= { swhDIStatusEntry 1 }

	--swhDIStatusNormal OBJECT-TYPE
	--	SYNTAX    INTEGER { open(1), close(0) }
	--	ACCESS    read-only
	--	STATUS    mandatory
	--	DESCRIPTION
	--		"digital input normal."
	--	::= { swhDIStatusEntry 2 }

--	swhDIStatusStatus OBJECT-TYPE
--		SYNTAX    INTEGER { open(1), close(0) }
--		ACCESS    read-only
--		STATUS    mandatory
--		DESCRIPTION
--			"digital input status."
--		::= { swhDIStatusEntry 3 }

--	swhDIStatusAlarm OBJECT-TYPE
--		SYNTAX    INTEGER { on(1), off(0) }
--		ACCESS    read-only
--		STATUS    mandatory
--		DESCRIPTION
--			"digital input alarm."
--		::= { swhDIStatusEntry 4 }


-- SwitchMonitor(5).DODIStatus(41).DOStatus(2)

--	swhDOStatusTable OBJECT-TYPE
--		SYNTAX    SEQUENCE OF SWHDOStatusEntry
--		ACCESS    not-accessible
--		STATUS    mandatory
--		DESCRIPTION
--			"Table of digital output status."
--		::= { swhDIDOStatus 2 }

	-- Table Entry
--	swhDOStatusEntry OBJECT-TYPE
--		SYNTAX    SWHDOStatusEntry
--		ACCESS    not-accessible
--		STATUS    mandatory
--		DESCRIPTION
--			"An entry in the table, containing information
--			about digital output status"
--		INDEX    { swhDOStatusIndex }
--		::= { swhDOStatusTable 1 }

--	SWHDOStatusEntry ::=
--		SEQUENCE {
--			swhDOStatusIndex
--				INTEGER,
		--	swhDOStatusNormal
		--		INTEGER,
--			swhDOStatusStatus
--				INTEGER,
--			swhDOStatusAlarm
--				INTEGER,
--			swhDOStatusTrigger
--				INTEGER,
--			swhDOStatusDigitalInput1
--				INTEGER,
--			swhDOStatusDigitalInput2
--				INTEGER,
--			swhDOStatusPower1
--				INTEGER,
--			swhDOStatusPower2
--				INTEGER
--		}

--	swhDOStatusIndex OBJECT-TYPE
--		SYNTAX    INTEGER 
--		ACCESS    read-only
--		STATUS    mandatory
--		DESCRIPTION
--			"A unique value for digital output index."
--		::= { swhDOStatusEntry 1 }

	--swhDOStatusNormal OBJECT-TYPE
	--	SYNTAX    INTEGER { open(1), close(0) }
	--	ACCESS    read-only
	--	STATUS    mandatory
	--	DESCRIPTION
	--		"digital output normal."
	--	::= { swhDOStatusEntry 2 }

--	swhDOStatusStatus OBJECT-TYPE
--		SYNTAX    INTEGER { open(1), close(0) }
--		ACCESS    read-only
--		STATUS    mandatory
--		DESCRIPTION
--			"digital output status."
--		::= { swhDOStatusEntry 3 }

--	swhDOStatusAlarm OBJECT-TYPE
--		SYNTAX    INTEGER { on(1), off(0) }
--		ACCESS    read-only
--		STATUS    mandatory
--		DESCRIPTION
--			"digital output alarm."
--		::= { swhDOStatusEntry 4 }

--	swhDOStatusTrigger OBJECT-TYPE
--		SYNTAX    INTEGER { enable(1), disable(0) }
--		ACCESS    read-only
--		STATUS    mandatory
--		DESCRIPTION
--			"digital trigger."
--		::= { swhDOStatusEntry 5 }

--	swhDOStatusDigitalInput1 OBJECT-TYPE
--		SYNTAX    INTEGER { on(1), off(0), na(-1), na(-2) }
--		ACCESS    read-only
--		STATUS    mandatory
--		DESCRIPTION
--			"digital input 1."
--		::= { swhDOStatusEntry 6 }

--	swhDOStatusDigitalInput2 OBJECT-TYPE
--		SYNTAX    INTEGER { on(1), off(0), na(-1), na(-2) }
--		ACCESS    read-only
--		STATUS    mandatory
--		DESCRIPTION
--			"digital input 2."
--		::= { swhDOStatusEntry 7 }

--	swhDOStatusPower1 OBJECT-TYPE
--		SYNTAX    INTEGER { on(1), off(0), na(-1), na(-2) }
--		ACCESS    read-only
--		STATUS    mandatory
--		DESCRIPTION
--			"digital power 1."
--		::= { swhDOStatusEntry 8 }

--	swhDOStatusPower2 OBJECT-TYPE
--		SYNTAX    INTEGER { on(1), off(0), na(-1), na(-2) }
--		ACCESS    read-only
--		STATUS    mandatory
--		DESCRIPTION
--			"digital power 2."
--		::= { swhDOStatusEntry 9 }


-- SwitchMonitor(5).DODIStatus(41).DOPortStatus(2)

--	swhDOPortStatusTable OBJECT-TYPE
--		SYNTAX    SEQUENCE OF SWHDOPortStatusEntry
--		ACCESS    not-accessible
--		STATUS    mandatory
--		DESCRIPTION
--			"Table of digital port status."
--		::= { swhDIDOStatus 3 }

	-- Table Entry
--	swhDOPortStatusEntry OBJECT-TYPE
--		SYNTAX    SWHDOPortStatusEntry
--		ACCESS    not-accessible
--		STATUS    mandatory
--		DESCRIPTION
--			"An entry in the table, containing information
--			about digital port status"
--		INDEX    { swhDOPortStatusIndex }
--		::= { swhDOPortStatusTable 1 }

--	SWHDOPortStatusEntry ::=
--		SEQUENCE {
--			swhDOPortStatusIndex
--				INTEGER,
--			swhDOPortStatusDigitalOutput1Status
--				INTEGER,
--			swhDOPortStatusDigitalOutput2Status
--				INTEGER
--		}

--	swhDOPortStatusIndex OBJECT-TYPE
--		SYNTAX    INTEGER 
--		ACCESS    read-only
--		STATUS    mandatory
--		DESCRIPTION
--			"A unique value for port index."
--		::= { swhDOPortStatusEntry 1 }

--	swhDOPortStatusDigitalOutput1Status OBJECT-TYPE
--		SYNTAX    INTEGER { on(1), off(0), na(-1), na(-2) }
--		ACCESS    read-only
--		STATUS    mandatory
--		DESCRIPTION
--			"digital output 1 port status."
--		::= { swhDOPortStatusEntry 2 }

--	swhDOPortStatusDigitalOutput2Status OBJECT-TYPE
--		SYNTAX    INTEGER { on(1), off(0), na(-1), na(-2) }
--		ACCESS    read-only
--		STATUS    mandatory
--		DESCRIPTION
--			"digital output 1 port status."
--		::= { swhDOPortStatusEntry 3 }


-- SwitchMonitor(5).RingStatus(43)

	swhRingState OBJECT-TYPE
		SYNTAX    INTEGER { disable(0), enable(1) }
		ACCESS    read-only
		STATUS    mandatory
		DESCRIPTION
			"Ring Detection is disable or enable."
		::= { swhRingStatus 1 }

	swhRingStateAccording OBJECT-TYPE
		SYNTAX    INTEGER { software(0), hardware(1) }
		ACCESS    read-only
		STATUS    mandatory
		DESCRIPTION
			"Ring Status According from software or hardware"
		::= { swhRingStatus 3 }

	swhRingStateRole OBJECT-TYPE
		SYNTAX    INTEGER { slave(0), master(1) }
		ACCESS    read-only
		STATUS    mandatory
		DESCRIPTION
			"Ring Status Role from slave or master"
		::= { swhRingStatus 4 }


-- SwitchMonitor(5).RingStatus(43).RingStatusTable(1)

	swhRingStatusTable OBJECT-TYPE
		SYNTAX    SEQUENCE OF SWHRingStatusEntry
		ACCESS    not-accessible
		STATUS    mandatory
		DESCRIPTION
			"Table of Ring port status."
		::= { swhRingStatus 2 }

	-- Table Entry
	swhRingStatusEntry OBJECT-TYPE
		SYNTAX    SWHRingStatusEntry
		ACCESS    not-accessible
		STATUS    mandatory
		DESCRIPTION
			"An entry in the table, containing information
			about Ring port status"
		INDEX    { swhRingStatusIndex }
		::= { swhRingStatusTable 1 }

	SWHRingStatusEntry ::=
		SEQUENCE {
			swhRingStatusIndex
				INTEGER,
			swhRingStatusEnable
				INTEGER,
			swhRingStatusState
				INTEGER
		}

	swhRingStatusIndex OBJECT-TYPE
		SYNTAX    INTEGER 
		ACCESS    read-only
		STATUS    mandatory
		DESCRIPTION
			"A unique value for port index."
		::= { swhRingStatusEntry 1 }

	swhRingStatusEnable OBJECT-TYPE
		SYNTAX    INTEGER { disable(0), enable(1) }
		ACCESS    read-only
		STATUS    mandatory
		DESCRIPTION
			"port enable"
		::= { swhRingStatusEntry 2 }

	swhRingStatusState OBJECT-TYPE
		SYNTAX    INTEGER { blocking(0), forwarding(1), na(-1), na(-2) }
		ACCESS    read-only
		STATUS    mandatory
		DESCRIPTION
			"port status."
		::= { swhRingStatusEntry 3 }


-- SwitchMonitor(5).FastRedundancyStatus(52)

	swhRingStatusTimes OBJECT-TYPE
		SYNTAX    INTEGER (0..2147483647)
		ACCESS    read-only
		STATUS    mandatory
		DESCRIPTION
			"Fast Redundancy Topology Change Times"
		::= { swhFastRedundancyStatus 2 }

	swhRingStatusLastChangeTime OBJECT-TYPE
		SYNTAX    DisplayString
		ACCESS    read-only
		STATUS    mandatory
		DESCRIPTION
			"Fast Redundancy Topology Change Last Change Time"
		::= { swhFastRedundancyStatus 3 }

	swhRingStatusElapsedTime OBJECT-TYPE
		SYNTAX    DisplayString
		ACCESS    read-only
		STATUS    mandatory
		DESCRIPTION
			"Fast Redundancy Topology Change Elapsed Time"
		::= { swhFastRedundancyStatus 4 }

	swhRingStatusTopologyClear OBJECT-TYPE
		SYNTAX    INTEGER { normal(0), clear(1) }
		ACCESS    read-write
		STATUS    mandatory
		DESCRIPTION
			"Fast Redundancy Topology Change Clear"
		::= { swhFastRedundancyStatus 5 }


-- SwitchMonitor(5).FastRedundancyStatus(52).FastRedundancyStatusTable(1)

	swhFastRedundancyStatusTable OBJECT-TYPE
		SYNTAX    SEQUENCE OF SwhFastRedundancyStatusEntry
		ACCESS    not-accessible
		STATUS    mandatory
		DESCRIPTION
			"Table of Ring port status."
		::= { swhFastRedundancyStatus 1 }

	-- Table Entry
	swhFastRedundancyStatusEntry OBJECT-TYPE
		SYNTAX    SwhFastRedundancyStatusEntry
		ACCESS    not-accessible
		STATUS    mandatory
		DESCRIPTION
			"An entry in the table, containing information
			about Ring port status"
		INDEX    { swhFastRedundancyStatusIndex }
		::= { swhFastRedundancyStatusTable 1 }

	SwhFastRedundancyStatusEntry ::=
		SEQUENCE {
			swhFastRedundancyStatusIndex
				INTEGER,
			swhFastRedundancyStatusGroupID
				INTEGER,
			swhFastRedundancyStatusDescription
				DisplayString,
			swhFastRedundancyStatusEnable
				INTEGER,
			swhFastRedundancyStatusProtocol
				INTEGER,
			swhFastRedundancyStatusRole
				INTEGER,
			swhFastRedundancyStatusStatus
				INTEGER,
			swhFastRedundancyStatusPort1
				INTEGER,
			swhFastRedundancyStatusPort1Role
				INTEGER,
			swhFastRedundancyStatusPort1Statue
				INTEGER,
			swhFastRedundancyStatusPort2
				INTEGER,
			swhFastRedundancyStatusPort2Role
				INTEGER,
			swhFastRedundancyStatusPort2Statue
				INTEGER
		}

	swhFastRedundancyStatusIndex OBJECT-TYPE
		SYNTAX    INTEGER (0..2147483647)
		ACCESS    not-accessible
		STATUS    mandatory
		DESCRIPTION
			"A unique value for port index."
		::= { swhFastRedundancyStatusEntry 1 }

	swhFastRedundancyStatusGroupID OBJECT-TYPE
		SYNTAX    INTEGER { na(-1),
		                    id-1(1),
		                    id-2(2)
		                    }
		ACCESS    read-only
		STATUS    mandatory
		DESCRIPTION
			"digital input normal."
		::= { swhFastRedundancyStatusEntry 2 }

	swhFastRedundancyStatusDescription OBJECT-TYPE
		SYNTAX    DisplayString
		ACCESS    read-only
		STATUS    mandatory
		DESCRIPTION
			"Fast Redundancy Description"
		::= { swhFastRedundancyStatusEntry 3 }

	swhFastRedundancyStatusEnable OBJECT-TYPE
		SYNTAX    INTEGER { na(-1), disable(0), enable(1) }
		ACCESS    read-only
		STATUS    mandatory
		DESCRIPTION
			"port enable"
		::= { swhFastRedundancyStatusEntry 4 }

	swhFastRedundancyStatusProtocol OBJECT-TYPE
		SYNTAX    INTEGER { na(-1), fast-ringv2(0), chain(1) }
		ACCESS    read-only
		STATUS    mandatory
		DESCRIPTION
			"port enable"
		::= { swhFastRedundancyStatusEntry 5 }

	swhFastRedundancyStatusRole OBJECT-TYPE
		SYNTAX    INTEGER { na(-1), slave(0), master(1) }
		ACCESS    read-only
		STATUS    mandatory
		DESCRIPTION
			"port status."
		::= { swhFastRedundancyStatusEntry 6 }

	swhFastRedundancyStatusStatus OBJECT-TYPE
		SYNTAX    INTEGER { signal-fail(-2), na(-1), healthy(0), break(1) }
		ACCESS    read-only
		STATUS    mandatory
		DESCRIPTION
			"port status."
		::= { swhFastRedundancyStatusEntry 7 }

	swhFastRedundancyStatusPort1 OBJECT-TYPE
		SYNTAX    INTEGER { na(0),
		                    port01(1),
		                    port02(2),
		                    port03(3),
		                    port04(4),
		                    port05(5),
		                    port06(6),
		                    port07(7),
		                    port08(8),
		                    port09(9),
		                    port10(10)
		                    }
		ACCESS    read-only
		STATUS    mandatory
		DESCRIPTION
			"port status."
		::= { swhFastRedundancyStatusEntry 8 }

	swhFastRedundancyStatusPort1Role OBJECT-TYPE
		SYNTAX    INTEGER { na(-1), member(0), head(1), tail(2) }
		ACCESS    read-only
		STATUS    mandatory
		DESCRIPTION
			"port status."
		::= { swhFastRedundancyStatusEntry 9 }

	swhFastRedundancyStatusPort1Statue OBJECT-TYPE
		SYNTAX    INTEGER { na2(-2), na(-1), blocked(1), forwarding(4), link-down(5) }
		ACCESS    read-only
		STATUS    mandatory
		DESCRIPTION
			"port status."
		::= { swhFastRedundancyStatusEntry 10 }

	swhFastRedundancyStatusPort2 OBJECT-TYPE
		SYNTAX    INTEGER { na(0),
		                    port01(1),
		                    port02(2),
		                    port03(3),
		                    port04(4),
		                    port05(5),
		                    port06(6),
		                    port07(7),
		                    port08(8),
		                    port09(9),
		                    port10(10)
		                    }
		ACCESS    read-only
		STATUS    mandatory
		DESCRIPTION
			"port status."
		::= { swhFastRedundancyStatusEntry 11 }

	swhFastRedundancyStatusPort2Role OBJECT-TYPE
		SYNTAX    INTEGER { na(-1), member(0), head(1), tail(2) }
		ACCESS    read-only
		STATUS    mandatory
		DESCRIPTION
			"port status."
		::= { swhFastRedundancyStatusEntry 12 }

	swhFastRedundancyStatusPort2Statue OBJECT-TYPE
		SYNTAX    INTEGER { na2(-2), na(-1), blocked(1), forwarding(4), link-down(5) }
		ACCESS    read-only
		STATUS    mandatory
		DESCRIPTION
			"port status."
		::= { swhFastRedundancyStatusEntry 13 }


-- SwitchMonitor(5).FastRedundancyStatus(52).FastRedundancyStatisticsTable(2)

	swhFastRedundancyStatisticsTable OBJECT-TYPE
		SYNTAX    SEQUENCE OF SwhFastRedundancyStatisticsEntry
		ACCESS    not-accessible
		STATUS    mandatory
		DESCRIPTION
			"Table of Ring port status."
		::= { swhFastRedundancyStatus 6 }

	-- Table Entry
	swhFastRedundancyStatisticsEntry OBJECT-TYPE
		SYNTAX    SwhFastRedundancyStatisticsEntry
		ACCESS    not-accessible
		STATUS    mandatory
		DESCRIPTION
			"An entry in the table, containing information
			about Ring port status"
		INDEX    { swhFastRedundancyEntry }
		::= { swhFastRedundancyStatisticsTable 1 }

	SwhFastRedundancyStatisticsEntry ::=
		SEQUENCE {
			swhFastRedundancyEntry
				INTEGER,
			swhFastRedundancyTxNormal
				Counter,
			swhFastRedundancyTxFailure
				Counter,
			swhFastRedundancyRxNormal
				Counter,
			swhFastRedundancyRxFailure
				Counter,
			swhFastRedundancyCountersClear
				INTEGER
		}

	swhFastRedundancyEntry OBJECT-TYPE
		SYNTAX    INTEGER (0..2147483647)
		ACCESS    not-accessible
		STATUS    mandatory
		DESCRIPTION
			"A unique value for port index."
		::= { swhFastRedundancyStatisticsEntry 1 }

	swhFastRedundancyTxNormal OBJECT-TYPE
		SYNTAX    Counter
		ACCESS    read-only
		STATUS    mandatory
		DESCRIPTION
			"Tx Normal"
		::= { swhFastRedundancyStatisticsEntry 2 }

	swhFastRedundancyTxFailure OBJECT-TYPE
		SYNTAX    Counter
		ACCESS    read-only
		STATUS    mandatory
		DESCRIPTION
			"Tx Failure"
		::= { swhFastRedundancyStatisticsEntry 3 }

	swhFastRedundancyRxNormal OBJECT-TYPE
		SYNTAX    Counter
		ACCESS    read-only
		STATUS    mandatory
		DESCRIPTION
			"Rx Normal"
		::= { swhFastRedundancyStatisticsEntry 4 }

	swhFastRedundancyRxFailure OBJECT-TYPE
		SYNTAX    Counter
		ACCESS    read-only
		STATUS    mandatory
		DESCRIPTION
			"Rx Failure"
		::= { swhFastRedundancyStatisticsEntry 5 }

	swhFastRedundancyCountersClear OBJECT-TYPE
		SYNTAX    INTEGER { normal(0), clear(1) }
		ACCESS    read-write
		STATUS    mandatory
		DESCRIPTION
			"Fast Redundancy Counters Clear"
		::= { swhFastRedundancyStatisticsEntry 6 }


-- SwitchMonitor(5).POEStatus(48)

	swhPOETotalWattsAvailable OBJECT-TYPE
		SYNTAX    INTEGER
		ACCESS    read-only
		STATUS    mandatory
		DESCRIPTION
			"Total Watts Availavle."
		::= { swhPOEStatus 3 }

	swhPOETotalPower OBJECT-TYPE
		SYNTAX    DisplayString
		ACCESS    read-only
		STATUS    mandatory
		DESCRIPTION
			"Table of Port State."
		::= { swhPOEStatus 1 }

	swhPOEStatusTable OBJECT-TYPE
		SYNTAX    SEQUENCE OF SwhPOEStatusEntry
		ACCESS    not-accessible
		STATUS    mandatory
		DESCRIPTION
			"Table of Port State."
		::= { swhPOEStatus 2 }

	-- Table Entry
	swhPOEStatusEntry OBJECT-TYPE
		SYNTAX    SwhPOEStatusEntry
		ACCESS    not-accessible
		STATUS    mandatory
		DESCRIPTION
			"An entry in the table, containing information
			 about Port State."
		INDEX    { swhPOEStatusIndex }
		::= { swhPOEStatusTable 1 }

	SwhPOEStatusEntry ::=
		SEQUENCE {
			swhPOEStatusIndex
				INTEGER,
			swhPOEStatusPort
				INTEGER,
			swhPOEStatusName
				DisplayString,
			swhPOEStatusPower
				DisplayString,
			swhPOEStatusVoltage
				DisplayString,
			swhPOEStatusCurrent
				DisplayString,
			swhPOEStatusPDClass
				DisplayString,
			swhPOEStatusPoEDetection
				DisplayString,
			swhPOEStatusOperationMode
				INTEGER
		}

	swhPOEStatusIndex OBJECT-TYPE
		SYNTAX    INTEGER (0..2147483647)
		ACCESS    not-accessible
		STATUS    mandatory
		DESCRIPTION
			"A unique value for each port."
		::= { swhPOEStatusEntry 1 }

	swhPOEStatusPort  OBJECT-TYPE
		SYNTAX    INTEGER { port01(0),
		                    port02(1),
		                    port03(2),
		                    port04(3),
		                    port05(4),
		                    port06(5),
							port07(6),
							port08(7)
		                    }
		ACCESS    read-only
		STATUS    mandatory
		DESCRIPTION
			"Port Number."
		::= { swhPOEStatusEntry 2 }

	swhPOEStatusName OBJECT-TYPE
		SYNTAX    DisplayString (SIZE (0..255))
		ACCESS    read-only
		STATUS    mandatory
		DESCRIPTION
			"POE Name"
		::= { swhPOEStatusEntry 3 }

	swhPOEStatusPower OBJECT-TYPE
		SYNTAX    DisplayString (SIZE (0..255))
		ACCESS    read-only
		STATUS    mandatory
		DESCRIPTION
			"PoE Power"
		::= { swhPOEStatusEntry 4 }

	swhPOEStatusVoltage OBJECT-TYPE
		SYNTAX    DisplayString (SIZE (0..255))
		ACCESS    read-only
		STATUS    mandatory
		DESCRIPTION
			"PoE Voltage"
		::= { swhPOEStatusEntry 5 }

	swhPOEStatusCurrent OBJECT-TYPE
		SYNTAX    DisplayString (SIZE (0..255))
		ACCESS    read-only
		STATUS    mandatory
		DESCRIPTION
			"PoE Current"
		::= { swhPOEStatusEntry 6 }

	swhPOEStatusPDClass OBJECT-TYPE
		SYNTAX    DisplayString (SIZE (0..255))
		ACCESS    read-only
		STATUS    mandatory
		DESCRIPTION
			"PoE PD Class"
		::= { swhPOEStatusEntry 7 }

	swhPOEStatusPoEDetection OBJECT-TYPE
		SYNTAX    DisplayString (SIZE (0..255))
		ACCESS    read-only
		STATUS    mandatory
		DESCRIPTION
			"PoE Detection"
		::= { swhPOEStatusEntry 8 }

	swhPOEStatusOperationMode OBJECT-TYPE
		SYNTAX    INTEGER { shutdown(0), injector-30watt(1), auto-af-at(2), auto(3), injector-60watt(4) }
		ACCESS    read-only
		STATUS    mandatory
		DESCRIPTION
			"PoE Operation Mode"
		::= { swhPOEStatusEntry 9 }


-- SystemUtility(6)

	swhLoadFactorySetting OBJECT-TYPE
		SYNTAX    INTEGER { normal(0), load(1) }
		ACCESS    write-only
		STATUS    mandatory
		DESCRIPTION
			"LoadFactorySetting"
		::= { swhSystemUtility 1 }

	swhLoadFactorySettingExceptNetworkConfiguration OBJECT-TYPE
		SYNTAX    INTEGER { normal(0), load(1) }
		ACCESS    write-only
		STATUS    mandatory
		DESCRIPTION
			"LoadFactorySettingExceptNetworkConfiguration"
		::= { swhSystemUtility 2 }

	swhEventLog
		OBJECT IDENTIFIER ::= { swhSystemUtility 3 }
	swhUpdateFirmware
		OBJECT IDENTIFIER ::= { swhSystemUtility 4 }
	swhAutoBackupConfiguration
		OBJECT IDENTIFIER ::= { swhSystemUtility 5 }
--	swhBackupConfiguration
--		OBJECT IDENTIFIER ::= { swhSystemUtility 5 }


-- SystemUtility(6).EventLog(3)

	swhEventLogTable OBJECT-TYPE
		SYNTAX    SEQUENCE OF SWHEventLogEntry
		ACCESS    not-accessible
		STATUS    mandatory
		DESCRIPTION
			"Table of Event Log."
		::= { swhEventLog 1 }

	swhEventLogClear OBJECT-TYPE
		SYNTAX    INTEGER { normal(0), clear(1) }
		ACCESS    write-only
		STATUS    mandatory
		DESCRIPTION
			"Clear Event Log Table"
		::= { swhEventLog 2 }

	-- Table Entry
	swhEventLogEntry OBJECT-TYPE
		SYNTAX    SWHEventLogEntry
		ACCESS    not-accessible
		STATUS    mandatory
		DESCRIPTION
			"An entry in the table, containing information
			about Event Log"
		INDEX    { swhEventLogIndex }
		::= { swhEventLogTable 1 }

	SWHEventLogEntry ::=
		SEQUENCE {
			swhEventLogIndex
				INTEGER,
			swhEventLogType
				INTEGER,
			swhEventLogTime
				DisplayString,
			swhEventLogUpTime
				DisplayString,
			swhEventLogDescription
				DisplayString,
			swhEventLogSource
				INTEGER,
			swhEventLogEvent
				INTEGER,
			swhEventLogNameCommunity
				DisplayString,
			swhEventLogIPAddr
				IpAddress
		--	swhEventLogCategory
		--		INTEGER
		}

	swhEventLogIndex OBJECT-TYPE
		SYNTAX    INTEGER
		ACCESS    read-only
		STATUS    mandatory
		DESCRIPTION
			"A unique value for Event Log  index."
		::= { swhEventLogEntry 1 }

	swhEventLogType OBJECT-TYPE
		SYNTAX    INTEGER { error(1000), warning(2000), information(3000) }
		ACCESS    read-only
		STATUS    mandatory
		DESCRIPTION
			"event type
			error: some funtions not work
			warning: to warn something, ex. login failed
			information: just something happened
			"
		::= { swhEventLogEntry 2 }

	swhEventLogTime OBJECT-TYPE
		SYNTAX    DisplayString
		ACCESS    read-only
		STATUS    mandatory
		DESCRIPTION
			"event happening time,
			it is local time"
		::= { swhEventLogEntry 3 }

	swhEventLogUpTime OBJECT-TYPE
		SYNTAX    DisplayString
		ACCESS    read-only
		STATUS    mandatory
		DESCRIPTION
			"event happening time,
			it is system up time
			"
		::= { swhEventLogEntry 4 }

	swhEventLogDescription OBJECT-TYPE
		SYNTAX    DisplayString
		ACCESS    read-only
		STATUS    mandatory
		DESCRIPTION
			"event description"
		::= { swhEventLogEntry 5 }

	swhEventLogSource OBJECT-TYPE
		SYNTAX    INTEGER { local-machine(4000),
		                    rs232d(4001),
		                    rs232(4002),
		                    telnetd(4003),
		                    telnet(4004),
		                    tftpd(4005),
		                    tftp(4006),
		                    ftpd(4007),
		                    ftp(4008),
		                    snmpd(4009),
		                    snmp(4010),
		                    webd(4011),
		                    web(4012),
		                    ping(4013),
		                    watch-dog(4014),
		                    remote-machine(4015),
		                    catv-module(4016)
		                    }
		ACCESS    read-only
		STATUS    mandatory
		DESCRIPTION
			"event source"
		::= { swhEventLogEntry 6 }

	swhEventLogEvent OBJECT-TYPE
		SYNTAX    INTEGER { boot-failed(1001),
		                    load-config-failed(1002),
		                    load-default-config-failed(1003),
		                    save-config-failed(1004),
		                    save-default-config-failed(1005),
		                    login-failed(2001),
		                    module-down(2002),
		                    module-power-down(2003),
		                    power-module-down(2004),
		                    power-fan-failed(2005),
		                    auto-provision(2007),
		                    fan-failed(2008),
		                    temperature-abnormality(2009),
		                    voltage-abnormality(2010),
		                    tx-bias-abnormality(2011),
		                    loop(2012),
		                    upgrade(2013),
		                    digital-input(2015),
		                    digital-output(2016),
							power-module-missing(2021),
		                    cold-start(3001),
		                    warm-start(3002),
		                    login(3003),
		                    logout(3004),
		                    timeout(3005),
		                    disconnected(3006),
		                    link-up(3007),
		                    link-down(3008),
							power-supply-up(3011),
		                    fan-ok(3022),
		                    digital-input(3026),
		                    digital-output(3027)
		                    }
		ACCESS    read-only
		STATUS    mandatory
		DESCRIPTION
			"event"
		::= { swhEventLogEntry 7 }

	swhEventLogNameCommunity OBJECT-TYPE
		SYNTAX    DisplayString
		ACCESS    read-only
		STATUS    mandatory
		DESCRIPTION
			"user name or community name"
		::= { swhEventLogEntry 8 }

	swhEventLogIPAddr OBJECT-TYPE
		SYNTAX    IpAddress
		ACCESS    read-only
		STATUS    mandatory
		DESCRIPTION
			"event ip address,
			ex. login user ip address"
		::= { swhEventLogEntry 9 }

	--swhEventLogCategory OBJECT-TYPE
	--	SYNTAX    INTEGER 
	--	ACCESS    read-only
	--	STATUS    mandatory
	--	DESCRIPTION
	--		"Category"
	--	::= { swhEventLogEntry 10 }


-- SystemUtility(6).UpdateFirmware(4)

	swhUpdateProtocol OBJECT-TYPE
		SYNTAX    INTEGER { tftp(0), ftp(1) }
		ACCESS    read-write
		STATUS    mandatory
		DESCRIPTION
			"Update file from tftp or ftp server."
		::= { swhUpdateFirmware 1 }

	swhUpdateFileType OBJECT-TYPE
		SYNTAX    INTEGER { firmware(0), configuration(1) }
		ACCESS    read-write
		STATUS    mandatory
		DESCRIPTION
			"Update file type."
		::= { swhUpdateFirmware 2 }

	swhUpdateConfigeType OBJECT-TYPE
		SYNTAX    INTEGER { running(0), default(1) , startup(2) }
		ACCESS    read-write
		STATUS    mandatory
		DESCRIPTION
			"Update confige type."
		::= { swhUpdateFirmware 15 }

	swhUpdateImageOption OBJECT-TYPE
		SYNTAX    INTEGER { image1(1), image2(2) }
		ACCESS    read-write
		STATUS    mandatory
		DESCRIPTION
			"Update Image Option."
		::= { swhUpdateFirmware 16 }

	swhUpdateServerIPAddr OBJECT-TYPE
		SYNTAX    IpAddress
		ACCESS    read-write
		STATUS    mandatory
		DESCRIPTION
			"Tftp/ftp server ip address."
		::= { swhUpdateFirmware 3 }

	swhUpdateUserName OBJECT-TYPE
		SYNTAX    DisplayString (SIZE (0..255))
		ACCESS    read-write
		STATUS    mandatory
		DESCRIPTION
			"Ftp server login user name."
		::= { swhUpdateFirmware 4 }

	swhUpdatePassword OBJECT-TYPE
		SYNTAX    DisplayString (SIZE (0..255))
		ACCESS    read-write
		STATUS    mandatory
		DESCRIPTION
			"Ftp server login password."
		::= { swhUpdateFirmware 5 }

	swhUpdateFileLocation OBJECT-TYPE
		SYNTAX    DisplayString (SIZE (0..255))
		ACCESS    read-write
		STATUS    mandatory
		DESCRIPTION
			"Upate file location."
		::= { swhUpdateFirmware 6 }

	--swhUpdateGet OBJECT-TYPE
	--	SYNTAX    INTEGER { normal(0), get(1) }
	--	ACCESS    write-only
	--	STATUS    mandatory
	--	DESCRIPTION
	--		"Get file from server."
	--	::= { swhUpdateFirmware 7 }

	swhUpdatePut OBJECT-TYPE
		SYNTAX    INTEGER { normal(0), put(1) }
		ACCESS    write-only
		STATUS    mandatory
		DESCRIPTION
			"Put file to server."
		::= { swhUpdateFirmware 8 }

	swhUpdateUpdate OBJECT-TYPE
		SYNTAX    INTEGER { normal(0), update(1) }
		ACCESS    write-only
		STATUS    mandatory
		DESCRIPTION
			"Get configuration or firmware, then update it.
			 When update succeeded, system will reboot automatically."
		::= { swhUpdateFirmware 10 }

	swhUpdateState OBJECT-TYPE
		SYNTAX    DisplayString (SIZE (0..255))
		ACCESS    read-only
		STATUS    mandatory
		DESCRIPTION
			"Messages for getting/putting file, updating config/firmware."
		::= { swhUpdateFirmware 12 }


-- SystemUtility(6).BackupConfiguration(5)

	swhBackupNTPStatus OBJECT-TYPE
		SYNTAX    DisplayString (SIZE (0..255))
		ACCESS    read-only
		STATUS    mandatory
		DESCRIPTION
			"NTP Status."
		::= { swhAutoBackupConfiguration 14 }

	swhBackupAuto OBJECT-TYPE
		SYNTAX    INTEGER { disable(0), enable(1) }
		ACCESS    read-write
		STATUS    mandatory
		DESCRIPTION
			"Enable or disable auto backup.
			 In order for the Auto Backup function to work properly,
			 the NTP function must be enabled for the device to acquire local time information."
		::= { swhAutoBackupConfiguration 2 }

	swhBackupTrigger OBJECT-TYPE
		SYNTAX    INTEGER { ntp-time(0), save-configuration(1) }
		ACCESS    read-write
		STATUS    mandatory
		DESCRIPTION
			"Backup trigger condition."
		::= { swhAutoBackupConfiguration 13 }

	swhBackupTime OBJECT-TYPE
		SYNTAX    INTEGER (0..23)
		ACCESS    read-write
		STATUS    mandatory
		DESCRIPTION
			"Backup time at which hour of a day."
		::= { swhAutoBackupConfiguration 3 }

	swhBackupProtocol OBJECT-TYPE
		SYNTAX    INTEGER { tftp(0), ftp(1) }
		ACCESS    read-write
		STATUS    mandatory
		DESCRIPTION
			"Backup file from tftp or ftp server."
		::= { swhAutoBackupConfiguration 4 }

	swhBackupFileType OBJECT-TYPE
		SYNTAX    INTEGER { configuration(1) }
		ACCESS    read-only
		STATUS    mandatory
		DESCRIPTION
			"Backup file type."
		::= { swhAutoBackupConfiguration 5 }

	swhBackupServerIPAddr OBJECT-TYPE
		SYNTAX    DisplayString (SIZE (0..255))
		ACCESS    read-write
		STATUS    mandatory
		DESCRIPTION
			"TFTP/FTP server ip address."
		::= { swhAutoBackupConfiguration 6 }

	swhBackupUserName OBJECT-TYPE
		SYNTAX    DisplayString (SIZE (0..255))
		ACCESS    read-write
		STATUS    mandatory
		DESCRIPTION
			"FTP server login user name."
		::= { swhAutoBackupConfiguration 7 }

	swhBackupPassword OBJECT-TYPE
		SYNTAX    DisplayString (SIZE (0..255))
		ACCESS    read-write
		STATUS    mandatory
		DESCRIPTION
			"FTP server login password."
		::= { swhAutoBackupConfiguration 8 }

	swhBackupFileDirectory OBJECT-TYPE
		SYNTAX    DisplayString (SIZE (0..255))
		ACCESS    read-write
		STATUS    mandatory
		DESCRIPTION
			"Backup file directory."
		::= { swhAutoBackupConfiguration 9 }

	swhBackupFileName OBJECT-TYPE
		SYNTAX    DisplayString (SIZE (0..255))
		ACCESS    read-only
		STATUS    mandatory
		DESCRIPTION
			"Backup file name."
		::= { swhAutoBackupConfiguration 10 }

	swhBackupState OBJECT-TYPE
		SYNTAX    DisplayString (SIZE (0..255))
		ACCESS    read-only
		STATUS    mandatory
		DESCRIPTION
			"Messages for backup."
		::= { swhAutoBackupConfiguration 12 }

-- Traps(9)

	swhSystemPowerDown TRAP-TYPE
		ENTERPRISE    switchTraps
		--&ACTIONS    { critical }
		--&MESG       "System Power Down"
		DESCRIPTION
			"when system power down, send this trap."
		::=  1

	swhBroadcastStorm TRAP-TYPE
		ENTERPRISE    switchTraps
		VARIABLES     { ifIndex, etherStatsBroadcastPkts }
		--&ACTIONS    { warning }
		--&MESG       "Interface $1 Broadcast Storm Occurs, $2 packets"
		DESCRIPTION
			"when received broadcast packets arrive upper limit, send this trap."
		::=  2

	swhBroadcastNormal TRAP-TYPE
		ENTERPRISE    switchTraps
		VARIABLES     { ifIndex, etherStatsBroadcastPkts }
		--&ACTIONS    { minor }
		--&MESG       "Interface $1 Broadcast Packets Normal, $2 packets"
		DESCRIPTION
			"when received broadcast packets are normal, send this trap."
		::=  3

	swhSFPAbnormality TRAP-TYPE
		ENTERPRISE    switchTraps
		VARIABLES     { ifIndex, sysLocation }
		--&ACTIONS    { warning }
		--&MESG       "SFP Interface $1 $2 Abnormality"
		DESCRIPTION   "when sfp status abnormality , send this trap."
		::=  7

	swhFaultAlarm TRAP-TYPE
		ENTERPRISE    switchTraps
		VARIABLES     { ifIndex, sysLocation }
		--&ACTIONS    { warning }
		--&MESG       "$2"
		DESCRIPTION   "when fault Alarm , send this trap."
		::=  8

	swhWarningAlarm TRAP-TYPE
		ENTERPRISE    switchTraps
		VARIABLES     { ifIndex, sysLocation }
		--&ACTIONS    { warning }
		--&MESG       "$2"
		DESCRIPTION   "when Warning Alarm , send this trap."
		::=  9

	swhMinorAlarm TRAP-TYPE
		ENTERPRISE    switchTraps
		VARIABLES     { ifIndex, sysLocation }
		--&ACTIONS    { minor }
		--&MESG       "$2"
		DESCRIPTION   "when Minor Alarm , send this trap."
		::=  10

	swhLoopBack TRAP-TYPE
		ENTERPRISE    switchTraps
		VARIABLES     { ifIndex, sysLocation }
		--&ACTIONS    { warning }
		--&MESG       "$2"
		DESCRIPTION   "when Loop back, send this trap."
		::=  13

	swhBatteryMode TRAP-TYPE
		ENTERPRISE    switchTraps
		VARIABLES     { ifIndex, sysLocation }
		--&ACTIONS    { warning }
		--&MESG       "$2"
		DESCRIPTION
			"when Battery is discharge electricity, send this trap."
		::=  14

	swhCATVPower TRAP-TYPE
		ENTERPRISE    switchTraps
		VARIABLES     { ifIndex, sysLocation }
		--&ACTIONS    { warning }
		--&MESG       "$2"
		DESCRIPTION
			"when CATV power, send this trap."
		::=  15

	swhNormalAlarm TRAP-TYPE
		ENTERPRISE    switchTraps
		VARIABLES     { ifIndex, sysLocation }
		--&ACTIONS    { normal }
		--&MESG       "$2"
		DESCRIPTION   "when Normal Alarm(Information), send this trap."
		::=  16

	swhPowerExceptional TRAP-TYPE
		ENTERPRISE    switchTraps
		VARIABLES     { ifIndex, sysLocation }
		--&ACTIONS    { warning }
		--&MESG       "$2"
		DESCRIPTION
			"when Power Exceptional, send this trap."
		::=  17

	swhSystemPowerOn TRAP-TYPE
		ENTERPRISE    switchTraps
		VARIABLES     { ifIndex, sysLocation }
		--&ACTIONS    { critical }
		--&MESG       "$2"
		DESCRIPTION   "when system power up, send this trap."
		::=  20

END
