--
-- Zhone.mib
-- MIB generated by MG-SOFT Visual MIB Builder Version 3.0 Build 285
-- Friday, January 13, 2012 at 14:10:45
--

	Zhone DEFINITIONS ::= BEGIN
 
		IMPORTS
			OBJECT-GROUP, MODULE-COMPLIANCE			
				FROM SNMPv2-CONF			
			enterprises, Integer32, OBJECT-TYPE, MODULE-IDENTITY, OBJECT-IDENTITY			
				FROM SNMPv2-SMI;
	
	
		-- 1.3.6.1.4.1.5504
		zhone MODULE-IDENTITY 
			LAST-UPDATED "201112052000Z"		-- December 05, 2011 at 20:00 GMT
			ORGANIZATION 
				"Zhone Technologies"
			CONTACT-INFO 
				"  Postal: 
				Zhone Technologies, Inc.
				@ Zhone Way
				7001 Oakport Street
				Oakland, CA  94621
				USA
				Toll-Free: +1 877-ZHONE20 (+1 877-946-6320)
				Tel: +1-510-777-7000
				Fax: +1-510-777-7001
				E-mail: support@zhone.com"
			DESCRIPTION 
				"This is the Zhone Information MIB for all entries that are used
				across all Zhone platforms."
			REVISION "201112051658Z"		-- December 05, 2011 at 16:58 GMT
			DESCRIPTION 
				"Add 1588 Precision Timing Module."
			REVISION "201105060020Z"		-- May 06, 2011 at 00:20 GMT
			DESCRIPTION 
				"IEEE 802.1 related mibs."
			REVISION "201002191051Z"		-- February 19, 2010 at 10:51 GMT
			DESCRIPTION 
				"V01.01.27 - Added zhoneRmonMibModule."
			REVISION "200905270208Z"		-- May 27, 2009 at 02:08 GMT
			DESCRIPTION 
				"V01.01.26 - Added zhoneIua."
			REVISION "200801231146Z"		-- January 23, 2008 at 11:46 GMT
			DESCRIPTION 
				"add zhoneInterfaceConfig"
			REVISION "200711091305Z"		-- November 09, 2007 at 13:05 GMT
			DESCRIPTION 
				"V01.01.24 - Added zhoneSFF."
			REVISION "200710161026Z"		-- October 16, 2007 at 10:26 GMT
			DESCRIPTION 
				"V01.01.23 - Add zhoneWdm."
			REVISION "200702171343Z"		-- February 17, 2007 at 13:43 GMT
			DESCRIPTION 
				"V01.01.22 - Add zhoneRadius."
			REVISION "200606091248Z"		-- June 09, 2006 at 12:48 GMT
			DESCRIPTION 
				"V01.01.21 - Add zhoneVdsl
				Add efmOamMIB from ZOI 89562
				Add efmCuMIB from ZOI 89562"
			REVISION "200512011420Z"		-- December 01, 2005 at 14:20 GMT
			DESCRIPTION 
				"V01.01.20 - Add zhoneBonding."
			REVISION "200410131440Z"		-- October 13, 2004 at 14:40 GMT
			DESCRIPTION 
				"V01.01.19 - Added a new entry for pktcIetfSigMib"
			REVISION "200410081115Z"		-- October 08, 2004 at 11:15 GMT
			DESCRIPTION 
				"V01.01.18 - Added zhoneSs7 and zhoneClass5"
			REVISION "200408111542Z"		-- August 11, 2004 at 15:42 GMT
			DESCRIPTION 
				"V01.01.17 - Added zhoneCes"
			REVISION "200401301334Z"		-- January 30, 2004 at 13:34 GMT
			DESCRIPTION 
				"V01.01.17 - Added zhoneIsdn"
			REVISION "200310281103Z"		-- October 28, 2003 at 11:03 GMT
			DESCRIPTION 
				"V01.01.16 - Added zhoneVideo."
			REVISION "200307171429Z"		-- July 17, 2003 at 14:29 GMT
			DESCRIPTION 
				"V01.01.15 - Added zhoneVoiceStats to zhoneGeneric."
			REVISION "200203041534Z"		-- March 04, 2002 at 15:34 GMT
			DESCRIPTION 
				"V01.01.14 - Added zhoneExperimental branch for Sonet APS."
			REVISION "200110091207Z"		-- October 09, 2001 at 12:07 GMT
			DESCRIPTION 
				"V01.01.13 - Add Bridge group under communication protocols."
			REVISION "200009281632Z"		-- September 28, 2000 at 16:32 GMT
			DESCRIPTION 
				"V01.01.01 -
				Added zhoneRegWtn for registration of Zhone Wireless Transport Node.
				Added zhoneWtx for RF interfaces on Zhone Wireless Transport Node."
			REVISION "200012181632Z"		-- December 18, 2000 at 16:32 GMT
			DESCRIPTION 
				"V01.01.02 -
				Added zhoneSonet for Zhone SONET MIB used for Sechtor 100 and BAN products."
			REVISION "200012201720Z"		-- December 20, 2000 at 17:20 GMT
			DESCRIPTION 
				"V01.01.03 -
				Added sechtor100 under zhoneSechtor for Sechtor 100 MIB."
			REVISION "200102071711Z"		-- February 07, 2001 at 17:11 GMT
			DESCRIPTION 
				"V01.01.04 -
				Added zhonePpp under zhoneCommunicationProtocols for the PPP MIBs."
			REVISION "200102221135Z"		-- February 22, 2001 at 11:35 GMT
			DESCRIPTION 
				"V01.01.05 - Add Ds3 Medium Extension Table."
			REVISION "200104101435Z"		-- April 10, 2001 at 14:35 GMT
			DESCRIPTION 
				"V01.01.06 - Add zhoneIma Module definition"
			REVISION "200105151032Z"		-- May 15, 2001 at 10:32 GMT
			DESCRIPTION 
				"V01.01.07 - Make wireless component names uniformly wtn and radio."
			REVISION "200106261706Z"		-- June 26, 2001 at 17:06 GMT
			DESCRIPTION 
				"V01.01.08 - Added Malc Product Family"
			REVISION "200106281333Z"		-- June 28, 2001 at 13:33 GMT
			DESCRIPTION 
				"V01.01.09 - fix 17 slot limit problem"
			REVISION "200107310851Z"		-- July 31, 2001 at 08:51 GMT
			DESCRIPTION 
				"V01.01.10 - Add ZMS Product Family"
			REVISION "200108291656Z"		-- August 29, 2001 at 16:56 GMT
			DESCRIPTION 
				"V01.01.11 - Add zhoneZAP object to zhoneGeneric structure."
			REVISION "200108311533Z"		-- August 31, 2001 at 15:33 GMT
			DESCRIPTION 
				"V01.01.12 - Add sechtor300 group under sechtor"
			::= { enterprises 5504 }

		
	
	
--
-- Node definitions
--
	
		-- 1.3.6.1.4.1.5504.1
		zhoneRegistrations OBJECT-IDENTITY
			STATUS current
			DESCRIPTION 
				"Sub-tree for registrations. See the Zhone registrations
				MIB for the actual tree."
			::= { zhone 1 }

		
		-- 1.3.6.1.4.1.5504.1.1
		zhoneRegPls OBJECT-IDENTITY
			STATUS current
			DESCRIPTION 
				"PLS product registrations"
			::= { zhoneRegistrations 1 }

		
		-- 1.3.6.1.4.1.5504.1.2
		zhoneRegCpe OBJECT-IDENTITY
			STATUS current
			DESCRIPTION 
				"Zhone CPE equipment product registrations."
			::= { zhoneRegistrations 2 }

		
		-- 1.3.6.1.4.1.5504.1.3
		zhoneRegMux OBJECT-IDENTITY
			STATUS current
			DESCRIPTION 
				"Zhone Mux Product Registrations."
			::= { zhoneRegistrations 3 }

		
		-- 1.3.6.1.4.1.5504.1.4
		zhoneRegSechtor OBJECT-IDENTITY
			STATUS current
			DESCRIPTION 
				"Zhone Sechtor Product Registrations."
			::= { zhoneRegistrations 4 }

		
		-- 1.3.6.1.4.1.5504.1.5
		zhoneRegWtn OBJECT-IDENTITY
			STATUS current
			DESCRIPTION 
				"Zhone Wireless Transport Product Registrations."
			::= { zhoneRegistrations 5 }

		
		-- 1.3.6.1.4.1.5504.1.6
		zhoneRegMalc OBJECT-IDENTITY
			STATUS current
			DESCRIPTION 
				"Multiple Access Loop Concentrator product registrations"
			::= { zhoneRegistrations 6 }

		
		-- 1.3.6.1.4.1.5504.2
		zhoneProduct OBJECT-IDENTITY
			STATUS current
			DESCRIPTION 
				"Products hierarchy for the Zhone enterprise"
			::= { zhone 2 }

		
		-- 1.3.6.1.4.1.5504.2.1
		zhonePls OBJECT-IDENTITY
			STATUS current
			DESCRIPTION 
				"PLS product specific MIB hierarchy."
			::= { zhoneProduct 1 }

		
		-- 1.3.6.1.4.1.5504.2.2
		zhoneZedge OBJECT-IDENTITY
			STATUS current
			DESCRIPTION 
				"Zedge product specific MIB hierarchy."
			::= { zhoneProduct 2 }

		
		-- 1.3.6.1.4.1.5504.2.3
		zhoneZplex OBJECT-IDENTITY
			STATUS current
			DESCRIPTION 
				"Z-Plex product specific MIB hierarchy."
			::= { zhoneProduct 3 }

		
		-- 1.3.6.1.4.1.5504.2.4
		zhoneSechtor OBJECT-IDENTITY
			STATUS current
			DESCRIPTION 
				"Sechtor product specific MIB hierarchy."
			::= { zhoneProduct 4 }

		
		-- 1.3.6.1.4.1.5504.2.4.1
		sechtor100 OBJECT-IDENTITY
			STATUS current
			DESCRIPTION 
				"MIB module for Sechtor 100 product."
			::= { zhoneSechtor 1 }

		
		-- 1.3.6.1.4.1.5504.2.4.2
		sechtor300 OBJECT-IDENTITY
			STATUS current
			DESCRIPTION 
				"MIB module for Sechtor 300/ArcaDacs 100 product."
			::= { zhoneSechtor 2 }

		
		-- 1.3.6.1.4.1.5504.2.5
		zhoneWtn OBJECT-IDENTITY
			STATUS current
			DESCRIPTION 
				"Wireless Transport product specific MIB hierarchy."
			::= { zhoneProduct 5 }

		
		-- 1.3.6.1.4.1.5504.2.6
		zhoneMalc OBJECT-IDENTITY
			STATUS current
			DESCRIPTION 
				"Multiple Access Loop Concentrator product specific MIB hierarchy."
			::= { zhoneProduct 6 }

		
		-- 1.3.6.1.4.1.5504.2.7
		zhoneZmsProduct OBJECT-IDENTITY
			STATUS current
			DESCRIPTION 
				"ZMS Product Family mib hierarchy."
			::= { zhoneProduct 7 }

		
		-- 1.3.6.1.4.1.5504.3
		zhoneGeneric OBJECT-IDENTITY
			STATUS current
			DESCRIPTION 
				"This hierarchy defines MIB entities for system level 
				information as opposed to information valid only
				on a specific card type or protocol. MIBs in this 
				hierarchy may or may not be implemented on a specific
				Zhone platform but are not specific to only one
				product. Those MIBs will be in the Zhone product MIB 
				hierarchy."
			::= { zhone 3 }

		
		-- 1.3.6.1.4.1.5504.3.1
		zhoneSystem OBJECT-IDENTITY
			STATUS current
			DESCRIPTION 
				"Zhone parameters that apply to the complete system as
				opposed to just one card. This augments the standard 
				system MIB."
			::= { zhoneGeneric 1 }

		
		-- 1.3.6.1.4.1.5504.3.2
		zhoneShelf OBJECT-IDENTITY
			STATUS current
			DESCRIPTION 
				"The Zhone Shelf MIB contains information specific to 
				a single shelf."
			::= { zhoneGeneric 2 }

		
		-- 1.3.6.1.4.1.5504.3.3
		zhoneCard OBJECT-IDENTITY
			STATUS current
			DESCRIPTION 
				"The Zhone unit MIB containing generic information for
				a card based entity. This would cover cards in the
				case of the BAN and a system in the case of single
				cpu systems."
			::= { zhoneGeneric 3 }

		
		-- 1.3.6.1.4.1.5504.3.4
		zhoneSubscriber OBJECT-IDENTITY
			STATUS current
			DESCRIPTION 
				"Subscriber information. This contains all data 
				associated with a subscriber instance. It will contain 
				voice, data, and video information."
			::= { zhoneGeneric 4 }

		
		-- 1.3.6.1.4.1.5504.3.5
		zhoneInterfaceTranslation OBJECT-IDENTITY
			STATUS current
			DESCRIPTION 
				"The interface translation MIB is the Zhone specific mapping
				of a physical interface to an ifTable entry and vice versa. "
			::= { zhoneGeneric 5 }

		
		-- 1.3.6.1.4.1.5504.3.6
		zhoneInterfaceGroup OBJECT-IDENTITY
			STATUS current
			DESCRIPTION 
				"The Interface Group is the Zhone specific  mapping of two lines 
				to a common group. The group represents their primary/secondary
				relationship and determines their group behavior during line
				switching due to failure or maintainance operations."
			::= { zhoneGeneric 6 }

		
		-- 1.3.6.1.4.1.5504.3.7
		zhoneMasterAgent OBJECT-IDENTITY
			STATUS current
			DESCRIPTION 
				"Zhone Master Agent implementation."
			::= { zhoneGeneric 7 }

		
		-- 1.3.6.1.4.1.5504.3.8
		zhoneTrapModules OBJECT-IDENTITY
			STATUS current
			DESCRIPTION 
				"This provides a grouping for miscellaneous Traps.  This
				space should only be used by modules that don't have a MIB
				associated with them."
			::= { zhoneGeneric 8 }

		
		-- 1.3.6.1.4.1.5504.3.9
		zhoneGenWtn OBJECT-IDENTITY
			STATUS current
			DESCRIPTION 
				"Zhone Wireless Transport generic Mib group."
			::= { zhoneGeneric 9 }

		
		-- 1.3.6.1.4.1.5504.3.10
		zhoneZAP OBJECT-IDENTITY
			STATUS current
			DESCRIPTION 
				"Zhone Wireless Transport generic Mib group."
			::= { zhoneGeneric 10 }

		
		-- 1.3.6.1.4.1.5504.3.11
		zhoneVoiceStats OBJECT-IDENTITY
			STATUS current
			DESCRIPTION 
				"Voice Call Statistics. This Object contains all
				instances associated with voice calls statistics."
			::= { zhoneGeneric 11 }

		
		-- 1.3.6.1.4.1.5504.3.12
		zhoneSFF OBJECT-IDENTITY
			STATUS current
			DESCRIPTION 
				"Small Form Factor (SFF) Pluggable and Fixed for both
				1Gb (SFP) and 10Gb (XFP) modules."
			::= { zhoneGeneric 12 }

		
		-- 1.3.6.1.4.1.5504.3.13
		zhoneInterfaceConfig OBJECT-IDENTITY
			STATUS current
			DESCRIPTION 
				"The Zhone Interface Config table is a mechanism to be
				able to configure a group of physical ifIndex to the 
				same parameters."
			::= { zhoneGeneric 13 }

		
		-- 1.3.6.1.4.1.5504.4
		zhoneCommunicationProtocols OBJECT-IDENTITY
			STATUS current
			DESCRIPTION 
				"This MIB hierarchy defines the communication protocol 
				specific MIBs (e.g. IP) that are Zhone proprietary. 
				They may or may not be implemented on a specific Zhone 
				product based upon what functionality is supported on 
				that product."
			::= { zhone 4 }

		
		-- 1.3.6.1.4.1.5504.4.1
		zhoneIp OBJECT-IDENTITY
			STATUS current
			DESCRIPTION 
				"IP related Zhone MIBs."
			::= { zhoneCommunicationProtocols 1 }

		
		-- 1.3.6.1.4.1.5504.4.2
		zhoneAtm OBJECT-IDENTITY
			STATUS current
			DESCRIPTION 
				"ATM related Zhone MIBs."
			::= { zhoneCommunicationProtocols 2 }

		
		-- 1.3.6.1.4.1.5504.4.3
		zhoneVoice OBJECT-IDENTITY
			STATUS current
			DESCRIPTION 
				"Voice related Zhone MIBs."
			::= { zhoneCommunicationProtocols 3 }

		
		-- 1.3.6.1.4.1.5504.4.4
		zhoneVoip OBJECT-IDENTITY
			STATUS current
			DESCRIPTION 
				"Voice over IP related Zhone MIBs."
			::= { zhoneCommunicationProtocols 4 }

		
		-- 1.3.6.1.4.1.5504.4.5
		zhonePpp OBJECT-IDENTITY
			STATUS current
			DESCRIPTION 
				"PPP related Zhone MIBs."
			::= { zhoneCommunicationProtocols 5 }

		
		-- 1.3.6.1.4.1.5504.4.6
		zhoneIma OBJECT-IDENTITY
			STATUS current
			DESCRIPTION 
				"IMA related Zhone MIBs."
			::= { zhoneCommunicationProtocols 6 }

		
		-- 1.3.6.1.4.1.5504.4.7
		zhoneBridge OBJECT-IDENTITY
			STATUS current
			DESCRIPTION 
				"Ip Bridge related Zhone MIBs."
			::= { zhoneCommunicationProtocols 7 }

		
		-- 1.3.6.1.4.1.5504.4.8
		zhoneVideo OBJECT-IDENTITY
			STATUS current
			DESCRIPTION 
				"Video related Zhone MIBs."
			::= { zhoneCommunicationProtocols 8 }

		
		-- 1.3.6.1.4.1.5504.4.9
		zhoneIsdn OBJECT-IDENTITY
			STATUS current
			DESCRIPTION 
				"ISDN related Zhone MIBs."
			::= { zhoneCommunicationProtocols 9 }

		
		-- 1.3.6.1.4.1.5504.4.10
		zhoneCes OBJECT-IDENTITY
			STATUS current
			DESCRIPTION 
				"Circuit Emulation Service related (CES) Zhone MIBs."
			::= { zhoneCommunicationProtocols 10 }

		
		-- 1.3.6.1.4.1.5504.4.11
		zhoneSs7 OBJECT-IDENTITY
			STATUS current
			DESCRIPTION 
				"SS7 related MIBs."
			::= { zhoneCommunicationProtocols 11 }

		
		-- 1.3.6.1.4.1.5504.4.12
		zhoneClass5 OBJECT-IDENTITY
			STATUS current
			DESCRIPTION 
				"Class-5 switch related MIBs."
			::= { zhoneCommunicationProtocols 12 }

		
		-- 1.3.6.1.4.1.5504.4.13
		zhoneBonding OBJECT-IDENTITY
			STATUS current
			DESCRIPTION 
				"Zhone Bonding protocols, including EFM, N2N and MLPPP."
			::= { zhoneCommunicationProtocols 13 }

		
		-- 1.3.6.1.4.1.5504.4.14
		zhoneRadius OBJECT-IDENTITY
			STATUS current
			DESCRIPTION 
				"Zhone RADIUS protocols including both client and server."
			::= { zhoneCommunicationProtocols 14 }

		
		-- 1.3.6.1.4.1.5504.4.15
		zhoneIua OBJECT-IDENTITY
			STATUS current
			DESCRIPTION 
				"IUA/SCTP related Zhone MIBs"
			::= { zhoneCommunicationProtocols 15 }

		
		-- 1.3.6.1.4.1.5504.4.16
		zhone802Dot1Mibs OBJECT-IDENTITY
			STATUS current
			DESCRIPTION 
				"IEEE 802.1 related mibs."
			::= { zhoneCommunicationProtocols 16 }

		
		-- 1.3.6.1.4.1.5504.4.17
		zhonePtp OBJECT-IDENTITY
			STATUS current
			DESCRIPTION 
				"MIB elements for Zhone's implementation of the
				IEEE Precision Timing Protocol."
			::= { zhoneCommunicationProtocols 17 }

		
		-- 1.3.6.1.4.1.5504.5
		zhonePhysical OBJECT-IDENTITY
			STATUS current
			DESCRIPTION 
				"This MIB hierarchy contains Zhone proprietary MIBs for
				implementing different physical interfaces."
			::= { zhone 5 }

		
		-- 1.3.6.1.4.1.5504.5.1
		zhoneEnet OBJECT-IDENTITY
			STATUS current
			DESCRIPTION 
				"Ethernet related Zhone MIBs."
			::= { zhonePhysical 1 }

		
		-- 1.3.6.1.4.1.5504.5.2
		zhoneDsx OBJECT-IDENTITY
			STATUS current
			DESCRIPTION 
				"DS3/DS1 related Zhone MIBs."
			::= { zhonePhysical 2 }

		
		-- 1.3.6.1.4.1.5504.5.3
		zhoneOcx OBJECT-IDENTITY
			STATUS current
			DESCRIPTION 
				"OC3/OC12 related Zhone MIBs."
			::= { zhonePhysical 3 }

		
		-- 1.3.6.1.4.1.5504.5.4
		zhoneDsl OBJECT-IDENTITY
			STATUS current
			DESCRIPTION 
				"DSL related Zhone MIBs."
			::= { zhonePhysical 4 }

		
		-- 1.3.6.1.4.1.5504.5.5
		zhoneConsole OBJECT-IDENTITY
			STATUS current
			DESCRIPTION 
				"Zhone MIBs required for implementing the console interface. 
				The RS-232 MIB was not implemented due to the fact this 
				was much more complex than what was required for this simple
				interface."
			::= { zhonePhysical 5 }

		
		-- 1.3.6.1.4.1.5504.5.8
		zhoneRadio OBJECT-IDENTITY
			STATUS current
			DESCRIPTION 
				"Zhone MIBs for radio interfaces used in the Zhone Wireless Transport Node."
			::= { zhonePhysical 8 }

		
		-- 1.3.6.1.4.1.5504.5.9
		zhoneSonet OBJECT-IDENTITY
			STATUS current
			DESCRIPTION 
				"Zhone SONET MIB used in the Zhone Sechtor 100 and BAN products."
			::= { zhonePhysical 9 }

		
		-- 1.3.6.1.4.1.5504.5.10
		zhoneDs3Ext OBJECT-IDENTITY
			STATUS current
			DESCRIPTION 
				"Zhone Ds3Ext MIB used in the Zhone BAN product."
			::= { zhonePhysical 10 }

		
		-- 1.3.6.1.4.1.5504.5.11
		zhoneLineTypes OBJECT-IDENTITY
			STATUS current
			DESCRIPTION 
				"Zhone custom physical line and port configurations."
			::= { zhonePhysical 11 }

		
		-- 1.3.6.1.4.1.5504.5.12
		zhoneApon OBJECT-IDENTITY
			STATUS current
			DESCRIPTION 
				"ATM-PON related Zhone MIBs."
			::= { zhonePhysical 12 }

		
		-- 1.3.6.1.4.1.5504.5.13
		zhoneVdsl OBJECT-IDENTITY
			STATUS current
			DESCRIPTION 
				"VDSL2 related Zhone MIBs."
			::= { zhonePhysical 13 }

		
		-- 1.3.6.1.4.1.5504.5.14
		zhoneGpon OBJECT-IDENTITY
			STATUS current
			DESCRIPTION 
				"Description."
			::= { zhonePhysical 14 }

		
		-- 1.3.6.1.4.1.5504.5.15
		zhoneWdm OBJECT-IDENTITY
			STATUS current
			DESCRIPTION 
				"Wave Division Multiplexing related Zhone MIBs."
			::= { zhonePhysical 15 }

		
		-- 1.3.6.1.4.1.5504.5.16
		zhoneCpe OBJECT-IDENTITY
			STATUS current
			DESCRIPTION 
				"CPE profiles for Voip and Pseudo wire."
			::= { zhonePhysical 16 }

		
		-- 1.3.6.1.4.1.5504.6
		zhoneModules OBJECT-IDENTITY
			STATUS current
			DESCRIPTION 
				"Sub-tree used for Module-Identity declarations."
			::= { zhone 6 }

		
		-- 1.3.6.1.4.1.5504.7
		zhoneShelfSlotTable OBJECT-TYPE
			SYNTAX SEQUENCE OF ZhoneShelfSlotEntry
			MAX-ACCESS not-accessible
			STATUS current
			DESCRIPTION
				"The shelf/slot table is included to provide the table
				entries zhoneShelfIndex and zhoneSlotIndex allowing
				these indexes to be imported and used globally."
			::= { zhone 7 }

		
		-- 1.3.6.1.4.1.5504.7.1
		zhoneShelfSlotEntry OBJECT-TYPE
			SYNTAX ZhoneShelfSlotEntry
			MAX-ACCESS not-accessible
			STATUS current
			DESCRIPTION
				"Entry for the shelf/slot index table."
			INDEX { zhoneShelfIndex, zhoneSlotIndex }
			::= { zhoneShelfSlotTable 1 }

		
		ZhoneShelfSlotEntry ::=
			SEQUENCE { 
				zhoneShelfIndex
					Integer32,
				zhoneSlotIndex
					Integer32
			 }

		-- 1.3.6.1.4.1.5504.7.1.1
		zhoneShelfIndex OBJECT-TYPE
			SYNTAX Integer32 (1..255)
			MAX-ACCESS read-only
			STATUS current
			DESCRIPTION
				"The global shelf index.  This index can be used by
				tables that index by shelf and slot eliminating the
				need for shelf and slot columns in the table."
			::= { zhoneShelfSlotEntry 1 }

		
		-- 1.3.6.1.4.1.5504.7.1.2
		zhoneSlotIndex OBJECT-TYPE
			SYNTAX Integer32 (1..31)
			MAX-ACCESS read-only
			STATUS current
			DESCRIPTION
				"The global slot index.  This index can be used by tables
				that index by shelf and slot eliminating the need to
				include shelf and slot columns in the table."
			::= { zhoneShelfSlotEntry 2 }

		
		-- 1.3.6.1.4.1.5504.9
		zhoneCompliances OBJECT IDENTIFIER::= { zhone 9 }

		
		-- 1.3.6.1.4.1.5504.9.1
		zhoneGroups OBJECT IDENTIFIER::= { zhoneCompliances 1 }

		
		-- 1.3.6.1.4.1.5504.9.1.1
		zhoneShelfSlotGroup OBJECT-GROUP
			OBJECTS { zhoneShelfIndex, zhoneSlotIndex }
			STATUS current
			DESCRIPTION 
				"Group which contains the standard objects for addressing shelf
				and slot values on Zhone products"
			::= { zhoneGroups 1 }

		
		-- 1.3.6.1.4.1.5504.9.2
		zhoneCompliance OBJECT IDENTIFIER::= { zhoneCompliances 2 }

		
		-- 1.3.6.1.4.1.5504.9.2.1
		zhoneShelfSlotCompliance MODULE-COMPLIANCE
			STATUS current
			DESCRIPTION 
				"The compliance statement for SNMP entities
				which manage Zhone Devices."
			MODULE -- this module
				MANDATORY-GROUPS { zhoneShelfSlotGroup }
			::= { zhoneCompliance 1 }

		
		-- 1.3.6.1.4.1.5504.10
		zhoneExperimental OBJECT-IDENTITY
			STATUS current
			DESCRIPTION 
				"Zhone Experimental Mibs."
			::= { zhone 10 }

		
		-- 1.3.6.1.4.1.5504.10.1
		ietfDrafts OBJECT-IDENTITY
			STATUS current
			DESCRIPTION 
				"IETF Draft Mibs currently under review."
			::= { zhoneExperimental 1 }

		
		-- 1.3.6.1.4.1.5504.10.1.1
		apsMIB OBJECT-IDENTITY
			STATUS current
			DESCRIPTION 
				"SONET Linear APS architectures taken from
				draft-ietf-atommib-sonetaps-mib-05.txt."
			::= { ietfDrafts 1 }

		
		-- 1.3.6.1.4.1.5504.10.1.2
		sipTC OBJECT-IDENTITY
			STATUS current
			DESCRIPTION 
				"SIP (Session Initiated Protocol) taken from
				draft-ietf-sip-mib-05.txt."
			::= { ietfDrafts 2 }

		
		-- 1.3.6.1.4.1.5504.10.1.3
		sipCommonMIB OBJECT-IDENTITY
			STATUS current
			DESCRIPTION 
				"SIP (Session Initiated Protocol) taken from
				draft-ietf-sip-mib-05.txt."
			::= { ietfDrafts 3 }

		
		-- 1.3.6.1.4.1.5504.10.1.4
		sipUAMIB OBJECT-IDENTITY
			STATUS current
			DESCRIPTION 
				"SIP (Session Initiated Protocol) taken from
				draft-ietf-sip-mib-05.txt."
			::= { ietfDrafts 4 }

		
		-- 1.3.6.1.4.1.5504.10.1.5
		pktcIetfSigMib OBJECT-IDENTITY
			STATUS current
			DESCRIPTION 
				"Endpoint signaling mib taken from
				draft-ietf-ipcdn-signaling-06.txt."
			::= { ietfDrafts 5 }

		
		-- 1.3.6.1.4.1.5504.10.1.6
		efmOamMIB OBJECT-IDENTITY
			STATUS current
			DESCRIPTION 
				"EFM Oam mib taken from 
				draft-ietf-hubmib-efm-mib-03.txt."
			::= { ietfDrafts 6 }

		
		-- 1.3.6.1.4.1.5504.10.1.7
		efmCuMIB OBJECT-IDENTITY
			STATUS current
			DESCRIPTION 
				"EFM Cu mib taken from 
				draft-ietf-hubmib-efm-mib-04.txt."
			::= { ietfDrafts 7 }

		
		-- 1.3.6.1.4.1.5504.10.1.8
		pwTcStdMIB OBJECT-IDENTITY
			STATUS current
			DESCRIPTION 
				"This MIB module defines TEXTUAL CONVENTIONs
				for concepts used in Pseudo Wire Edge-to-Edge
				networks."
			::= { ietfDrafts 8 }

		
		-- 1.3.6.1.4.1.5504.10.1.9
		ianaPwe3MIB OBJECT-IDENTITY
			STATUS current
			DESCRIPTION 
				"This MIB module defines the IANAPwTypeTC and
				IANAPwPsnTypeTC textual conventions for use in PWE3
				MIB modules."
			::= { ietfDrafts 9 }

		
		-- 1.3.6.1.4.1.5504.10.1.10
		pwStdMIB OBJECT-IDENTITY
			STATUS current
			DESCRIPTION 
				"This MIB module contains managed object definitions for
				pseudowire operation as in Bryant, S. and P. Pate, 'Pseudo
				Wire Emulation Edge-to-Edge (PWE3) Architecture' [RFC3985]."
			::= { ietfDrafts 10 }

		
		-- 1.3.6.1.4.1.5504.10.1.11
		pwTDMMIB OBJECT-IDENTITY
			STATUS current
			DESCRIPTION 
				"This MIB contains managed object definitions for
				encapsulating TDM (T1,E1, T3, E3, NxDS0) as
				pseudo-wires over packet-switching networks (PSN)."
			::= { ietfDrafts 11 }

		
		-- 1.3.6.1.4.1.5504.10.1.12
		zhoneRmonMibModule OBJECT-IDENTITY
			STATUS current
			DESCRIPTION 
				"This MIB contains objects similar to rfc2819 RMON-2.
				
				The etherStatsEntry index has been modified to be an
				ifIndex value.  There is also added support for
				various Broadcom supported stats.
				"
			::= { ietfDrafts 12 }

		
		-- 1.3.6.1.4.1.5504.10.2
		zhoneDrafts OBJECT-IDENTITY
			STATUS current
			DESCRIPTION 
				"Zhone proprietary draft MIBs."
			::= { zhoneExperimental 2 }

		
	
	END

--
-- Zhone.mib
--
