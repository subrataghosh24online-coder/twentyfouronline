ALGSMXS-v0-MIB DEFINITIONS ::= BEGIN
IMPORTS
DisplayString FROM RFC1213-MIB
OBJECT-TYPE FROM RFC-1212
enterprises FROM RFC1155-SMI;
algcom OBJECT IDENTIFIER ::= { enterprises 49136 }
SMxSOIDs OBJECT IDENTIFIER ::= { algcom 100 }
SensorNames OBJECT IDENTIFIER ::= { SMxSOIDs 1 }
SensorDescriptions OBJECT IDENTIFIER ::= { SMxSOIDs 2 }
SensorValues OBJECT IDENTIFIER ::= { SMxSOIDs 3 }
SensorUnits OBJECT IDENTIFIER ::= { SMxSOIDs 4 }
SensorThrMin OBJECT IDENTIFIER ::= { SMxSOIDs 5 }
SensorThrMax OBJECT IDENTIFIER ::= { SMxSOIDs 6 }
END
