--------------------------------------------------------------------------------  
--------------------------------------------------------------------------------  
-- The lineintegrator MIB
-- ______________
--
-- 1. Introduction
-- This document defines the enterprise specific MIB for the LineIntegrater,
-- which provides the management of the ULAF+ transmission family.
-- The MIB is divided into three basic MIBs
--    proxyAgent MIB
--    device MIB
--    links MIB
--
-- 2. The proxyAgent MIB
-- _____________________
--
-- The proxyAgent MIB consists of a table with information about the 
-- supervised serial ports and the connected devices. Either a rack or a
-- Desktop device can be connected. This part of the mib is identical for
-- Ulaf-2 and Ulaf+ devices
--
--
-- 3. The device MIB
-- _________________
--
-- The device MIB is a table, where each entry refers to a line card slot.
-- It contains the name of the inserted cards and a alarm attribute, which
-- is used to send SNMP traps to the manager, if a link goes down.
--
-- 5. The links MIB
-- _____________________
--
-- The links MIB consists of several tables, which contain detailed
-- management information about the line cards.
-- The links MIB is divided into Xxxx parts
--
--------------------------------------------------------------------------------  
          ULAFPLUS-MIB DEFINITIONS ::= BEGIN

          IMPORTS
	          enterprises, NetworkAddress, IpAddress, Counter, Gauge,
		  TimeTicks
                          FROM RFC1155-SMI
		  DisplayString
                          FROM RFC1213-MIB
                  OBJECT-TYPE
                          FROM RFC-1212;
			  
	  siemensCH		OBJECT IDENTIFIER ::= { enterprises 1887 }

	  lineintegrator	OBJECT IDENTIFIER ::= { siemensCH 1 }
                    
          ulaf2			OBJECT IDENTIFIER ::= { lineintegrator 1 }

          links			OBJECT IDENTIFIER ::= { ulaf2 4 }

	
	  linksVers3		OBJECT IDENTIFIER ::= { links 3 }


--==============================================================================
--==============================================================================
--
--      CM-RO
--
--==============================================================================
--==============================================================================
	cmro	OBJECT IDENTIFIER ::= { linksVers3 1 }

--------------------------------------------------------------------------------
--	CM-RO	HTU-local
--------------------------------------------------------------------------------
cmroHtuLocalTable OBJECT-TYPE
	SYNTAX SEQUENCE OF CmroHtuLocalEntry
	ACCESS not-accessible
	STATUS mandatory
	DESCRIPTION ""
	::= { cmro 1 }

cmroHtuLocalEntry OBJECT-TYPE
	SYNTAX CmroHtuLocalEntry
	ACCESS not-accessible
	STATUS mandatory
	DESCRIPTION ""
	INDEX { cmroHtuLocalPortIndex, cmroHtuLocalLinkIndex }
	::= { cmroHtuLocalTable 1 }

CmroHtuLocalEntry ::=
	SEQUENCE
	{
		cmroHtuLocalPortIndex INTEGER,
		cmroHtuLocalLinkIndex INTEGER,
		cmroHtuLocalHwFabData DisplayString,
		cmroHtuLocalActFwType DisplayString,
		cmroHtuLocalActFwVers DisplayString,
		cmroHtuLocalPasBankState INTEGER,
		cmroHtuLocalPasFwType DisplayString,
		cmroHtuLocalPasFwVers DisplayString,
		cmroHtuLocalSeepromVers DisplayString,
		cmroHtuLocalDFabData DisplayString,
		cmroHtuLocalDType INTEGER,
		cmroHtuLocalTFabData DisplayString,
		cmroHtuLocalTType INTEGER,
		cmroHtuLocalRpsFabData DisplayString,
		cmroHtuLocalRpsType INTEGER,
		cmroHtuLocalClkFabData DisplayString,
		cmroHtuLocalClkType INTEGER,
		cmroHtuLocalDbgFabData DisplayString,
		cmroHtuLocalDbgType INTEGER,
		cmroHtuLocalHousing INTEGER,
		cmroHtuLocalRackVersion INTEGER,
		cmroHtuLocalLtNtType INTEGER,
		cmroHtuLocalHdslChipset INTEGER,
		cmroHtuLocalDipCfg INTEGER,
		cmroHtuLocalEocCfg INTEGER,
		cmroHtuLocalRpsVoltage INTEGER,
		cmroHtuLocalPowerConfiguration INTEGER,
		cmroHtuLocalIsdnFabData DisplayString,
		cmroHtuLocalIsdnType INTEGER,
		cmroHtuLocalTipRingReversal1 INTEGER,
		cmroHtuLocalTipRingReversal2 INTEGER,
		cmroHtuLocalTipRingReversal3 INTEGER,
		cmroHtuLocalTipRingReversal4 INTEGER,
		cmroHtuLocalPacketFabData DisplayString,
		cmroHtuLocalPacketType INTEGER,
		cmroHtuLocalPacketMacAddr1 OCTET STRING,
		cmroHtuLocalMcsCh1aIsRemCh INTEGER,
		cmroHtuLocalMcsCh2bIsRemCh INTEGER,
		cmroHtuLocalMcsCh3cIsRemCh INTEGER,
		cmroHtuLocalMcsCh4dIsRemCh INTEGER,
		cmroHtuLocalMcsFarCh1aIsRemCh INTEGER,
		cmroHtuLocalMcsFarCh2bIsRemCh INTEGER,
		cmroHtuLocalMcsFarCh3cIsRemCh INTEGER,
		cmroHtuLocalMcsFarCh4dIsRemCh INTEGER,
		cmroHtuLocalDslChipset DisplayString,
		cmroHtuLocalDslFwLoad DisplayString,
		cmroHtuLocalFpgaLoad DisplayString,
		cmroHtuLocalEthWanChip DisplayString,
		cmroHtuLocalSwitchChip DisplayString,
		cmroHtuLocalBootloaderVers DisplayString,
		cmroHtuLocalSerialNumber DisplayString,
		cmroHtuLocalHwManufacturingDate DisplayString,
		cmroHtuLocalRpsManufacturingDate DisplayString,
		cmroHtuLocalClkManufacturingDate DisplayString,
		cmroHtuLocalTManufacturingDate DisplayString,
		cmroHtuLocalDManufacturingDate DisplayString,
		cmroHtuLocalPacketManufacturingDate DisplayString,
		cmroHtuLocalL2SDriverVersion DisplayString
	}

cmroHtuLocalPortIndex OBJECT-TYPE
	SYNTAX INTEGER
	ACCESS read-only
	STATUS mandatory
	DESCRIPTION
		"This variable addresses the port number of the proxy
		and is used as index for the other elements in the Table"
	::= { cmroHtuLocalEntry 1 }

cmroHtuLocalLinkIndex OBJECT-TYPE
	SYNTAX INTEGER
	ACCESS read-only
	STATUS mandatory
	DESCRIPTION
		"This variable addresses the slot number of the OMI sub-rack
		and is used as index for the other elements in the Table"
	::= { cmroHtuLocalEntry 2 }

cmroHtuLocalHwFabData OBJECT-TYPE
	SYNTAX DisplayString(SIZE(20))
	ACCESS read-only
	STATUS mandatory
	DESCRIPTION
		"Device Hardware Fabrication Data"
	::= { cmroHtuLocalEntry 3 }

cmroHtuLocalActFwType OBJECT-TYPE
	SYNTAX DisplayString
	ACCESS read-only
	STATUS mandatory
	DESCRIPTION
		"Type of active Firmware"
	::= { cmroHtuLocalEntry 4 }

cmroHtuLocalActFwVers OBJECT-TYPE
	SYNTAX DisplayString
	ACCESS read-only
	STATUS mandatory
	DESCRIPTION
		"Version of active Firmware"
	::= { cmroHtuLocalEntry 5 }

cmroHtuLocalPasBankState OBJECT-TYPE
	SYNTAX INTEGER
	{
		empty(1),
		loaded(2),
		foreign(3),
		unknown(254),
		unsupported(255)
	}
	ACCESS read-only
	STATUS mandatory
	DESCRIPTION
		"State of passive firmware bank
		1	Empty	contains no firmware
		2	Loaded	contains a valid firmware
		3	Foreign	contains regenerator firmware
		254		unknown value
		255		unsupported variable for addressed device"
	::= { cmroHtuLocalEntry 6 }

cmroHtuLocalPasFwType OBJECT-TYPE
	SYNTAX DisplayString
	ACCESS read-only
	STATUS mandatory
	DESCRIPTION
		"Type of passive firmware"
	::= { cmroHtuLocalEntry 7 }

cmroHtuLocalPasFwVers OBJECT-TYPE
	SYNTAX DisplayString
	ACCESS read-only
	STATUS mandatory
	DESCRIPTION
		"Version of passive firmware"
	::= { cmroHtuLocalEntry 8 }

cmroHtuLocalSeepromVers OBJECT-TYPE
	SYNTAX DisplayString
	ACCESS read-only
	STATUS mandatory
	DESCRIPTION
		"Version of SEEPROM data format"
	::= { cmroHtuLocalEntry 9 }

cmroHtuLocalDFabData OBJECT-TYPE
	SYNTAX DisplayString(SIZE(20))
	ACCESS read-only
	STATUS mandatory
	DESCRIPTION
		"Fabrication Data of Data-Module"
	::= { cmroHtuLocalEntry 10 }

cmroHtuLocalDType OBJECT-TYPE
	SYNTAX INTEGER
	{
		none(1),
		dce(2),
		dte(3),
		tenBaseT(4),
		abar(5),
		unknown(254),
		unsupported(255)
	}
	ACCESS read-only
	STATUS mandatory
	DESCRIPTION
		"Type of Data-Module in corresponding module-slot of the device.
		1	None		No module inserted
		2	DCE		Data module with DCE configuration
		3	DTE		Data module with DTE configuration
		4	10Base-T	10Base-T Ethernet module
		5	ABAR		Advanced Bridge and Router module
		254			unknown value
		255			unsupported variable for addressed device
		
		For details of the module (connector sub-types, ...) the 
		fabrication data has to evaluated"
	::= { cmroHtuLocalEntry 11 }

cmroHtuLocalTFabData OBJECT-TYPE
	SYNTAX DisplayString(SIZE(20))
	ACCESS read-only
	STATUS mandatory
	DESCRIPTION
		"Fabrication Data of 2Mbit-Module"
	::= { cmroHtuLocalEntry 12 }

cmroHtuLocalTType OBJECT-TYPE
	SYNTAX INTEGER
	{
		none(1),
		twoMbps(2),
		quadTwoMbps(3),
		codirTwoMbps(4),
		twoMbpsVarImps(5),
		quadTwoMbpsVarImp(6),
		fourTwoMbpsVarImp(7),
		unknown(254),
		unsupported(255)
	}
	ACCESS read-only
	STATUS mandatory
	DESCRIPTION
		"Type of 2Mbit-Module in corresponding module-slot of the device.
		1	None		No module present
		2	TwoMbps		A 2Mbit/s module is present
		3	QuadTwoMbps	A Quad 2Mbit/s module is present
		4	CodirTwoMbps	A Co-Directional G.703 module is present
		5	TwoMbpsVarImp	A 2Mbit/s module with variable impedance is present
		6	QuadTwoMbpsVarImp	A Quad 2Mbit/s module with variable impedance is present
		7	FourTwoMbpsVarImp	Module with four independent 2Mbit/s (variable impedance) is present
		254			unknown value
		255			unsupported variable for addressed device
		
		For details of the module (connector sub-types, ...) the 
		fabrication data has to evaluated"
	::= { cmroHtuLocalEntry 13 }

cmroHtuLocalRpsFabData OBJECT-TYPE
	SYNTAX DisplayString(SIZE(20))
	ACCESS read-only
	STATUS mandatory
	DESCRIPTION
		"Fabrication Data of Remote Power Supply (RPS) Module"
	::= { cmroHtuLocalEntry 14 }

cmroHtuLocalRpsType OBJECT-TYPE
	SYNTAX INTEGER
	{
		none(1),
		rps(2),
		unknown(254),
		unsupported(255)
	}
	ACCESS read-only
	STATUS mandatory
	DESCRIPTION
		"Type of Remote Power Supply (RPS) Module in corresponding
		 module-slot of the device.
		1	None	No module inserted
		2	Rps	A RPS module is inserted
		254		unknown value
		255		unsupported variable for addressed device
		
		For details of the module (connector sub-types, ...) the 
		fabrication data has to evaluated"
	::= { cmroHtuLocalEntry 15 }

cmroHtuLocalClkFabData OBJECT-TYPE
	SYNTAX DisplayString(SIZE(20))
	ACCESS read-only
	STATUS mandatory
	DESCRIPTION
		"Fabrication Data of Clock and Alarm Module"
	::= { cmroHtuLocalEntry 16 }

cmroHtuLocalClkType OBJECT-TYPE
	SYNTAX INTEGER
	{
		none(1),
		clockAlarm(2),
		clock(3),
		alarm(4),
		unknown(254),
		unsupported(255)
	}
	ACCESS read-only
	STATUS mandatory
	DESCRIPTION
		"Type of Clock and Alarm Module in corresponding
		 module-slot of the device.
		1	None		No module inserted
		2	ClockAlarm	A combined Clock and Alarm module is inserted
		3	Clock		A Clock module is inserted
		3	Alarm		An Alarm module is inserted
		254			unknown value
		255			unsupported variable for addressed device
		
		For details of the module (connector sub-types, ...) the 
		fabrication data has to evaluated"
	::= { cmroHtuLocalEntry 17 }

cmroHtuLocalDbgFabData OBJECT-TYPE
	SYNTAX DisplayString(SIZE(20))
	ACCESS read-only
	STATUS mandatory
	DESCRIPTION
		"Fabrication Data of Debug-Module"
	::= { cmroHtuLocalEntry 18 }

cmroHtuLocalDbgType OBJECT-TYPE
	SYNTAX INTEGER
	{
		none(1),
		debug(2),
		unknown(254),
		unsupported(255)
	}
	ACCESS read-only
	STATUS mandatory
	DESCRIPTION
		"Type of Debug-Module in corresponding module-slot of the device.
		1	None	No module inserted
		2	Debug	A Debug module is inserted
		254		unknown value
		255		unsupported variable for addressed device
		
		For details of the module (connector sub-types, ...) the 
		fabrication data has to evaluated"
	::= { cmroHtuLocalEntry 19 }

cmroHtuLocalHousing OBJECT-TYPE
	SYNTAX INTEGER
	{
		rack(1),
		desktop(2),
		unknown(254),
		unsupported(255)
	}
	ACCESS read-only
	STATUS mandatory
	DESCRIPTION
		"Type of housing / installation of the device.
		1	Rack	The device is a line card to be installed in a sub-rack
		2	Desktop	The device is a desktop device
		254		unknown value
		255		unsupported variable for addressed device"
	::= { cmroHtuLocalEntry 20 }

cmroHtuLocalRackVersion OBJECT-TYPE
	SYNTAX INTEGER
	{
		rackV1(1),
		rackV2(2),
		rackV3(3),
		desktop(4),
		unknown(254),
		unsupported(255)
	}
	ACCESS read-only
	STATUS mandatory
	DESCRIPTION
		"Version of the sub-rack in which the device is installed.
		1	RackV1	The device is installed in a rack with V1
		2	RackV2	The device is installed in a rack with V2
		3	RackV3	The device is installed in a rack with V3
		4	Desktop	The device is a desktop device (and therefore not installed in a sub-rack)
		254		unknown value
		255		unsupported variable for addressed device"
	::= { cmroHtuLocalEntry 21 }

cmroHtuLocalLtNtType OBJECT-TYPE
	SYNTAX INTEGER
	{
		lt(1),
		nt(2),
		unknown(254),
		unsupported(255)
	}
	ACCESS read-only
	STATUS mandatory
	DESCRIPTION
		"Indicates whether the device is configured as LT or NT.
		1	LT	The device is configured as LT
		2	NT	The device is configured as NT
		254		unknown value
		255		unsupported variable for addressed device"
	::= { cmroHtuLocalEntry 22 }

cmroHtuLocalHdslChipset OBJECT-TYPE
	SYNTAX INTEGER
	{
		level1(1),
		metalink(2),
		infineon(3),
		unknown(254),
		unsupported(255)
	}
	ACCESS read-only
	STATUS mandatory
	DESCRIPTION
		"Indicates which chipset the partner device uses for HDSL transmission
		1	Level1		The partner device uses a Level 1 chipset
		2	Metalink	The partner device uses a MetaLink chipset
		3	Infineon	The partner device uses an Infineon chipset
		254			unknown value
		255			unsupported variable for addressed device"
	::= { cmroHtuLocalEntry 23 }

cmroHtuLocalDipCfg OBJECT-TYPE
	SYNTAX INTEGER
	{
		disabled(1),
		enabled(2),
		unknown(254),
		unsupported(255)
	}
	ACCESS read-only
	STATUS mandatory
	DESCRIPTION
		"Indicates whether the device is configured through DIP Switches.
		1	Disabled	The device can be configured through management software
		2	Enabled		The device is configured by DIP switches
		254			unknown value
		255			unsupported variable for addressed device"
	::= { cmroHtuLocalEntry 24 }

cmroHtuLocalEocCfg OBJECT-TYPE
	SYNTAX INTEGER
	{
		disabled(1),
		enabled(2),
		reg1(3),
		reg2(4),
		reg3(5),
		reg4(6),
		reg5(7),
		reg6(8),
		reg7(9),
		reg8(10),
		unknown(254),
		unsupported(255)
	}
	ACCESS read-only
	STATUS mandatory
	DESCRIPTION
		"Indicates how far the EOC has been built up.
		1	Disabled	The device can be configured locally
		2	Enabled		The device is being configured over the EOC
		3	Reg1		The EOC is up until the first regenerator section
		4	Reg2		The EOC is up until the second regenerator section
		5	Reg3		The EOC is up until the third regenerator section
		6	Reg4		The EOC is up until the fourth regenerator section
		7	Reg5		The EOC is up until the fifth regenerator section
		8	Reg6		The EOC is up until the sixth regenerator section
		9	Reg7		The EOC is up until the seventh regenerator section
		10	Reg8		The EOC is up until the eighth regenerator section
		254			unknown value
		255			unsupported variable for addressed device"
	::= { cmroHtuLocalEntry 25 }

cmroHtuLocalRpsVoltage OBJECT-TYPE
	SYNTAX INTEGER
	{
		v120(1),
		v180(2),
		unknown(254),
		unsupported(255)
	}
	ACCESS read-only
	STATUS mandatory
	DESCRIPTION
		"Indicates which Remote Power Supply (RPS) Voltage is being used by the device
		1	V120	The RPS uses 120 Volts
		2	V180	The RPS uses 180 Volts
		254		unknown value
		255		unsupported variable for addressed device"
	::= { cmroHtuLocalEntry 26 }

cmroHtuLocalPowerConfiguration OBJECT-TYPE
	SYNTAX INTEGER
	{
		multifunctional(1),
		redundant(2),
		remoteFeeding(3),
		batteryDC(4),
		unknown(254),
		unsupported(255)
	}
	ACCESS read-only
	STATUS mandatory
	DESCRIPTION
		"Indicates which kind of power supply is equiped
		1	multifunctional	No redundant supply possible
		2	redundant	Redundant supply possible
		3	remoteFeeding	Remote feeding possible
		4	batteryDC	DC-only supply
		254			unknown value
		255			unsupported variable for addressed device"
	::= { cmroHtuLocalEntry 27 }


cmroHtuLocalIsdnFabData OBJECT-TYPE
	SYNTAX DisplayString(SIZE(20))
	ACCESS read-only
	STATUS mandatory
	DESCRIPTION
		"Fabrication Data of ISDN-Module"
	::= { cmroHtuLocalEntry 28 }


cmroHtuLocalIsdnType OBJECT-TYPE
	SYNTAX INTEGER
	{
		none(1),
		te(2),
		nt(3),
		uk0(4),
		unknown(254),
		unsupported(255)
	}
	ACCESS read-only
	STATUS mandatory
	DESCRIPTION
		"Type of ISDN-Module in corresponding module-slot of the device
		1	None	No module inserted
		2	TE	A module for S0(TE mode) operation is inserted
		3	NT	A module for S0(NT mode) operation is inserted
		4	Uk0	A module for Uk0 operation is inserted
		254		unknown value
		255		unsupported variable for addressed device"
	::= { cmroHtuLocalEntry 29 }


cmroHtuLocalTipRingReversal1 OBJECT-TYPE
	SYNTAX INTEGER
	{
		no(1),
		yes(2),
		unknown(254),
		unsupported(255)
	}
	ACCESS read-only
	STATUS mandatory
	DESCRIPTION
		"Indicates whether tip-ring reversal has been detected and compensated
		 for on the first wire pair
		 1	No	Reversal not detected
		 2	Yes	Reversal detected and compensated for
		 254		unknown value
		 255		unsupported variable for addressed device"
	::= { cmroHtuLocalEntry 30 }

cmroHtuLocalTipRingReversal2 OBJECT-TYPE
	SYNTAX INTEGER
	{
		no(1),
		yes(2),
		unknown(254),
		unsupported(255)
	}
	ACCESS read-only
	STATUS mandatory
	DESCRIPTION
		"Indicates whether tip-ring reversal has been detected and compensated
		 for on the second wire pair
		 1	No	Reversal not detected
		 2	Yes	Reversal detected and compensated for
		 254		unknown value
		 255		unsupported variable for addressed device"
	::= { cmroHtuLocalEntry 31 }

cmroHtuLocalTipRingReversal3 OBJECT-TYPE
	SYNTAX INTEGER
	{
		no(1),
		yes(2),
		unknown(254),
		unsupported(255)
	}
	ACCESS read-only
	STATUS mandatory
	DESCRIPTION
		"Indicates whether tip-ring reversal has been detected and compensated
		 for on the third wire pair
		 1	No	Reversal not detected
		 2	Yes	Reversal detected and compensated for
		 254		unknown value
		 255		unsupported variable for addressed device"
	::= { cmroHtuLocalEntry 32 }

cmroHtuLocalTipRingReversal4 OBJECT-TYPE
	SYNTAX INTEGER
	{
		no(1),
		yes(2),
		unknown(254),
		unsupported(255)
	}
	ACCESS read-only
	STATUS mandatory
	DESCRIPTION
		"Indicates whether tip-ring reversal has been detected and compensated
		 for on the fourth wire pair
		 1	No	Reversal not detected
		 2	Yes	Reversal detected and compensated for
		 254		unknown value
		 255		unsupported variable for addressed device"
	::= { cmroHtuLocalEntry 33 }

cmroHtuLocalPacketFabData OBJECT-TYPE
	SYNTAX DisplayString(SIZE(20))
	ACCESS read-only
	STATUS mandatory
	DESCRIPTION
		"Fabrication Data of L2 Switch"
	::= { cmroHtuLocalEntry 34 }

cmroHtuLocalPacketType OBJECT-TYPE
	SYNTAX INTEGER
	{
		none(1),
		fourPort10-100(2),
		onePort10-100(3),
		twoPort10-100(4),
		threePort10-100(5),
		unknown(254),
		unsupported(255)
	}
	ACCESS read-only
	STATUS mandatory
	DESCRIPTION
		"Type of L2 Switch module.
		1	None		No module inserted
		2	4P10/100	4-Port 10/100Base-T ethernet switch
		3	1P10/100	1-Port 10/100Base-T ethernet switch
		4	2P10/100	2-Port 10/100Base-T ethernet switch
		5	3P10/100	3-Port 10/100Base-T ethernet switch
		254			unknown value
		255			unsupported variable for addressed device
		
		For details of the module (connector sub-types, ...) the 
		fabrication data has to evaluated"
	::= { cmroHtuLocalEntry 35 }

cmroHtuLocalPacketMacAddr1 OBJECT-TYPE
	SYNTAX OCTET STRING(SIZE(6))
	ACCESS read-only
	STATUS mandatory
	DESCRIPTION
		"MAC address of L2 ethernet switch.
		Value of Byte 0..5	Meaning
		
		0x00 - 0xFD		MAC address
		all 0xFE		unknown value
		all 0xFF		unsupported variable"
	::= { cmroHtuLocalEntry 36 }

cmroHtuLocalMcsCh1aIsRemCh OBJECT-TYPE
	SYNTAX INTEGER
	{
		first(1),
		second(2),
		third(3),
		fourth(4),
		unknown(254),
		unsupported(255)
	}
	ACCESS read-only
	STATUS mandatory
	DESCRIPTION
		"Indicates MCS channel crossover. This variable shows which
		MCS channel the local channel a is conntected to on the far
		end MCS device.
		1	U1/VA	first interface (SHDSL U1 or G.704 VA)
		2	U2/VB	second interface (SHDSL U2 or G.704 VB)
		3	U3/VC	third interface (SHDSL U3 or G.704 VC)
		4	U4/VD	fourth interface (SHDSL U4 or G.704 VD)
		254		unknown value
		255		unsupported variable for addressed device"
	::= { cmroHtuLocalEntry 37 }

cmroHtuLocalMcsCh2bIsRemCh OBJECT-TYPE
	SYNTAX INTEGER
	{
		first(1),
		second(2),
		third(3),
		fourth(4),
		unknown(254),
		unsupported(255)
	}
	ACCESS read-only
	STATUS mandatory
	DESCRIPTION
		"Indicates MCS channel crossover. This variable shows which
		MCS channel the local channel b is conntected to on the far
		end MCS device.
		1	U1/VA	first interface (SHDSL U1 or G.704 VA)
		2	U2/VB	second interface (SHDSL U2 or G.704 VB)
		3	U3/VC	third interface (SHDSL U3 or G.704 VC)
		4	U4/VD	fourth interface (SHDSL U4 or G.704 VD)
		254		unknown value
		255		unsupported variable for addressed device"
	::= { cmroHtuLocalEntry 38 }

cmroHtuLocalMcsCh3cIsRemCh OBJECT-TYPE
	SYNTAX INTEGER
	{
		first(1),
		second(2),
		third(3),
		fourth(4),
		unknown(254),
		unsupported(255)
	}
	ACCESS read-only
	STATUS mandatory
	DESCRIPTION
		"Indicates MCS channel crossover. This variable shows which
		MCS channel the local channel c is conntected to on the far
		end MCS device.
		1	U1/VA	first interface (SHDSL U1 or G.704 VA)
		2	U2/VB	second interface (SHDSL U2 or G.704 VB)
		3	U3/VC	third interface (SHDSL U3 or G.704 VC)
		4	U4/VD	fourth interface (SHDSL U4 or G.704 VD)
		254		unknown value
		255		unsupported variable for addressed device"
	::= { cmroHtuLocalEntry 39 }

cmroHtuLocalMcsCh4dIsRemCh OBJECT-TYPE
	SYNTAX INTEGER
	{
		first(1),
		second(2),
		third(3),
		fourth(4),
		unknown(254),
		unsupported(255)
	}
	ACCESS read-only
	STATUS mandatory
	DESCRIPTION
		"Indicates MCS channel crossover. This variable shows which
		MCS channel the local channel d is conntected to on the far
		end MCS device.
		1	U1/VA	first interface (SHDSL U1 or G.704 VA)
		2	U2/VB	second interface (SHDSL U2 or G.704 VB)
		3	U3/VC	third interface (SHDSL U3 or G.704 VC)
		4	U4/VD	fourth interface (SHDSL U4 or G.704 VD)
		254		unknown value
		255		unsupported variable for addressed device"
	::= { cmroHtuLocalEntry 40 }

cmroHtuLocalMcsFarCh1aIsRemCh OBJECT-TYPE
	SYNTAX INTEGER
	{
		first(1),
		second(2),
		third(3),
		fourth(4),
		unknown(254),
		unsupported(255)
	}
	ACCESS read-only
	STATUS mandatory
	DESCRIPTION
		"Indicates MCS channel crossover. This variable shows which
		MCS channel the remote channel a is conntected to on the local
		end MCS device.
		1	U1/VA	first interface (SHDSL U1 or G.704 VA)
		2	U2/VB	second interface (SHDSL U2 or G.704 VB)
		3	U3/VC	third interface (SHDSL U3 or G.704 VC)
		4	U4/VD	fourth interface (SHDSL U4 or G.704 VD)
		254		unknown value
		255		unsupported variable for addressed device"
	::= { cmroHtuLocalEntry 41 }

cmroHtuLocalMcsFarCh2bIsRemCh OBJECT-TYPE
	SYNTAX INTEGER
	{
		first(1),
		second(2),
		third(3),
		fourth(4),
		unknown(254),
		unsupported(255)
	}
	ACCESS read-only
	STATUS mandatory
	DESCRIPTION
		"Indicates MCS channel crossover. This variable shows which
		MCS channel the remote channel b is conntected to on the local
		end MCS device.
		1	U1/VA	first interface (SHDSL U1 or G.704 VA)
		2	U2/VB	second interface (SHDSL U2 or G.704 VB)
		3	U3/VC	third interface (SHDSL U3 or G.704 VC)
		4	U4/VD	fourth interface (SHDSL U4 or G.704 VD)
		254		unknown value
		255		unsupported variable for addressed device"
	::= { cmroHtuLocalEntry 42 }

cmroHtuLocalMcsFarCh3cIsRemCh OBJECT-TYPE
	SYNTAX INTEGER
	{
		first(1),
		second(2),
		third(3),
		fourth(4),
		unknown(254),
		unsupported(255)
	}
	ACCESS read-only
	STATUS mandatory
	DESCRIPTION
		"Indicates MCS channel crossover. This variable shows which
		MCS channel the remote channel c is conntected to on the local
		end MCS device.
		1	U1/VA	first interface (SHDSL U1 or G.704 VA)
		2	U2/VB	second interface (SHDSL U2 or G.704 VB)
		3	U3/VC	third interface (SHDSL U3 or G.704 VC)
		4	U4/VD	fourth interface (SHDSL U4 or G.704 VD)
		254		unknown value
		255		unsupported variable for addressed device"
	::= { cmroHtuLocalEntry 43 }

cmroHtuLocalMcsFarCh4dIsRemCh OBJECT-TYPE
	SYNTAX INTEGER
	{
		first(1),
		second(2),
		third(3),
		fourth(4),
		unknown(254),
		unsupported(255)
	}
	ACCESS read-only
	STATUS mandatory
	DESCRIPTION
		"Indicates MCS channel crossover. This variable shows which
		MCS channel the remote channel d is conntected to on the local
		end MCS device.
		1	U1/VA	first interface (SHDSL U1 or G.704 VA)
		2	U2/VB	second interface (SHDSL U2 or G.704 VB)
		3	U3/VC	third interface (SHDSL U3 or G.704 VC)
		4	U4/VD	fourth interface (SHDSL U4 or G.704 VD)
		254		unknown value
		255		unsupported variable for addressed device"
	::= { cmroHtuLocalEntry 44 }

cmroHtuLocalDslChipset OBJECT-TYPE
	SYNTAX DisplayString(SIZE(20))
	ACCESS read-only
	STATUS mandatory
	DESCRIPTION
		"Type of xDSL chipset"
	::= { cmroHtuLocalEntry 45 }

cmroHtuLocalDslFwLoad OBJECT-TYPE
	SYNTAX DisplayString(SIZE(20))
	ACCESS read-only
	STATUS mandatory
	DESCRIPTION
		"Type of firmware load of xDSL chipset"
	::= { cmroHtuLocalEntry 46 }

cmroHtuLocalFpgaLoad OBJECT-TYPE
	SYNTAX DisplayString(SIZE(20))
	ACCESS read-only
	STATUS mandatory
	DESCRIPTION
		"Type of FPGA load"
	::= { cmroHtuLocalEntry 47 }

cmroHtuLocalEthWanChip OBJECT-TYPE
	SYNTAX DisplayString(SIZE(20))
	ACCESS read-only
	STATUS mandatory
	DESCRIPTION
		"Type of WAN chip which connects L2 switch and xDSL link"
	::= { cmroHtuLocalEntry 48 }

cmroHtuLocalSwitchChip OBJECT-TYPE
	SYNTAX DisplayString(SIZE(20))
	ACCESS read-only
	STATUS mandatory
	DESCRIPTION
		"Type of Switch Chip"
	::= { cmroHtuLocalEntry 49 }

cmroHtuLocalBootloaderVers OBJECT-TYPE
	SYNTAX DisplayString(SIZE(20))
	ACCESS read-only
	STATUS mandatory
	DESCRIPTION
		"Version of firmware boot loader"
	::= { cmroHtuLocalEntry 50 }

cmroHtuLocalSerialNumber OBJECT-TYPE
	SYNTAX DisplayString(SIZE(20))
	ACCESS read-only
	STATUS mandatory
	DESCRIPTION
		"Serial number of device"
	::= { cmroHtuLocalEntry 51 }

cmroHtuLocalHwManufacturingDate OBJECT-TYPE
	SYNTAX DisplayString
	ACCESS read-only
	STATUS mandatory
	DESCRIPTION
		"Manufacturing Date of the motherboard"
	::= { cmroHtuLocalEntry 52 }

cmroHtuLocalRpsManufacturingDate OBJECT-TYPE
	SYNTAX DisplayString
	ACCESS read-only
	STATUS mandatory
	DESCRIPTION
		"Manufacturing Date of the RPS Module"
	::= { cmroHtuLocalEntry 53 }

cmroHtuLocalClkManufacturingDate OBJECT-TYPE
	SYNTAX DisplayString
	ACCESS read-only
	STATUS mandatory
	DESCRIPTION
		"Manufacturing Date of the Clock and Alarm Module"
	::= { cmroHtuLocalEntry 54 }

cmroHtuLocalTManufacturingDate OBJECT-TYPE
	SYNTAX DisplayString
	ACCESS read-only
	STATUS mandatory
	DESCRIPTION
		"Manufacturing Date of the 2Mbps Module"
	::= { cmroHtuLocalEntry 55 }

cmroHtuLocalDManufacturingDate OBJECT-TYPE
	SYNTAX DisplayString
	ACCESS read-only
	STATUS mandatory
	DESCRIPTION
		"Manufacturing Date of the Data Module"
	::= { cmroHtuLocalEntry 56 }

cmroHtuLocalPacketManufacturingDate OBJECT-TYPE
	SYNTAX DisplayString
	ACCESS read-only
	STATUS mandatory
	DESCRIPTION
		"Manufacturing Date of the Packet Module"
	::= { cmroHtuLocalEntry 57 }

cmroHtuLocalL2SDriverVersion OBJECT-TYPE
	SYNTAX DisplayString
	ACCESS read-only
	STATUS mandatory
	DESCRIPTION
		"L2 Switch Driver Version"
	::= { cmroHtuLocalEntry 58 }

--------------------------------------------------------------------------------
--	CM-RO	HTU-far
--------------------------------------------------------------------------------
cmroHtuFarTable OBJECT-TYPE
	SYNTAX SEQUENCE OF CmroHtuFarEntry
	ACCESS not-accessible
	STATUS mandatory
	DESCRIPTION ""
	::= { cmro 2 }

cmroHtuFarEntry OBJECT-TYPE
	SYNTAX CmroHtuFarEntry
	ACCESS not-accessible
	STATUS mandatory
	DESCRIPTION ""
	INDEX { cmroHtuFarPortIndex, cmroHtuFarLinkIndex }
	::= { cmroHtuFarTable 1 }

CmroHtuFarEntry ::=
	SEQUENCE
	{
		cmroHtuFarPortIndex INTEGER,
		cmroHtuFarLinkIndex INTEGER,
		cmroHtuFarHwFabData DisplayString,
		cmroHtuFarActFwType DisplayString,
		cmroHtuFarActFwVers DisplayString,
		cmroHtuFarPasBankState INTEGER,
		cmroHtuFarPasFwType DisplayString,
		cmroHtuFarPasFwVers DisplayString,
		cmroHtuFarSeepromVers DisplayString,
		cmroHtuFarDFabData DisplayString,
		cmroHtuFarDType INTEGER,
		cmroHtuFarTFabData DisplayString,
		cmroHtuFarTType INTEGER,
		cmroHtuFarRpsFabData DisplayString,
		cmroHtuFarRpsType INTEGER,
		cmroHtuFarClkFabData DisplayString,
		cmroHtuFarClkType INTEGER,
		cmroHtuFarDbgFabData DisplayString,
		cmroHtuFarDbgType INTEGER,
		cmroHtuFarHousing INTEGER,
		cmroHtuFarRackVersion INTEGER,
		cmroHtuFarLtNtType INTEGER,
		cmroHtuFarHdslChipset INTEGER,
		cmroHtuFarDipCfg INTEGER,
		cmroHtuFarEocCfg INTEGER,
		cmroHtuFarRpsVoltage INTEGER,
		cmroHtuFarPowerConfiguration INTEGER,
		cmroHtuFarIsdnFabData DisplayString,
		cmroHtuFarIsdnType INTEGER,
		cmroHtuFarTipRingReversal1 INTEGER,
		cmroHtuFarTipRingReversal2 INTEGER,
		cmroHtuFarTipRingReversal3 INTEGER,
		cmroHtuFarTipRingReversal4 INTEGER,
		cmroHtuFarPacketFabData DisplayString,
		cmroHtuFarPacketType INTEGER,
		cmroHtuFarPacketMacAddr1 OCTET STRING,
		cmroHtuFarDslChipset DisplayString,
		cmroHtuFarDslFwLoad DisplayString,
		cmroHtuFarFpgaLoad DisplayString,
		cmroHtuFarEthWanChip DisplayString,
		cmroHtuFarSwitchChip DisplayString,
		cmroHtuFarBootloaderVers DisplayString,
		cmroHtuFarSerialNumber DisplayString,
		cmroHtuFarHwManufacturingDate DisplayString,
		cmroHtuFarRpsManufacturingDate DisplayString,
		cmroHtuFarClkManufacturingDate DisplayString,
		cmroHtuFarTManufacturingDate DisplayString,
		cmroHtuFarDManufacturingDate DisplayString,
		cmroHtuFarPacketManufacturingDate DisplayString,
		cmroHtuFarL2SDriverVersion DisplayString
	}

cmroHtuFarPortIndex OBJECT-TYPE
	SYNTAX INTEGER
	ACCESS read-only
	STATUS mandatory
	DESCRIPTION
		"This variable addresses the port number of the proxy
		and is used as index for the other elements in the Table"
	::= { cmroHtuFarEntry 1 }

cmroHtuFarLinkIndex OBJECT-TYPE
	SYNTAX INTEGER
	ACCESS read-only
	STATUS mandatory
	DESCRIPTION
		"This variable addresses the slot number of the OMI sub-rack
		and is used as index for the other elements in the Table"
	::= { cmroHtuFarEntry 2 }

cmroHtuFarHwFabData OBJECT-TYPE
	SYNTAX DisplayString(SIZE(20))
	ACCESS read-only
	STATUS mandatory
	DESCRIPTION
		"Device Hardware Fabrication Data"
	::= { cmroHtuFarEntry 3 }

cmroHtuFarActFwType OBJECT-TYPE
	SYNTAX DisplayString
	ACCESS read-only
	STATUS mandatory
	DESCRIPTION
		"Type of active Firmware"
	::= { cmroHtuFarEntry 4 }

cmroHtuFarActFwVers OBJECT-TYPE
	SYNTAX DisplayString
	ACCESS read-only
	STATUS mandatory
	DESCRIPTION
		"Version of active Firmware"
	::= { cmroHtuFarEntry 5 }

cmroHtuFarPasBankState OBJECT-TYPE
	SYNTAX INTEGER
	{
		empty(1),
		loaded(2),
		foreign(3),
		unknown(254),
		unsupported(255)
	}
	ACCESS read-only
	STATUS mandatory
	DESCRIPTION
		"State of passive firmware bank
		1	Empty	contains no firmware
		2	Loaded	contains a valid firmware
		3	Foreign	contains regenerator firmware
		254		unknown value
		255		unsupported variable for addressed device"
	::= { cmroHtuFarEntry 6 }

cmroHtuFarPasFwType OBJECT-TYPE
	SYNTAX DisplayString
	ACCESS read-only
	STATUS mandatory
	DESCRIPTION
		"Type of passive firmware"
	::= { cmroHtuFarEntry 7 }

cmroHtuFarPasFwVers OBJECT-TYPE
	SYNTAX DisplayString
	ACCESS read-only
	STATUS mandatory
	DESCRIPTION
		"Version of passive firmware"
	::= { cmroHtuFarEntry 8 }

cmroHtuFarSeepromVers OBJECT-TYPE
	SYNTAX DisplayString
	ACCESS read-only
	STATUS mandatory
	DESCRIPTION
		"Version of SEEPROM data format"
	::= { cmroHtuFarEntry 9 }

cmroHtuFarDFabData OBJECT-TYPE
	SYNTAX DisplayString(SIZE(20))
	ACCESS read-only
	STATUS mandatory
	DESCRIPTION
		"Fabrication Data of Data-Module"
	::= { cmroHtuFarEntry 10 }

cmroHtuFarDType OBJECT-TYPE
	SYNTAX INTEGER
	{
		none(1),
		dce(2),
		dte(3),
		tenBaseT(4),
		abar(5),
		unknown(254),
		unsupported(255)
	}
	ACCESS read-only
	STATUS mandatory
	DESCRIPTION
		"Type of Data-Module in corresponding module-slot of the device.
		1	None		No module inserted
		2	DCE		Data module with DCE configuration
		3	DTE		Data module with DTE configuration
		4	10Base-T	10Base-T Ethernet module
		5	ABAR		Advanced Bridge and Router module
		254			unknown value
		255			unsupported variable for addressed device
		
		For details of the module (connector sub-types, ...) the 
		fabrication data has to evaluated"
	::= { cmroHtuFarEntry 11 }

cmroHtuFarTFabData OBJECT-TYPE
	SYNTAX DisplayString(SIZE(20))
	ACCESS read-only
	STATUS mandatory
	DESCRIPTION
		"Fabrication Data of 2Mbit-Module"
	::= { cmroHtuFarEntry 12 }

cmroHtuFarTType OBJECT-TYPE
	SYNTAX INTEGER
	{
		none(1),
		twoMbps(2),
		quadTwoMbps(3),
		codirTwoMbps(4),
		twoMbpsVarImp(5),
		quadTwoMbpsVarImp(6),
		fourTwoMbpsVarImp(7),
		unknown(254),
		unsupported(255)
	}
	ACCESS read-only
	STATUS mandatory
	DESCRIPTION
		"Type of 2Mbit-Module in corresponding module-slot of the device.
		1	None		No module present
		2	TwoMbps		A 2Mbit/s module is present
		3	QuadTwoMbps	A Quad 2Mbit/s module is present
		4	CodirTwoMbps	A Co-Directional G.703 module is present
		5	TwoMbpsVarImp	A 2Mbit/s module with variable impedance is present
		6	QuadTwoMbpsVarImp	A Quad 2Mbit/s module with variable impedance is present
		7	FourTwoMbpsVarImp	Module with four independent 2Mbit/s (variable impedance) is present
		254			unknown value
		255			unsupported variable for addressed device
		
		For details of the module (connector sub-types, ...) the 
		fabrication data has to evaluated"
	::= { cmroHtuFarEntry 13 }

cmroHtuFarRpsFabData OBJECT-TYPE
	SYNTAX DisplayString(SIZE(20))
	ACCESS read-only
	STATUS mandatory
	DESCRIPTION
		"Fabrication Data of Remote Power Supply (RPS) Module"
	::= { cmroHtuFarEntry 14 }

cmroHtuFarRpsType OBJECT-TYPE
	SYNTAX INTEGER
	{
		none(1),
		rps(2),
		unknown(254),
		unsupported(255)
	}
	ACCESS read-only
	STATUS mandatory
	DESCRIPTION
		"Type of Remote Power Supply (RPS) Module in corresponding
		 module-slot of the device.
		1	None	No module inserted
		2	Rps	A RPS module is inserted
		254		unknown value
		255		unsupported variable for addressed device
		
		For details of the module (connector sub-types, ...) the 
		fabrication data has to evaluated"
	::= { cmroHtuFarEntry 15 }

cmroHtuFarClkFabData OBJECT-TYPE
	SYNTAX DisplayString(SIZE(20))
	ACCESS read-only
	STATUS mandatory
	DESCRIPTION
		"Fabrication Data of Clock and Alarm Module"
	::= { cmroHtuFarEntry 16 }

cmroHtuFarClkType OBJECT-TYPE
	SYNTAX INTEGER
	{
		none(1),
		clockAlarm(2),
		clock(3),
		alarm(4),
		unknown(254),
		unsupported(255)
	}
	ACCESS read-only
	STATUS mandatory
	DESCRIPTION
		"Type of Clock and Alarm Module in corresponding
		 module-slot of the device.
		1	None		No module inserted
		2	ClockAlarm	A combined Clock and Alarm module is inserted
		3	Clock		A Clock module is inserted
		3	Alarm		An Alarm module is inserted
		254			unknown value
		255			unsupported variable for addressed device
		
		For details of the module (connector sub-types, ...) the 
		fabrication data has to evaluated"
	::= { cmroHtuFarEntry 17 }

cmroHtuFarDbgFabData OBJECT-TYPE
	SYNTAX DisplayString(SIZE(20))
	ACCESS read-only
	STATUS mandatory
	DESCRIPTION
		"Fabrication Data of Debug-Module"
	::= { cmroHtuFarEntry 18 }

cmroHtuFarDbgType OBJECT-TYPE
	SYNTAX INTEGER
	{
		none(1),
		debug(2),
		unknown(254),
		unsupported(255)
	}
	ACCESS read-only
	STATUS mandatory
	DESCRIPTION
		"Type of Debug-Module in corresponding module-slot of the device.
		1	None	No module inserted
		2	Debug	A Debug module is inserted
		254		unknown value
		255		unsupported variable for addressed device
		
		For details of the module (connector sub-types, ...) the 
		fabrication data has to evaluated"
	::= { cmroHtuFarEntry 19 }

cmroHtuFarHousing OBJECT-TYPE
	SYNTAX INTEGER
	{
		rack(1),
		desktop(2),
		unknown(254),
		unsupported(255)
	}
	ACCESS read-only
	STATUS mandatory
	DESCRIPTION
		"Type of housing / installation of the device.
		1	Rack	The device is a line card to be installed in a sub-rack
		2	Desktop	The device is a desktop device
		254		unknown value
		255		unsupported variable for addressed device"
	::= { cmroHtuFarEntry 20 }

cmroHtuFarRackVersion OBJECT-TYPE
	SYNTAX INTEGER
	{
		rackV1(1),
		rackV2(2),
		rackV3(3),
		desktop(4),
		unknown(254),
		unsupported(255)
	}
	ACCESS read-only
	STATUS mandatory
	DESCRIPTION
		"Version of the sub-rack in which the device is installed.
		1	RackV1	The device is installed in a rack with V1
		2	RackV2	The device is installed in a rack with V2
		3	RackV3	The device is installed in a rack with V3
		4	Desktop	The device is a desktop device (and therefore not installed in a sub-rack)
		254		unknown value
		255		unsupported variable for addressed device"
	::= { cmroHtuFarEntry 21 }

cmroHtuFarLtNtType OBJECT-TYPE
	SYNTAX INTEGER
	{
		lt(1),
		nt(2),
		unknown(254),
		unsupported(255)
	}
	ACCESS read-only
	STATUS mandatory
	DESCRIPTION
		"Indicates whether the device is configured as LT or NT.
		1	LT	The device is configured as LT
		2	NT	The device is configured as NT
		254		unknown value
		255		unsupported variable for addressed device"
	::= { cmroHtuFarEntry 22 }

cmroHtuFarHdslChipset OBJECT-TYPE
	SYNTAX INTEGER
	{
		level1(1),
		metalink(2),
		infineon(3),
		unknown(254),
		unsupported(255)
	}
	ACCESS read-only
	STATUS mandatory
	DESCRIPTION
		"Indicates which chipset the partner device uses for HDSL transmission
		1	Level1		The partner device uses a Level 1 chipset
		2	Metalink	The partner device uses a MetaLink chipset
		3	Infineon	The partner device uses an Infineon chipset
		254			unknown value
		255			unsupported variable for addressed device"
	::= { cmroHtuFarEntry 23 }

cmroHtuFarDipCfg OBJECT-TYPE
	SYNTAX INTEGER
	{
		disabled(1),
		enabled(2),
		unknown(254),
		unsupported(255)
	}
	ACCESS read-only
	STATUS mandatory
	DESCRIPTION
		"Indicates whether the device is configured through DIP Switches.
		1	Disabled	The device can be configured through management software
		2	Enabled		The device is configured by DIP switches
		254			unknown value
		255			unsupported variable for addressed device"
	::= { cmroHtuFarEntry 24 }

cmroHtuFarEocCfg OBJECT-TYPE
	SYNTAX INTEGER
	{
		disabled(1),
		enabled(2),
		reg1(3),
		reg2(4),
		reg3(5),
		reg4(6),
		reg5(7),
		reg6(8),
		reg7(9),
		reg8(10),
		unknown(254),
		unsupported(255)
	}
	ACCESS read-only
	STATUS mandatory
	DESCRIPTION
		"Indicates whether the far device is reached by EOC or not.
		1	Disabled	The far device cannot be reached by EOC
		2	Enabled		The far device can be reached by EOC
		3	Reg1		The EOC is up until the first regenerator section
		4	Reg2		The EOC is up until the second regenerator section
		5	Reg3		The EOC is up until the third regenerator section
		6	Reg4		The EOC is up until the fourth regenerator section
		7	Reg5		The EOC is up until the fifth regenerator section
		8	Reg6		The EOC is up until the sixth regenerator section
		9	Reg7		The EOC is up until the seventh regenerator section
		10	Reg8		The EOC is up until the eighth regenerator section
		254			unknown value
		255			unsupported variable for addressed device"
	::= { cmroHtuFarEntry 25 }

cmroHtuFarRpsVoltage OBJECT-TYPE
	SYNTAX INTEGER
	{
		v120(1),
		v180(2),
		noRps(3),
		unknown(254),
		unsupported(255)
	}
	ACCESS read-only
	STATUS mandatory
	DESCRIPTION
		"Indicates which Remote Power Supply (RPS) Voltage is being used by the device
		1	V120	The RPS uses 120 Volts
		2	V180	The RPS uses 180 Volts
		3	NoRps	The device is not equipped with an RPS
		254		unknown value
		255		unsupported variable for addressed device"
	::= { cmroHtuFarEntry 26 }

cmroHtuFarPowerConfiguration OBJECT-TYPE
	SYNTAX INTEGER
	{
		multifunctional(1),
		redundant(2),
		remoteFeeding(3),
		batteryDC(4),
		unknown(254),
		unsupported(255)
	}
	ACCESS read-only
	STATUS mandatory
	DESCRIPTION
		"Indicates which kind of power supply is equiped
		1	multifunctional	No redundant supply possible
		2	redundant	Redundant supply possible
		3	remoteFeeding	Remote feeding possible
		4	batteryDC	DC-only supply
		254			unknown value
		255			unsupported variable for addressed device"
	::= { cmroHtuFarEntry 27 }


cmroHtuFarIsdnFabData OBJECT-TYPE
	SYNTAX DisplayString(SIZE(20))
	ACCESS read-only
	STATUS mandatory
	DESCRIPTION
		"Fabrication Data of ISDN-Module"
	::= { cmroHtuFarEntry 28 }


cmroHtuFarIsdnType OBJECT-TYPE
	SYNTAX INTEGER
	{
		none(1),
		te(2),
		nt(3),
		uk0(4),
		unknown(254),
		unsupported(255)
	}
	ACCESS read-only
	STATUS mandatory
	DESCRIPTION
		"Type of ISDN-Module in corresponding module-slot of the device
		1	None	No module inserted
		2	TE	A module for S0(TE mode) operation is inserted
		3	NT	A module for S0(NT mode) operation is inserted
		4	Uk0	A module for Uk0 operation is inserted
		254		unknown value
		255		unsupported variable for addressed device"
	::= { cmroHtuFarEntry 29 }


cmroHtuFarTipRingReversal1 OBJECT-TYPE
	SYNTAX INTEGER
	{
		no(1),
		yes(2),
		unknown(254),
		unsupported(255)
	}
	ACCESS read-only
	STATUS mandatory
	DESCRIPTION
		"Indicates whether tip-ring reversal has been detected and compensated
		 for on the first wire pair
		 1	No	Reversal not detected
		 2	Yes	Reversal detected and compensated for
		 254		unknown value
		 255		unsupported variable for addressed device"
	::= { cmroHtuFarEntry 30 }


cmroHtuFarTipRingReversal2 OBJECT-TYPE
	SYNTAX INTEGER
	{
		no(1),
		yes(2),
		unknown(254),
		unsupported(255)
	}
	ACCESS read-only
	STATUS mandatory
	DESCRIPTION
		"Indicates whether tip-ring reversal has been detected and compensated
		 for on the second wire pair
		 1	No	Reversal not detected
		 2	Yes	Reversal detected and compensated for
		 254		unknown value
		 255		unsupported variable for addressed device"
	::= { cmroHtuFarEntry 31 }

cmroHtuFarTipRingReversal3 OBJECT-TYPE
	SYNTAX INTEGER
	{
		no(1),
		yes(2),
		unknown(254),
		unsupported(255)
	}
	ACCESS read-only
	STATUS mandatory
	DESCRIPTION
		"Indicates whether tip-ring reversal has been detected and compensated
		 for on the third wire pair
		 1	No	Reversal not detected
		 2	Yes	Reversal detected and compensated for
		 254		unknown value
		 255		unsupported variable for addressed device"
	::= { cmroHtuFarEntry 32 }


cmroHtuFarTipRingReversal4 OBJECT-TYPE
	SYNTAX INTEGER
	{
		no(1),
		yes(2),
		unknown(254),
		unsupported(255)
	}
	ACCESS read-only
	STATUS mandatory
	DESCRIPTION
		"Indicates whether tip-ring reversal has been detected and compensated
		 for on the fourth wire pair
		 1	No	Reversal not detected
		 2	Yes	Reversal detected and compensated for
		 254		unknown value
		 255		unsupported variable for addressed device"
	::= { cmroHtuFarEntry 33 }

cmroHtuFarPacketFabData OBJECT-TYPE
	SYNTAX DisplayString(SIZE(20))
	ACCESS read-only
	STATUS mandatory
	DESCRIPTION
		"Fabrication Data of L2 Switch"
	::= { cmroHtuFarEntry 34 }

cmroHtuFarPacketType OBJECT-TYPE
	SYNTAX INTEGER
	{
		none(1),
		fourPort10-100(2),
		onePort10-100(3),
		twoPort10-100(4),
		threePort10-100(5),
		unknown(254),
		unsupported(255)
	}
	ACCESS read-only
	STATUS mandatory
	DESCRIPTION
		"Type of L2 Switch module.
		1	None		No module inserted
		2	4P10/100	4-Port 10/100Base-T ethernet switch
		3	1P10/100	1-Port 10/100Base-T ethernet switch
		4	2P10/100	2-Port 10/100Base-T ethernet switch
		5	3P10/100	3-Port 10/100Base-T ethernet switch
		254			unknown value
		255			unsupported variable for addressed device
		
		For details of the module (connector sub-types, ...) the 
		fabrication data has to evaluated"
	::= { cmroHtuFarEntry 35 }

cmroHtuFarPacketMacAddr1 OBJECT-TYPE
	SYNTAX OCTET STRING(SIZE(6))
	ACCESS read-only
	STATUS mandatory
	DESCRIPTION
		"MAC address of L2 ethernet switch.
		Value of Byte 0..5	Meaning
		
		0x00 - 0xFD		MAC address
		all 0xFE		unknown value
		all 0xFF		unsupported variable"
	::= { cmroHtuFarEntry 36 }

cmroHtuFarDslChipset OBJECT-TYPE
	SYNTAX DisplayString(SIZE(20))
	ACCESS read-only
	STATUS mandatory
	DESCRIPTION
		"Type of xDSL chipset"
	::= { cmroHtuFarEntry 37 }

cmroHtuFarDslFwLoad OBJECT-TYPE
	SYNTAX DisplayString(SIZE(20))
	ACCESS read-only
	STATUS mandatory
	DESCRIPTION
		"Type of firmware load of xDSL chipset"
	::= { cmroHtuFarEntry 38 }

cmroHtuFarFpgaLoad OBJECT-TYPE
	SYNTAX DisplayString(SIZE(20))
	ACCESS read-only
	STATUS mandatory
	DESCRIPTION
		"Type of FPGA load"
	::= { cmroHtuFarEntry 39 }

cmroHtuFarEthWanChip OBJECT-TYPE
	SYNTAX DisplayString(SIZE(20))
	ACCESS read-only
	STATUS mandatory
	DESCRIPTION
		"Type of WAN chip which connects L2 switch and xDSL link"
	::= { cmroHtuFarEntry 40 }

cmroHtuFarSwitchChip OBJECT-TYPE
	SYNTAX DisplayString(SIZE(20))
	ACCESS read-only
	STATUS mandatory
	DESCRIPTION
		"Type of Switch Chip"
	::= { cmroHtuFarEntry 41 }

cmroHtuFarBootloaderVers OBJECT-TYPE
	SYNTAX DisplayString(SIZE(20))
	ACCESS read-only
	STATUS mandatory
	DESCRIPTION
		"Version of firmware boot loader"
	::= { cmroHtuFarEntry 42 }

cmroHtuFarSerialNumber OBJECT-TYPE
	SYNTAX DisplayString(SIZE(20))
	ACCESS read-only
	STATUS mandatory
	DESCRIPTION
		"Serial number of device"
	::= { cmroHtuFarEntry 43 }

cmroHtuFarHwManufacturingDate OBJECT-TYPE
	SYNTAX DisplayString
	ACCESS read-only
	STATUS mandatory
	DESCRIPTION
		"Manufacturing Date of the motherboard"
	::= { cmroHtuFarEntry 44 }

cmroHtuFarRpsManufacturingDate OBJECT-TYPE
	SYNTAX DisplayString
	ACCESS read-only
	STATUS mandatory
	DESCRIPTION
		"Manufacturing Date of the RPS Module"
	::= { cmroHtuFarEntry 45 }

cmroHtuFarClkManufacturingDate OBJECT-TYPE
	SYNTAX DisplayString
	ACCESS read-only
	STATUS mandatory
	DESCRIPTION
		"Manufacturing Date of the Clock and Alarm Module"
	::= { cmroHtuFarEntry 46 }

cmroHtuFarTManufacturingDate OBJECT-TYPE
	SYNTAX DisplayString
	ACCESS read-only
	STATUS mandatory
	DESCRIPTION
		"Manufacturing Date of the 2Mbps Module"
	::= { cmroHtuFarEntry 47 }

cmroHtuFarDManufacturingDate OBJECT-TYPE
	SYNTAX DisplayString
	ACCESS read-only
	STATUS mandatory
	DESCRIPTION
		"Manufacturing Date of the Data Module"
	::= { cmroHtuFarEntry 48 }

cmroHtuFarPacketManufacturingDate OBJECT-TYPE
	SYNTAX DisplayString
	ACCESS read-only
	STATUS mandatory
	DESCRIPTION
		"Manufacturing Date of the Packet Module"
	::= { cmroHtuFarEntry 49 }

cmroHtuFarL2SDriverVersion OBJECT-TYPE
	SYNTAX DisplayString
	ACCESS read-only
	STATUS mandatory
	DESCRIPTION
		"L2 Switch Driver Version"
	::= { cmroHtuFarEntry 50 }

--------------------------------------------------------------------------------
--	CM-RO	Used TS
--------------------------------------------------------------------------------
cmroUsedTsTable OBJECT-TYPE
	SYNTAX SEQUENCE OF CmroUsedTsEntry
	ACCESS not-accessible
	STATUS mandatory
	DESCRIPTION ""
	::= { cmro 3 }

cmroUsedTsEntry OBJECT-TYPE
	SYNTAX CmroUsedTsEntry
	ACCESS not-accessible
	STATUS mandatory
	DESCRIPTION ""
	INDEX { cmroUsedTsPortIndex, cmroUsedTsLinkIndex }
	::= { cmroUsedTsTable 1 }

CmroUsedTsEntry ::=
	SEQUENCE
	{
		cmroUsedTsPortIndex INTEGER,
		cmroUsedTsLinkIndex INTEGER,
		cmroUsedTsAll INTEGER,
		cmroUsedTsMap OCTET STRING,
		cmroUsedTsMapStuExtension OCTET STRING
	}

cmroUsedTsPortIndex OBJECT-TYPE
	SYNTAX INTEGER
	ACCESS read-only
	STATUS mandatory
	DESCRIPTION
		"This variable addresses the port number of the proxy
		and is used as index for the other elements in the Table"
	::= { cmroUsedTsEntry 1 }

cmroUsedTsLinkIndex OBJECT-TYPE
	SYNTAX INTEGER
	ACCESS read-only
	STATUS mandatory
	DESCRIPTION
		"This variable addresses the slot number of the OMI sub-rack
		and is used as index for the other elements in the Table"
	::= { cmroUsedTsEntry 2 }

cmroUsedTsAll OBJECT-TYPE
	SYNTAX INTEGER
	{
		true(1),
		false(2),
		unknown(254),
		unsupported(255)
	}
	ACCESS read-only
	STATUS mandatory
	DESCRIPTION
		"Indicates whether all timeslots are used or not. If all of them
		are used, cmroUsedTsMap will return 'allUsed' for all time slots.
		1	true	All time slots are being used (ignore cmroUsedTsMap)
		2	false	Not all time slots are being used, details in cmroUsedTsMap
		254		unknown value
		255		unsupported variable for addressed device"
	::= { cmroUsedTsEntry 3 }

cmroUsedTsMap OBJECT-TYPE
	SYNTAX OCTET STRING(SIZE(32))
	ACCESS read-only
	STATUS mandatory
	DESCRIPTION
		"If cmroUsedTsAll is 'false(2)' this variable reports which
		time slot in the E1 2Mbit/s signal is used for which purpose.
		The variable consists of an array with length 32. Each array
		position corresponds to a time slot in the E1 signal and 
		its content indicates what the time slot is used for.
		The following codes are used:
		1	N1	Used for G.703 signal
		2	N2	Used for Data signal
		3	FastSig1	Used for Fast Signalling in stream 1
		4	FastSig2	Used for Fast Signalling in stream 2
		5	CAS		Used for CAS Signalling
		6	Unused		Time slot is unused
		7	Sync		Used for synchronisation (Time slot 0)
		8	Ignore		No mapping (cmroUsedTsAll is 'true')
		254			unknown value
		255			unsupported variable for addressed device"
	::= { cmroUsedTsEntry 4 }

cmroUsedTsMapStuExtension OBJECT-TYPE
	SYNTAX OCTET STRING(SIZE(4))
	ACCESS read-only
	STATUS mandatory
	DESCRIPTION
		"If cmroUsedTsAll is 'false(2)' this variable reports which
		time slot in the E1 2Mbit/s signal is used for which purpose.
		
		This variable describes the addidtional 4 timeslots which are
		available with the SDSL system. The 4 bytes in this variable
		correspond to the time slots 32..35. Each array position
		corresponds to a time slot in the E1 signal and its content
		indicates what the time slot is used for.
		The following codes are used:
		1	N1	Used for G.703 signal
		2	N2	Used for Data signal
		3	FastSig1	Used for Fast Signalling in stream 1
		4	FastSig2	Used for Fast Signalling in stream 2
		5	CAS		Used for CAS Signalling
		6	Unused		Time slot is unused
		7	Sync		Used for synchronisation (Time slot 0)
		8	Ignore		No mapping (cmroUsedTsAll is 'true')
		254			unknown value
		255			unsupported variable for addressed device"
	::= { cmroUsedTsEntry 5 }

--------------------------------------------------------------------------------
--	CM-RO	OMI
--------------------------------------------------------------------------------
cmroOmiTable OBJECT-TYPE
	SYNTAX SEQUENCE OF CmroOmiEntry
	ACCESS not-accessible
	STATUS mandatory
	DESCRIPTION ""
	::= { cmro 4 }

cmroOmiEntry OBJECT-TYPE
	SYNTAX CmroOmiEntry
	ACCESS not-accessible
	STATUS mandatory
	DESCRIPTION ""
	INDEX { cmroOmiPortIndex }
	::= { cmroOmiTable 1 }

CmroOmiEntry ::=
	SEQUENCE
	{
		cmroOmiPortIndex INTEGER,
		cmroOmiHwFabData DisplayString,
		cmroOmiActFwVers DisplayString,
		cmroOmiPasBankState INTEGER,
		cmroOmiPasFwVers DisplayString,
		cmroOmiRackVersion INTEGER,
		cmroOmiActFwType DisplayString,
		cmroOmiRackVersion2 INTEGER,
		cmroOmiRackVersion3 INTEGER,
		cmroOmiRackVersion4 INTEGER,
		cmroOmiCardLocation INTEGER,
		cmroOmiSeepromVers DisplayString,
		cmroOmiMCUSerialNo DisplayString,
		cmroOmiPasFwType DisplayString,
		cmroOmiBootLoaderVers DisplayString,
		cmroOmiMACAddress OCTET STRING,
		cmroOmiNMSHwPartNo DisplayString,
		cmroOmiNMSChipPartNo DisplayString,
		cmroOmiL2SMACAddress OCTET STRING,
		cmroOmiL2SHwPartNo DisplayString,
		cmroOmiL2SChipPartNo DisplayString,
		cmroOmiL2SFwVers DisplayString,
		cmroOmiL2SFeatureFlags OCTET STRING,
		cmroOmiL2SModuleType INTEGER,
		cmroOmiGBEHwPartNo DisplayString,
		cmroOmiGBEModuleType INTEGER,
		cmroOmiSFP1ModuleType INTEGER,
		cmroOmiSFP1TranscType INTEGER,
		cmroOmiSFP1TranscCode OCTET STRING,
		cmroOmiSFP1VendorName DisplayString,
		cmroOmiSFP1VendorOUI OCTET STRING,
		cmroOmiSFP1VendorPartNo DisplayString,
		cmroOmiSFP1VendorRevNo DisplayString,
		cmroOmiSFP1VendorSerialNo DisplayString,
		cmroOmiSFP1VendorDateCode OCTET STRING,
		cmroOmiSFP2ModuleType INTEGER,
		cmroOmiSFP2TranscType INTEGER,
		cmroOmiSFP2TranscCode OCTET STRING,
		cmroOmiSFP2VendorName DisplayString,
		cmroOmiSFP2VendorOUI OCTET STRING,
		cmroOmiSFP2VendorPartNo DisplayString,
		cmroOmiSFP2VendorRevNo DisplayString,
		cmroOmiSFP2VendorSerialNo DisplayString,
		cmroOmiSFP2VendorDateCode OCTET STRING,
		cmroOmiCESHwPartNo DisplayString,
		cmroOmiCESType INTEGER,
		cmroOmiCESMACAddress OCTET STRING,
		cmroOmiCESSerialNo DisplayString
	}

cmroOmiPortIndex OBJECT-TYPE
	SYNTAX INTEGER
	ACCESS read-only
	STATUS mandatory
	DESCRIPTION
		"This variable addresses the port number of the proxy
		and is used as index for the other elements in the Table"
	::= { cmroOmiEntry 1 }

cmroOmiHwFabData OBJECT-TYPE
	SYNTAX DisplayString(SIZE(20))
	ACCESS read-only
	STATUS mandatory
	DESCRIPTION
		"Hardware Fabrication Data"
	::= { cmroOmiEntry 2 }

cmroOmiActFwVers OBJECT-TYPE
	SYNTAX DisplayString
	ACCESS read-only
	STATUS mandatory
	DESCRIPTION
		"Version of active Firmware"
	::= { cmroOmiEntry 3 }

cmroOmiPasBankState OBJECT-TYPE
	SYNTAX INTEGER
	{
		empty(1),
		loaded(2),
		unknown(254),
		unsupported(255)
	}
	ACCESS read-only
	STATUS mandatory
	DESCRIPTION
		"State of passive firmware bank
		1	Empty	contains no firmware
		2	Loaded	contains a valid firmware
		254		unknown value
		255		unsupported variable for addressed device"
	::= { cmroOmiEntry 4 }

cmroOmiPasFwVers OBJECT-TYPE
	SYNTAX DisplayString
	ACCESS read-only
	STATUS mandatory
	DESCRIPTION
		"Version of passive firmware"
	::= { cmroOmiEntry 5 }

cmroOmiRackVersion OBJECT-TYPE
	SYNTAX INTEGER
	{
		rackV1(1),
		rackV2(2),
		rackV3(3),
		desktop(4),
		unknown(254),
		unsupported(255)
	}
	ACCESS read-only
	STATUS mandatory
	DESCRIPTION
		"Version of the sub-rack in which the device is installed.
		1	RackV1	The device is installed in a rack with V1
		2	RackV2	The device is installed in a rack with V2
		3	RackV3	The device is installed in a rack with V3
		4	Desktop	The device is a desktop device (and therefore not installed in a sub-rack)
		254		unknown value
		255		unsupported variable for addressed device"
	::= { cmroOmiEntry 6 }

cmroOmiActFwType OBJECT-TYPE
	SYNTAX DisplayString
	ACCESS read-only
	STATUS mandatory
	DESCRIPTION
		"Contains the firmware type of the active firmware"
	::= { cmroOmiEntry 7 }

cmroOmiRackVersion2 OBJECT-TYPE
	SYNTAX INTEGER
	{
		rackV1(1),
		rackV2(2),
		rackV3(3),
		desktop(4),
		unknown(254),
		unsupported(255)
	}
	ACCESS read-only
	STATUS mandatory
	DESCRIPTION
		"Version of the sub-rack 2.
		1	RackV1	rack with V1
		2	RackV2	rack with V2
		3	RackV3	rack with V3
		4	Desktop	desktop device (and therefore not installed in a sub-rack)
		254		unknown value
		255		unsupported variable for addressed device"
	::= { cmroOmiEntry 8 }

cmroOmiRackVersion3 OBJECT-TYPE
	SYNTAX INTEGER
	{
		rackV1(1),
		rackV2(2),
		rackV3(3),
		desktop(4),
		unknown(254),
		unsupported(255)
	}
	ACCESS read-only
	STATUS mandatory
	DESCRIPTION
		"Version of the sub-rack 3.
		1	RackV1	rack with V1
		2	RackV2	rack with V2
		3	RackV3	rack with V3
		4	Desktop	desktop device (and therefore not installed in a sub-rack)
		254		unknown value
		255		unsupported variable for addressed device"
	::= { cmroOmiEntry 9 }

cmroOmiRackVersion4 OBJECT-TYPE
	SYNTAX INTEGER
	{
		rackV1(1),
		rackV2(2),
		rackV3(3),
		desktop(4),
		unknown(254),
		unsupported(255)
	}
	ACCESS read-only
	STATUS mandatory
	DESCRIPTION
		"Version of the sub-rack 4.
		1	RackV1	rack with V1
		2	RackV2	rack with V2
		3	RackV3	rack with V3
		4	Desktop	desktop device (and therefore not installed in a sub-rack)
		254		unknown value
		255		unsupported variable for addressed device"
	::= { cmroOmiEntry 10 }

cmroOmiCardLocation OBJECT-TYPE
	SYNTAX INTEGER
	ACCESS read-only
	STATUS mandatory
	DESCRIPTION
		"Card location in subrack: 0..254"
	::= { cmroOmiEntry 11 }

cmroOmiSeepromVers OBJECT-TYPE
	SYNTAX DisplayString(SIZE(3))
	ACCESS read-only
	STATUS mandatory
	DESCRIPTION
		"Version of configuration data format"
	::= { cmroOmiEntry 12 }

cmroOmiMCUSerialNo OBJECT-TYPE
	SYNTAX DisplayString(SIZE(5))
	ACCESS read-only
	STATUS mandatory
	DESCRIPTION
		"Serial number of the device"
	::= { cmroOmiEntry 13 }

cmroOmiPasFwType OBJECT-TYPE
	SYNTAX DisplayString(SIZE(5))
	ACCESS read-only
	STATUS mandatory
	DESCRIPTION
		"Contains the firmware type of the passive firmware"
	::= { cmroOmiEntry 14 }

cmroOmiBootLoaderVers OBJECT-TYPE
	SYNTAX DisplayString
	ACCESS read-only
	STATUS mandatory
	DESCRIPTION
		"Contains the Boot loader version"
	::= { cmroOmiEntry 15 }

cmroOmiMACAddress OBJECT-TYPE
	SYNTAX OCTET STRING (SIZE(6))
	ACCESS read-only
	STATUS mandatory
	DESCRIPTION
		"Contains the MCU MAC address
		Value of Byte 0..5	Meaning

		0x00 - 0xFD		MAC address
		all 0xFE		unknown value
		all 0xFF		unsupported variable"
	::= { cmroOmiEntry 16 }


cmroOmiNMSHwPartNo OBJECT-TYPE
	SYNTAX DisplayString(SIZE(20))
	ACCESS read-only
	STATUS mandatory
	DESCRIPTION
		"Contains the Hw partition number"
	::= { cmroOmiEntry 17 }

cmroOmiNMSChipPartNo OBJECT-TYPE
	SYNTAX DisplayString(SIZE(20))
	ACCESS read-only
	STATUS mandatory
	DESCRIPTION
		"Contains the chip partition number"
	::= { cmroOmiEntry 18 }

cmroOmiL2SMACAddress OBJECT-TYPE
	SYNTAX OCTET STRING (SIZE(6))
	ACCESS read-only
	STATUS mandatory
	DESCRIPTION
		"Contains the MAC Address of L2 switch
		Value of Byte 0..5	Meaning

		0x00 - 0xFD		MAC address
		all 0xFE		unknown value
		all 0xFF		unsupported variable"
	::= { cmroOmiEntry 19 }

cmroOmiL2SHwPartNo OBJECT-TYPE
	SYNTAX DisplayString(SIZE(20))
	ACCESS read-only
	STATUS mandatory
	DESCRIPTION
		"Hardware partition number"
	::= { cmroOmiEntry 20 }

cmroOmiL2SChipPartNo OBJECT-TYPE
	SYNTAX DisplayString(SIZE(20))
	ACCESS read-only
	STATUS mandatory
	DESCRIPTION
		"Chip partition number"
	::= { cmroOmiEntry 21 }

cmroOmiL2SFwVers OBJECT-TYPE
	SYNTAX DisplayString(SIZE(20))
	ACCESS read-only
	STATUS mandatory
	DESCRIPTION
		"L2 Switch Firmware version"
	::= { cmroOmiEntry 22 }

cmroOmiL2SFeatureFlags OBJECT-TYPE
	SYNTAX OCTET STRING (SIZE(128))
	ACCESS read-only
	STATUS mandatory
	DESCRIPTION
		"L2 Switch partition feature flags"
	::= { cmroOmiEntry 23 }

cmroOmiL2SModuleType OBJECT-TYPE
	SYNTAX INTEGER
	{
		l2s2GbE16FE(1),
		none(254)
	}
	ACCESS read-only
	STATUS mandatory
	DESCRIPTION
		"L2 Switch module type:
		1	24 Fast Ethernet + 3GigaBit Ethernet,
		254	NONE"
	::= { cmroOmiEntry 24 }

cmroOmiGBEHwPartNo OBJECT-TYPE
	SYNTAX DisplayString(SIZE(20))
	ACCESS read-only
	STATUS mandatory
	DESCRIPTION
		"Gigabit ethernet Hw partition number"
	::= { cmroOmiEntry 25 }

cmroOmiGBEModuleType OBJECT-TYPE
	SYNTAX INTEGER
	{
		gbe1000BaseT(1),
		none(254)
	}
	ACCESS read-only
	STATUS mandatory
	DESCRIPTION
		"Gigabit ethernet module type:
		1   1000BASE-T copper,
		254   NONE"
	::= { cmroOmiEntry 26 }

cmroOmiSFP1ModuleType OBJECT-TYPE
	SYNTAX INTEGER
	{
		sfp1000BaseT(1),
		sfp1000BaseSX(2),
		sfp1000BaseLX(3),
		none (254),
		unknown(255)
	}
	ACCESS read-only
	STATUS mandatory
	DESCRIPTION
		"SFP module type.
		Enum type corresponding to accepted values in following two fields:
		1	1000BASE-T  copper,
		2	1000BASE-SX short wavelength,
		3	1000BASE-LX long wavelength,
		254	NONE
		255	UNKNOWN
		"
	::= { cmroOmiEntry 27 }

cmroOmiSFP1TranscType OBJECT-TYPE
	SYNTAX INTEGER
	ACCESS read-only
	STATUS mandatory
	DESCRIPTION
		"SFP transceiver type (0..255)"
	::= { cmroOmiEntry 28 }

cmroOmiSFP1TranscCode OBJECT-TYPE
	SYNTAX OCTET STRING (SIZE(8))
	ACCESS read-only
	STATUS mandatory
	DESCRIPTION
		"SFP transceiver code:
		accepted values are those corresponding to module type"
	::= { cmroOmiEntry 29 }

cmroOmiSFP1VendorName OBJECT-TYPE
	SYNTAX DisplayString(SIZE(16))
	ACCESS read-only
	STATUS mandatory
	DESCRIPTION
		"SFP vendor name"
	::= { cmroOmiEntry 30 }

cmroOmiSFP1VendorOUI OBJECT-TYPE
	SYNTAX OCTET STRING (SIZE(3))
	ACCESS read-only
	STATUS mandatory
	DESCRIPTION
		"SFP IEEE company ID"
	::= { cmroOmiEntry 31 }

cmroOmiSFP1VendorPartNo OBJECT-TYPE
	SYNTAX DisplayString(SIZE(16))
	ACCESS read-only
	STATUS mandatory
	DESCRIPTION
		"SFP vendor partition number"
	::= { cmroOmiEntry 32 }

cmroOmiSFP1VendorRevNo OBJECT-TYPE
	SYNTAX DisplayString(SIZE(4))
	ACCESS read-only
	STATUS mandatory
	DESCRIPTION
		"SFP vendor revision number"
	::= { cmroOmiEntry 33 }

cmroOmiSFP1VendorSerialNo OBJECT-TYPE
	SYNTAX DisplayString(SIZE(16))
	ACCESS read-only
	STATUS mandatory
	DESCRIPTION
		"SFP vendor serial number"
	::= { cmroOmiEntry 34 }

cmroOmiSFP1VendorDateCode OBJECT-TYPE
	SYNTAX OCTET STRING (SIZE(8))
	ACCESS read-only
	STATUS mandatory
	DESCRIPTION
		"SFP vendor date code
		YYMMDDLL (LL=vendor specific lot code)"
	::= { cmroOmiEntry 35 }


cmroOmiSFP2ModuleType OBJECT-TYPE
	SYNTAX INTEGER
	{
		sfp1000BaseT(1),
		sfp1000BaseSX(2),
		sfp1000BaseLX(3),
		none (254),
		unknown(255)
	}
	ACCESS read-only
	STATUS mandatory
	DESCRIPTION
		"SFP module type.
		Enum type corresponding to accepted values in following two fields:
		1   1000BASE-T  copper,
		2   1000BASE-SX short wavelength,
		3   1000BASE-LX long wavelength,
		254 NONE
		255 UNKNOWN
		"
	::= { cmroOmiEntry 36 }

cmroOmiSFP2TranscType OBJECT-TYPE
	SYNTAX INTEGER
	ACCESS read-only
	STATUS mandatory
	DESCRIPTION
		"SFP transceiver type (0..255)"
	::= { cmroOmiEntry 37 }

cmroOmiSFP2TranscCode OBJECT-TYPE
	SYNTAX OCTET STRING (SIZE(8))
	ACCESS read-only
	STATUS mandatory
	DESCRIPTION
		"SFP transceiver code:
		accepted values are those corresponding to module type"
	::= { cmroOmiEntry 38 }

cmroOmiSFP2VendorName OBJECT-TYPE
	SYNTAX DisplayString(SIZE(16))
	ACCESS read-only
	STATUS mandatory
	DESCRIPTION
		"SFP vendor name"
	::= { cmroOmiEntry 39 }

cmroOmiSFP2VendorOUI OBJECT-TYPE
	SYNTAX OCTET STRING (SIZE(3))
	ACCESS read-only
	STATUS mandatory
	DESCRIPTION
		"SFP IEEE company ID"
	::= { cmroOmiEntry 40 }

cmroOmiSFP2VendorPartNo OBJECT-TYPE
	SYNTAX DisplayString(SIZE(16))
	ACCESS read-only
	STATUS mandatory
	DESCRIPTION
		"SFP vendor partition number"
	::= { cmroOmiEntry 41 }

cmroOmiSFP2VendorRevNo OBJECT-TYPE
	SYNTAX DisplayString(SIZE(4))
	ACCESS read-only
	STATUS mandatory
	DESCRIPTION
		"SFP vendor revision number"
	::= { cmroOmiEntry 42 }

cmroOmiSFP2VendorSerialNo OBJECT-TYPE
	SYNTAX DisplayString(SIZE(16))
	ACCESS read-only
	STATUS mandatory
	DESCRIPTION
		"SFP vendor serial number"
	::= { cmroOmiEntry 43 }

cmroOmiSFP2VendorDateCode OBJECT-TYPE
	SYNTAX OCTET STRING (SIZE(8))
	ACCESS read-only
	STATUS mandatory
	DESCRIPTION
		"SFP vendor date code
		YYMMDDLL (LL=vendor specific lot code)"
	::= { cmroOmiEntry 44 }

cmroOmiCESHwPartNo OBJECT-TYPE
	SYNTAX DisplayString(SIZE(20))
	ACCESS read-only
	STATUS mandatory
	DESCRIPTION
		"CES HW part number"
	::= { cmroOmiEntry 45 }

cmroOmiCESType OBJECT-TYPE
	SYNTAX INTEGER
	{
		none(1),
		thirtyTwoE1tcxo(2),
		thirtyTwoE1ocxo(3),
		unknown(254),
		unsupported(255)
	}
	ACCESS read-only
	STATUS mandatory
	DESCRIPTION
		"CES type:
		1	None	No CES available
		2	ThirtyTwoE1tcxo		32 x E1 with Temperature Compensated Crystal Oscillator
		3	ThirtyTwoE1ocxo		32 x E1 with Oven Compensated Crystal Oscillator
		254			unknown value
		255			unsupported variable for addressed device"
	::= { cmroOmiEntry 46 }

cmroOmiCESMACAddress OBJECT-TYPE
	SYNTAX OCTET STRING (SIZE(6))
	ACCESS read-only
	STATUS mandatory
	DESCRIPTION
		"Contains the MAC Address of CES
		Value of Byte 0..5	Meaning

		0x00 - 0xFD		MAC address
		all 0xFE		unknown value
		all 0xFF		unsupported variable"
	::= { cmroOmiEntry 47 }

cmroOmiCESSerialNo OBJECT-TYPE
	SYNTAX DisplayString(SIZE(5))
	ACCESS read-only
	STATUS mandatory
	DESCRIPTION
		"Serial number of CES"
	::= { cmroOmiEntry 48 }

--------------------------------------------------------------------------------
--	CM-RO	HDSL Regenerator
--------------------------------------------------------------------------------
cmroRegTable OBJECT-TYPE
	SYNTAX SEQUENCE OF CmroRegEntry
	ACCESS not-accessible
	STATUS mandatory
	DESCRIPTION ""
	::= { cmro 5 }

cmroRegEntry OBJECT-TYPE
	SYNTAX CmroRegEntry
	ACCESS not-accessible
	STATUS mandatory
	DESCRIPTION ""
	INDEX { cmroRegPortIndex, cmroRegLinkIndex }
	::= { cmroRegTable 1 }

CmroRegEntry ::=
	SEQUENCE
	{
		cmroRegPortIndex INTEGER,
		cmroRegLinkIndex INTEGER,
		cmroRegNumReg1 INTEGER,
		cmroRegNumReg2 INTEGER,
		cmroRegFabData1A DisplayString,
		cmroRegFwVers1A DisplayString,
		cmroRegFabData2A DisplayString,
		cmroRegFwVers2A DisplayString,
		cmroRegFabData1B DisplayString,
		cmroRegFwVers1B DisplayString,
		cmroRegFabData2B DisplayString,
		cmroRegFwVers2B DisplayString,
		cmroRegTipRingReversal1ALt INTEGER,
		cmroRegTipRingReversal1ANt INTEGER,
		cmroRegTipRingReversal2ALt INTEGER,
		cmroRegTipRingReversal2ANt INTEGER,
		cmroRegTipRingReversal1BLt INTEGER,
		cmroRegTipRingReversal1BNt INTEGER,
		cmroRegTipRingReversal2BLt INTEGER,
		cmroRegTipRingReversal2BNt INTEGER
	}

cmroRegPortIndex OBJECT-TYPE
	SYNTAX INTEGER
	ACCESS read-only
	STATUS mandatory
	DESCRIPTION
		"This variable addresses the port number of the proxy
		and is used as index for the other elements in the Table"
	::= { cmroRegEntry 1 }

cmroRegLinkIndex OBJECT-TYPE
	SYNTAX INTEGER
	ACCESS read-only
	STATUS mandatory
	DESCRIPTION
		"This variable addresses the slot number of the OMI sub-rack
		and is used as index for the other elements in the Table"
	::= { cmroRegEntry 2 }

cmroRegNumReg1 OBJECT-TYPE
	SYNTAX INTEGER
	{
		none(1),
		one(2),
		two(3),
		unknown(254),
		unsupported(255)
	}
	ACCESS read-only
	STATUS mandatory
	DESCRIPTION
		"Number of Regenerators in HDSL Path 1.
		1	None	No Regenerators
		2	One	One Regenerator (A)
		3	Two	Two Regenerators (A and B)
		254		unknown value
		255		unsupported variable for addressed device"
	::= { cmroRegEntry 3 }

cmroRegNumReg2 OBJECT-TYPE
	SYNTAX INTEGER
	{
		none(1),
		one(2),
		two(3),
		unknown(254),
		unsupported(255)
	}
	ACCESS read-only
	STATUS mandatory
	DESCRIPTION
		"Number of Regenerators in HDSL Path 2.
		1	None	No Regenerators
		2	One	One Regenerator (A)
		3	Two	Two Regenerators (A and B)
		254		unknown value
		255		unsupported variable for addressed device"
	::= { cmroRegEntry 4 }

cmroRegFabData1A OBJECT-TYPE
	SYNTAX DisplayString(SIZE(20))
	ACCESS read-only
	STATUS mandatory
	DESCRIPTION
		"Fabrication Data of Regenerator Section A in HDSL Path 1"
	::= { cmroRegEntry 5 }

cmroRegFwVers1A OBJECT-TYPE
	SYNTAX DisplayString
	ACCESS read-only
	STATUS mandatory
	DESCRIPTION
		"Firmware Version of Regenerator Section A in HDSL Path 1"
	::= { cmroRegEntry 6 }

cmroRegFabData2A OBJECT-TYPE
	SYNTAX DisplayString(SIZE(20))
	ACCESS read-only
	STATUS mandatory
	DESCRIPTION
		"Fabrication Data of Regenerator Section A in HDSL Path 2"
	::= { cmroRegEntry 7 }

cmroRegFwVers2A OBJECT-TYPE
	SYNTAX DisplayString
	ACCESS read-only
	STATUS mandatory
	DESCRIPTION
		"Firmware Version of Regenerator Section A in HDSL Path 2"
	::= { cmroRegEntry 8 }

cmroRegFabData1B OBJECT-TYPE
	SYNTAX DisplayString(SIZE(20))
	ACCESS read-only
	STATUS mandatory
	DESCRIPTION
		"Fabrication Data of Regenerator Section B in HDSL Path 1"
	::= { cmroRegEntry 9 }

cmroRegFwVers1B OBJECT-TYPE
	SYNTAX DisplayString
	ACCESS read-only
	STATUS mandatory
	DESCRIPTION
		"Firmware Version of Regenerator Section B in HDSL Path 1"
	::= { cmroRegEntry 10 }

cmroRegFabData2B OBJECT-TYPE
	SYNTAX DisplayString(SIZE(20))
	ACCESS read-only
	STATUS mandatory
	DESCRIPTION
		"Fabrication Data of Regenerator Section B in HDSL Path 2"
	::= { cmroRegEntry 11 }

cmroRegFwVers2B OBJECT-TYPE
	SYNTAX DisplayString
	ACCESS read-only
	STATUS mandatory
	DESCRIPTION
		"Firmware Version of Regenerator Section B in HDSL Path 2"
	::= { cmroRegEntry 12 }

cmroRegTipRingReversal1ALt OBJECT-TYPE
	SYNTAX INTEGER
	{
		unknown(254),
		unsupported(255)
	}
	ACCESS read-only
	STATUS mandatory
	DESCRIPTION
		"Unused variable. Only used for compatibility reasons.
		Refer to cmroSruTipRingReversalLt and cmroSruTipRingReversalNt.
		 254		unknown value
		 255		unsupported variable for addressed device"
	::= { cmroRegEntry 13  }

cmroRegTipRingReversal1ANt OBJECT-TYPE
	SYNTAX INTEGER
	{
		unknown(254),
		unsupported(255)
	}
	ACCESS read-only
	STATUS mandatory
	DESCRIPTION
		"Unused variable. Only used for compatibility reasons.
		Refer to cmroSruTipRingReversalLt and cmroSruTipRingReversalNt.
		 254		unknown value
		 255		unsupported variable for addressed device"
	::= { cmroRegEntry 14 }

cmroRegTipRingReversal2ALt OBJECT-TYPE
	SYNTAX INTEGER
	{
		unknown(254),
		unsupported(255)
	}
	ACCESS read-only
	STATUS mandatory
	DESCRIPTION
		"Unused variable. Only used for compatibility reasons.
		Refer to cmroSruTipRingReversalLt and cmroSruTipRingReversalNt.
		 254		unknown value
		 255		unsupported variable for addressed device"
	::= { cmroRegEntry 15 }

cmroRegTipRingReversal2ANt OBJECT-TYPE
	SYNTAX INTEGER
	{
		unknown(254),
		unsupported(255)
	}
	ACCESS read-only
	STATUS mandatory
	DESCRIPTION
		"Unused variable. Only used for compatibility reasons.
		Refer to cmroSruTipRingReversalLt and cmroSruTipRingReversalNt.
		 254		unknown value
		 255		unsupported variable for addressed device"
	::= { cmroRegEntry 16 }

cmroRegTipRingReversal1BLt OBJECT-TYPE
	SYNTAX INTEGER
	{
		unknown(254),
		unsupported(255)
	}
	ACCESS read-only
	STATUS mandatory
	DESCRIPTION
		"Unused variable. Only used for compatibility reasons.
		Refer to cmroSruTipRingReversalLt and cmroSruTipRingReversalNt.
		 254		unknown value
		 255		unsupported variable for addressed device"
	::= { cmroRegEntry 17 }

cmroRegTipRingReversal1BNt OBJECT-TYPE
	SYNTAX INTEGER
	{
		unknown(254),
		unsupported(255)
	}
	ACCESS read-only
	STATUS mandatory
	DESCRIPTION
		"Unused variable. Only used for compatibility reasons.
		Refer to cmroSruTipRingReversalLt and cmroSruTipRingReversalNt.
		 254		unknown value
		 255		unsupported variable for addressed device"
	::= { cmroRegEntry 18 }

cmroRegTipRingReversal2BLt OBJECT-TYPE
	SYNTAX INTEGER
	{
		unknown(254),
		unsupported(255)
	}
	ACCESS read-only
	STATUS mandatory
	DESCRIPTION
		"Unused variable. Only used for compatibility reasons.
		Refer to cmroSruTipRingReversalLt and cmroSruTipRingReversalNt.
		 254		unknown value
		 255		unsupported variable for addressed device"
	::= { cmroRegEntry 19 }

cmroRegTipRingReversal2BNt OBJECT-TYPE
	SYNTAX INTEGER
	{
		unknown(254),
		unsupported(255)
	}
	ACCESS read-only
	STATUS mandatory
	DESCRIPTION
		"Unused variable. Only used for compatibility reasons.
		Refer to cmroSruTipRingReversalLt and cmroSruTipRingReversalNt.
		 254		unknown value
		 255		unsupported variable for addressed device"
	::= { cmroRegEntry 20 }


--------------------------------------------------------------------------------
--	CM-RO	SHDSL Regenerator
--------------------------------------------------------------------------------
cmroSruTable OBJECT-TYPE
	SYNTAX SEQUENCE OF CmroSruEntry
	ACCESS not-accessible
	STATUS mandatory
	DESCRIPTION ""
	::= { cmro 6 }

cmroSruEntry OBJECT-TYPE
	SYNTAX CmroSruEntry
	ACCESS not-accessible
	STATUS mandatory
	DESCRIPTION ""
	INDEX { cmroSruPortIndex, cmroSruLinkIndex, cmroSruRegIndex }
	::= { cmroSruTable 1 }

CmroSruEntry ::=
	SEQUENCE
	{
		cmroSruPortIndex INTEGER,
		cmroSruLinkIndex INTEGER,
		cmroSruRegIndex INTEGER,
		cmroSruFabData DisplayString,
		cmroSruActFwType DisplayString,
		cmroSruActFwVers DisplayString,
		cmroSruPasBankState INTEGER,
		cmroSruPasFwType DisplayString,
		cmroSruPasFwVers DisplayString,
		cmroSruTipRingReversalLt INTEGER,
		cmroSruTipRingReversalNt INTEGER,
		cmroSruRedundantlyPowered INTEGER,
		cmroSruPowerPassThrough INTEGER,
		cmroSruSerialNumber DisplayString,
		cmroSruHwManufacturingDate DisplayString
	}

cmroSruPortIndex OBJECT-TYPE
	SYNTAX INTEGER
	ACCESS read-only
	STATUS mandatory
	DESCRIPTION
		"This variable addresses the port number of the proxy
		and is used as index for the other elements in the Table"
	::= { cmroSruEntry 1 }

cmroSruLinkIndex OBJECT-TYPE
	SYNTAX INTEGER
	ACCESS read-only
	STATUS mandatory
	DESCRIPTION
		"This variable addresses the slot number of the OMI sub-rack
		and is used as index for the other elements in the Table"
	::= { cmroSruEntry 2 }

cmroSruRegIndex OBJECT-TYPE
	SYNTAX INTEGER
	{
		reg11(3),
		reg12(4),
		reg21(5),
		reg22(6),
		reg31(7),
		reg32(8),
		reg41(9),
		reg42(10),
		reg51(11),
		reg52(12),
		reg61(13),
		reg62(14),
		reg71(15),
		reg72(16),
		reg81(17),
		reg82(18),
		reg13(19),
		reg14(20),
		reg23(21),
		reg24(22),
		reg33(23),
		reg34(24),
		reg43(25),
		reg44(26),
		reg53(27),
		reg54(28),
		reg63(29),
		reg64(30),
		reg73(31),
		reg74(32),
		reg83(33),
		reg84(34)
	}
	ACCESS read-only
	STATUS mandatory
	DESCRIPTION
		"This variable addresses the regenerator device and is
		used as index for the other elements in the Table"
	::= { cmroSruEntry 3 }

cmroSruFabData OBJECT-TYPE
	SYNTAX DisplayString(SIZE(20))
	ACCESS read-only
	STATUS mandatory
	DESCRIPTION
		"Fabrication Data of Regenerator"
	::= { cmroSruEntry 5 }

cmroSruActFwType OBJECT-TYPE
	SYNTAX DisplayString
	ACCESS read-only
	STATUS mandatory
	DESCRIPTION
		"Active firmware Type of Regenerator"
	::= { cmroSruEntry 6 }

cmroSruActFwVers OBJECT-TYPE
	SYNTAX DisplayString
	ACCESS read-only
	STATUS mandatory
	DESCRIPTION
		"Active firmware Version of Regenerator"
	::= { cmroSruEntry 7 }

cmroSruPasBankState OBJECT-TYPE
	SYNTAX INTEGER
	{
		empty(1),
		loaded(2),
		unknown(254),
		unsupported(255)
	}
	ACCESS read-only
	STATUS mandatory
	DESCRIPTION
		"State of passive firmware bank
		1	Empty	contains no firmware
		2	Loaded	contains a valid firmware
		254		unknown value
		255		unsupported variable for addressed device"
	::= { cmroSruEntry 8 }

cmroSruPasFwType OBJECT-TYPE
	SYNTAX DisplayString
	ACCESS read-only
	STATUS mandatory
	DESCRIPTION
		"Passive firmware Type of Regenerator"
	::= { cmroSruEntry 9 }

cmroSruPasFwVers OBJECT-TYPE
	SYNTAX DisplayString
	ACCESS read-only
	STATUS mandatory
	DESCRIPTION
		"Passive firmware Version of Regenerator"
	::= { cmroSruEntry 10 }

cmroSruTipRingReversalLt OBJECT-TYPE
	SYNTAX INTEGER
	{
		no(1),
		yes(2),
		unknown(254),
		unsupported(255)
	}
	ACCESS read-only
	STATUS mandatory
	DESCRIPTION
		"Indicates whether tip-ring reversal has been detected and compensated
		 for in direction of the LT
		 1	No	Reversal not detected
		 2	Yes	Reversal detected and compensated for
		 254		unknown value
		 255		unsupported variable for addressed device"
	::= { cmroSruEntry 11  }

cmroSruTipRingReversalNt OBJECT-TYPE
	SYNTAX INTEGER
	{
		no(1),
		yes(2),
		unknown(254),
		unsupported(255)
	}
	ACCESS read-only
	STATUS mandatory
	DESCRIPTION
		"Indicates whether tip-ring reversal has been detected and compensated
		 for in direction of the NT
		 1	No	Reversal not detected
		 2	Yes	Reversal detected and compensated for
		 254		unknown value
		 255		unsupported variable for addressed device"
	::= { cmroSruEntry 12 }

cmroSruRedundantlyPowered OBJECT-TYPE
	SYNTAX INTEGER
	{
		no(1),
		yes(2),
		unknown(254),
		unsupported(255)
	}
	ACCESS read-only
	STATUS mandatory
	DESCRIPTION
		"Indicates whether the regenerator is being redundantly powered
		 1	No	Regenerator is not being redundantly powered
		 2	Yes	Regenerator is being redundantly powered
		 254		unknown value
		 255		unsupported variable for addressed device"
	::= { cmroSruEntry 13 }

cmroSruPowerPassThrough OBJECT-TYPE
	SYNTAX INTEGER
	{
		no(1),
		yes(2),
		unknown(254),
		unsupported(255)
	}
	ACCESS read-only
	STATUS mandatory
	DESCRIPTION
		"Indicates whether the regenerator is passing power
		through to the next regenerator section.
		 1	No	Regenerator is not passing through power
		 2	Yes	Regenerator is passing through power
		 254		unknown value
		 255		unsupported variable for addressed device"
	::= { cmroSruEntry 14 }

cmroSruSerialNumber OBJECT-TYPE
	SYNTAX DisplayString(SIZE(20))
	ACCESS read-only
	STATUS mandatory
	DESCRIPTION
		"Serial number of regenerator"
	::= { cmroSruEntry 15 }

cmroSruHwManufacturingDate OBJECT-TYPE
	SYNTAX DisplayString
	ACCESS read-only
	STATUS mandatory
	DESCRIPTION
		"Manufacturing Date of the motherboard"
	::= { cmroSruEntry 16 }

--------------------------------------------------------------------------------
--	CM-RO	Card Token
--------------------------------------------------------------------------------
cmroCardTokenTable OBJECT-TYPE
	SYNTAX SEQUENCE OF CmroCardTokenEntry
	ACCESS not-accessible
	STATUS mandatory
	DESCRIPTION ""
	::= { cmro 7 }

cmroCardTokenEntry OBJECT-TYPE
	SYNTAX CmroCardTokenEntry
	ACCESS not-accessible
	STATUS mandatory
	DESCRIPTION ""
	INDEX { cmroCardTokenPortIndex, cmroCardTokenLinkIndex }
	::= { cmroCardTokenTable 1 }

CmroCardTokenEntry ::=
	SEQUENCE
	{
		cmroCardTokenPortIndex INTEGER,
		cmroCardTokenLinkIndex INTEGER,
		cmroCardTokenResId1 INTEGER,
		cmroCardTokenResId2 INTEGER,
		cmroCardTokenResId3 INTEGER,
		cmroCardTokenResId4 INTEGER
	}

cmroCardTokenPortIndex OBJECT-TYPE
	SYNTAX INTEGER
	ACCESS read-only
	STATUS mandatory
	DESCRIPTION
		"This variable addresses the port number of the proxy
		and is used as index for the other elements in the Table"
	::= { cmroCardTokenEntry 1 }

cmroCardTokenLinkIndex OBJECT-TYPE
	SYNTAX INTEGER
	ACCESS read-only
	STATUS mandatory
	DESCRIPTION
		"This variable addresses the slot number of the OMI sub-rack
		and is used as index for the other elements in the Table"
	::= { cmroCardTokenEntry 2 }

cmroCardTokenResId1 OBJECT-TYPE
	SYNTAX INTEGER
	{
		available(1),
		lineint(2),
		lct(3),
		unknown(254),
		unsupported(255)
	}
	ACCESS read-only
	STATUS mandatory
	DESCRIPTION
		"Indicates who is in posession of the reservation token for system one.
		1	Available	The token is free
		2	Lineint		The token is given to the LineIntegrator
		3	Lct		The token is given to the Local Craft Terminal (LCT)
		254			unknown value
		255			unsupported variable for the addressed device"
	::= { cmroCardTokenEntry 3 }

cmroCardTokenResId2 OBJECT-TYPE
	SYNTAX INTEGER
	{
		available(1),
		lineint(2),
		lct(3),
		unknown(254),
		unsupported(255)
	}
	ACCESS read-only
	STATUS mandatory
	DESCRIPTION
		"Indicates who is in posession of the reservation token for system two.
		1	Available	The token is free
		2	Lineint		The token is given to the LineIntegrator
		3	Lct		The token is given to the Local Craft Terminal (LCT)
		254			unknown value
		255			unsupported variable for the addressed device"
	::= { cmroCardTokenEntry 4 }

cmroCardTokenResId3 OBJECT-TYPE
	SYNTAX INTEGER
	{
		available(1),
		lineint(2),
		lct(3),
		unknown(254),
		unsupported(255)
	}
	ACCESS read-only
	STATUS mandatory
	DESCRIPTION
		"Indicates who is in posession of the reservation token for system three.
		1	Available	The token is free
		2	Lineint		The token is given to the LineIntegrator
		3	Lct		The token is given to the Local Craft Terminal (LCT)
		254			unknown value
		255			unsupported variable for the addressed device"
	::= { cmroCardTokenEntry 5 }

cmroCardTokenResId4 OBJECT-TYPE
	SYNTAX INTEGER
	{
		available(1),
		lineint(2),
		lct(3),
		unknown(254),
		unsupported(255)
	}
	ACCESS read-only
	STATUS mandatory
	DESCRIPTION
		"Indicates who is in posession of the reservation token for system four.
		1	Available	The token is free
		2	Lineint		The token is given to the LineIntegrator
		3	Lct		The token is given to the Local Craft Terminal (LCT)
		254			unknown value
		255			unsupported variable for the addressed device"
	::= { cmroCardTokenEntry 6 }

--------------------------------------------------------------------------------  
--	CM-RO	sub OIDs
--------------------------------------------------------------------------------  
	cmroLocalInventory	OBJECT IDENTIFIER ::= { cmro 8 }
	cmroFarInventory	OBJECT IDENTIFIER ::= { cmro 9 }
	cmroSruInventory	OBJECT IDENTIFIER ::= { cmro 10 }

--------------------------------------------------------------------------------  
--	CM-RO	Local Inventory FrontPanel
--------------------------------------------------------------------------------  
cmroLocalInventoryFpTable OBJECT-TYPE
	SYNTAX SEQUENCE OF CmroLocalInventoryFpEntry
	ACCESS not-accessible
	STATUS mandatory
	DESCRIPTION ""
	::= { cmroLocalInventory 1 }

cmroLocalInventoryFpEntry OBJECT-TYPE
	SYNTAX CmroLocalInventoryFpEntry
	ACCESS not-accessible
	STATUS mandatory
	DESCRIPTION ""
	INDEX { cmroLocalInventoryFpPortIndex, cmroLocalInventoryFpLinkIndex }
	::= { cmroLocalInventoryFpTable 1 }

CmroLocalInventoryFpEntry ::=
	SEQUENCE
	{
		cmroLocalInventoryFpPortIndex INTEGER,
		cmroLocalInventoryFpLinkIndex INTEGER,
		cmroLocalInventoryFpModule1Type INTEGER,
		cmroLocalInventoryFpModule2Type INTEGER,
		cmroLocalInventoryFpModule3Type INTEGER,
		cmroLocalInventoryFpModule4Type INTEGER,
		cmroLocalInventoryFpModule5Type INTEGER,
		cmroLocalInventoryFpModule6Type INTEGER,
		cmroLocalInventoryFpModule1FabData DisplayString,
		cmroLocalInventoryFpModule2FabData DisplayString,
		cmroLocalInventoryFpModule3FabData DisplayString,
		cmroLocalInventoryFpModule4FabData DisplayString,
		cmroLocalInventoryFpModule5FabData DisplayString,
		cmroLocalInventoryFpModule6FabData DisplayString
	}

cmroLocalInventoryFpPortIndex OBJECT-TYPE
	SYNTAX INTEGER
	ACCESS read-only
	STATUS mandatory
	DESCRIPTION
		"This variable addresses the port number of the proxy
		and is used as index for the other elements in the Table"
	::= { cmroLocalInventoryFpEntry 1 }

cmroLocalInventoryFpLinkIndex OBJECT-TYPE
	SYNTAX INTEGER
	ACCESS read-only
	STATUS mandatory
	DESCRIPTION
		"This variable addresses the slot number of the OMI sub-rack
		and is used as index for the other elements in the Table"
	::= { cmroLocalInventoryFpEntry 2 }

cmroLocalInventoryFpModule1Type OBJECT-TYPE
	SYNTAX INTEGER
	{
		none(1),
		dce(2),
		dte(3),
		tenBaseT(4),
		abar(5),
		unknown(254),
		unsupported(255)
	}
	ACCESS read-only
	STATUS mandatory
	DESCRIPTION
		"Type of Front Panel Module 1
		1	None		No module
		2	DCE		DCE module
		3	DTE		DTE module
		4	10Base-T	10Base-T Ethernet module
		5	ABAR		Advanced Bridge and Router module
		254			unknown value
		255			unsupported variable for addressed device"
	::= { cmroLocalInventoryFpEntry 3 }

cmroLocalInventoryFpModule2Type OBJECT-TYPE
	SYNTAX INTEGER
	{
		none(1),
		dce(2),
		dte(3),
		tenBaseT(4),
		abar(5),
		unknown(254),
		unsupported(255)
	}
	ACCESS read-only
	STATUS mandatory
	DESCRIPTION
		"Type of Front Panel Module 2
		1	None		No module
		2	DCE		DCE module
		3	DTE		DTE module
		4	10Base-T	10Base-T Ethernet module
		5	ABAR		Advanced Bridge and Router module
		254			unknown value
		255			unsupported variable for addressed device"
	::= { cmroLocalInventoryFpEntry 4 }

cmroLocalInventoryFpModule3Type OBJECT-TYPE
	SYNTAX INTEGER
	{
		none(1),
		dce(2),
		dte(3),
		tenBaseT(4),
		abar(5),
		unknown(254),
		unsupported(255)
	}
	ACCESS read-only
	STATUS mandatory
	DESCRIPTION
		"Type of Front Panel Module 3
		1	None		No module
		2	DCE		DCE module
		3	DTE		DTE module
		4	10Base-T	10Base-T Ethernet module
		5	ABAR		Advanced Bridge and Router module
		254			unknown value
		255			unsupported variable for addressed device"
	::= { cmroLocalInventoryFpEntry 5 }

cmroLocalInventoryFpModule4Type OBJECT-TYPE
	SYNTAX INTEGER
	{
		none(1),
		dce(2),
		dte(3),
		tenBaseT(4),
		abar(5),
		unknown(254),
		unsupported(255)
	}
	ACCESS read-only
	STATUS mandatory
	DESCRIPTION
		"Type of Front Panel Module 4
		1	None		No module
		2	DCE		DCE module
		3	DTE		DTE module
		4	10Base-T	10Base-T Ethernet module
		5	ABAR		Advanced Bridge and Router module
		254			unknown value
		255			unsupported variable for addressed device"
	::= { cmroLocalInventoryFpEntry 6 }

cmroLocalInventoryFpModule5Type OBJECT-TYPE
	SYNTAX INTEGER
	{
		none(1),
		dce(2),
		dte(3),
		tenBaseT(4),
		abar(5),
		unknown(254),
		unsupported(255)
	}
	ACCESS read-only
	STATUS mandatory
	DESCRIPTION
		"Type of Front Panel Module 5
		1	None		No module
		2	DCE		DCE module
		3	DTE		DTE module
		4	10Base-T	10Base-T Ethernet module
		5	ABAR		Advanced Bridge and Router module
		254			unknown value
		255			unsupported variable for addressed device"
	::= { cmroLocalInventoryFpEntry 7 }

cmroLocalInventoryFpModule6Type OBJECT-TYPE
	SYNTAX INTEGER
	{
		none(1),
		dce(2),
		dte(3),
		tenBaseT(4),
		abar(5),
		unknown(254),
		unsupported(255)
	}
	ACCESS read-only
	STATUS mandatory
	DESCRIPTION
		"Type of Front Panel Module 6
		1	None		No module
		2	DCE		DCE module
		3	DTE		DTE module
		4	10Base-T	10Base-T Ethernet module
		5	ABAR		Advanced Bridge and Router module
		254			unknown value
		255			unsupported variable for addressed device"
	::= { cmroLocalInventoryFpEntry 8 }

cmroLocalInventoryFpModule1FabData OBJECT-TYPE
	SYNTAX DisplayString(SIZE(20))
	ACCESS read-only
	STATUS mandatory
	DESCRIPTION
		"Fabrication Data of Front Panel Module 1"
	::= { cmroLocalInventoryFpEntry 9 }

cmroLocalInventoryFpModule2FabData OBJECT-TYPE
	SYNTAX DisplayString(SIZE(20))
	ACCESS read-only
	STATUS mandatory
	DESCRIPTION
		"Fabrication Data of Front Panel Module 2"
	::= { cmroLocalInventoryFpEntry 10 }

cmroLocalInventoryFpModule3FabData OBJECT-TYPE
	SYNTAX DisplayString(SIZE(20))
	ACCESS read-only
	STATUS mandatory
	DESCRIPTION
		"Fabrication Data of Front Panel Module 3"
	::= { cmroLocalInventoryFpEntry 11 }

cmroLocalInventoryFpModule4FabData OBJECT-TYPE
	SYNTAX DisplayString(SIZE(20))
	ACCESS read-only
	STATUS mandatory
	DESCRIPTION
		"Fabrication Data of Front Panel Module 4"
	::= { cmroLocalInventoryFpEntry 12 }

cmroLocalInventoryFpModule5FabData OBJECT-TYPE
	SYNTAX DisplayString(SIZE(20))
	ACCESS read-only
	STATUS mandatory
	DESCRIPTION
		"Fabrication Data of Front Panel Module 5"
	::= { cmroLocalInventoryFpEntry 13 }

cmroLocalInventoryFpModule6FabData OBJECT-TYPE
	SYNTAX DisplayString(SIZE(20))
	ACCESS read-only
	STATUS mandatory
	DESCRIPTION
		"Fabrication Data of Front Panel Module 6"
	::= { cmroLocalInventoryFpEntry 14 }

--------------------------------------------------------------------------------  
--	CM-RO	Local Inventory Info
--------------------------------------------------------------------------------  
cmroLocalInventoryInfoTable OBJECT-TYPE
	SYNTAX SEQUENCE OF CmroLocalInventoryInfoEntry
	ACCESS not-accessible
	STATUS mandatory
	DESCRIPTION ""
	::= { cmroLocalInventory 2 }

cmroLocalInventoryInfoEntry OBJECT-TYPE
	SYNTAX CmroLocalInventoryInfoEntry
	ACCESS not-accessible
	STATUS mandatory
	DESCRIPTION ""
	INDEX { cmroLocalInventoryInfoPortIndex, cmroLocalInventoryInfoLinkIndex }
	::= { cmroLocalInventoryInfoTable 1 }

CmroLocalInventoryInfoEntry ::=
	SEQUENCE
	{
		cmroLocalInventoryInfoPortIndex INTEGER,
		cmroLocalInventoryInfoLinkIndex INTEGER,
		cmroLocalInventoryInfoString1Type INTEGER,
		cmroLocalInventoryInfoString2Type INTEGER,
		cmroLocalInventoryInfoString3Type INTEGER,
		cmroLocalInventoryInfoString4Type INTEGER,
		cmroLocalInventoryInfoString5Type INTEGER,
		cmroLocalInventoryInfoString1 DisplayString,
		cmroLocalInventoryInfoString2 DisplayString,
		cmroLocalInventoryInfoString3 DisplayString,
		cmroLocalInventoryInfoString4 DisplayString,
		cmroLocalInventoryInfoString5 DisplayString
	}

cmroLocalInventoryInfoPortIndex OBJECT-TYPE
	SYNTAX INTEGER
	ACCESS read-only
	STATUS mandatory
	DESCRIPTION
		"This variable addresses the port number of the proxy
		and is used as index for the other elements in the Table"
	::= { cmroLocalInventoryInfoEntry 1 }

cmroLocalInventoryInfoLinkIndex OBJECT-TYPE
	SYNTAX INTEGER
	ACCESS read-only
	STATUS mandatory
	DESCRIPTION
		"This variable addresses the slot number of the OMI sub-rack
		and is used as index for the other elements in the Table"
	::= { cmroLocalInventoryInfoEntry 2 }

cmroLocalInventoryInfoString1Type OBJECT-TYPE
	SYNTAX INTEGER
	{
		empty(1),
		dslChip(2),
		dslFirmwareLoad(3),
		fpgaLoad(4),
		ethWanChip(5),
		l2sChip(6),
		bootLoaderVersion(7),
		unknown(254),
		unsupported(255)
	}
	ACCESS read-only
	STATUS mandatory
	DESCRIPTION
		"Type of InfoString 1
		1	Empty			InfoString is empty
		2	DSL Chip		InfoString is related to the DSL Chip
		3	DSL Firmware Load	InfoString is related to the DSL Firmware Load
		4	FPGA Load		InfoString is related to the FPGA Load
		5	ETH WAN Chip		InfoString is related to the Ethernet WAN Chip
		5	L2S Chip		InfoString is related to the Layer2 Switch Chip
		254				unknown value
		255				unsupported variable for addressed device"
	::= { cmroLocalInventoryInfoEntry 3 }

cmroLocalInventoryInfoString2Type OBJECT-TYPE
	SYNTAX INTEGER
	{
		empty(1),
		dslChip(2),
		dslFirmwareLoad(3),
		fpgaLoad(4),
		ethWanChip(5),
		l2sChip(6),
		bootLoaderVersion(7),
		unknown(254),
		unsupported(255)
	}
	ACCESS read-only
	STATUS mandatory
	DESCRIPTION
		"Type of InfoString 2
		1	Empty			InfoString is empty
		2	DSL Chip		InfoString is related to the DSL Chip
		3	DSL Firmware Load	InfoString is related to the DSL Firmware Load
		4	FPGA Load		InfoString is related to the FPGA Load
		5	ETH WAN Chip		InfoString is related to the Ethernet WAN Chip
		5	L2S Chip		InfoString is related to the Layer2 Switch Chip
		254				unknown value
		255				unsupported variable for addressed device"
	::= { cmroLocalInventoryInfoEntry 4 }

cmroLocalInventoryInfoString3Type OBJECT-TYPE
	SYNTAX INTEGER
	{
		empty(1),
		dslChip(2),
		dslFirmwareLoad(3),
		fpgaLoad(4),
		ethWanChip(5),
		l2sChip(6),
		bootLoaderVersion(7),
		unknown(254),
		unsupported(255)
	}
	ACCESS read-only
	STATUS mandatory
	DESCRIPTION
		"Type of InfoString 3
		1	Empty			InfoString is empty
		2	DSL Chip		InfoString is related to the DSL Chip
		3	DSL Firmware Load	InfoString is related to the DSL Firmware Load
		4	FPGA Load		InfoString is related to the FPGA Load
		5	ETH WAN Chip		InfoString is related to the Ethernet WAN Chip
		5	L2S Chip		InfoString is related to the Layer2 Switch Chip
		254				unknown value
		255				unsupported variable for addressed device"
	::= { cmroLocalInventoryInfoEntry 5 }

cmroLocalInventoryInfoString4Type OBJECT-TYPE
	SYNTAX INTEGER
	{
		empty(1),
		dslChip(2),
		dslFirmwareLoad(3),
		fpgaLoad(4),
		ethWanChip(5),
		l2sChip(6),
		bootLoaderVersion(7),
		unknown(254),
		unsupported(255)
	}
	ACCESS read-only
	STATUS mandatory
	DESCRIPTION
		"Type of InfoString 4
		1	Empty			InfoString is empty
		2	DSL Chip		InfoString is related to the DSL Chip
		3	DSL Firmware Load	InfoString is related to the DSL Firmware Load
		4	FPGA Load		InfoString is related to the FPGA Load
		5	ETH WAN Chip		InfoString is related to the Ethernet WAN Chip
		5	L2S Chip		InfoString is related to the Layer2 Switch Chip
		254				unknown value
		255				unsupported variable for addressed device"
	::= { cmroLocalInventoryInfoEntry 6 }

cmroLocalInventoryInfoString5Type OBJECT-TYPE
	SYNTAX INTEGER
	{
		empty(1),
		dslChip(2),
		dslFirmwareLoad(3),
		fpgaLoad(4),
		ethWanChip(5),
		l2sChip(6),
		bootLoaderVersion(7),
		unknown(254),
		unsupported(255)
	}
	ACCESS read-only
	STATUS mandatory
	DESCRIPTION
		"Type of InfoString 5
		1	Empty			InfoString is empty
		2	DSL Chip		InfoString is related to the DSL Chip
		3	DSL Firmware Load	InfoString is related to the DSL Firmware Load
		4	FPGA Load		InfoString is related to the FPGA Load
		5	ETH WAN Chip		InfoString is related to the Ethernet WAN Chip
		5	L2S Chip		InfoString is related to the Layer2 Switch Chip
		254				unknown value
		255				unsupported variable for addressed device"
	::= { cmroLocalInventoryInfoEntry 7 }

cmroLocalInventoryInfoString1 OBJECT-TYPE
	SYNTAX DisplayString(SIZE(25))
	ACCESS read-only
	STATUS mandatory
	DESCRIPTION
		"InfoString 1"
	::= { cmroLocalInventoryInfoEntry 8 }

cmroLocalInventoryInfoString2 OBJECT-TYPE
	SYNTAX DisplayString(SIZE(25))
	ACCESS read-only
	STATUS mandatory
	DESCRIPTION
		"InfoString 2"
	::= { cmroLocalInventoryInfoEntry 9 }

cmroLocalInventoryInfoString3 OBJECT-TYPE
	SYNTAX DisplayString(SIZE(25))
	ACCESS read-only
	STATUS mandatory
	DESCRIPTION
		"InfoString 3"
	::= { cmroLocalInventoryInfoEntry 10 }

cmroLocalInventoryInfoString4 OBJECT-TYPE
	SYNTAX DisplayString(SIZE(25))
	ACCESS read-only
	STATUS mandatory
	DESCRIPTION
		"InfoString 4"
	::= { cmroLocalInventoryInfoEntry 11 }

cmroLocalInventoryInfoString5 OBJECT-TYPE
	SYNTAX DisplayString(SIZE(25))
	ACCESS read-only
	STATUS mandatory
	DESCRIPTION
		"InfoString 5"
	::= { cmroLocalInventoryInfoEntry 12 }

--------------------------------------------------------------------------------  
--	CM-RO	Far Inventory FrontPanel
--------------------------------------------------------------------------------  
cmroFarInventoryFpTable OBJECT-TYPE
	SYNTAX SEQUENCE OF CmroFarInventoryFpEntry
	ACCESS not-accessible
	STATUS mandatory
	DESCRIPTION ""
	::= { cmroFarInventory 1 }

cmroFarInventoryFpEntry OBJECT-TYPE
	SYNTAX CmroFarInventoryFpEntry
	ACCESS not-accessible
	STATUS mandatory
	DESCRIPTION ""
	INDEX { cmroFarInventoryFpPortIndex, cmroFarInventoryFpLinkIndex }
	::= { cmroFarInventoryFpTable 1 }

CmroFarInventoryFpEntry ::=
	SEQUENCE
	{
		cmroFarInventoryFpPortIndex INTEGER,
		cmroFarInventoryFpLinkIndex INTEGER,
		cmroFarInventoryFpModule1Type INTEGER,
		cmroFarInventoryFpModule2Type INTEGER,
		cmroFarInventoryFpModule3Type INTEGER,
		cmroFarInventoryFpModule4Type INTEGER,
		cmroFarInventoryFpModule5Type INTEGER,
		cmroFarInventoryFpModule6Type INTEGER,
		cmroFarInventoryFpModule1FabData DisplayString,
		cmroFarInventoryFpModule2FabData DisplayString,
		cmroFarInventoryFpModule3FabData DisplayString,
		cmroFarInventoryFpModule4FabData DisplayString,
		cmroFarInventoryFpModule5FabData DisplayString,
		cmroFarInventoryFpModule6FabData DisplayString
	}

cmroFarInventoryFpPortIndex OBJECT-TYPE
	SYNTAX INTEGER
	ACCESS read-only
	STATUS mandatory
	DESCRIPTION
		"This variable addresses the port number of the proxy
		and is used as index for the other elements in the Table"
	::= { cmroFarInventoryFpEntry 1 }

cmroFarInventoryFpLinkIndex OBJECT-TYPE
	SYNTAX INTEGER
	ACCESS read-only
	STATUS mandatory
	DESCRIPTION
		"This variable addresses the slot number of the OMI sub-rack
		and is used as index for the other elements in the Table"
	::= { cmroFarInventoryFpEntry 2 }

cmroFarInventoryFpModule1Type OBJECT-TYPE
	SYNTAX INTEGER
	{
		none(1),
		dce(2),
		dte(3),
		tenBaseT(4),
		abar(5),
		unknown(254),
		unsupported(255)
	}
	ACCESS read-only
	STATUS mandatory
	DESCRIPTION
		"Type of Front Panel Module 1
		1	None		No module
		2	DCE		DCE module
		3	DTE		DTE module
		4	10Base-T	10Base-T Ethernet module
		5	ABAR		Advanced Bridge and Router module
		254			unknown value
		255			unsupported variable for addressed device"
	::= { cmroFarInventoryFpEntry 3 }

cmroFarInventoryFpModule2Type OBJECT-TYPE
	SYNTAX INTEGER
	{
		none(1),
		dce(2),
		dte(3),
		tenBaseT(4),
		abar(5),
		unknown(254),
		unsupported(255)
	}
	ACCESS read-only
	STATUS mandatory
	DESCRIPTION
		"Type of Front Panel Module 2
		1	None		No module
		2	DCE		DCE module
		3	DTE		DTE module
		4	10Base-T	10Base-T Ethernet module
		5	ABAR		Advanced Bridge and Router module
		254			unknown value
		255			unsupported variable for addressed device"
	::= { cmroFarInventoryFpEntry 4 }

cmroFarInventoryFpModule3Type OBJECT-TYPE
	SYNTAX INTEGER
	{
		none(1),
		dce(2),
		dte(3),
		tenBaseT(4),
		abar(5),
		unknown(254),
		unsupported(255)
	}
	ACCESS read-only
	STATUS mandatory
	DESCRIPTION
		"Type of Front Panel Module 3
		1	None		No module
		2	DCE		DCE module
		3	DTE		DTE module
		4	10Base-T	10Base-T Ethernet module
		5	ABAR		Advanced Bridge and Router module
		254			unknown value
		255			unsupported variable for addressed device"
	::= { cmroFarInventoryFpEntry 5 }

cmroFarInventoryFpModule4Type OBJECT-TYPE
	SYNTAX INTEGER
	{
		none(1),
		dce(2),
		dte(3),
		tenBaseT(4),
		abar(5),
		unknown(254),
		unsupported(255)
	}
	ACCESS read-only
	STATUS mandatory
	DESCRIPTION
		"Type of Front Panel Module 4
		1	None		No module
		2	DCE		DCE module
		3	DTE		DTE module
		4	10Base-T	10Base-T Ethernet module
		5	ABAR		Advanced Bridge and Router module
		254			unknown value
		255			unsupported variable for addressed device"
	::= { cmroFarInventoryFpEntry 6 }

cmroFarInventoryFpModule5Type OBJECT-TYPE
	SYNTAX INTEGER
	{
		none(1),
		dce(2),
		dte(3),
		tenBaseT(4),
		abar(5),
		unknown(254),
		unsupported(255)
	}
	ACCESS read-only
	STATUS mandatory
	DESCRIPTION
		"Type of Front Panel Module 5
		1	None		No module
		2	DCE		DCE module
		3	DTE		DTE module
		4	10Base-T	10Base-T Ethernet module
		5	ABAR		Advanced Bridge and Router module
		254			unknown value
		255			unsupported variable for addressed device"
	::= { cmroFarInventoryFpEntry 7 }

cmroFarInventoryFpModule6Type OBJECT-TYPE
	SYNTAX INTEGER
	{
		none(1),
		dce(2),
		dte(3),
		tenBaseT(4),
		abar(5),
		unknown(254),
		unsupported(255)
	}
	ACCESS read-only
	STATUS mandatory
	DESCRIPTION
		"Type of Front Panel Module 6
		1	None		No module
		2	DCE		DCE module
		3	DTE		DTE module
		4	10Base-T	10Base-T Ethernet module
		5	ABAR		Advanced Bridge and Router module
		254			unknown value
		255			unsupported variable for addressed device"
	::= { cmroFarInventoryFpEntry 8 }

cmroFarInventoryFpModule1FabData OBJECT-TYPE
	SYNTAX DisplayString(SIZE(20))
	ACCESS read-only
	STATUS mandatory
	DESCRIPTION
		"Fabrication Data of Front Panel Module 1"
	::= { cmroFarInventoryFpEntry 9 }

cmroFarInventoryFpModule2FabData OBJECT-TYPE
	SYNTAX DisplayString(SIZE(20))
	ACCESS read-only
	STATUS mandatory
	DESCRIPTION
		"Fabrication Data of Front Panel Module 2"
	::= { cmroFarInventoryFpEntry 10 }

cmroFarInventoryFpModule3FabData OBJECT-TYPE
	SYNTAX DisplayString(SIZE(20))
	ACCESS read-only
	STATUS mandatory
	DESCRIPTION
		"Fabrication Data of Front Panel Module 3"
	::= { cmroFarInventoryFpEntry 11 }

cmroFarInventoryFpModule4FabData OBJECT-TYPE
	SYNTAX DisplayString(SIZE(20))
	ACCESS read-only
	STATUS mandatory
	DESCRIPTION
		"Fabrication Data of Front Panel Module 4"
	::= { cmroFarInventoryFpEntry 12 }

cmroFarInventoryFpModule5FabData OBJECT-TYPE
	SYNTAX DisplayString(SIZE(20))
	ACCESS read-only
	STATUS mandatory
	DESCRIPTION
		"Fabrication Data of Front Panel Module 5"
	::= { cmroFarInventoryFpEntry 13 }

cmroFarInventoryFpModule6FabData OBJECT-TYPE
	SYNTAX DisplayString(SIZE(20))
	ACCESS read-only
	STATUS mandatory
	DESCRIPTION
		"Fabrication Data of Front Panel Module 6"
	::= { cmroFarInventoryFpEntry 14 }

--------------------------------------------------------------------------------  
--	CM-RO	Far Inventory Info
--------------------------------------------------------------------------------  
cmroFarInventoryInfoTable OBJECT-TYPE
	SYNTAX SEQUENCE OF CmroFarInventoryInfoEntry
	ACCESS not-accessible
	STATUS mandatory
	DESCRIPTION ""
	::= { cmroFarInventory 2 }

cmroFarInventoryInfoEntry OBJECT-TYPE
	SYNTAX CmroFarInventoryInfoEntry
	ACCESS not-accessible
	STATUS mandatory
	DESCRIPTION ""
	INDEX { cmroFarInventoryInfoPortIndex, cmroFarInventoryInfoLinkIndex }
	::= { cmroFarInventoryInfoTable 1 }

CmroFarInventoryInfoEntry ::=
	SEQUENCE
	{
		cmroFarInventoryInfoPortIndex INTEGER,
		cmroFarInventoryInfoLinkIndex INTEGER,
		cmroFarInventoryInfoString1Type INTEGER,
		cmroFarInventoryInfoString2Type INTEGER,
		cmroFarInventoryInfoString3Type INTEGER,
		cmroFarInventoryInfoString4Type INTEGER,
		cmroFarInventoryInfoString5Type INTEGER,
		cmroFarInventoryInfoString1 DisplayString,
		cmroFarInventoryInfoString2 DisplayString,
		cmroFarInventoryInfoString3 DisplayString,
		cmroFarInventoryInfoString4 DisplayString,
		cmroFarInventoryInfoString5 DisplayString
	}

cmroFarInventoryInfoPortIndex OBJECT-TYPE
	SYNTAX INTEGER
	ACCESS read-only
	STATUS mandatory
	DESCRIPTION
		"This variable addresses the port number of the proxy
		and is used as index for the other elements in the Table"
	::= { cmroFarInventoryInfoEntry 1 }

cmroFarInventoryInfoLinkIndex OBJECT-TYPE
	SYNTAX INTEGER
	ACCESS read-only
	STATUS mandatory
	DESCRIPTION
		"This variable addresses the slot number of the OMI sub-rack
		and is used as index for the other elements in the Table"
	::= { cmroFarInventoryInfoEntry 2 }

cmroFarInventoryInfoString1Type OBJECT-TYPE
	SYNTAX INTEGER
	{
		empty(1),
		dslChip(2),
		dslFirmwareLoad(3),
		fpgaLoad(4),
		ethWanChip(5),
		l2sChip(6),
		bootLoaderVersion(7),
		unknown(254),
		unsupported(255)
	}
	ACCESS read-only
	STATUS mandatory
	DESCRIPTION
		"Type of InfoString 1
		1	Empty			InfoString is empty
		2	DSL Chip		InfoString is related to the DSL Chip
		3	DSL Firmware Load	InfoString is related to the DSL Firmware Load
		4	FPGA Load		InfoString is related to the FPGA Load
		5	ETH WAN Chip		InfoString is related to the Ethernet WAN Chip
		5	L2S Chip		InfoString is related to the Layer2 Switch Chip
		254				unknown value
		255				unsupported variable for addressed device"
	::= { cmroFarInventoryInfoEntry 3 }

cmroFarInventoryInfoString2Type OBJECT-TYPE
	SYNTAX INTEGER
	{
		empty(1),
		dslChip(2),
		dslFirmwareLoad(3),
		fpgaLoad(4),
		ethWanChip(5),
		l2sChip(6),
		bootLoaderVersion(7),
		unknown(254),
		unsupported(255)
	}
	ACCESS read-only
	STATUS mandatory
	DESCRIPTION
		"Type of InfoString 2
		1	Empty			InfoString is empty
		2	DSL Chip		InfoString is related to the DSL Chip
		3	DSL Firmware Load	InfoString is related to the DSL Firmware Load
		4	FPGA Load		InfoString is related to the FPGA Load
		5	ETH WAN Chip		InfoString is related to the Ethernet WAN Chip
		5	L2S Chip		InfoString is related to the Layer2 Switch Chip
		254				unknown value
		255				unsupported variable for addressed device"
	::= { cmroFarInventoryInfoEntry 4 }

cmroFarInventoryInfoString3Type OBJECT-TYPE
	SYNTAX INTEGER
	{
		empty(1),
		dslChip(2),
		dslFirmwareLoad(3),
		fpgaLoad(4),
		ethWanChip(5),
		l2sChip(6),
		bootLoaderVersion(7),
		unknown(254),
		unsupported(255)
	}
	ACCESS read-only
	STATUS mandatory
	DESCRIPTION
		"Type of InfoString 3
		1	Empty			InfoString is empty
		2	DSL Chip		InfoString is related to the DSL Chip
		3	DSL Firmware Load	InfoString is related to the DSL Firmware Load
		4	FPGA Load		InfoString is related to the FPGA Load
		5	ETH WAN Chip		InfoString is related to the Ethernet WAN Chip
		5	L2S Chip		InfoString is related to the Layer2 Switch Chip
		254				unknown value
		255				unsupported variable for addressed device"
	::= { cmroFarInventoryInfoEntry 5 }

cmroFarInventoryInfoString4Type OBJECT-TYPE
	SYNTAX INTEGER
	{
		empty(1),
		dslChip(2),
		dslFirmwareLoad(3),
		fpgaLoad(4),
		ethWanChip(5),
		l2sChip(6),
		bootLoaderVersion(7),
		unknown(254),
		unsupported(255)
	}
	ACCESS read-only
	STATUS mandatory
	DESCRIPTION
		"Type of InfoString 4
		1	Empty			InfoString is empty
		2	DSL Chip		InfoString is related to the DSL Chip
		3	DSL Firmware Load	InfoString is related to the DSL Firmware Load
		4	FPGA Load		InfoString is related to the FPGA Load
		5	ETH WAN Chip		InfoString is related to the Ethernet WAN Chip
		5	L2S Chip		InfoString is related to the Layer2 Switch Chip
		254				unknown value
		255				unsupported variable for addressed device"
	::= { cmroFarInventoryInfoEntry 6 }

cmroFarInventoryInfoString5Type OBJECT-TYPE
	SYNTAX INTEGER
	{
		empty(1),
		dslChip(2),
		dslFirmwareLoad(3),
		fpgaLoad(4),
		ethWanChip(5),
		l2sChip(6),
		bootLoaderVersion(7),
		unknown(254),
		unsupported(255)
	}
	ACCESS read-only
	STATUS mandatory
	DESCRIPTION
		"Type of InfoString 5
		1	Empty			InfoString is empty
		2	DSL Chip		InfoString is related to the DSL Chip
		3	DSL Firmware Load	InfoString is related to the DSL Firmware Load
		4	FPGA Load		InfoString is related to the FPGA Load
		5	ETH WAN Chip		InfoString is related to the Ethernet WAN Chip
		5	L2S Chip		InfoString is related to the Layer2 Switch Chip
		254				unknown value
		255				unsupported variable for addressed device"
	::= { cmroFarInventoryInfoEntry 7 }

cmroFarInventoryInfoString1 OBJECT-TYPE
	SYNTAX DisplayString(SIZE(25))
	ACCESS read-only
	STATUS mandatory
	DESCRIPTION
		"InfoString 1"
	::= { cmroFarInventoryInfoEntry 8 }

cmroFarInventoryInfoString2 OBJECT-TYPE
	SYNTAX DisplayString(SIZE(25))
	ACCESS read-only
	STATUS mandatory
	DESCRIPTION
		"InfoString 2"
	::= { cmroFarInventoryInfoEntry 9 }

cmroFarInventoryInfoString3 OBJECT-TYPE
	SYNTAX DisplayString(SIZE(25))
	ACCESS read-only
	STATUS mandatory
	DESCRIPTION
		"InfoString 3"
	::= { cmroFarInventoryInfoEntry 10 }

cmroFarInventoryInfoString4 OBJECT-TYPE
	SYNTAX DisplayString(SIZE(25))
	ACCESS read-only
	STATUS mandatory
	DESCRIPTION
		"InfoString 4"
	::= { cmroFarInventoryInfoEntry 11 }

cmroFarInventoryInfoString5 OBJECT-TYPE
	SYNTAX DisplayString(SIZE(25))
	ACCESS read-only
	STATUS mandatory
	DESCRIPTION
		"InfoString 5"
	::= { cmroFarInventoryInfoEntry 12 }
	
--------------------------------------------------------------------------------  
--	CM-RO	SRU Inventory Info
--------------------------------------------------------------------------------  
cmroSruInventoryInfoTable OBJECT-TYPE
	SYNTAX SEQUENCE OF CmroSruInventoryInfoEntry
	ACCESS not-accessible
	STATUS mandatory
	DESCRIPTION ""
	::= { cmroSruInventory 1 }

cmroSruInventoryInfoEntry OBJECT-TYPE
	SYNTAX CmroSruInventoryInfoEntry
	ACCESS not-accessible
	STATUS mandatory
	DESCRIPTION ""
	INDEX { cmroSruInventoryInfoPortIndex, cmroSruInventoryInfoLinkIndex, cmroSruInventoryInfoRegIndex }
	::= { cmroSruInventoryInfoTable 1 }

CmroSruInventoryInfoEntry ::=
	SEQUENCE
	{
		cmroSruInventoryInfoPortIndex INTEGER,
		cmroSruInventoryInfoLinkIndex INTEGER,
		cmroSruInventoryInfoRegIndex INTEGER,
		cmroSruInventoryInfoString1Type INTEGER,
		cmroSruInventoryInfoString2Type INTEGER,
		cmroSruInventoryInfoString3Type INTEGER,
		cmroSruInventoryInfoString4Type INTEGER,
		cmroSruInventoryInfoString5Type INTEGER,
		cmroSruInventoryInfoString1 DisplayString,
		cmroSruInventoryInfoString2 DisplayString,
		cmroSruInventoryInfoString3 DisplayString,
		cmroSruInventoryInfoString4 DisplayString,
		cmroSruInventoryInfoString5 DisplayString
	}

cmroSruInventoryInfoPortIndex OBJECT-TYPE
	SYNTAX INTEGER
	ACCESS read-only
	STATUS mandatory
	DESCRIPTION
		"This variable addresses the port number of the proxy
		and is used as index for the other elements in the Table"
	::= { cmroSruInventoryInfoEntry 1 }

cmroSruInventoryInfoLinkIndex OBJECT-TYPE
	SYNTAX INTEGER
	ACCESS read-only
	STATUS mandatory
	DESCRIPTION
		"This variable addresses the slot number of the OMI sub-rack
		and is used as index for the other elements in the Table"
	::= { cmroSruInventoryInfoEntry 2 }

cmroSruInventoryInfoRegIndex OBJECT-TYPE
	SYNTAX INTEGER
	{
		reg11(3),
		reg12(4),
		reg21(5),
		reg22(6),
		reg31(7),
		reg32(8),
		reg41(9),
		reg42(10),
		reg51(11),
		reg52(12),
		reg61(13),
		reg62(14),
		reg71(15),
		reg72(16),
		reg81(17),
		reg82(18),
		reg13(19),
		reg14(20),
		reg23(21),
		reg24(22),
		reg33(23),
		reg34(24),
		reg43(25),
		reg44(26),
		reg53(27),
		reg54(28),
		reg63(29),
		reg64(30),
		reg73(31),
		reg74(32),
		reg83(33),
		reg84(34)
	}
	ACCESS read-only
	STATUS mandatory
	DESCRIPTION
		"This variable addresses the regenerator device and is
		used as index for the other elements in the Table"
	::= { cmroSruInventoryInfoEntry 3 }

cmroSruInventoryInfoString1Type OBJECT-TYPE
	SYNTAX INTEGER
	{
		empty(1),
		dslChip(2),
		dslFirmwareLoad(3),
		fpgaLoad(4),
		ethWanChip(5),
		l2sChip(6),
		bootLoaderVersion(7),
		unknown(254),
		unsupported(255)
	}
	ACCESS read-only
	STATUS mandatory
	DESCRIPTION
		"Type of InfoString 1
		1	Empty			InfoString is empty
		2	DSL Chip		InfoString is related to the DSL Chip
		3	DSL Firmware Load	InfoString is related to the DSL Firmware Load
		4	FPGA Load		InfoString is related to the FPGA Load
		5	ETH WAN Chip		InfoString is related to the Ethernet WAN Chip
		5	L2S Chip		InfoString is related to the Layer2 Switch Chip
		254				unknown value
		255				unsupported variable for addressed device"
	::= { cmroSruInventoryInfoEntry 4 }

cmroSruInventoryInfoString2Type OBJECT-TYPE
	SYNTAX INTEGER
	{
		empty(1),
		dslChip(2),
		dslFirmwareLoad(3),
		fpgaLoad(4),
		ethWanChip(5),
		l2sChip(6),
		bootLoaderVersion(7),
		unknown(254),
		unsupported(255)
	}
	ACCESS read-only
	STATUS mandatory
	DESCRIPTION
		"Type of InfoString 2
		1	Empty			InfoString is empty
		2	DSL Chip		InfoString is related to the DSL Chip
		3	DSL Firmware Load	InfoString is related to the DSL Firmware Load
		4	FPGA Load		InfoString is related to the FPGA Load
		5	ETH WAN Chip		InfoString is related to the Ethernet WAN Chip
		5	L2S Chip		InfoString is related to the Layer2 Switch Chip
		254				unknown value
		255				unsupported variable for addressed device"
	::= { cmroSruInventoryInfoEntry 5 }

cmroSruInventoryInfoString3Type OBJECT-TYPE
	SYNTAX INTEGER
	{
		empty(1),
		dslChip(2),
		dslFirmwareLoad(3),
		fpgaLoad(4),
		ethWanChip(5),
		l2sChip(6),
		bootLoaderVersion(7),
		unknown(254),
		unsupported(255)
	}
	ACCESS read-only
	STATUS mandatory
	DESCRIPTION
		"Type of InfoString 3
		1	Empty			InfoString is empty
		2	DSL Chip		InfoString is related to the DSL Chip
		3	DSL Firmware Load	InfoString is related to the DSL Firmware Load
		4	FPGA Load		InfoString is related to the FPGA Load
		5	ETH WAN Chip		InfoString is related to the Ethernet WAN Chip
		5	L2S Chip		InfoString is related to the Layer2 Switch Chip
		254				unknown value
		255				unsupported variable for addressed device"
	::= { cmroSruInventoryInfoEntry 6 }

cmroSruInventoryInfoString4Type OBJECT-TYPE
	SYNTAX INTEGER
	{
		empty(1),
		dslChip(2),
		dslFirmwareLoad(3),
		fpgaLoad(4),
		ethWanChip(5),
		l2sChip(6),
		bootLoaderVersion(7),
		unknown(254),
		unsupported(255)
	}
	ACCESS read-only
	STATUS mandatory
	DESCRIPTION
		"Type of InfoString 4
		1	Empty			InfoString is empty
		2	DSL Chip		InfoString is related to the DSL Chip
		3	DSL Firmware Load	InfoString is related to the DSL Firmware Load
		4	FPGA Load		InfoString is related to the FPGA Load
		5	ETH WAN Chip		InfoString is related to the Ethernet WAN Chip
		5	L2S Chip		InfoString is related to the Layer2 Switch Chip
		254				unknown value
		255				unsupported variable for addressed device"
	::= { cmroSruInventoryInfoEntry 7 }

cmroSruInventoryInfoString5Type OBJECT-TYPE
	SYNTAX INTEGER
	{
		empty(1),
		dslChip(2),
		dslFirmwareLoad(3),
		fpgaLoad(4),
		ethWanChip(5),
		l2sChip(6),
		bootLoaderVersion(7),
		unknown(254),
		unsupported(255)
	}
	ACCESS read-only
	STATUS mandatory
	DESCRIPTION
		"Type of InfoString 5
		1	Empty			InfoString is empty
		2	DSL Chip		InfoString is related to the DSL Chip
		3	DSL Firmware Load	InfoString is related to the DSL Firmware Load
		4	FPGA Load		InfoString is related to the FPGA Load
		5	ETH WAN Chip		InfoString is related to the Ethernet WAN Chip
		5	L2S Chip		InfoString is related to the Layer2 Switch Chip
		254				unknown value
		255				unsupported variable for addressed device"
	::= { cmroSruInventoryInfoEntry 8 }

cmroSruInventoryInfoString1 OBJECT-TYPE
	SYNTAX DisplayString(SIZE(25))
	ACCESS read-only
	STATUS mandatory
	DESCRIPTION
		"InfoString 1"
	::= { cmroSruInventoryInfoEntry 9 }

cmroSruInventoryInfoString2 OBJECT-TYPE
	SYNTAX DisplayString(SIZE(25))
	ACCESS read-only
	STATUS mandatory
	DESCRIPTION
		"InfoString 2"
	::= { cmroSruInventoryInfoEntry 10 }

cmroSruInventoryInfoString3 OBJECT-TYPE
	SYNTAX DisplayString(SIZE(25))
	ACCESS read-only
	STATUS mandatory
	DESCRIPTION
		"InfoString 3"
	::= { cmroSruInventoryInfoEntry 11 }

cmroSruInventoryInfoString4 OBJECT-TYPE
	SYNTAX DisplayString(SIZE(25))
	ACCESS read-only
	STATUS mandatory
	DESCRIPTION
		"InfoString 4"
	::= { cmroSruInventoryInfoEntry 12 }

cmroSruInventoryInfoString5 OBJECT-TYPE
	SYNTAX DisplayString(SIZE(25))
	ACCESS read-only
	STATUS mandatory
	DESCRIPTION
		"InfoString 5"
	::= { cmroSruInventoryInfoEntry 13 }


--==============================================================================
--==============================================================================
--
--      CM-RW
--
--==============================================================================
--==============================================================================
	cmrw	OBJECT IDENTIFIER ::= { linksVers3 2 }
	
--------------------------------------------------------------------------------  
--	CM-RW	sub OIDs
--------------------------------------------------------------------------------  
	cmrwLocal	OBJECT IDENTIFIER ::= { cmrw 1 }
	cmrwFar		OBJECT IDENTIFIER ::= { cmrw 2 }
	cmrwOmi		OBJECT IDENTIFIER ::= { cmrw 3 }
	cmrwSru		OBJECT IDENTIFIER ::= { cmrw 4 }

--------------------------------------------------------------------------------
--	CM-RW	local Token
--------------------------------------------------------------------------------
cmrwLocalTokenTable OBJECT-TYPE
	SYNTAX SEQUENCE OF CmrwLocalTokenEntry
	ACCESS not-accessible
	STATUS mandatory
	DESCRIPTION ""
	::= { cmrwLocal 1 }

cmrwLocalTokenEntry OBJECT-TYPE
	SYNTAX CmrwLocalTokenEntry
	ACCESS not-accessible
	STATUS mandatory
	DESCRIPTION ""
	INDEX { cmrwLocalTokenPortIndex, cmrwLocalTokenLinkIndex }
	::= { cmrwLocalTokenTable 1 }

CmrwLocalTokenEntry ::=
	SEQUENCE
	{
		cmrwLocalTokenPortIndex INTEGER,
		cmrwLocalTokenLinkIndex INTEGER,
		cmrwLocalTokenResId INTEGER,
		cmrwLocalTokenDipLt INTEGER,
		cmrwLocalTokenDipNt INTEGER,
		cmrwLocalTokenEoc INTEGER,
		cmrwLocalTokenTicket INTEGER,
		cmrwLocalTokenRelease INTEGER,
		cmrwLocalTokenSessionId INTEGER
	}

cmrwLocalTokenPortIndex OBJECT-TYPE
	SYNTAX INTEGER
	ACCESS read-only
	STATUS mandatory
	DESCRIPTION
		"This variable addresses the port number of the proxy
		and is used as index for the other elements in the Table"
	::= { cmrwLocalTokenEntry 1 }

cmrwLocalTokenLinkIndex OBJECT-TYPE
	SYNTAX INTEGER
	ACCESS read-only
	STATUS mandatory
	DESCRIPTION
		"This variable addresses the slot number of the OMI sub-rack
		and is used as index for the other elements in the Table"
	::= {cmrwLocalTokenEntry 2 }

cmrwLocalTokenResId OBJECT-TYPE
	SYNTAX INTEGER
	{
		available(1),
		lineint(2),
		lct(3),
		unknown(254),
		unsupported(255)
	}
	ACCESS read-only
	STATUS mandatory
	DESCRIPTION
		"Indicates who is in posession of the reservation token for this
		device.
		1	Available	The token is free
		2	Lineint		The token is given to the LineIntegrator
		3	Lct		The token is given to the Local Craft Terminal (LCT)
		254			unknown value
		255			unsupported variable for the addressed device"
	::= { cmrwLocalTokenEntry 3 }

cmrwLocalTokenDipLt OBJECT-TYPE
	SYNTAX INTEGER
	{
		inactive(1),
		active(2),
		notLt(3),
		unknown(254),
		unsupported(255)
	}
	ACCESS read-only
	STATUS mandatory
	DESCRIPTION
		"Indicates whether the LT is configured by DIP switch. If it is, 
		then software configuration is not possible.
		1	Inactive	The LT is not configured by DIP switch
		2	Active		The LT is configured by DIP switch
		3	NotLt		The management system is connected to an NT locally
		254			Unknown value
		255			Unsupported variable for addressed device"
	::= { cmrwLocalTokenEntry 4}

cmrwLocalTokenDipNt OBJECT-TYPE
	SYNTAX INTEGER
	{
		inactive(1),
		active(2),
		unknown(254),
		unsupported(255)
	}
	ACCESS read-only
	STATUS mandatory
	DESCRIPTION
		"Indicates whether the NT is configured by DIP switch. If it is, 
		then software configuration is not possible.
		1	Inactive	The NT is not configured by DIP switch
		2	Active		The NT is configured by DIP switch
		254			Unknown value
		255			Unsupported variable for addressed device"
	::= { cmrwLocalTokenEntry 5 }

cmrwLocalTokenEoc OBJECT-TYPE
	SYNTAX INTEGER
	{
		inactive(1),
		active(2),
		reg1(3),
		reg2(4),
		reg3(5),
		reg4(6),
		reg5(7),
		reg6(8),
		reg7(9),
		reg8(10),
		unknown(254),
		unsupported(255)
	}
	ACCESS read-only
	STATUS mandatory
	DESCRIPTION
		"Indicates whether there is an EOC connection between the LT
		and the NT over the HDSL link.
		1	Inactive	EOC connection not available
		2	Active		EOC connection available
		3	Reg1		The EOC is up until the first regenerator section
		4	Reg2		The EOC is up until the second regenerator section
		5	Reg3		The EOC is up until the third regenerator section
		6	Reg4		The EOC is up until the fourth regenerator section
		7	Reg5		The EOC is up until the fifth regenerator section
		8	Reg6		The EOC is up until the sixth regenerator section
		9	Reg7		The EOC is up until the seventh regenerator section
		10	Reg8		The EOC is up until the eighth regenerator section
		254			Unknown value
		255			Unsupported variable for addressed device"
	::= { cmrwLocalTokenEntry 6 }

cmrwLocalTokenTicket OBJECT-TYPE
	SYNTAX INTEGER
	{
		token1(1),
		token2(2),
		token3(3),
		token4(4),
		token5(5),
		token6(6),
		token7(7),
		token8(8),
		token9(9),
		token10(10),
		notGranted(11),
		lost(12),
		notRequested(13),
		unknown(254),
		unsupported(255)
	}
	ACCESS read-only
	STATUS mandatory
	DESCRIPTION
		"Is used to request or refresh the token
		device.
		1-10	Token1-10	The token was granted/refreshed, the index helps to detect whether it has expried since last reading from this variable
		11	NotGranted	The token was not granted
		12	Lost		The token could not be refreshed
		13	NotRequested	The token has not been requested
		254			unknown value
		255			unsupported variable for the addressed device"
	::= { cmrwLocalTokenEntry 7 }

cmrwLocalTokenRelease OBJECT-TYPE
	SYNTAX INTEGER
	{
		tokenReleased (1),
		noNeedToRelease (2),
		notReleased (3),			
		unknown(254),
		unsupported(255)
	}
	ACCESS read-only
	STATUS mandatory
	DESCRIPTION
		"Is used to release the token device.
		1		TokenReleased		Token has been successfully released.
		2		NoNeedToRelease		Token was not reserved, so need to release.
		3		NotReleased		Granted to LCT and coudn`t been released.
		254					unknown value
		255					unsupported variable for the addressed device"
	::= { cmrwLocalTokenEntry 8 }

cmrwLocalTokenSessionId OBJECT-TYPE
	SYNTAX INTEGER (0..65535)
	ACCESS read-write
	STATUS mandatory
	DESCRIPTION
		"Indicates which SNMP management is in posession of the reservation token for this
		device.
		0	Invalid		The session value is invalid
		65535	Unsupported	Unsupported variable for the addressed device"
	::= { cmrwLocalTokenEntry 9 }

--------------------------------------------------------------------------------
--	CM-RW	local Common
--------------------------------------------------------------------------------
cmrwLocalCommonTable OBJECT-TYPE
	SYNTAX SEQUENCE OF CmrwLocalCommonEntry
	ACCESS not-accessible
	STATUS mandatory
	DESCRIPTION ""
	::= { cmrwLocal 2 }

cmrwLocalCommonEntry OBJECT-TYPE
	SYNTAX CmrwLocalCommonEntry
	ACCESS not-accessible
	STATUS mandatory
	DESCRIPTION ""
	INDEX { cmrwLocalCommonPortIndex, cmrwLocalCommonLinkIndex }
	::= { cmrwLocalCommonTable 1 }

CmrwLocalCommonEntry ::=
	SEQUENCE
	{
		cmrwLocalCommonPortIndex INTEGER,
		cmrwLocalCommonLinkIndex INTEGER,
		cmrwLocalCommonMode INTEGER,
		cmrwLocalCommonFipo INTEGER,
		cmrwLocalCommonRps INTEGER,
		cmrwLocalCommonTimeslotsU INTEGER,
		cmrwLocalCommonClockMode INTEGER,
		cmrwLocalCommonMcsStructTdm INTEGER,
		cmrwLocalCommonMcsChBandwidth INTEGER,
		cmrwLocalCommonRpsCurrent INTEGER,
		cmrwLocalCommonLineModulation INTEGER,
		cmrwLocalCommonUseFixTimeslotsU INTEGER,
		cmrwLocalCommonFixTimeslotsU INTEGER
	}

cmrwLocalCommonPortIndex OBJECT-TYPE
	SYNTAX INTEGER
	ACCESS read-only
	STATUS mandatory
	DESCRIPTION
		"This variable addresses the port number of the proxy
		and is used as index for the other elements in the Table"
	::= { cmrwLocalCommonEntry 1 }

cmrwLocalCommonLinkIndex OBJECT-TYPE
	SYNTAX INTEGER
	ACCESS read-only
	STATUS mandatory
	DESCRIPTION
		"This variable addresses the slot number of the OMI sub-rack
		and is used as index for the other elements in the Table"
	::= {cmrwLocalCommonEntry 2 }

cmrwLocalCommonMode OBJECT-TYPE
	SYNTAX INTEGER
	{
		transparent(1),
		structured(2),
		pra(3),
		data(4),
		addDrop(5),
		twoMData(6),
		twoMAddDrop(7),
		manual(8),
		tiTwoM(9),
		tiData(10),
		oneTdmEth(11),
		twoTdmEth(12),
		fourTdmEth(13),
		hTdmEth(14),
		ethEth(15),
		dualE1(16),
		mapped(17),
		unknown(254),
		unsupported(255)
	}
	ACCESS read-write
	STATUS mandatory
	DESCRIPTION
		"Defines the basic Mode the device is in. This has an influence on
		the default values of most configuration variables (if not overwritten)
		and on the limitations of options in the GUI of the element manager.
		1	Transparent	Transparent G.704 mode 2Mbit/s
		2	Structured	Structured 2Mbit/s mode (Framed)
		3	Pra		ISDN PRA mode
		4	Data		Standard Data-Data application
		5	AddDrop		Standard Add/Drop-Add/Drop application
		6	TwoMData	Standard 2Mbit/s-Data application
		7	TwoMAddDrop	Standard 2Mbit/s-Add/Drop application
		8	Manual		Manual mode (full freedom for configuration)
		9	TiTwoM		2Mbit/s-Data application (TI style)
		10	TiData		Data-Data application
		11	1TdmEth		TDM-Ethernet application (TDM:DSL 1:1)
		12	2TdmEth		TDM-Ethernet application (TDM:DSL 1:2)
		13	4TdmEth		TDM-Ethernet application (TDM:DSL 1:4)
		14	HalfTdmEth	TDM-Ethernet application (TDM:DSL 2:1)
		15	EthEth		Ethernet application with 2 L2 Switches
		16	DualE1		Dual E1 application
		17	Mapped		Mapped mode
		254			unknown value
		255			unsupported variable for addressed device"
	::= { cmrwLocalCommonEntry 3 }
 
cmrwLocalCommonFipo OBJECT-TYPE
	SYNTAX INTEGER
	{
		normal(1),
		fractional(2),
		partial(3),
		unknown(254),
		unsupported(255)
	}
	ACCESS read-write
	STATUS mandatory
	DESCRIPTION
		"FIPO Mode (Fractional Installation/Partial Operation).
		This allows the use of only one wire-pair with a reduced
		data rate of 960kbit/s (Fractional Installation) or the
		operation with two wire-pairs with fall-back to 960kbit/s
		if one wire-pair fails.
		1	Normal		Normal 2Mbit/s operation
		2	Fractional	Fractional Installation
		3	Partial		Partial Operation
		254			unknown value
		255			unsupported variable for addressed device"
	::= { cmrwLocalCommonEntry 4 }

cmrwLocalCommonRps OBJECT-TYPE
	SYNTAX INTEGER
	{
		inactive(1),
		active(2),
		unknown(254),
		unsupported(255)
	}
	ACCESS read-write
	STATUS mandatory
	DESCRIPTION
		"Used to turn the Remote Power Supply on/off.
		1	Inactive	The RPS is turned off
		2	Active		The RPS is turned on
		254			unknown value
		255			unsupported
		"
	::= { cmrwLocalCommonEntry 5 }

cmrwLocalCommonTimeslotsU OBJECT-TYPE
	SYNTAX INTEGER
	{
		bw64(1),
		bw128(2),
		bw192(3),
		bw256(4),
		bw320(5),
		bw384(6),
		bw448(7),
		bw512(8),
		bw576(9),
		bw640(10),
		bw704(11),
		bw768(12),
		bw832(13),
		bw896(14),
		bw960(15),
		bw1024(16),
		bw1088(17),
		bw1152(18),
		bw1216(19),
		bw1280(20),
		bw1344(21),
		bw1408(22),
		bw1472(23),
		bw1536(24),
		bw1600(25),
		bw1664(26),
		bw1728(27),
		bw1792(28),
		bw1856(29),
		bw1920(30),
		bw1984(31),
		bw2048(32),
		bw2112(33),
		bw2176(34),
		bw2240(35),
		bw2304(36),
		bw2368(37),
		bw2432(38),
		bw2496(39),
		bw2560(40),
		bw2624(41),
		bw2688(42),
		bw2752(43),
		bw2816(44),
		bw2880(45),
		bw2944(46),
		bw3008(47),
		bw3072(48),
		bw3136(49),
		bw3200(50),
		bw3264(51),
		bw3328(52),
		bw3392(53),
		bw3456(54),
		bw3520(55),
		bw3584(56),
		bw3648(57),
		bw3712(58),
		bw3776(59),
		bw3840(60),
		bw3904(61),
		bw3968(62),
		bw4032(63),
		bw4096(64),
		bw4160(65),
		bw4224(66),
		bw4288(67),
		bw4352(68),
		bw4416(69),
		bw4480(70),
		bw4544(71),
		bw4608(72),
		bw4672(73),
		bw4736(74),
		bw4800(75),
		bw4864(76),
		bw4928(77),
		bw4992(78),
		bw5056(79),
		bw5120(80),
		bw5184(81),
		bw5248(82),
		bw5312(83),
		bw5376(84),
		bw5440(85),
		bw5504(86),
		bw5568(87),
		bw5632(88),
		bw5696(89),
		bw5760(90),
		bw5824(91),
		bw5888(92),
		bw5952(93),
		bw6016(94),
		bw6080(95),
		bw6144(96),
		bw6208(97),
		bw6272(98),
		bw6336(99),
		bw6400(100),
		bw6464(101),
		bw6528(102),
		bw6592(103),
		bw6656(104),
		bw6720(105),
		bw6784(106),
		bw6848(107),
		bw6912(108),
		bw6976(109),
		bw7040(110),
		bw7104(111),
		bw7168(112),
		bw7232(113),
		bw7296(114),
		bw7360(115),
		bw7424(116),
		bw7488(117),
		bw7552(118),
		bw7616(119),
		bw7680(120),
		bw7744(121),
		bw7808(122),
		bw7872(123),
		bw7936(124),
		bw8000(125),
		bw8064(126),
		bw8128(127),
		bw8192(128),
		bw8256(129),
		bw8320(130),
		bw8384(131),
		bw8448(132),
		bw8512(133),
		bw8576(134),
		bw8640(135),
		bw8704(136),
		bw8768(137),
		bw8832(138),
		bw8896(139),
		bw8960(140),
		bw9024(141),
		bw9088(142),
		bw9152(143),
		bw9216(144),
		bw9280(145),
		bw9344(146),
		bw9408(147),
		bw9472(148),
		bw9536(149),
		bw9600(150),
		bw9664(151),
		bw9728(152),
		bw9792(153),
		bw9856(154),
		bw9920(155),
		bw9984(156),
		bw10048(157),
		bw10112(158),
		bw10176(159),
		bw10240(160),
		bw10304(161),
		bw10368(162),
		bw10432(163),
		bw10496(164),
		bw10560(165),
		bw10624(166),
		bw10688(167),
		bw10752(168),
		bw10816(169),
		bw10880(170),
		bw10944(171),
		bw11008(172),
		bw11072(173),
		bw11136(174),
		bw11200(175),
		bw11264(176),
		bw11328(177),
		bw11392(178),
		unknown(254),
		unsupported(255)
	}
	ACCESS read-write
	STATUS mandatory
	DESCRIPTION
		"Bandwidth allocated for transmission interface (U-Interface) as
		a number of 64kbit/s time slots.
		
		When reading the following values can be returned:
		1	bw64		Bandwidth   64 kbit/s
		2	bw128		Bandwidth  128 kbit/s
		3	bw192		Bandwidth  192 kbit/s
		4	bw256		Bandwidth  256 kbit/s
		5	bw320		Bandwidth  320 kbit/s
		6	bw384		Bandwidth  384 kbit/s
		7	bw448		Bandwidth  448 kbit/s
		8	bw512		Bandwidth  512 kbit/s
		9	bw576		Bandwidth  576 kbit/s
		10	bw640		Bandwidth  640 kbit/s
		11	bw704		Bandwidth  704 kbit/s
		12	bw768		Bandwidth  768 kbit/s
		13	bw832		Bandwidth  832 kbit/s
		14	bw896		Bandwidth  896 kbit/s
		15	bw960		Bandwidth  960 kbit/s
		16	bw1024		Bandwidth 1024 kbit/s
		17	bw1088		Bandwidth 1088 kbit/s
		18	bw1152		Bandwidth 1152 kbit/s
		19	bw1216		Bandwidth 1216 kbit/s
		20	bw1280		Bandwidth 1280 kbit/s
		21	bw1344		Bandwidth 1344 kbit/s
		22	bw1408		Bandwidth 1408 kbit/s
		23	bw1472		Bandwidth 1472 kbit/s
		24	bw1536		Bandwidth 1536 kbit/s
		25	bw1600		Bandwidth 1600 kbit/s
		26	bw1664		Bandwidth 1664 kbit/s
		27	bw1728		Bandwidth 1728 kbit/s
		28	bw1792		Bandwidth 1792 kbit/s
		29	bw1856		Bandwidth 1856 kbit/s
		30	bw1920		Bandwidth 1920 kbit/s
		31	bw1984		Bandwidth 1984 kbit/s
		32	bw2048		Bandwidth 2048 kbit/s
		33	bw2112		Bandwidth 2112 kbit/s
		34	bw2176		Bandwidth 2176 kbit/s
		35	bw2240		Bandwidth 2240 kbit/s
		36	bw2304		Bandwidth 2304 kbit/s
		37	bw2368		Bandwidth 2368 kbit/s
		38	bw2432		Bandwidth 2432 kbit/s
		39	bw2496		Bandwidth 2496 kbit/s
		40	bw2560		Bandwidth 2560 kbit/s
		41	bw2624		Bandwidth 2624 kbit/s
		42	bw2688		Bandwidth 2688 kbit/s
		43	bw2752		Bandwidth 2752 kbit/s
		44	bw2816		Bandwidth 2816 kbit/s
		45	bw2880		Bandwidth 2880 kbit/s
		46	bw2944		Bandwidth 2944 kbit/s
		47	bw3008		Bandwidth 3008 kbit/s
		48	bw3072		Bandwidth 3072 kbit/s
		49	bw3136		Bandwidth 3136 kbit/s
		50	bw3200		Bandwidth 3200 kbit/s
		51	bw3264		Bandwidth 3264 kbit/s
		52	bw3328		Bandwidth 3328 kbit/s
		53	bw3392		Bandwidth 3392 kbit/s
		54	bw3456		Bandwidth 3456 kbit/s
		55	bw3520		Bandwidth 3520 kbit/s
		56	bw3584		Bandwidth 3584 kbit/s
		57	bw3648		Bandwidth 3648 kbit/s
		58	bw3712		Bandwidth 3712 kbit/s
		59	bw3776		Bandwidth 3776 kbit/s
		60	bw3840		Bandwidth 3840 kbit/s
		61	bw3904		Bandwidth 3904 kbit/s
		62	bw3968		Bandwidth 3968 kbit/s
		63	bw4032		Bandwidth 4032 kbit/s
		64	bw4096		Bandwidth 4096 kbit/s
		65	bw4160		Bandwidth 4160 kbit/s
		66	bw4224		Bandwidth 4224 kbit/s
		67	bw4288		Bandwidth 4288 kbit/s
		68	bw4352		Bandwidth 4352 kbit/s
		69	bw4416		Bandwidth 4416 kbit/s
		70	bw4480		Bandwidth 4480 kbit/s
		71	bw4544		Bandwidth 4544 kbit/s
		72	bw4608		Bandwidth 4608 kbit/s
		73	bw4672		Bandwidth 4672 kbit/s
		74	bw4736		Bandwidth 4736 kbit/s
		75	bw4800		Bandwidth 4800 kbit/s
		76	bw4864		Bandwidth 4864 kbit/s
		77	bw4928		Bandwidth 4928 kbit/s
		78	bw4992		Bandwidth 4992 kbit/s
		79	bw5056		Bandwidth 5056 kbit/s
		80	bw5120		Bandwidth 5120 kbit/s
		81	bw5184		Bandwidth 5184 kbit/s
		82	bw5248		Bandwidth 5248 kbit/s
		83	bw5312		Bandwidth 5312 kbit/s
		84	bw5376		Bandwidth 5376 kbit/s
		85	bw5440		Bandwidth 5440 kbit/s
		86	bw5504		Bandwidth 5504 kbit/s
		87	bw5568		Bandwidth 5568 kbit/s
		88	bw5632		Bandwidth 5632 kbit/s
		89	bw5696		Bandwidth 5696 kbit/s
		90	bw5760		Bandwidth 5760 kbit/s
		91	bw5824		Bandwidth 5824 kbit/s
		92	bw5888		Bandwidth 5888 kbit/s
		93	bw5952		Bandwidth 5952 kbit/s
		94	bw6016		Bandwidth 6016 kbit/s
		95	bw6080		Bandwidth 6080 kbit/s
		96	bw6144		Bandwidth 6144 kbit/s
		97	bw6208		Bandwidth 6208 kbit/s
		98	bw6272		Bandwidth 6272 kbit/s
		99	bw6336		Bandwidth 6336 kbit/s
		100	bw6400		Bandwidth 6400 kbit/s
		101	bw6464		Bandwidth 6464 kbit/s
		102	bw6528		Bandwidth 6528 kbit/s
		103	bw6592		Bandwidth 6592 kbit/s
		104	bw6656		Bandwidth 6656 kbit/s
		105	bw6720		Bandwidth 6720 kbit/s
		106	bw6784		Bandwidth 6784 kbit/s
		107	bw6848		Bandwidth 6848 kbit/s
		108	bw6912		Bandwidth 6912 kbit/s
		109	bw6976		Bandwidth 6976 kbit/s
		110	bw7040		Bandwidth 7040 kbit/s
		111	bw7104		Bandwidth 7104 kbit/s
		112	bw7168		Bandwidth 7168 kbit/s
		113	bw7232		Bandwidth 7232 kbit/s
		114	bw7296		Bandwidth 7296 kbit/s
		115	bw7360		Bandwidth 7360 kbit/s
		116	bw7424		Bandwidth 7424 kbit/s
		117	bw7488		Bandwidth 7488 kbit/s
		118	bw7552		Bandwidth 7552 kbit/s
		119	bw7616		Bandwidth 7616 kbit/s
		120	bw7680		Bandwidth 7680 kbit/s
		121	bw7744		Bandwidth 7744 kbit/s
		122	bw7808		Bandwidth 7808 kbit/s
		123	bw7872		Bandwidth 7872 kbit/s
		124	bw7936		Bandwidth 7936 kbit/s
		125	bw8000		Bandwidth 8000 kbit/s
		126	bw8064		Bandwidth 8064 kbit/s
		127	bw8128		Bandwidth 8128 kbit/s
		128	bw8192		Bandwidth 8192 kbit/s
		129	bw8256		Bandwidth 8256 kbit/s
		130	bw8320		Bandwidth 8320 kbit/s
		131	bw8384		Bandwidth 8384 kbit/s
		132	bw8448		Bandwidth 8448 kbit/s
		133	bw8512		Bandwidth 8512 kbit/s
		134	bw8576		Bandwidth 8576 kbit/s
		135	bw8640		Bandwidth 8640 kbit/s
		136	bw8704		Bandwidth 8704 kbit/s
		137	bw8768		Bandwidth 8768 kbit/s
		138	bw8832		Bandwidth 8832 kbit/s
		139	bw8896		Bandwidth 8896 kbit/s
		140	bw8960		Bandwidth 8960 kbit/s
		141	bw9024		Bandwidth 9024 kbit/s
		142	bw9088		Bandwidth 9088 kbit/s
		143	bw9152		Bandwidth 9152 kbit/s
		144	bw9216		Bandwidth 9216 kbit/s
		145	bw9280		Bandwidth 9280 kbit/s
		146	bw9344		Bandwidth 9344 kbit/s
		147	bw9408		Bandwidth 9408 kbit/s
		148	bw9472		Bandwidth 9472 kbit/s
		149	bw9536		Bandwidth 9536 kbit/s
		150	bw9600		Bandwidth 9600 kbit/s
		151	bw9664		Bandwidth 9664 kbit/s
		152	bw9728		Bandwidth 9728 kbit/s
		153	bw9792		Bandwidth 9792 kbit/s
		154	bw9856		Bandwidth 9856 kbit/s
		155	bw9920		Bandwidth 9920 kbit/s
		156	bw9984		Bandwidth 9984 kbit/s
		157	bw10048		Bandwidth 10048 kbit/s
		158	bw10112		Bandwidth 10112 kbit/s
		159	bw10176		Bandwidth 10176 kbit/s
		160	bw10240		Bandwidth 10240 kbit/s
		161	bw10304		Bandwidth 10304 kbit/s
		162	bw10368		Bandwidth 10368 kbit/s
		163	bw10432		Bandwidth 10432 kbit/s
		164	bw10496		Bandwidth 10496 kbit/s
		165	bw10560		Bandwidth 10560 kbit/s
		166	bw10624		Bandwidth 10624 kbit/s
		167	bw10688		Bandwidth 10688 kbit/s
		168	bw10752		Bandwidth 10752 kbit/s
		169	bw10816		Bandwidth 10816 kbit/s
		170	bw10880		Bandwidth 10880 kbit/s
		171	bw10944		Bandwidth 10944 kbit/s
		172	bw11008		Bandwidth 11008 kbit/s
		173	bw11072		Bandwidth 11072 kbit/s
		174	bw11136		Bandwidth 11136 kbit/s
		175	bw11200		Bandwidth 11200 kbit/s
		176	bw11264		Bandwidth 11264 kbit/s
		177	bw11328		Bandwidth 11328 kbit/s
		178	bw11392		Bandwidth 11392 kbit/s
		254			unknown value
		255			unsupported variable for addressed device"
	::= { cmrwLocalCommonEntry 6 }

cmrwLocalCommonClockMode OBJECT-TYPE
	SYNTAX INTEGER
	{
		systemClock(1),
		shdslClock(2),
		synchronousClock(3),
		unknown(254),
		unsupported(255)
	}
	ACCESS read-write
	STATUS mandatory
	DESCRIPTION
		"Source for the clock out.
		1	SystemClock       The source is the system clock
		2	ShdslClock	      The source is the SHDSL clock
		3	SynchronousClock	Clock Mode 3a (synchronous)
		254			unknown value
		255			unsupported
		"
	::= { cmrwLocalCommonEntry 7 }

cmrwLocalCommonMcsStructTdm OBJECT-TYPE
	SYNTAX INTEGER
	{
		disabled(1),
		enabled(2),
		unknown(254),
		unsupported(255)
	}
	ACCESS read-write
	STATUS mandatory
	DESCRIPTION
		"Determines whether MCS framing for structured TDM
		networks is enabled or not.
		1	Disabled	Transparent TDM network
		2	Enabled		Structured TDM network (TS0)
		254			unknown value
		255			unsupported
		"
	::= { cmrwLocalCommonEntry 8 }

cmrwLocalCommonMcsChBandwidth OBJECT-TYPE
	SYNTAX INTEGER
	{
		bw64(1),
		bw128(2),
		bw192(3),
		bw256(4),
		bw320(5),
		bw384(6),
		bw448(7),
		bw512(8),
		bw576(9),
		bw640(10),
		bw704(11),
		bw768(12),
		bw832(13),
		bw896(14),
		bw960(15),
		bw1024(16),
		bw1088(17),
		bw1152(18),
		bw1216(19),
		bw1280(20),
		bw1344(21),
		bw1408(22),
		bw1472(23),
		bw1536(24),
		bw1600(25),
		bw1664(26),
		bw1728(27),
		bw1792(28),
		bw1856(29),
		bw1920(30),
		bw1984(31),
		bw2048(32),
		bw2112(33),
		bw2176(34),
		bw2240(35),
		bw2304(36),
		bw2368(37),
		bw2432(38),
		bw2496(39),
		bw2560(40),
		bw2624(41),
		bw2688(42),
		bw2752(43),
		bw2816(44),
		bw2880(45),
		bw2944(46),
		bw3008(47),
		bw3072(48),
		bw3136(49),
		bw3200(50),
		bw3264(51),
		bw3328(52),
		bw3392(53),
		bw3456(54),
		bw3520(55),
		bw3584(56),
		bw3648(57),
		bw3712(58),
		bw3776(59),
		bw3840(60),
		bw3904(61),
		bw3968(62),
		bw4032(63),
		bw4096(64),
		bw4160(65),
		bw4224(66),
		bw4288(67),
		bw4352(68),
		bw4416(69),
		bw4480(70),
		bw4544(71),
		bw4608(72),
		bw4672(73),
		bw4736(74),
		bw4800(75),
		bw4864(76),
		bw4928(77),
		bw4992(78),
		bw5056(79),
		bw5120(80),
		bw5184(81),
		bw5248(82),
		bw5312(83),
		bw5376(84),
		bw5440(85),
		bw5504(86),
		bw5568(87),
		bw5632(88),
		bw5696(89),
		unknown(254),
		unsupported(255)
	}
	ACCESS read-write
	STATUS mandatory
	DESCRIPTION
		"Bandwidth allocated for all MCS channels as
		a number of 64kbit/s time slots. Between 1 and 89.
		
		When reading the following values can also be returned:
		1	bw64		Bandwidth   64 kbit/s
		2	bw128		Bandwidth  128 kbit/s
		3	bw192		Bandwidth  192 kbit/s
		4	bw256		Bandwidth  256 kbit/s
		5	bw320		Bandwidth  320 kbit/s
		6	bw384		Bandwidth  384 kbit/s
		7	bw448		Bandwidth  448 kbit/s
		8	bw512		Bandwidth  512 kbit/s
		9	bw576		Bandwidth  576 kbit/s
		10	bw640		Bandwidth  640 kbit/s
		11	bw704		Bandwidth  704 kbit/s
		12	bw768		Bandwidth  768 kbit/s
		13	bw832		Bandwidth  832 kbit/s
		14	bw896		Bandwidth  896 kbit/s
		15	bw960		Bandwidth  960 kbit/s
		16	bw1024		Bandwidth 1024 kbit/s
		17	bw1088		Bandwidth 1088 kbit/s
		18	bw1152		Bandwidth 1152 kbit/s
		19	bw1216		Bandwidth 1216 kbit/s
		20	bw1280		Bandwidth 1280 kbit/s
		21	bw1344		Bandwidth 1344 kbit/s
		22	bw1408		Bandwidth 1408 kbit/s
		23	bw1472		Bandwidth 1472 kbit/s
		24	bw1536		Bandwidth 1536 kbit/s
		25	bw1600		Bandwidth 1600 kbit/s
		26	bw1664		Bandwidth 1664 kbit/s
		27	bw1728		Bandwidth 1728 kbit/s
		28	bw1792		Bandwidth 1792 kbit/s
		29	bw1856		Bandwidth 1856 kbit/s
		30	bw1920		Bandwidth 1920 kbit/s
		31	bw1984		Bandwidth 1984 kbit/s
		32	bw2048		Bandwidth 2048 kbit/s
		33	bw2112		Bandwidth 2112 kbit/s
		34	bw2176		Bandwidth 2176 kbit/s
		35	bw2240		Bandwidth 2240 kbit/s
		36	bw2304		Bandwidth 2304 kbit/s
		37	bw2368		Bandwidth 2368 kbit/s
		38	bw2432		Bandwidth 2432 kbit/s
		39	bw2496		Bandwidth 2496 kbit/s
		40	bw2560		Bandwidth 2560 kbit/s
		41	bw2624		Bandwidth 2624 kbit/s
		42	bw2688		Bandwidth 2688 kbit/s
		43	bw2752		Bandwidth 2752 kbit/s
		44	bw2816		Bandwidth 2816 kbit/s
		45	bw2880		Bandwidth 2880 kbit/s
		46	bw2944		Bandwidth 2944 kbit/s
		47	bw3008		Bandwidth 3008 kbit/s
		48	bw3072		Bandwidth 3072 kbit/s
		49	bw3136		Bandwidth 3136 kbit/s
		50	bw3200		Bandwidth 3200 kbit/s
		51	bw3264		Bandwidth 3264 kbit/s
		52	bw3328		Bandwidth 3328 kbit/s
		53	bw3392		Bandwidth 3392 kbit/s
		54	bw3456		Bandwidth 3456 kbit/s
		55	bw3520		Bandwidth 3520 kbit/s
		56	bw3584		Bandwidth 3584 kbit/s
		57	bw3648		Bandwidth 3648 kbit/s
		58	bw3712		Bandwidth 3712 kbit/s
		59	bw3776		Bandwidth 3776 kbit/s
		60	bw3840		Bandwidth 3840 kbit/s
		61	bw3904		Bandwidth 3904 kbit/s
		62	bw3968		Bandwidth 3968 kbit/s
		63	bw4032		Bandwidth 4032 kbit/s
		64	bw4096		Bandwidth 4096 kbit/s
		65	bw4160		Bandwidth 4160 kbit/s
		66	bw4224		Bandwidth 4224 kbit/s
		67	bw4288		Bandwidth 4288 kbit/s
		68	bw4352		Bandwidth 4352 kbit/s
		69	bw4416		Bandwidth 4416 kbit/s
		70	bw4480		Bandwidth 4480 kbit/s
		71	bw4544		Bandwidth 4544 kbit/s
		72	bw4608		Bandwidth 4608 kbit/s
		73	bw4672		Bandwidth 4672 kbit/s
		74	bw4736		Bandwidth 4736 kbit/s
		75	bw4800		Bandwidth 4800 kbit/s
		76	bw4864		Bandwidth 4864 kbit/s
		77	bw4928		Bandwidth 4928 kbit/s
		78	bw4992		Bandwidth 4992 kbit/s
		79	bw5056		Bandwidth 5056 kbit/s
		80	bw5120		Bandwidth 5120 kbit/s
		81	bw5184		Bandwidth 5184 kbit/s
		82	bw5248		Bandwidth 5248 kbit/s
		83	bw5312		Bandwidth 5312 kbit/s
		84	bw5376		Bandwidth 5376 kbit/s
		85	bw5440		Bandwidth 5440 kbit/s
		86	bw5504		Bandwidth 5504 kbit/s
		87	bw5568		Bandwidth 5568 kbit/s
		88	bw5632		Bandwidth 5632 kbit/s
		89	bw5696		Bandwidth 5696 kbit/s
		254			unknown value
		255			unsupported variable for addressed device"
	::= { cmrwLocalCommonEntry 9 }

cmrwLocalCommonRpsCurrent OBJECT-TYPE
	SYNTAX INTEGER
	{
		mA50(50),
		mA60(60),
		unknown(254),
		unsupported(255)
	}
	ACCESS read-write
	STATUS mandatory
	DESCRIPTION
		"Indicates the Remote Power Supply current.
		50	mA50		RPS current limied to 50 mA
		60	mA60		RPS current limited to 60 mA
		254			unknown value
		255			unsupported
		"
	::= {cmrwLocalCommonEntry 10 }

cmrwLocalCommonLineModulation OBJECT-TYPE
	SYNTAX INTEGER
	{
		tcpam16(1),
		tcpam32(2),
		unknown(254),
		unsupported(255)
	}
	ACCESS read-write
	STATUS mandatory
	DESCRIPTION
		"Indicates the Remote Power Supply current.
		1	TC-PAM16	Line modulation TC-PAM16
		2	TC-PAM32	Line modulation TC-PAM32
		254			unknown value
		255			unsupported
		"
	::= {cmrwLocalCommonEntry 11 }

cmrwLocalCommonUseFixTimeslotsU OBJECT-TYPE
	SYNTAX INTEGER
	{
		disabled(1),
		enabled(2),
		unknown(254),
		unsupported(255)
	}
	ACCESS read-write
	STATUS mandatory
	DESCRIPTION
		"Enable or disable the fixed SHDSL Bitrate 
		configured in cmrwLocalCommonFixTimeslotsU.
		1	Disabled	SHDSL Bitrate is not fixed
		2	Enabled	SHDSL 	Bitrate is fixed
		254			unknown value
		255			unsupported variable for addressed device"
	::= { cmrwLocalCommonEntry 12 }

cmrwLocalCommonFixTimeslotsU OBJECT-TYPE
	SYNTAX INTEGER
	{
		bw64(1),
		bw128(2),
		bw192(3),
		bw256(4),
		bw320(5),
		bw384(6),
		bw448(7),
		bw512(8),
		bw576(9),
		bw640(10),
		bw704(11),
		bw768(12),
		bw832(13),
		bw896(14),
		bw960(15),
		bw1024(16),
		bw1088(17),
		bw1152(18),
		bw1216(19),
		bw1280(20),
		bw1344(21),
		bw1408(22),
		bw1472(23),
		bw1536(24),
		bw1600(25),
		bw1664(26),
		bw1728(27),
		bw1792(28),
		bw1856(29),
		bw1920(30),
		bw1984(31),
		bw2048(32),
		bw2112(33),
		bw2176(34),
		bw2240(35),
		bw2304(36),
		bw2368(37),
		bw2432(38),
		bw2496(39),
		bw2560(40),
		bw2624(41),
		bw2688(42),
		bw2752(43),
		bw2816(44),
		bw2880(45),
		bw2944(46),
		bw3008(47),
		bw3072(48),
		bw3136(49),
		bw3200(50),
		bw3264(51),
		bw3328(52),
		bw3392(53),
		bw3456(54),
		bw3520(55),
		bw3584(56),
		bw3648(57),
		bw3712(58),
		bw3776(59),
		bw3840(60),
		bw3904(61),
		bw3968(62),
		bw4032(63),
		bw4096(64),
		bw4160(65),
		bw4224(66),
		bw4288(67),
		bw4352(68),
		bw4416(69),
		bw4480(70),
		bw4544(71),
		bw4608(72),
		bw4672(73),
		bw4736(74),
		bw4800(75),
		bw4864(76),
		bw4928(77),
		bw4992(78),
		bw5056(79),
		bw5120(80),
		bw5184(81),
		bw5248(82),
		bw5312(83),
		bw5376(84),
		bw5440(85),
		bw5504(86),
		bw5568(87),
		bw5632(88),
		bw5696(89),
		unknown(254),
		unsupported(255)
	}
	ACCESS read-write
	STATUS mandatory
	DESCRIPTION
		"Fixed SHDSL Bitrate per Wire Pair (can be enabled 
		by configuring cmrwLocalCommonUseFixTimeslotsU).
		
		When reading the following values can be returned:
		1	bw64		Bandwidth   64 kbit/s
		2	bw128		Bandwidth  128 kbit/s
		3	bw192		Bandwidth  192 kbit/s
		4	bw256		Bandwidth  256 kbit/s
		5	bw320		Bandwidth  320 kbit/s
		6	bw384		Bandwidth  384 kbit/s
		7	bw448		Bandwidth  448 kbit/s
		8	bw512		Bandwidth  512 kbit/s
		9	bw576		Bandwidth  576 kbit/s
		10	bw640		Bandwidth  640 kbit/s
		11	bw704		Bandwidth  704 kbit/s
		12	bw768		Bandwidth  768 kbit/s
		13	bw832		Bandwidth  832 kbit/s
		14	bw896		Bandwidth  896 kbit/s
		15	bw960		Bandwidth  960 kbit/s
		16	bw1024		Bandwidth 1024 kbit/s
		17	bw1088		Bandwidth 1088 kbit/s
		18	bw1152		Bandwidth 1152 kbit/s
		19	bw1216		Bandwidth 1216 kbit/s
		20	bw1280		Bandwidth 1280 kbit/s
		21	bw1344		Bandwidth 1344 kbit/s
		22	bw1408		Bandwidth 1408 kbit/s
		23	bw1472		Bandwidth 1472 kbit/s
		24	bw1536		Bandwidth 1536 kbit/s
		25	bw1600		Bandwidth 1600 kbit/s
		26	bw1664		Bandwidth 1664 kbit/s
		27	bw1728		Bandwidth 1728 kbit/s
		28	bw1792		Bandwidth 1792 kbit/s
		29	bw1856		Bandwidth 1856 kbit/s
		30	bw1920		Bandwidth 1920 kbit/s
		31	bw1984		Bandwidth 1984 kbit/s
		32	bw2048		Bandwidth 2048 kbit/s
		33	bw2112		Bandwidth 2112 kbit/s
		34	bw2176		Bandwidth 2176 kbit/s
		35	bw2240		Bandwidth 2240 kbit/s
		36	bw2304		Bandwidth 2304 kbit/s
		37	bw2368		Bandwidth 2368 kbit/s
		38	bw2432		Bandwidth 2432 kbit/s
		39	bw2496		Bandwidth 2496 kbit/s
		40	bw2560		Bandwidth 2560 kbit/s
		41	bw2624		Bandwidth 2624 kbit/s
		42	bw2688		Bandwidth 2688 kbit/s
		43	bw2752		Bandwidth 2752 kbit/s
		44	bw2816		Bandwidth 2816 kbit/s
		45	bw2880		Bandwidth 2880 kbit/s
		46	bw2944		Bandwidth 2944 kbit/s
		47	bw3008		Bandwidth 3008 kbit/s
		48	bw3072		Bandwidth 3072 kbit/s
		49	bw3136		Bandwidth 3136 kbit/s
		50	bw3200		Bandwidth 3200 kbit/s
		51	bw3264		Bandwidth 3264 kbit/s
		52	bw3328		Bandwidth 3328 kbit/s
		53	bw3392		Bandwidth 3392 kbit/s
		54	bw3456		Bandwidth 3456 kbit/s
		55	bw3520		Bandwidth 3520 kbit/s
		56	bw3584		Bandwidth 3584 kbit/s
		57	bw3648		Bandwidth 3648 kbit/s
		58	bw3712		Bandwidth 3712 kbit/s
		59	bw3776		Bandwidth 3776 kbit/s
		60	bw3840		Bandwidth 3840 kbit/s
		61	bw3904		Bandwidth 3904 kbit/s
		62	bw3968		Bandwidth 3968 kbit/s
		63	bw4032		Bandwidth 4032 kbit/s
		64	bw4096		Bandwidth 4096 kbit/s
		65	bw4160		Bandwidth 4160 kbit/s
		66	bw4224		Bandwidth 4224 kbit/s
		67	bw4288		Bandwidth 4288 kbit/s
		68	bw4352		Bandwidth 4352 kbit/s
		69	bw4416		Bandwidth 4416 kbit/s
		70	bw4480		Bandwidth 4480 kbit/s
		71	bw4544		Bandwidth 4544 kbit/s
		72	bw4608		Bandwidth 4608 kbit/s
		73	bw4672		Bandwidth 4672 kbit/s
		74	bw4736		Bandwidth 4736 kbit/s
		75	bw4800		Bandwidth 4800 kbit/s
		76	bw4864		Bandwidth 4864 kbit/s
		77	bw4928		Bandwidth 4928 kbit/s
		78	bw4992		Bandwidth 4992 kbit/s
		79	bw5056		Bandwidth 5056 kbit/s
		80	bw5120		Bandwidth 5120 kbit/s
		81	bw5184		Bandwidth 5184 kbit/s
		82	bw5248		Bandwidth 5248 kbit/s
		83	bw5312		Bandwidth 5312 kbit/s
		84	bw5376		Bandwidth 5376 kbit/s
		85	bw5440		Bandwidth 5440 kbit/s
		86	bw5504		Bandwidth 5504 kbit/s
		87	bw5568		Bandwidth 5568 kbit/s
		88	bw5632		Bandwidth 5632 kbit/s
		89	bw5696		Bandwidth 5696 kbit/s
		254			unknown value
		255			unsupported variable for addressed device"
	::= { cmrwLocalCommonEntry 13 }

--------------------------------------------------------------------------------
--	CM-RW	local Clock
--------------------------------------------------------------------------------
cmrwLocalClockTable OBJECT-TYPE
	SYNTAX SEQUENCE OF CmrwLocalClockEntry
	ACCESS not-accessible
	STATUS mandatory
	DESCRIPTION ""
	::= { cmrwLocal 3 }

cmrwLocalClockEntry OBJECT-TYPE
	SYNTAX CmrwLocalClockEntry
	ACCESS not-accessible
	STATUS mandatory
	DESCRIPTION ""
	INDEX { cmrwLocalClockPortIndex, cmrwLocalClockLinkIndex }
	::= { cmrwLocalClockTable 1 }

CmrwLocalClockEntry ::=
	SEQUENCE
	{
		cmrwLocalClockPortIndex INTEGER,
		cmrwLocalClockLinkIndex INTEGER,
		cmrwLocalClockActive INTEGER,
		cmrwLocalClockT3InAvailable INTEGER,
		cmrwLocalClockTInterfaceAvailable INTEGER,
		cmrwLocalClockUInterfaceAvailable INTEGER,
		cmrwLocalClockInternalAvailable INTEGER,
		cmrwLocalClockPriority OCTET STRING
	}

cmrwLocalClockPortIndex OBJECT-TYPE
	SYNTAX INTEGER
	ACCESS read-only
	STATUS mandatory
	DESCRIPTION
		"This variable addresses the port number of the proxy
		and is used as index for the other elements in the Table"
	::= { cmrwLocalClockEntry 1 }

cmrwLocalClockLinkIndex OBJECT-TYPE
	SYNTAX INTEGER
	ACCESS read-only
	STATUS mandatory
	DESCRIPTION
		"This variable addresses the slot number of the OMI sub-rack
		and is used as index for the other elements in the Table"
	::= {cmrwLocalClockEntry 2 }

cmrwLocalClockActive OBJECT-TYPE
	SYNTAX INTEGER
	{
		t3in(1),
		tInterface(2),
		uInterface(3),
		internal(4),
		unknown(254),
		unsupported(255)
	}
	ACCESS read-only
	STATUS mandatory
	DESCRIPTION
		"Indicates which clock source is currently being used.
		1	T3In		Uses Clock input T3In
		2	TInterface	Taking Clock from signal on T-Interface
		3	UInterface	Taking Clock from signal on U-Interface
		4	Internal	Using internal oscillator to generate Clock
		254			unknown value
		255			unsupported variable for addressed device"
	::= { cmrwLocalClockEntry 3 }

cmrwLocalClockT3InAvailable OBJECT-TYPE
	SYNTAX INTEGER
	{
		false(1),
		true(2),
		unknown(254),
		unsupported(255)
	}
	ACCESS read-only
	STATUS mandatory
	DESCRIPTION
		"Reports whether Clock Input T3In is available
		1	False	Clock Input T3In not available
		2	True	Clock Input T3In available
		254		unknown value
		255		unsupported variable for addressed device"
	::= { cmrwLocalClockEntry 4 }

cmrwLocalClockTInterfaceAvailable OBJECT-TYPE
	SYNTAX INTEGER
	{
		false(1),
		true(2),
		unknown(254),
		unsupported(255)
	}
	ACCESS read-only
	STATUS mandatory
	DESCRIPTION
		"Reports whether a clock signal can be derrived from the signal
		on the T-Interface
		1	False	Clock signal available
		2	True	Clock signal available
		254		unknown value
		255		unsupported variable for addressed device"
	::= { cmrwLocalClockEntry 5 }

cmrwLocalClockUInterfaceAvailable OBJECT-TYPE
	SYNTAX INTEGER
	{
		false(1),
		true(2),
		unknown(254),
		unsupported(255)
	}
	ACCESS read-only
	STATUS mandatory
	DESCRIPTION
		"Reports whether a clock signal can be derrived from the signal
		on the U-Interface
		1	False	Clock signal available
		2	True	Clock signal available
		254		unknown value
		255		unsupported variable for addressed device"
	::= { cmrwLocalClockEntry 6 }

cmrwLocalClockInternalAvailable OBJECT-TYPE
	SYNTAX INTEGER
	{
		false(1),
		true(2),
		unknown(254),
		unsupported(255)
	}
	ACCESS read-only
	STATUS mandatory
	DESCRIPTION
		"Reports whether the internal oscillator is available
		1	False	oscillator not available
		2	True	oscillator available
		254		unknown value
		255		unsupported variable for addressed device"
	::= { cmrwLocalClockEntry 7 }

cmrwLocalClockPriority OBJECT-TYPE
	SYNTAX OCTET STRING(SIZE(4))
	ACCESS read-write
	STATUS mandatory
	DESCRIPTION
		"Used to read and set the clock priority for the different
		clock sources. The variable is an array with length 4. The
		indices correspond to the priorities (0=highest, 3=lowest).
		The following values can be contained in each position, 
		indicating which clock source has the corresponding priority:
		1	T3In		Clock Input T3In
		2	TInterface	Clock derrived from Signal at T-Interface
		3	UInterface	Clock derrived from Signal at U-Interface
		4	Internal	Internal oscillator
		254			unknown	value
		255			unsupported variable for addressed device"
	::= { cmrwLocalClockEntry 8 }

--------------------------------------------------------------------------------
--	CM-RW	local 2M
--------------------------------------------------------------------------------
cmrwLocal2MTable OBJECT-TYPE
	SYNTAX SEQUENCE OF CmrwLocal2MEntry
	ACCESS not-accessible
	STATUS mandatory
	DESCRIPTION ""
	::= { cmrwLocal 4 }

cmrwLocal2MEntry OBJECT-TYPE
	SYNTAX CmrwLocal2MEntry
	ACCESS not-accessible
	STATUS mandatory
	DESCRIPTION ""
	INDEX { cmrwLocal2MPortIndex, cmrwLocal2MLinkIndex }
	::= { cmrwLocal2MTable 1 }

CmrwLocal2MEntry ::=
	SEQUENCE
	{
		cmrwLocal2MPortIndex INTEGER,
		cmrwLocal2MLinkIndex INTEGER,
		cmrwLocal2MFraming INTEGER,
		cmrwLocal2MEnableT INTEGER,
		cmrwLocal2MTimeslotsT INTEGER,
		cmrwLocal2MIdlecodeT INTEGER,
		cmrwLocal2MCrc4T INTEGER,
		cmrwLocal2MCrc4U INTEGER,
		cmrwLocal2MDetectAis INTEGER,
		cmrwLocal2MInsertAis INTEGER,
		cmrwLocal2MSaBits OCTET STRING,
		cmrwLocal2MTs16Signalling INTEGER,
		cmrwLocal2MIdlecodeU INTEGER,
		cmrwLocal2MTs0Present INTEGER,
		cmrwLocal2MCrc4V INTEGER,
		cmrwLocal2MInterfaceImpedance INTEGER
	}

cmrwLocal2MPortIndex OBJECT-TYPE
	SYNTAX INTEGER
	ACCESS read-only
	STATUS mandatory
	DESCRIPTION
		"This variable addresses the port number of the proxy
		and is used as index for the other elements in the Table"
	::= { cmrwLocal2MEntry 1 }

cmrwLocal2MLinkIndex OBJECT-TYPE
	SYNTAX INTEGER
	ACCESS read-only
	STATUS mandatory
	DESCRIPTION
		"This variable addresses the slot number of the OMI sub-rack
		and is used as index for the other elements in the Table"
	::= {cmrwLocal2MEntry 2 }

cmrwLocal2MFraming OBJECT-TYPE
	SYNTAX INTEGER
	{
		transparent(1),
		monitoring(2),
		termination(3),
		channelized(4),
		unknown(254),
		unsupported(255)
	}
	ACCESS read-write
	STATUS mandatory
	DESCRIPTION
		"Configures Frame Alignment
		1	Transparent	No frame or multi-frame synchronisation
		2	Monitoring	Frame and Multi-Frame synchronisation but no reinsertion of Frame
		3	Termination	Frame and Multi-Frame synchronisation and reinsertion
		4	Channelized	Frame and Multi-Frame synchronisation without transmission of timeslot 0
		254			unknown value
		255			unsupported variable for addressed device"
	::= { cmrwLocal2MEntry 3 }

cmrwLocal2MEnableT OBJECT-TYPE
	SYNTAX INTEGER
	{
		disabled(1),
		enabled(2),
		unknown(254),
		unsupported(255)
	}
	ACCESS read-write
	STATUS mandatory
	DESCRIPTION
		"Enable or disable the G.703 interface (T-Interface)
		1	Disabled	G.703 Interface is disabled
		2	Enabled		G.703 Interface is enabled
		254			unknown value
		255			unsupported variable for addressed device"
	::= { cmrwLocal2MEntry 4 }

cmrwLocal2MTimeslotsT OBJECT-TYPE
	SYNTAX INTEGER
	{
		bw64(1),
		bw128(2),
		bw192(3),
		bw256(4),
		bw320(5),
		bw384(6),
		bw448(7),
		bw512(8),
		bw576(9),
		bw640(10),
		bw704(11),
		bw768(12),
		bw832(13),
		bw896(14),
		bw960(15),
		bw1024(16),
		bw1088(17),
		bw1152(18),
		bw1216(19),
		bw1280(20),
		bw1344(21),
		bw1408(22),
		bw1472(23),
		bw1536(24),
		bw1600(25),
		bw1664(26),
		bw1728(27),
		bw1792(28),
		bw1856(29),
		bw1920(30),
		bw1984(31),
		bw2048(32),
		unknown(254),
		unsupported(255)
	}
	ACCESS read-write
	STATUS mandatory
	DESCRIPTION
		"Bandwidth allocated for G.703 Interface (T-Interface) as
		a number of 64kbit/s time slots. Between 1 and 32.
		
		When reading the following values can also be returned:
		1	bw64		Bandwidth   64 kbit/s
		2	bw128		Bandwidth  128 kbit/s
		3	bw192		Bandwidth  192 kbit/s
		4	bw256		Bandwidth  256 kbit/s
		5	bw320		Bandwidth  320 kbit/s
		6	bw384		Bandwidth  384 kbit/s
		7	bw448		Bandwidth  448 kbit/s
		8	bw512		Bandwidth  512 kbit/s
		9	bw576		Bandwidth  576 kbit/s
		10	bw640		Bandwidth  640 kbit/s
		11	bw704		Bandwidth  704 kbit/s
		12	bw768		Bandwidth  768 kbit/s
		13	bw832		Bandwidth  832 kbit/s
		14	bw896		Bandwidth  896 kbit/s
		15	bw960		Bandwidth  960 kbit/s
		16	bw1024		Bandwidth 1024 kbit/s
		17	bw1088		Bandwidth 1088 kbit/s
		18	bw1152		Bandwidth 1152 kbit/s
		19	bw1216		Bandwidth 1216 kbit/s
		20	bw1280		Bandwidth 1280 kbit/s
		21	bw1344		Bandwidth 1344 kbit/s
		22	bw1408		Bandwidth 1408 kbit/s
		23	bw1472		Bandwidth 1472 kbit/s
		24	bw1536		Bandwidth 1536 kbit/s
		25	bw1600		Bandwidth 1600 kbit/s
		26	bw1664		Bandwidth 1664 kbit/s
		27	bw1728		Bandwidth 1728 kbit/s
		28	bw1792		Bandwidth 1792 kbit/s
		29	bw1856		Bandwidth 1856 kbit/s
		30	bw1920		Bandwidth 1920 kbit/s
		31	bw1984		Bandwidth 1984 kbit/s
		32	bw2048		Bandwidth 2048 kbit/s
		254			unknown value
		255			unsupported variable for addressed device"
	::= { cmrwLocal2MEntry 5 }

cmrwLocal2MIdlecodeT OBJECT-TYPE
	SYNTAX INTEGER
	{
		ais(1),
		es(2),
		pais(3),
		none(4),
		unknown(254),
		unsupported(255)
	}
	ACCESS read-write
	STATUS mandatory
	DESCRIPTION
		"Defines the Idle Code on the T-Interface.
		1	AIS	AIS
		2	ES	ES
		3	PAIS	PAIS
		4	None	No Idle Code 
		254		unknown value
		255		unsupported variable for addressed device"
	::= { cmrwLocal2MEntry 6 }

cmrwLocal2MCrc4T OBJECT-TYPE
	SYNTAX INTEGER
	{
		off(1),
		on(2),
		autoOff(3),
		unknown(254),
		unsupported(255)
	}
	ACCESS read-write
	STATUS mandatory
	DESCRIPTION
		"Defines whether CRC-4 evaluation at the T-Interface is done.
		1	Off	CRC-4 Data is not evaluated
		2	On	CRC-4 Data is evaluated, error if none present in signal
		3	AutoOff	CRC-4 Data is evaluated, if none is present, evaluation is disabled
		254		unknown value
		255		unsupported variable for addressed device"
	::= { cmrwLocal2MEntry 7 }

cmrwLocal2MCrc4U OBJECT-TYPE
	SYNTAX INTEGER
	{
		off(1),
		on(2),
		unknown(254),
		unsupported(255)
	}
	ACCESS read-write
	STATUS mandatory
	DESCRIPTION
		"Defines whether CRC-4 evaluation at the U-Interface is done.
		1	Off	CRC-4 Data is not evaluated
		2	On	CRC-4 Data is evaluated, error if none present in signal
		254		unknown value
		255		unsupported variable for addressed device"
	::= { cmrwLocal2MEntry 8 }

cmrwLocal2MDetectAis OBJECT-TYPE
	SYNTAX INTEGER
	{
		noDetect(1),
		detect(2),
		unknown(254),
		unsupported(255)
	}
	ACCESS read-write
	STATUS mandatory
	DESCRIPTION
		"Defines whether AIS detection is enabled or not
		1	NoDetect	AIS is not detected
		2	Detect		AIS is detected
		254			unknown value
		255			unsupported variable for addressed device"
	::= { cmrwLocal2MEntry 9 }

cmrwLocal2MInsertAis OBJECT-TYPE
	SYNTAX INTEGER
	{
		noInsertion(1),
		insertion(2),
		unknown(254),
		unsupported(255)
	}
	ACCESS read-write
	STATUS mandatory
	DESCRIPTION
		"Defines whether an AIS signal is regenerated or just passed through
		1	NoInsertion	Pass signal through
		2	Insertion	Regenerate signal
		254			unknown value
		255			unsupported variable for addressed device"
	::= { cmrwLocal2MEntry 10 }

cmrwLocal2MSaBits OBJECT-TYPE
	SYNTAX OCTET STRING(SIZE(6))
	ACCESS read-write
	STATUS mandatory
	DESCRIPTION
		"Contains the Sa-bit configuration. The variable is an array with length 6.
		The indicies address the Sa bits as follows:
		[0]	Sa4
		[1]	Sa5
		[2]	Sa6
		[3]	Sa7
		[4]	Sa8
		[5]	Sa6 Loop Detection
		Positions 0,3 and 4 (Sa4, Sa7, Sa8) can contain the following values:
		1	Transparent
		2	Constant Ones
		Position 1 (Sa5) can contain the following values:
		1	Transparent
		2	Constant Ones
		3	Insert
		Position 2 (Sa6) can contain the following values:
		1	Transparent
		2	Constant Ones
		3	ETSI Norm
		4	ANSI Norm
		Position 5 (Sa6 Loop Detection) can contain the following values:
		1	Loop Detection Off
		2	Loop Detection On
		
		All 6 positions can contain the values below:
		254		unknown value
		255		unsupported variable for addressed device"
	::= { cmrwLocal2MEntry 11 }

cmrwLocal2MTs16Signalling OBJECT-TYPE
	SYNTAX INTEGER
	{
		transparent(1),
		new(2),
		unknown(254),
		unsupported(255)
	}
	ACCESS read-write
	STATUS mandatory
	DESCRIPTION
		"Defines whether time slot 16 is passed through transparently or
		whether it is reinsertet.
		1	Transparent	Passing through TS16
		2	New		Reinserting TS16
		254			unknown value
		255			unsupported variable for addressed device"
	::= { cmrwLocal2MEntry 12 }

cmrwLocal2MIdlecodeU OBJECT-TYPE
	SYNTAX INTEGER
	{
		ais(1),
		es(2),
		pais(3),
		none(4),
		unknown(254),
		unsupported(255)
	}
	ACCESS read-write
	STATUS mandatory
	DESCRIPTION
		"Defines the Idle Code on the U-Interface.
		1	AIS	AIS
		2	ES	ES
		3	PAIS	PAIS
		4	none	no Idle Code
		254		unknown value
		255		unsupported variable for addressed device"
	::= { cmrwLocal2MEntry 13 }

cmrwLocal2MTs0Present OBJECT-TYPE
	SYNTAX INTEGER
	{
		no(1),
		yes(2),
		unknown(254),
		unsupported(255)
	}
	ACCESS read-write
	STATUS mandatory
	DESCRIPTION
		"Defines whether timeslot 0 (G.704 frame) is actually
		transmitted by the U interface.
		1	No	Timeslot 0 is re-inserted by receiver
		2	Yes	Timeslot 0 is actually sent
		254		unknown value
		255		unsupported variable for addressed device"
	::= { cmrwLocal2MEntry 14 }

cmrwLocal2MCrc4V OBJECT-TYPE
	SYNTAX INTEGER
	{
		off(1),
		on(2),
		unknown(254),
		unsupported(255)
	}
	ACCESS read-write
	STATUS mandatory
	DESCRIPTION
		"Defines whether CRC-4 evaluation at the V-Interfaces is done.
		1	Off	CRC-4 Data is not evaluated
		2	On	CRC-4 Data is evaluated, error if none present in signal
		254		unknown value
		255		unsupported variable for addressed device"
	::= { cmrwLocal2MEntry 15 }

cmrwLocal2MInterfaceImpedance OBJECT-TYPE
	SYNTAX INTEGER
	{
		ohm75(75),
		ohm120(120),
		unknown(254),
		unsupported(255)
	}
	ACCESS read-write
	STATUS mandatory
	DESCRIPTION
		"Indicates the impedance of the G.703 interface.
		75	ohm75	The impedance of the G.703 interface is 75 Ohm.
		120	ohm120	The impedance of the G.703 interface is 120 Ohm.
		254		unknown value
		255		unsupported variable for addressed device"
	::= { cmrwLocal2MEntry 16 }

--------------------------------------------------------------------------------
--	CM-RW	local Data
--------------------------------------------------------------------------------
cmrwLocalDataTable OBJECT-TYPE
	SYNTAX SEQUENCE OF CmrwLocalDataEntry
	ACCESS not-accessible
	STATUS mandatory
	DESCRIPTION ""
	::= { cmrwLocal 5 }

cmrwLocalDataEntry OBJECT-TYPE
	SYNTAX CmrwLocalDataEntry
	ACCESS not-accessible
	STATUS mandatory
	DESCRIPTION ""
	INDEX { cmrwLocalDataPortIndex, cmrwLocalDataLinkIndex }
	::= { cmrwLocalDataTable 1 }

CmrwLocalDataEntry ::=
	SEQUENCE
	{
		cmrwLocalDataPortIndex INTEGER,
		cmrwLocalDataLinkIndex INTEGER,
		cmrwLocalDataEnabledD INTEGER,
		cmrwLocalDataTimeslotsD INTEGER,
		cmrwLocalDataIdlecodeD INTEGER,
		cmrwLocalDataFastSig INTEGER,
		cmrwLocalDataLine106 INTEGER,
		cmrwLocalDataLine107 INTEGER,
		cmrwLocalDataLine109 INTEGER,
		cmrwLocalDataLine140 INTEGER,
		cmrwLocalDataLine141 INTEGER,
		cmrwLocalDataUseTs16ForData INTEGER,
		cmrwLocalDataEndToEndSignalling INTEGER,
		cmrwLocalDataDteDceMode INTEGER,
		cmrwLocalDataIfSelector INTEGER
	}

cmrwLocalDataPortIndex OBJECT-TYPE
	SYNTAX INTEGER
	ACCESS read-only
	STATUS mandatory
	DESCRIPTION
		"This variable addresses the port number of the proxy
		and is used as index for the other elements in the Table"
	::= { cmrwLocalDataEntry 1 }

cmrwLocalDataLinkIndex OBJECT-TYPE
	SYNTAX INTEGER
	ACCESS read-only
	STATUS mandatory
	DESCRIPTION
		"This variable addresses the slot number of the OMI sub-rack
		and is used as index for the other elements in the Table"
	::= {cmrwLocalDataEntry 2 }

cmrwLocalDataEnabledD OBJECT-TYPE
	SYNTAX INTEGER
	{
		disabled(1),
		enabled(2),
		unknown(254),
		unsupported(255)
	}
	ACCESS read-write
	STATUS mandatory
	DESCRIPTION
		"Defines whether the Data Interface is enabled or not.
		1	Disabled	Data Interface is disabled
		2	Enabled		Data Interface is enabled
		254			unknown value
		255			unsupported variable for addressed device"
	::= { cmrwLocalDataEntry 3 }

cmrwLocalDataTimeslotsD OBJECT-TYPE
	SYNTAX INTEGER
	{
		bw64(1),
		bw128(2),
		bw192(3),
		bw256(4),
		bw320(5),
		bw384(6),
		bw448(7),
		bw512(8),
		bw576(9),
		bw640(10),
		bw704(11),
		bw768(12),
		bw832(13),
		bw896(14),
		bw960(15),
		bw1024(16),
		bw1088(17),
		bw1152(18),
		bw1216(19),
		bw1280(20),
		bw1344(21),
		bw1408(22),
		bw1472(23),
		bw1536(24),
		bw1600(25),
		bw1664(26),
		bw1728(27),
		bw1792(28),
		bw1856(29),
		bw1920(30),
		bw1984(31),
		bw2048(32),
		bw2112(33),
		bw2176(34),
		bw2240(35),
		bw2304(36),
		bw2368(37),
		bw2432(38),
		bw2496(39),
		bw2560(40),
		bw2624(41),
		bw2688(42),
		bw2752(43),
		bw2816(44),
		bw2880(45),
		bw2944(46),
		bw3008(47),
		bw3072(48),
		bw3136(49),
		bw3200(50),
		bw3264(51),
		bw3328(52),
		bw3392(53),
		bw3456(54),
		bw3520(55),
		bw3584(56),
		bw3648(57),
		bw3712(58),
		bw3776(59),
		bw3840(60),
		bw3904(61),
		bw3968(62),
		bw4032(63),
		bw4096(64),
		bw4160(65),
		bw4224(66),
		bw4288(67),
		bw4352(68),
		bw4416(69),
		bw4480(70),
		bw4544(71),
		bw4608(72),
		bw4672(73),
		bw4736(74),
		bw4800(75),
		bw4864(76),
		bw4928(77),
		bw4992(78),
		bw5056(79),
		bw5120(80),
		bw5184(81),
		bw5248(82),
		bw5312(83),
		bw5376(84),
		bw5440(85),
		bw5504(86),
		bw5568(87),
		bw5632(88),
		bw5696(89),
		bw5760(90),
		bw5824(91),
		bw5888(92),
		bw5952(93),
		bw6016(94),
		bw6080(95),
		bw6144(96),
		bw6208(97),
		bw6272(98),
		bw6336(99),
		bw6400(100),
		bw6464(101),
		bw6528(102),
		bw6592(103),
		bw6656(104),
		bw6720(105),
		bw6784(106),
		bw6848(107),
		bw6912(108),
		bw6976(109),
		bw7040(110),
		bw7104(111),
		bw7168(112),
		bw7232(113),
		bw7296(114),
		bw7360(115),
		bw7424(116),
		bw7488(117),
		bw7552(118),
		bw7616(119),
		bw7680(120),
		bw7744(121),
		bw7808(122),
		bw7872(123),
		bw7936(124),
		bw8000(125),
		bw8064(126),
		bw8128(127),
		bw8192(128),
		bw8256(129),
		bw8320(130),
		bw8384(131),
		bw8448(132),
		bw8512(133),
		bw8576(134),
		bw8640(135),
		bw8704(136),
		bw8768(137),
		bw8832(138),
		bw8896(139),
		bw8960(140),
		bw9024(141),
		bw9088(142),
		bw9152(143),
		bw9216(144),
		bw9280(145),
		bw9344(146),
		bw9408(147),
		bw9472(148),
		bw9536(149),
		bw9600(150),
		bw9664(151),
		bw9728(152),
		bw9792(153),
		bw9856(154),
		bw9920(155),
		bw9984(156),
		bw10048(157),
		bw10112(158),
		bw10176(159),
		bw10240(160),
		bw10304(161),
		bw10368(162),
		bw10432(163),
		bw10496(164),
		bw10560(165),
		bw10624(166),
		bw10688(167),
		bw10752(168),
		bw10816(169),
		bw10880(170),
		bw10944(171),
		bw11008(172),
		bw11072(173),
		bw11136(174),
		bw11200(175),
		bw11264(176),
		bw11328(177),
		bw11392(178),
		unknown(254),
		unsupported(255)
	}
	ACCESS read-write
	STATUS mandatory
	DESCRIPTION
		"Bandwidth allocated for Data (D-Interface) as
		a number of 64kbit/s time slots.
		
		When reading the following values can also be returned:
		1	bw64		Bandwidth   64 kbit/s
		2	bw128		Bandwidth  128 kbit/s
		3	bw192		Bandwidth  192 kbit/s
		4	bw256		Bandwidth  256 kbit/s
		5	bw320		Bandwidth  320 kbit/s
		6	bw384		Bandwidth  384 kbit/s
		7	bw448		Bandwidth  448 kbit/s
		8	bw512		Bandwidth  512 kbit/s
		9	bw576		Bandwidth  576 kbit/s
		10	bw640		Bandwidth  640 kbit/s
		11	bw704		Bandwidth  704 kbit/s
		12	bw768		Bandwidth  768 kbit/s
		13	bw832		Bandwidth  832 kbit/s
		14	bw896		Bandwidth  896 kbit/s
		15	bw960		Bandwidth  960 kbit/s
		16	bw1024		Bandwidth 1024 kbit/s
		17	bw1088		Bandwidth 1088 kbit/s
		18	bw1152		Bandwidth 1152 kbit/s
		19	bw1216		Bandwidth 1216 kbit/s
		20	bw1280		Bandwidth 1280 kbit/s
		21	bw1344		Bandwidth 1344 kbit/s
		22	bw1408		Bandwidth 1408 kbit/s
		23	bw1472		Bandwidth 1472 kbit/s
		24	bw1536		Bandwidth 1536 kbit/s
		25	bw1600		Bandwidth 1600 kbit/s
		26	bw1664		Bandwidth 1664 kbit/s
		27	bw1728		Bandwidth 1728 kbit/s
		28	bw1792		Bandwidth 1792 kbit/s
		29	bw1856		Bandwidth 1856 kbit/s
		30	bw1920		Bandwidth 1920 kbit/s
		31	bw1984		Bandwidth 1984 kbit/s
		32	bw2048		Bandwidth 2048 kbit/s
		33	bw2112		Bandwidth 2112 kbit/s
		34	bw2176		Bandwidth 2176 kbit/s
		35	bw2240		Bandwidth 2240 kbit/s
		36	bw2304		Bandwidth 2304 kbit/s
		37	bw2368		Bandwidth 2368 kbit/s
		38	bw2432		Bandwidth 2432 kbit/s
		39	bw2496		Bandwidth 2496 kbit/s
		40	bw2560		Bandwidth 2560 kbit/s
		41	bw2624		Bandwidth 2624 kbit/s
		42	bw2688		Bandwidth 2688 kbit/s
		43	bw2752		Bandwidth 2752 kbit/s
		44	bw2816		Bandwidth 2816 kbit/s
		45	bw2880		Bandwidth 2880 kbit/s
		46	bw2944		Bandwidth 2944 kbit/s
		47	bw3008		Bandwidth 3008 kbit/s
		48	bw3072		Bandwidth 3072 kbit/s
		49	bw3136		Bandwidth 3136 kbit/s
		50	bw3200		Bandwidth 3200 kbit/s
		51	bw3264		Bandwidth 3264 kbit/s
		52	bw3328		Bandwidth 3328 kbit/s
		53	bw3392		Bandwidth 3392 kbit/s
		54	bw3456		Bandwidth 3456 kbit/s
		55	bw3520		Bandwidth 3520 kbit/s
		56	bw3584		Bandwidth 3584 kbit/s
		57	bw3648		Bandwidth 3648 kbit/s
		58	bw3712		Bandwidth 3712 kbit/s
		59	bw3776		Bandwidth 3776 kbit/s
		60	bw3840		Bandwidth 3840 kbit/s
		61	bw3904		Bandwidth 3904 kbit/s
		62	bw3968		Bandwidth 3968 kbit/s
		63	bw4032		Bandwidth 4032 kbit/s
		64	bw4096		Bandwidth 4096 kbit/s
		65	bw4160		Bandwidth 4160 kbit/s
		66	bw4224		Bandwidth 4224 kbit/s
		67	bw4288		Bandwidth 4288 kbit/s
		68	bw4352		Bandwidth 4352 kbit/s
		69	bw4416		Bandwidth 4416 kbit/s
		70	bw4480		Bandwidth 4480 kbit/s
		71	bw4544		Bandwidth 4544 kbit/s
		72	bw4608		Bandwidth 4608 kbit/s
		73	bw4672		Bandwidth 4672 kbit/s
		74	bw4736		Bandwidth 4736 kbit/s
		75	bw4800		Bandwidth 4800 kbit/s
		76	bw4864		Bandwidth 4864 kbit/s
		77	bw4928		Bandwidth 4928 kbit/s
		78	bw4992		Bandwidth 4992 kbit/s
		79	bw5056		Bandwidth 5056 kbit/s
		80	bw5120		Bandwidth 5120 kbit/s
		81	bw5184		Bandwidth 5184 kbit/s
		82	bw5248		Bandwidth 5248 kbit/s
		83	bw5312		Bandwidth 5312 kbit/s
		84	bw5376		Bandwidth 5376 kbit/s
		85	bw5440		Bandwidth 5440 kbit/s
		86	bw5504		Bandwidth 5504 kbit/s
		87	bw5568		Bandwidth 5568 kbit/s
		88	bw5632		Bandwidth 5632 kbit/s
		89	bw5696		Bandwidth 5696 kbit/s
		90	bw5760		Bandwidth 5760 kbit/s
		91	bw5824		Bandwidth 5824 kbit/s
		92	bw5888		Bandwidth 5888 kbit/s
		93	bw5952		Bandwidth 5952 kbit/s
		94	bw6016		Bandwidth 6016 kbit/s
		95	bw6080		Bandwidth 6080 kbit/s
		96	bw6144		Bandwidth 6144 kbit/s
		97	bw6208		Bandwidth 6208 kbit/s
		98	bw6272		Bandwidth 6272 kbit/s
		99	bw6336		Bandwidth 6336 kbit/s
		100	bw6400		Bandwidth 6400 kbit/s
		101	bw6464		Bandwidth 6464 kbit/s
		102	bw6528		Bandwidth 6528 kbit/s
		103	bw6592		Bandwidth 6592 kbit/s
		104	bw6656		Bandwidth 6656 kbit/s
		105	bw6720		Bandwidth 6720 kbit/s
		106	bw6784		Bandwidth 6784 kbit/s
		107	bw6848		Bandwidth 6848 kbit/s
		108	bw6912		Bandwidth 6912 kbit/s
		109	bw6976		Bandwidth 6976 kbit/s
		110	bw7040		Bandwidth 7040 kbit/s
		111	bw7104		Bandwidth 7104 kbit/s
		112	bw7168		Bandwidth 7168 kbit/s
		113	bw7232		Bandwidth 7232 kbit/s
		114	bw7296		Bandwidth 7296 kbit/s
		115	bw7360		Bandwidth 7360 kbit/s
		116	bw7424		Bandwidth 7424 kbit/s
		117	bw7488		Bandwidth 7488 kbit/s
		118	bw7552		Bandwidth 7552 kbit/s
		119	bw7616		Bandwidth 7616 kbit/s
		120	bw7680		Bandwidth 7680 kbit/s
		121	bw7744		Bandwidth 7744 kbit/s
		122	bw7808		Bandwidth 7808 kbit/s
		123	bw7872		Bandwidth 7872 kbit/s
		124	bw7936		Bandwidth 7936 kbit/s
		125	bw8000		Bandwidth 8000 kbit/s
		126	bw8064		Bandwidth 8064 kbit/s
		127	bw8128		Bandwidth 8128 kbit/s
		128	bw8192		Bandwidth 8192 kbit/s
		129	bw8256		Bandwidth 8256 kbit/s
		130	bw8320		Bandwidth 8320 kbit/s
		131	bw8384		Bandwidth 8384 kbit/s
		132	bw8448		Bandwidth 8448 kbit/s
		133	bw8512		Bandwidth 8512 kbit/s
		134	bw8576		Bandwidth 8576 kbit/s
		135	bw8640		Bandwidth 8640 kbit/s
		136	bw8704		Bandwidth 8704 kbit/s
		137	bw8768		Bandwidth 8768 kbit/s
		138	bw8832		Bandwidth 8832 kbit/s
		139	bw8896		Bandwidth 8896 kbit/s
		140	bw8960		Bandwidth 8960 kbit/s
		141	bw9024		Bandwidth 9024 kbit/s
		142	bw9088		Bandwidth 9088 kbit/s
		143	bw9152		Bandwidth 9152 kbit/s
		144	bw9216		Bandwidth 9216 kbit/s
		145	bw9280		Bandwidth 9280 kbit/s
		146	bw9344		Bandwidth 9344 kbit/s
		147	bw9408		Bandwidth 9408 kbit/s
		148	bw9472		Bandwidth 9472 kbit/s
		149	bw9536		Bandwidth 9536 kbit/s
		150	bw9600		Bandwidth 9600 kbit/s
		151	bw9664		Bandwidth 9664 kbit/s
		152	bw9728		Bandwidth 9728 kbit/s
		153	bw9792		Bandwidth 9792 kbit/s
		154	bw9856		Bandwidth 9856 kbit/s
		155	bw9920		Bandwidth 9920 kbit/s
		156	bw9984		Bandwidth 9984 kbit/s
		157	bw10048		Bandwidth 10048 kbit/s
		158	bw10112		Bandwidth 10112 kbit/s
		159	bw10176		Bandwidth 10176 kbit/s
		160	bw10240		Bandwidth 10240 kbit/s
		161	bw10304		Bandwidth 10304 kbit/s
		162	bw10368		Bandwidth 10368 kbit/s
		163	bw10432		Bandwidth 10432 kbit/s
		164	bw10496		Bandwidth 10496 kbit/s
		165	bw10560		Bandwidth 10560 kbit/s
		166	bw10624		Bandwidth 10624 kbit/s
		167	bw10688		Bandwidth 10688 kbit/s
		168	bw10752		Bandwidth 10752 kbit/s
		169	bw10816		Bandwidth 10816 kbit/s
		170	bw10880		Bandwidth 10880 kbit/s
		171	bw10944		Bandwidth 10944 kbit/s
		172	bw11008		Bandwidth 11008 kbit/s
		173	bw11072		Bandwidth 11072 kbit/s
		174	bw11136		Bandwidth 11136 kbit/s
		175	bw11200		Bandwidth 11200 kbit/s
		176	bw11264		Bandwidth 11264 kbit/s
		177	bw11328		Bandwidth 11328 kbit/s
		178	bw11392		Bandwidth 11392 kbit/s
		254			unknown value
		255			unsupported variable for addressed device"
	::= { cmrwLocalDataEntry 4 }

cmrwLocalDataIdlecodeD OBJECT-TYPE
	SYNTAX INTEGER
	{
		null(1),
		ais(2),
		unknown(254),
		unsupported(255)
	}
	ACCESS read-write
	STATUS mandatory
	DESCRIPTION
		"Defines the Idle Code for the Data Interface.
		1	Null	Always send 0
		2	Ais	Always send 1
		254		unknown value
		255		unsupported variable for addressed device"
	::= { cmrwLocalDataEntry 5 }

cmrwLocalDataFastSig OBJECT-TYPE
	SYNTAX INTEGER
	{
		off(1),
		on(2),
		unknown(254),
		unsupported(255)
	}
	ACCESS read-write
	STATUS mandatory
	DESCRIPTION
		"Defines whether Fast Signalling is used or not
		1	Off	Fast Signalling is not used
		2	On	Fast Signalling is used
		254		unknown value
		255		unsupported variable for addressed device"
	::= { cmrwLocalDataEntry 6 }

cmrwLocalDataLine106 OBJECT-TYPE
	SYNTAX INTEGER
	{
		auto(1),
		perm(2),
		unknown(254),
		unsupported(255)
	}
	ACCESS read-write
	STATUS mandatory
	DESCRIPTION
		"Defines whether control line 106 is set automatically or
		permanently turned on.
		1	Auto	Automatically set
		2	Perm	Permanently on
		254		unknown value
		255		unsupported variable for addressed device"
	::= { cmrwLocalDataEntry 7 }

cmrwLocalDataLine107 OBJECT-TYPE
	SYNTAX INTEGER
	{
		auto(1),
		perm(2),
		unknown(254),
		unsupported(255)
	}
	ACCESS read-write
	STATUS mandatory
	DESCRIPTION
		"Defines whether control line 107 is set automatically or
		permanently turned on.
		1	Auto	Automatically set
		2	Perm	Permanently on
		254		unknown value
		255		unsupported variable for addressed device"
	::= { cmrwLocalDataEntry 8 }

cmrwLocalDataLine109 OBJECT-TYPE
	SYNTAX INTEGER
	{
		auto(1),
		perm(2),
		unknown(254),
		unsupported(255)
	}
	ACCESS read-write
	STATUS mandatory
	DESCRIPTION
		"Defines whether control line 109 is set automatically or
		permanently turned on.
		1	Auto	Automatically set
		2	Perm	Permanently on
		254		unknown value
		255		unsupported variable for addressed device"
	::= { cmrwLocalDataEntry 9 }

cmrwLocalDataLine140 OBJECT-TYPE
	SYNTAX INTEGER
	{
		auto(1),
		perm(2),
		unknown(254),
		unsupported(255)
	}
	ACCESS read-write
	STATUS mandatory
	DESCRIPTION
		"Defines whether control line 140 is set automatically or
		permanently turned off.
		1	Auto	Automatically set
		2	Perm	Permanently off
		254		unknown value
		255		unsupported variable for addressed device"
	::= { cmrwLocalDataEntry 10 }

cmrwLocalDataLine141 OBJECT-TYPE
	SYNTAX INTEGER
	{
		auto(1),
		perm(2),
		unknown(254),
		unsupported(255)
	}
	ACCESS read-write
	STATUS mandatory
	DESCRIPTION
		"Defines whether control line 141 is set automatically or
		permanently turned off.
		1	Auto	Automatically set
		2	Perm	Permanently off
		254		unknown value
		255		unsupported variable for addressed device"
	::= { cmrwLocalDataEntry 11 }

cmrwLocalDataUseTs16ForData OBJECT-TYPE
	SYNTAX INTEGER
	{
		no(1),
		yes(2),
		unknown(254),
		unsupported(255)
	}
	ACCESS read-write
	STATUS mandatory
	DESCRIPTION
		"Defines whether timeslot 16 can be used for data when
		no signalling information is transmitted in it.
		1	No	Timeslot 16 is reserved even if no signalling is used
		2	Yes	Timeslot 16 is used for data if no signalling is used
		254		unknown value
		255		unsupported variable for addressed device"
	::= { cmrwLocalDataEntry 12 }

cmrwLocalDataEndToEndSignalling OBJECT-TYPE
	SYNTAX INTEGER
	{
		disabled(1),
		fastSig(2),
		cas(3),
		unknown(254),
		unsupported(255)
	}
	ACCESS read-write
	STATUS mandatory
	DESCRIPTION
		"Defines whether End To End Signalling is enabled.
		1	Disabled	End To End Signalling is disabled
		2	FastSig		End To End Signalling is fast signalling
		3	CAS		End To End Signalling is CAS
		254			unknown value
		255			unsupported variable for addressed device"
	::= { cmrwLocalDataEntry 13 }

cmrwLocalDataDteDceMode OBJECT-TYPE
	SYNTAX INTEGER
	{
		dce(1),
		dte(2),
		unknown(254),
		unsupported(255)
	}
	ACCESS read-write
	STATUS mandatory
	DESCRIPTION
		"Defines the operation mode of the data interface.
		1	DCE	Data Interface operates in DCE (Data Circuit-Terminating Equipment) mode
		2	DTE	Data Interface operates in DTE (Data Terminal Equipment) mode
		254		unknown value
		255		unsupported variable for addressed device"
	::= { cmrwLocalDataEntry 14 }

cmrwLocalDataIfSelector OBJECT-TYPE
	SYNTAX INTEGER
	{
		mgblEthIf(1),
		multiPurpDataIf(2),
		unknown(254),
		unsupported(255)
	}
	ACCESS read-write
	STATUS mandatory
	DESCRIPTION
		"Selects the active data Interface.
		1	mgblEthIf	Manageable Ethernet Interface is selected
		2	multiPurpDataIf	Multi Purpose Data Interface is selected
		254			unknown value
		255			unsupported variable for addressed device"
	::= { cmrwLocalDataEntry 15 }

--------------------------------------------------------------------------------
--	CM-RW	local Action
--------------------------------------------------------------------------------
cmrwLocalActionTable OBJECT-TYPE
	SYNTAX SEQUENCE OF CmrwLocalActionEntry
	ACCESS not-accessible
	STATUS mandatory
	DESCRIPTION ""
	::= { cmrwLocal 6 }

cmrwLocalActionEntry OBJECT-TYPE
	SYNTAX CmrwLocalActionEntry
	ACCESS not-accessible
	STATUS mandatory
	DESCRIPTION ""
	INDEX { cmrwLocalActionPortIndex, cmrwLocalActionLinkIndex }
	::= { cmrwLocalActionTable 1 }

CmrwLocalActionEntry ::=
	SEQUENCE
	{
		cmrwLocalActionPortIndex INTEGER,
		cmrwLocalActionLinkIndex INTEGER,
		cmrwLocalActionReboot INTEGER
	}

cmrwLocalActionPortIndex OBJECT-TYPE
	SYNTAX INTEGER
	ACCESS read-only
	STATUS mandatory
	DESCRIPTION
		"This variable addresses the port number of the proxy
		and is used as index for the other elements in the Table"
	::= { cmrwLocalActionEntry 1 }

cmrwLocalActionLinkIndex OBJECT-TYPE
	SYNTAX INTEGER
	ACCESS read-only
	STATUS mandatory
	DESCRIPTION
		"This variable addresses the slot number of the OMI sub-rack
		and is used as index for the other elements in the Table"
	::= {cmrwLocalActionEntry 2 }

cmrwLocalActionReboot OBJECT-TYPE
	SYNTAX INTEGER {
		passive(1),
		active(2),
		unknown(254),
		unsupported(255)
	}
	ACCESS read-write
	STATUS mandatory
	DESCRIPTION
		"Command to reboot device. The parameter specifies whether
		the firmware in the active or passive bank shall be started.
		1	Passive	Reboot using the passive firmware
		2	Active	Reboot using the active firmware
		254		unknown value
		255		unsupported variable for addressed device
		
		If the parameter 'passive' is specified but the passive
		firmware bank contains no valid code, the device reboots
		using the active firmware."
	::= { cmrwLocalActionEntry 3 }

--------------------------------------------------------------------------------
--	CM-RW	Local User Data
------------------------------------------------------------------------------
cmrwLocalUserDataTable OBJECT-TYPE
	SYNTAX SEQUENCE OF CmrwLocalUserDataEntry
	ACCESS not-accessible
	STATUS mandatory
	DESCRIPTION ""
	::= { cmrwLocal 7 }

cmrwLocalUserDataEntry OBJECT-TYPE
	SYNTAX CmrwLocalUserDataEntry
	ACCESS not-accessible
	STATUS mandatory
	DESCRIPTION ""
	INDEX { cmrwLocalUserDataPortIndex, cmrwLocalUserDataLinkIndex, cmrwLocalUserDataItemIndex }
	::= { cmrwLocalUserDataTable 1 }

CmrwLocalUserDataEntry ::=
	SEQUENCE
	{
		cmrwLocalUserDataPortIndex INTEGER,
		cmrwLocalUserDataLinkIndex INTEGER,
		cmrwLocalUserDataItemIndex INTEGER,
		cmrwLocalUserData DisplayString
	}

cmrwLocalUserDataPortIndex OBJECT-TYPE
	SYNTAX INTEGER
	ACCESS read-only
	STATUS mandatory
	DESCRIPTION
		"This variable addresses the port number of the proxy
		and is used as index for the other elements in the Table"
	::= { cmrwLocalUserDataEntry 1 }

cmrwLocalUserDataLinkIndex OBJECT-TYPE
	SYNTAX INTEGER
	ACCESS read-only
	STATUS mandatory
	DESCRIPTION
		"This variable addresses the slot number of the OMI sub-rack
		and is used as index for the other elements in the Table"
	::= {cmrwLocalUserDataEntry 2 }

cmrwLocalUserDataItemIndex OBJECT-TYPE
	SYNTAX INTEGER
	ACCESS read-only
	STATUS mandatory
	DESCRIPTION
		"This variable addresses the data field number of the user data 
		and is used as index for the other elements in the Table"
	::= {cmrwLocalUserDataEntry 3 }

cmrwLocalUserData OBJECT-TYPE
	SYNTAX DisplayString(SIZE(100))
	ACCESS read-write
	STATUS mandatory
	DESCRIPTION
	"User data that can be written to the device"
	::= {cmrwLocalUserDataEntry 4 }

--------------------------------------------------------------------------------
--	CM-RW	Power Back Off
--------------------------------------------------------------------------------
cmrwLocalPowerBackOffTable OBJECT-TYPE
	SYNTAX SEQUENCE OF CmrwLocalPowerBackOffEntry
	ACCESS not-accessible
	STATUS mandatory
	DESCRIPTION ""
	::= { cmrwLocal 8 }

cmrwLocalPowerBackOffEntry OBJECT-TYPE
	SYNTAX CmrwLocalPowerBackOffEntry
	ACCESS not-accessible
	STATUS mandatory
	DESCRIPTION ""
	INDEX { cmrwLocalPowerBackOffPortIndex, cmrwLocalPowerBackOffLinkIndex }
	::= { cmrwLocalPowerBackOffTable 1 }

CmrwLocalPowerBackOffEntry ::=
	SEQUENCE
	{
		cmrwLocalPowerBackOffPortIndex INTEGER,
		cmrwLocalPowerBackOffLinkIndex INTEGER,
		cmrwLocalPowerBackOffLevel INTEGER,
		cmrwLocalPowerBackOffAutoEnable INTEGER
	}

cmrwLocalPowerBackOffPortIndex OBJECT-TYPE
	SYNTAX INTEGER
	ACCESS read-only
	STATUS mandatory
	DESCRIPTION
		"This variable addresses the port number of the proxy
		and is used as index for the other elements in the Table"
	::= { cmrwLocalPowerBackOffEntry 1 }

cmrwLocalPowerBackOffLinkIndex OBJECT-TYPE
	SYNTAX INTEGER
	ACCESS read-only
	STATUS mandatory
	DESCRIPTION
		"This variable addresses the slot number of the OMI sub-rack
		and is used as index for the other elements in the Table"
	::= {cmrwLocalPowerBackOffEntry 2 }

cmrwLocalPowerBackOffLevel OBJECT-TYPE
	SYNTAX INTEGER
	{
		db0(1),
		db1(2),
		db2(3),
		db3(4),
		db4(5),
		db5(6),
		db6(7),
		db7(8),
		db8(9),
		db9(10),
		db10(11),
		db11(12),
		db12(13),
		db13(14),
		db14(15),
		db15(16),
		db16(17),
		db17(18),
		db18(19),
		db19(20),
		db20(21),
		db21(22),
		db22(23),
		db23(24),
		db24(25),
		db25(26),
		db26(27),
		db27(28),
		db28(29),
		db29(30),
		db30(31),
		db31(32),
		unknown(254),
		unsupported(255)
	}
	ACCESS read-write
	STATUS mandatory
	DESCRIPTION
		"Returns the configured power back off level
		1	Db0	The configured level is 0 dB.
		2	Db1	The configured level is 1 dB.
		3	Db2	The configured level is 2 dB.
		4	Db3	The configured level is 3 dB.
		5	Db4	The configured level is 4 dB.
		6	Db5	The configured level is 5 dB.
		7	Db6	The configured level is 6 dB.
		8	Db7	The configured level is 7 dB.
		9	Db8	The configured level is 8 dB.
		10	Db9	The configured level is 9 dB.
		11	Db10	The configured level is 10 dB.
		12	Db11	The configured level is 11 dB.
		13	Db12	The configured level is 12 dB.
		14	Db13	The configured level is 13 dB.
		15	Db14	The configured level is 14 dB.
		16	Db15	The configured level is 15 dB.
		17	Db16	The configured level is 16 dB.
		18	Db17	The configured level is 17 dB.
		19	Db18	The configured level is 18 dB.
		20	Db19	The configured level is 19 dB.
		21	Db20	The configured level is 20 dB.
		22	Db21	The configured level is 21 dB.
		23	Db22	The configured level is 22 dB.
		24	Db23	The configured level is 23 dB.
		25	Db24	The configured level is 24 dB.
		26	Db25	The configured level is 25 dB.
		27	Db26	The configured level is 26 dB.
		28	Db27	The configured level is 27 dB.
		29	Db28	The configured level is 28 dB.
		30	Db29	The configured level is 29 dB.
		31	Db30	The configured level is 30 dB.
		32	Db31	The configured level is 31 dB.
		254		unknown value
		255		unsupported variable for addressed device"
	::= { cmrwLocalPowerBackOffEntry 3 }

cmrwLocalPowerBackOffAutoEnable OBJECT-TYPE
	SYNTAX INTEGER
	{
		false(1),
		true(2),
		unknown(254),
		unsupported(255)
	}
	ACCESS read-write
	STATUS mandatory
	DESCRIPTION
		"Reports whether auto power backoff is enabled
		1	Off	Auto power backoff is disabled 
		2	On	Auto power backoff is enabled
		254		unknown value
		255		unsupported variable for addressed device"
	::= { cmrwLocalPowerBackOffEntry 4 }

--------------------------------------------------------------------------------
--	CM-RW	Section Power Back Off
--------------------------------------------------------------------------------
cmrwLocalSectionPboTable OBJECT-TYPE
	SYNTAX SEQUENCE OF CmrwLocalSectionPboEntry
	ACCESS not-accessible
	STATUS mandatory
	DESCRIPTION ""
	::= { cmrwLocal 9 }

cmrwLocalSectionPboEntry OBJECT-TYPE
	SYNTAX CmrwLocalSectionPboEntry
	ACCESS not-accessible
	STATUS mandatory
	DESCRIPTION ""
	INDEX { cmrwLocalSectionPboPortIndex, cmrwLocalSectionPboLinkIndex, cmrwLocalSectionPboSectionIndex }
	::= { cmrwLocalSectionPboTable 1 }

CmrwLocalSectionPboEntry ::=
	SEQUENCE
	{
		cmrwLocalSectionPboPortIndex INTEGER,
		cmrwLocalSectionPboLinkIndex INTEGER,
		cmrwLocalSectionPboSectionIndex INTEGER,
		cmrwLocalSectionPboLevelLt INTEGER,
		cmrwLocalSectionPboLevelNt INTEGER,
		cmrwLocalSectionPboAutoEnableLt INTEGER,
		cmrwLocalSectionPboAutoEnableNt INTEGER
	}

cmrwLocalSectionPboPortIndex OBJECT-TYPE
	SYNTAX INTEGER
	ACCESS read-only
	STATUS mandatory
	DESCRIPTION
		"This variable addresses the port number of the proxy
		and is used as index for the other elements in the Table"
	::= { cmrwLocalSectionPboEntry 1 }

cmrwLocalSectionPboLinkIndex OBJECT-TYPE
	SYNTAX INTEGER
	ACCESS read-only
	STATUS mandatory
	DESCRIPTION
		"This variable addresses the slot number of the OMI sub-rack
		and is used as index for the other elements in the Table"
	::= {cmrwLocalSectionPboEntry 2 }

cmrwLocalSectionPboSectionIndex OBJECT-TYPE
	SYNTAX INTEGER
	{
		lt1(1),
		lt2(2),
		reg11(4),
		reg12(5),
		reg21(6),
		reg22(7),
		reg31(8),
		reg32(9),
		reg41(10),
		reg42(11),
		reg51(12),
		reg52(13),
		reg61(14),
		reg62(15),
		reg71(16),
		reg72(17),
		reg81(18),
		reg82(19),
		reg13(20),
		reg14(21),
		reg23(22),
		reg24(23),
		reg33(24),
		reg34(25),
		reg43(26),
		reg44(27),
		reg53(28),
		reg54(29),
		reg63(30),
		reg64(31),
		reg73(32),
		reg74(33),
		reg83(34),
		reg84(35)
	}
	ACCESS read-only
	STATUS mandatory
	DESCRIPTION
		"Selects the section for which the Power Back-off
		values are set."
	::= {cmrwLocalSectionPboEntry 3 }

cmrwLocalSectionPboLevelLt OBJECT-TYPE
	SYNTAX INTEGER
	{
		db0(1),
		db1(2),
		db2(3),
		db3(4),
		db4(5),
		db5(6),
		db6(7),
		db7(8),
		db8(9),
		db9(10),
		db10(11),
		db11(12),
		db12(13),
		db13(14),
		db14(15),
		db15(16),
		db16(17),
		db17(18),
		db18(19),
		db19(20),
		db20(21),
		db21(22),
		db22(23),
		db23(24),
		db24(25),
		db25(26),
		db26(27),
		db27(28),
		db28(29),
		db29(30),
		db30(31),
		db31(32),
		dbMin1(130),
		dbMin2(131),
		dbMin3(132),
		dbMin4(133),
		unknown(254),
		unsupported(255)
	}
	ACCESS read-write
	STATUS mandatory
	DESCRIPTION
		"Returns the configured power back off level
		1	Db0	The configured level is 0 dB.
		2	Db1	The configured level is 1 dB.
		3	Db2	The configured level is 2 dB.
		4	Db3	The configured level is 3 dB.
		5	Db4	The configured level is 4 dB.
		6	Db5	The configured level is 5 dB.
		7	Db6	The configured level is 6 dB.
		8	Db7	The configured level is 7 dB.
		9	Db8	The configured level is 8 dB.
		10	Db9	The configured level is 9 dB.
		11	Db10	The configured level is 10 dB.
		12	Db11	The configured level is 11 dB.
		13	Db12	The configured level is 12 dB.
		14	Db13	The configured level is 13 dB.
		15	Db14	The configured level is 14 dB.
		16	Db15	The configured level is 15 dB.
		17	Db16	The configured level is 16 dB.
		18	Db17	The configured level is 17 dB.
		19	Db18	The configured level is 18 dB.
		20	Db19	The configured level is 19 dB.
		21	Db20	The configured level is 20 dB.
		22	Db21	The configured level is 21 dB.
		23	Db22	The configured level is 22 dB.
		24	Db23	The configured level is 23 dB.
		25	Db24	The configured level is 24 dB.
		26	Db25	The configured level is 25 dB.
		27	Db26	The configured level is 26 dB.
		28	Db27	The configured level is 27 dB.
		29	Db28	The configured level is 28 dB.
		30	Db29	The configured level is 29 dB.
		31	Db30	The configured level is 30 dB.
		32	Db31	The configured level is 31 dB.
		130	DbMin1	The configured level is -1 dB (Power Boost).
		131	DbMin2	The configured level is -2 dB (Power Boost).
		132	DbMin3	The configured level is -3 dB (Power Boost).
		133	DbMin4	The configured level is -4 dB (Power Boost).
		254		unknown value
		255		unsupported variable for addressed device"
	::= { cmrwLocalSectionPboEntry 4 }

cmrwLocalSectionPboLevelNt OBJECT-TYPE
	SYNTAX INTEGER
	{
		db0(1),
		db1(2),
		db2(3),
		db3(4),
		db4(5),
		db5(6),
		db6(7),
		db7(8),
		db8(9),
		db9(10),
		db10(11),
		db11(12),
		db12(13),
		db13(14),
		db14(15),
		db15(16),
		db16(17),
		db17(18),
		db18(19),
		db19(20),
		db20(21),
		db21(22),
		db22(23),
		db23(24),
		db24(25),
		db25(26),
		db26(27),
		db27(28),
		db28(29),
		db29(30),
		db30(31),
		db31(32),
		dbMin1(130),
		dbMin2(131),
		dbMin3(132),
		dbMin4(133),
		unknown(254),
		unsupported(255)
	}
	ACCESS read-write
	STATUS mandatory
	DESCRIPTION
		"Returns the configured power back off level
		1	Db0	The configured level is 0 dB.
		2	Db1	The configured level is 1 dB.
		3	Db2	The configured level is 2 dB.
		4	Db3	The configured level is 3 dB.
		5	Db4	The configured level is 4 dB.
		6	Db5	The configured level is 5 dB.
		7	Db6	The configured level is 6 dB.
		8	Db7	The configured level is 7 dB.
		9	Db8	The configured level is 8 dB.
		10	Db9	The configured level is 9 dB.
		11	Db10	The configured level is 10 dB.
		12	Db11	The configured level is 11 dB.
		13	Db12	The configured level is 12 dB.
		14	Db13	The configured level is 13 dB.
		15	Db14	The configured level is 14 dB.
		16	Db15	The configured level is 15 dB.
		17	Db16	The configured level is 16 dB.
		18	Db17	The configured level is 17 dB.
		19	Db18	The configured level is 18 dB.
		20	Db19	The configured level is 19 dB.
		21	Db20	The configured level is 20 dB.
		22	Db21	The configured level is 21 dB.
		23	Db22	The configured level is 22 dB.
		24	Db23	The configured level is 23 dB.
		25	Db24	The configured level is 24 dB.
		26	Db25	The configured level is 25 dB.
		27	Db26	The configured level is 26 dB.
		28	Db27	The configured level is 27 dB.
		29	Db28	The configured level is 28 dB.
		30	Db29	The configured level is 29 dB.
		31	Db30	The configured level is 30 dB.
		32	Db31	The configured level is 31 dB.
		130	DbMin1	The configured level is -1 dB (Power Boost).
		131	DbMin2	The configured level is -2 dB (Power Boost).
		132	DbMin3	The configured level is -3 dB (Power Boost).
		133	DbMin4	The configured level is -4 dB (Power Boost).
		254		unknown value
		255		unsupported variable for addressed device"
	::= { cmrwLocalSectionPboEntry 5 }

cmrwLocalSectionPboAutoEnableLt OBJECT-TYPE
	SYNTAX INTEGER
	{
		false(1),
		true(2),
		unknown(254),
		unsupported(255)
	}
	ACCESS read-write
	STATUS mandatory
	DESCRIPTION
		"Reports whether auto power backoff is enabled
		1	Off	Auto power backoff is disabled 
		2	On	Auto power backoff is enabled
		254		unknown value
		255		unsupported variable for addressed device"
	::= { cmrwLocalSectionPboEntry 6 }

cmrwLocalSectionPboAutoEnableNt OBJECT-TYPE
	SYNTAX INTEGER
	{
		false(1),
		true(2),
		unknown(254),
		unsupported(255)
	}
	ACCESS read-write
	STATUS mandatory
	DESCRIPTION
		"Reports whether auto power backoff is enabled
		1	Off	Auto power backoff is disabled 
		2	On	Auto power backoff is enabled
		254		unknown value
		255		unsupported variable for addressed device"
	::= { cmrwLocalSectionPboEntry 7 }

--------------------------------------------------------------------------------
--	CM-RW	Setup
--------------------------------------------------------------------------------
cmrwLocalSetupTable OBJECT-TYPE
	SYNTAX SEQUENCE OF CmrwLocalSetupEntry
	ACCESS not-accessible
	STATUS mandatory
	DESCRIPTION ""
	::= { cmrwLocal 10 }

cmrwLocalSetupEntry OBJECT-TYPE
	SYNTAX CmrwLocalSetupEntry
	ACCESS not-accessible
	STATUS mandatory
	DESCRIPTION ""
	INDEX { cmrwLocalSetupPortIndex, cmrwLocalSetupLinkIndex }
	::= { cmrwLocalSetupTable 1 }

CmrwLocalSetupEntry ::=
	SEQUENCE
	{
		cmrwLocalSetupPortIndex INTEGER,
		cmrwLocalSetupLinkIndex INTEGER,
		cmrwLocalSetupNumWirePairs INTEGER,
		cmrwLocalSetupLineActivation INTEGER,
		cmrwLocalSetupVirtSysActivation INTEGER,
		cmrwLocalSetupCardActivation OCTET STRING,
		cmrwLocalSetupCardActState OCTET STRING,
		cmrwLocalSetupIfAssignment OCTET STRING
	}

cmrwLocalSetupPortIndex OBJECT-TYPE
	SYNTAX INTEGER
	ACCESS read-only
	STATUS mandatory
	DESCRIPTION
		"This variable addresses the port number of the proxy
		and is used as index for the other elements in the Table"
	::= { cmrwLocalSetupEntry 1 }

cmrwLocalSetupLinkIndex OBJECT-TYPE
	SYNTAX INTEGER
	ACCESS read-only
	STATUS mandatory
	DESCRIPTION
		"This variable addresses the slot number of the OMI sub-rack
		and is used as index for the other elements in the Table"
	::= { cmrwLocalSetupEntry 2 }

cmrwLocalSetupNumWirePairs OBJECT-TYPE
	SYNTAX INTEGER {
		oneWirePairs(1),
		twoWirePairs(2),
		fourWirePairs(3),
		unknown(254),
		unsupported(255)
	}
	ACCESS read-write
	STATUS mandatory
	DESCRIPTION
		"Indicates the number of wire pairs of the line
		1	OneWirePairs	Line with one wire pair
		2	TwoWirePairs	Line with two wire pairs
		3	FourWirePairs	Line with four wire pairs
		254			unknown
		255			unsupported
		Side effect: If you do change this variable all other lines on the card 
		will be affected as well"
	::= { cmrwLocalSetupEntry 3 }

cmrwLocalSetupLineActivation OBJECT-TYPE
	SYNTAX INTEGER {
		activated(1),
		deactivated(2),
		unknown(254),
		unsupported(255)
	}
	ACCESS read-write
	STATUS mandatory
	DESCRIPTION
		"Indicates whether a line is activated or deactiated.
		1	activated	The line is activated
		2	deactivated	The line is deactivated
		254			unknown
		255			unsupported"
	::= { cmrwLocalSetupEntry 4 }

cmrwLocalSetupVirtSysActivation OBJECT-TYPE
	SYNTAX INTEGER {
		disabled(1),
		enabled(2),
		unknown(254),
		unsupported(255)
	}
	ACCESS read-write
	STATUS mandatory
	DESCRIPTION
		"Indicates whether the virtual system is enabled or disabled.
		1	disabled	The virtual system is disabled
		2	enabled		The virtual system is enabled
		254			unknown
		255			unsupported"
	::= { cmrwLocalSetupEntry 5 }

cmrwLocalSetupCardActivation OBJECT-TYPE
	SYNTAX OCTET STRING(SIZE(8))
	ACCESS read-write
	STATUS mandatory
	DESCRIPTION
		"Indicates the system activation for the systems A to H on the card.
		Each byte consists of the following information for one system:
		1	Deactivated	The system is inactive
		2	Activated	The system is active
		254			unknown value
		255			unsupported variable for addressed device"
	::= { cmrwLocalSetupEntry 6 }

cmrwLocalSetupCardActState OBJECT-TYPE
	SYNTAX OCTET STRING(SIZE(8))
	ACCESS read-only
	STATUS mandatory
	DESCRIPTION
		"Indicates the system activation state for the systems A to H on the card .
		Each byte consists of the following information for one system:
		1	Current		The system belongs to the currently managed line
		2	Present		The system does not belong to the currently managed line
		254			unknown value
		255			unsupported variable for addressed device"
	::= { cmrwLocalSetupEntry 7 }

cmrwLocalSetupIfAssignment OBJECT-TYPE
	SYNTAX OCTET STRING(SIZE(4))
	ACCESS read-write
	STATUS mandatory
	DESCRIPTION
		"Indicates the assignment of the (moveable) interfaces 1..4 
		to the systems A..D on the card .
		Each byte consists of the following information for one interface:
		1	systemA		The interface is assigned to System A
		2	systemB		The interface is assigned to System B
		3	systemC		The interface is assigned to System C
		4	systemD		The interface is assigned to System D
		254			unknown value
		255			unsupported variable for addressed device"
	::= { cmrwLocalSetupEntry 8 }

--------------------------------------------------------------------------------
--	CM-RW	L2SwitchPort
--------------------------------------------------------------------------------
cmrwLocalL2SwitchPortTable OBJECT-TYPE
	SYNTAX SEQUENCE OF CmrwLocalL2SwitchPortEntry
	ACCESS not-accessible
	STATUS mandatory
	DESCRIPTION ""
	::= { cmrwLocal 11 }

cmrwLocalL2SwitchPortEntry OBJECT-TYPE
	SYNTAX CmrwLocalL2SwitchPortEntry
	ACCESS not-accessible
	STATUS mandatory
	DESCRIPTION ""
	INDEX { cmrwLocalL2SwitchPortPortIndex, cmrwLocalL2SwitchPortLinkIndex, cmrwLocalL2SwitchPortLanPortIndex }
	::= { cmrwLocalL2SwitchPortTable 1 }

CmrwLocalL2SwitchPortEntry ::=
	SEQUENCE
	{
		cmrwLocalL2SwitchPortPortIndex INTEGER,
		cmrwLocalL2SwitchPortLinkIndex INTEGER,
		cmrwLocalL2SwitchPortLanPortIndex INTEGER,
		cmrwLocalL2SwitchPortEnabled INTEGER,
		cmrwLocalL2SwitchPortPhyCfg INTEGER,
		cmrwLocalL2SwitchPortPhyAdvModes INTEGER,
		cmrwLocalL2SwitchPortPhyCfgReadout INTEGER,
		cmrwLocalL2SwitchPortAutoXover INTEGER,
		cmrwLocalL2SwitchPortFlowCtrl INTEGER,
		cmrwLocalL2SwitchPortRateLimit INTEGER,
		cmrwLocalL2SwitchPortRateLimitCfg INTEGER
	}

cmrwLocalL2SwitchPortPortIndex OBJECT-TYPE
	SYNTAX INTEGER
	ACCESS read-only
	STATUS mandatory
	DESCRIPTION
		"This variable addresses the port number of the proxy
		and is used as index for the other elements in the Table"
	::= { cmrwLocalL2SwitchPortEntry 1 }

cmrwLocalL2SwitchPortLinkIndex OBJECT-TYPE
	SYNTAX INTEGER
	ACCESS read-only
	STATUS mandatory
	DESCRIPTION
		"This variable addresses the slot number of the OMI sub-rack
		and is used as index for the other elements in the Table"
	::= { cmrwLocalL2SwitchPortEntry 2 }

cmrwLocalL2SwitchPortLanPortIndex OBJECT-TYPE
	SYNTAX INTEGER
	ACCESS read-only
	STATUS mandatory
	DESCRIPTION
		"This variable addresses the L2Switch port (LAN side)
		and is used as index for the other elements in the Table"
	::= { cmrwLocalL2SwitchPortEntry 3 }

cmrwLocalL2SwitchPortEnabled OBJECT-TYPE
	SYNTAX INTEGER {
		disabled(1),
		enabled(2),
		unknown(254),
		unsupported(255)
	}
	ACCESS read-write
	STATUS mandatory
	DESCRIPTION
		"Defines whether the L2Switch port is enabled or not.
		1	Disabled	L2Switch port is disabled
		2	Enabled		L2Switch port is enabled
		254	unknown
		255	unsupported"
	::= { cmrwLocalL2SwitchPortEntry 4 }

cmrwLocalL2SwitchPortPhyCfg OBJECT-TYPE
	SYNTAX INTEGER {
		full10(1),
		full100(2),
		half10(3),
		half100(4),
		auto(5),
		unknown(254),
		unsupported(255)
	}
	ACCESS read-write
	STATUS mandatory
	DESCRIPTION
		"Defines the ethernet phy config or allows auto negotiation.
		1	Full Duplex 10Mbps
		2	Full Duplex 100Mbps
		3	Half Duplex 10Mbps
		4	Half Duplex 100Mbps
		5	Auto Negotiation
		254	unknown
		255	unsupported"
	::= { cmrwLocalL2SwitchPortEntry 5 }

cmrwLocalL2SwitchPortPhyAdvModes OBJECT-TYPE
	SYNTAX INTEGER (0..1023)
	ACCESS read-write
	STATUS mandatory
	DESCRIPTION
		"Defines the phy modes to be offered during auto
		negotiation ('advertized modes').
		Bit 0	1	Full Duplex 10Mbps
		Bit 1	2	Full Duplex 100Mbps
		Bit 2	4	Half Duplex 10Mbps
		Bit 3	8	Half Duplex 100Mbps
		Bit 8	256	unknown value (ignore bits 0-7)
		Bit 9	512	unsupported variable for addressed device (ignore bits 0-7)"
	::= { cmrwLocalL2SwitchPortEntry 6 }

cmrwLocalL2SwitchPortPhyCfgReadout OBJECT-TYPE
	SYNTAX INTEGER {
		full10(1),
		full100(2),
		half10(3),
		half100(4),
		auto(5),
		linkdown(6),
		unknown(254),
		unsupported(255)
	}
	ACCESS read-only
	STATUS mandatory
	DESCRIPTION
		"Indicates the current ethernet phy config.
		1	Full Duplex 10Mbps
		2	Full Duplex 100Mbps
		3	Half Duplex 10Mbps
		4	Half Duplex 100Mbps
		5	Auto Negotiation
		6	Linkdown
		254	unknown
		255	unsupported"
	::= { cmrwLocalL2SwitchPortEntry 7 }

cmrwLocalL2SwitchPortAutoXover OBJECT-TYPE
	SYNTAX INTEGER {
		disabled(1),
		enabled(2),
		unknown(254),
		unsupported(255)
	}
	ACCESS read-write
	STATUS mandatory
	DESCRIPTION
		"Determines whether ethernet crossover (MDI/MDI-X)
		should automatically be detected and compensated
		for.
		1	Disabled	MDI
		2	Enabled		Auto MDI/MDI-X
		254	unknown
		255	unsupported"
	::= { cmrwLocalL2SwitchPortEntry 8 }

cmrwLocalL2SwitchPortFlowCtrl OBJECT-TYPE
	SYNTAX INTEGER {
		disabled(1),
		enabled(2),
		unknown(254),
		unsupported(255)
	}
	ACCESS read-write
	STATUS mandatory
	DESCRIPTION
		"Determines whether flow control should be performed
		on a specific port.
		1	Disabled	Flow control disabled
		2	Enabled		Flow control enabled
		254	unknown
		255	unsupported"
	::= { cmrwLocalL2SwitchPortEntry 9 }

cmrwLocalL2SwitchPortRateLimit OBJECT-TYPE
	SYNTAX INTEGER (0..65535)
	ACCESS read-write
	STATUS mandatory
	DESCRIPTION
		"Determines the maximum bit rate on a specific port
		in 32kbps increments. This setting can be
		overriden by the Rate Limit Cfg setting.
		1	Rate Limit 32kbps
		2	Rate Limit 64kbps
		...
		288	Rate Limit 9216kbps (equals 4*2304 kbps)
		...
		3125	Rate Limit 100Mbps
		65534	unknown
		65535	unsupported"
	::= { cmrwLocalL2SwitchPortEntry 10 }

cmrwLocalL2SwitchPortRateLimitCfg OBJECT-TYPE
	SYNTAX INTEGER {
		unlimited(1),
		userN32k(2),
		unknown(254),
		unsupported(255)
	}
	ACCESS read-write
	STATUS mandatory
	DESCRIPTION
		"Determines the behavior of the port rate limiter.
		on a specific port
		1	Unlimited	No rate limit enforced
		2	User-Def. n*32k	User-defined value in 32k increments
		254	unknown
		255	unsupported"
	::= { cmrwLocalL2SwitchPortEntry 11 }

--------------------------------------------------------------------------------
--	CM-RW	Local Multi Interfaces
--------------------------------------------------------------------------------
cmrwLocalMultiIfTable OBJECT-TYPE
	SYNTAX SEQUENCE OF CmrwLocalMultiIfEntry
	ACCESS not-accessible
	STATUS mandatory
	DESCRIPTION ""
	::= { cmrwLocal 12 }

cmrwLocalMultiIfEntry OBJECT-TYPE
	SYNTAX CmrwLocalMultiIfEntry
	ACCESS not-accessible
	STATUS mandatory
	DESCRIPTION ""
	INDEX { cmrwLocalMultiIfPortIndex, cmrwLocalMultiIfLinkIndex, cmrwLocalMultiIfInstanceIndex }
	::= { cmrwLocalMultiIfTable 1 }

CmrwLocalMultiIfEntry ::=
	SEQUENCE
	{
		cmrwLocalMultiIfPortIndex INTEGER,
		cmrwLocalMultiIfLinkIndex INTEGER,
		cmrwLocalMultiIfInstanceIndex INTEGER,
		cmrwLocalMultiIfUEnabled INTEGER,
		cmrwLocalMultiIfVEnabled INTEGER
	}

cmrwLocalMultiIfPortIndex OBJECT-TYPE
	SYNTAX INTEGER
	ACCESS read-only
	STATUS mandatory
	DESCRIPTION
		"This variable addresses the port number of the proxy
		and is used as index for the other elements in the Table"
	::= { cmrwLocalMultiIfEntry 1 }

cmrwLocalMultiIfLinkIndex OBJECT-TYPE
	SYNTAX INTEGER
	ACCESS read-only
	STATUS mandatory
	DESCRIPTION
		"This variable addresses the slot number of the OMI sub-rack
		and is used as index for the other elements in the Table"
	::= { cmrwLocalMultiIfEntry 2 }

cmrwLocalMultiIfInstanceIndex OBJECT-TYPE
	SYNTAX INTEGER
	ACCESS read-only
	STATUS mandatory
	DESCRIPTION
		"This variable addresses one of several instances
		and is used as index for the other elements in the Table.
		Instances can be
		- U interfaces 1,2,3,4...
		- V interfaces A,B,C,D...
		The numbering format is 1,2,3,4..."
	::= { cmrwLocalMultiIfEntry 3 }

cmrwLocalMultiIfUEnabled OBJECT-TYPE
	SYNTAX INTEGER {
		disabled(1),
		enabled(2),
		unknown(254),
		unsupported(255)
	}
	ACCESS read-write
	STATUS mandatory
	DESCRIPTION
		"Defines whether the U1,U2,U3,U4... interface is enabled or not.
		1	Disabled	Interface is disabled
		2	Enabled		Interface is enabled
		254	unknown
		255	unsupported"
	::= { cmrwLocalMultiIfEntry 4 }

cmrwLocalMultiIfVEnabled OBJECT-TYPE
	SYNTAX INTEGER {
		disabled(1),
		enabled(2),
		unknown(254),
		unsupported(255)
	}
	ACCESS read-write
	STATUS mandatory
	DESCRIPTION
		"Defines whether the V_A,V_B,V_C,V_D... interface is enabled or not.
		1	Disabled	Interface is disabled
		2	Enabled		Interface is enabled
		254	unknown
		255	unsupported"
	::= { cmrwLocalMultiIfEntry 5 }

--------------------------------------------------------------------------------
--	CM-RW	CommonMcsCh
--------------------------------------------------------------------------------
cmrwLocalCommonMultiChTable OBJECT-TYPE
	SYNTAX SEQUENCE OF CmrwLocalCommonMultiChEntry
	ACCESS not-accessible
	STATUS mandatory
	DESCRIPTION ""
	::= { cmrwLocal 13 }

cmrwLocalCommonMultiChEntry OBJECT-TYPE
	SYNTAX CmrwLocalCommonMultiChEntry
	ACCESS not-accessible
	STATUS mandatory
	DESCRIPTION ""
	INDEX { cmrwLocalCommonMultiChPortIndex, cmrwLocalCommonMultiChLinkIndex, cmrwLocalCommonMultiChannelIndex }
	::= { cmrwLocalCommonMultiChTable 1 }

CmrwLocalCommonMultiChEntry ::=
	SEQUENCE
	{
		cmrwLocalCommonMultiChPortIndex INTEGER,
		cmrwLocalCommonMultiChLinkIndex INTEGER,
		cmrwLocalCommonMultiChannelIndex INTEGER,
		cmrwLocalCommonMultiChMcsEnabled INTEGER
	}

cmrwLocalCommonMultiChPortIndex OBJECT-TYPE
	SYNTAX INTEGER
	ACCESS read-only
	STATUS mandatory
	DESCRIPTION
		"This variable addresses the port number of the proxy
		and is used as index for the other elements in the Table"
	::= { cmrwLocalCommonMultiChEntry 1 }

cmrwLocalCommonMultiChLinkIndex OBJECT-TYPE
	SYNTAX INTEGER
	ACCESS read-only
	STATUS mandatory
	DESCRIPTION
		"This variable addresses the slot number of the OMI sub-rack
		and is used as index for the other elements in the Table"
	::= { cmrwLocalCommonMultiChEntry 2 }

cmrwLocalCommonMultiChannelIndex OBJECT-TYPE
	SYNTAX INTEGER
	ACCESS read-only
	STATUS mandatory
	DESCRIPTION
		"This variable addresses one of several instances
		and is used as index for the other elements in the Table.
		Instances can be
		- MCS channels	a,b,c,d...
		- U interfaces 1,2,3,4...
		- V interfaces A,B,C,D...
		The numbering format is 1,2,3,4..."
	::= { cmrwLocalCommonMultiChEntry 3 }

cmrwLocalCommonMultiChMcsEnabled OBJECT-TYPE
	SYNTAX INTEGER {
		disabled(1),
		enabled(2),
		unknown(254),
		unsupported(255)
	}
	ACCESS read-write
	STATUS mandatory
	DESCRIPTION
		"Defines whether the MCS channel a,b,c,d... is enabled or not.
		1	Disabled	Channel is disabled
		2	Enabled		CHannel is enabled
		254	unknown
		255	unsupported"
	::= { cmrwLocalCommonMultiChEntry 4 }

--------------------------------------------------------------------------------
--	CM-RW	Local L2Switch
--------------------------------------------------------------------------------
cmrwLocalL2SwitchTable OBJECT-TYPE
	SYNTAX SEQUENCE OF CmrwLocalL2SwitchEntry
	ACCESS not-accessible
	STATUS mandatory
	DESCRIPTION ""
	::= { cmrwLocal 14 }

cmrwLocalL2SwitchEntry OBJECT-TYPE
	SYNTAX CmrwLocalL2SwitchEntry
	ACCESS not-accessible
	STATUS mandatory
	DESCRIPTION ""
	INDEX { cmrwLocalL2SwitchPortIndex, cmrwLocalL2SwitchLinkIndex }
	::= { cmrwLocalL2SwitchTable 1 }

CmrwLocalL2SwitchEntry ::=
	SEQUENCE
	{
		cmrwLocalL2SwitchPortIndex INTEGER,
		cmrwLocalL2SwitchLinkIndex INTEGER,
		cmrwLocalL2SwitchHugeFrames INTEGER,
		cmrwLocalL2SwitchAdaptiveFlowCtrl INTEGER,
		cmrwLocalL2SwitchFrameLengthCheck INTEGER
	}

cmrwLocalL2SwitchPortIndex OBJECT-TYPE
	SYNTAX INTEGER
	ACCESS read-only
	STATUS mandatory
	DESCRIPTION
		"This variable addresses the port number of the proxy
		and is used as index for the other elements in the Table"
	::= { cmrwLocalL2SwitchEntry 1 }

cmrwLocalL2SwitchLinkIndex OBJECT-TYPE
	SYNTAX INTEGER
	ACCESS read-only
	STATUS mandatory
	DESCRIPTION
		"This variable addresses the slot number of the OMI sub-rack
		and is used as index for the other elements in the Table"
	::= { cmrwLocalL2SwitchEntry 2 }

cmrwLocalL2SwitchHugeFrames OBJECT-TYPE
	SYNTAX INTEGER {
		disabled(1),
		enabled(2),
		unknown(254),
		unsupported(255)
	}
	ACCESS read-write
	STATUS mandatory
	DESCRIPTION
		"Indicates whether the Layer 2 Switch supports so-called Huge Frames
		(frames longer than 1522 bytes).
		1	Disabled	Huge frames will be discarded
		2	Enabled		Huge frames allowed
		254			unknown
		255			unsupported"
	::= { cmrwLocalL2SwitchEntry 3 }

cmrwLocalL2SwitchAdaptiveFlowCtrl OBJECT-TYPE
	SYNTAX INTEGER {
		disabled(1),
		enabled(2),
		unknown(254),
		unsupported(255)
	}
	ACCESS read-write
	STATUS mandatory
	DESCRIPTION
		"Indicates whether adaptive flow control on the Layer 2 Switch and on the 
		HDLC bridge is enabled (to avoid packet loss) or not.
		1	Disabled	Disable adaptive flow control
		2	Enabled		Enable adaptive flow control
		254			unknown
		255			unsupported"
	::= { cmrwLocalL2SwitchEntry 4 }

cmrwLocalL2SwitchFrameLengthCheck OBJECT-TYPE
	SYNTAX INTEGER {
		disabled(1),
		enabled(2),
		unknown(254),
		unsupported(255)
	}
	ACCESS read-write
	STATUS mandatory
	DESCRIPTION
		"Indicates whether frame length check on the Layer 2 Switch is enabled or not.
		1	Disabled	Disable frame length check
		2	Enabled		Enable frame length check
		254			unknown
		255			unsupported"
	::= { cmrwLocalL2SwitchEntry 5 }

--------------------------------------------------------------------------------
--	CM-RW	local Mapping
--------------------------------------------------------------------------------
cmrwLocalMappingTable OBJECT-TYPE
	SYNTAX SEQUENCE OF CmrwLocalMappingEntry
	ACCESS not-accessible
	STATUS mandatory
	DESCRIPTION ""
	::= { cmrwLocal 15 }

cmrwLocalMappingEntry OBJECT-TYPE
	SYNTAX CmrwLocalMappingEntry
	ACCESS not-accessible
	STATUS mandatory
	DESCRIPTION ""
	INDEX { cmrwLocalMappingPortIndex, cmrwLocalMappingLinkIndex }
	::= { cmrwLocalMappingTable 1 }

CmrwLocalMappingEntry ::=
	SEQUENCE
	{
		cmrwLocalMappingPortIndex INTEGER,
		cmrwLocalMappingLinkIndex INTEGER,
		cmrwLocalMappingEnabled INTEGER,
		cmrwLocalMappingMixedOperation INTEGER,
		cmrwLocalMappingOmitSTS INTEGER,
		cmrwLocalMappingSTSPosition INTEGER,
		cmrwLocalMappingTxTs0 INTEGER
	}

cmrwLocalMappingPortIndex OBJECT-TYPE
	SYNTAX INTEGER
	ACCESS read-only
	STATUS mandatory
	DESCRIPTION
		"This variable addresses the port number of the proxy
		and is used as index for the other elements in the Table"
	::= { cmrwLocalMappingEntry 1 }

cmrwLocalMappingLinkIndex OBJECT-TYPE
	SYNTAX INTEGER
	ACCESS read-only
	STATUS mandatory
	DESCRIPTION
		"This variable addresses the slot number of the OMI sub-rack
		and is used as index for the other elements in the Table"
	::= {cmrwLocalMappingEntry 2 }

cmrwLocalMappingEnabled OBJECT-TYPE
	SYNTAX INTEGER
	{
		disabled(1),
		enabled(2),
		unknown(254),
		unsupported(255)
	}
	ACCESS read-write
	STATUS mandatory
	DESCRIPTION
		"Defines whether Mapping is enabled or disabled.
		1	Disabled	Mapping is disabled
		2	Enabled		Mapping is enabled
		254			unknown value
		255			unsupported variable for addressed device"
	::= { cmrwLocalMappingEntry 3 }

cmrwLocalMappingMixedOperation OBJECT-TYPE
	SYNTAX INTEGER
	{
		disabled(1),
		enabled(2),
		unknown(254),
		unsupported(255)
	}
	ACCESS read-write
	STATUS mandatory
	DESCRIPTION
		"Defines whether Mixed Operation (Data to Structured TDM) is enabled or disabled.
		1	Disabled	Mixed Operation is disabled
		2	Enabled		Mixed Operation is enabled
		254			unknown value
		255			unsupported variable for addressed device"
	::= { cmrwLocalMappingEntry 4 }

cmrwLocalMappingOmitSTS OBJECT-TYPE
	SYNTAX INTEGER
	{
		transmit(1),
		omit(2),
		unknown(254),
		unsupported(255)
	}
	ACCESS read-write
	STATUS mandatory
	DESCRIPTION
		"Defines whether the Signalization Timeslot is actually being transmitted or just mapped, not transmitted.
		1	Transmit	STS is transmitted
		2	Omit		STS is mapped, but not transmitted
		254			unknown value
		255			unsupported variable for addressed device"
	::= { cmrwLocalMappingEntry 5 }

cmrwLocalMappingSTSPosition OBJECT-TYPE
	SYNTAX INTEGER
	{
		unchanged(1),
		tsPos1(2),
		tsPos2(3),
		tsPos3(4),
		tsPos4(5),
		tsPos5(6),
		tsPos6(7),
		tsPos7(8),
		tsPos8(9),
		tsPos9(10),
		tsPos10(11),
		tsPos11(12),
		tsPos12(13),
		tsPos13(14),
		tsPos14(15),
		tsPos15(16),
		tsPos16(17),
		tsPos17(18),
		tsPos18(19),
		tsPos19(20),
		tsPos20(21),
		tsPos21(22),
		tsPos22(23),
		tsPos23(24),
		tsPos24(25),
		tsPos25(26),
		tsPos26(27),
		tsPos27(28),
		tsPos28(29),
		tsPos29(30),
		tsPos30(31),
		tsPos31(32),
		unknown(254),
		unsupported(255)
	}
	ACCESS read-write
	STATUS mandatory
	DESCRIPTION
		"Defines the position of the Signalization Timeslot.
		1	unchanged	STS mapping is disabled
		2	tsPos1		STS position: Timeslot 1
		3	tsPos2		STS position: Timeslot 2
		4	tsPos3		STS position: Timeslot 3
		5	tsPos4		STS position: Timeslot 4
		6	tsPos5		STS position: Timeslot 5
		7	tsPos6		STS position: Timeslot 6
		8	tsPos7		STS position: Timeslot 7
		9	tsPos8		STS position: Timeslot 8
		10	tsPos9   	STS position: Timeslot 9
		11	tsPos10  	STS position: Timeslot 10
		12	tsPos11  	STS position: Timeslot 11
		13	tsPos12  	STS position: Timeslot 12
		14	tsPos13  	STS position: Timeslot 13
		15	tsPos14  	STS position: Timeslot 14
		16	tsPos15  	STS position: Timeslot 15
		17	tsPos16  	STS position: Timeslot 16
		18	tsPos17  	STS position: Timeslot 17
		19	tsPos18  	STS position: Timeslot 18
		20	tsPos19  	STS position: Timeslot 19
		21	tsPos20  	STS position: Timeslot 20
		22	tsPos21  	STS position: Timeslot 21
		23	tsPos22  	STS position: Timeslot 22
		24	tsPos23  	STS position: Timeslot 23
		25	tsPos24  	STS position: Timeslot 24
		26	tsPos25  	STS position: Timeslot 25
		27	tsPos26  	STS position: Timeslot 26
		28	tsPos27  	STS position: Timeslot 27
		29	tsPos28  	STS position: Timeslot 28
		30	tsPos29  	STS position: Timeslot 29
		31	tsPos30  	STS position: Timeslot 30
		32	tsPos31  	STS position: Timeslot 31
		254			unknown value
		255			unsupported variable for addressed device"
	::= { cmrwLocalMappingEntry 6 }

cmrwLocalMappingTxTs0 OBJECT-TYPE
	SYNTAX INTEGER
	{
		disabled(1),
		enabled(2),
		unknown(254),
		unsupported(255)
	}
	ACCESS read-write
	STATUS mandatory
	DESCRIPTION
		"Defines whether timeslot 0 is transmitted on the U interface.
		1	Disabled	TS0 is not transmitted
		2	Enabled		TS0 is transmitted
		254			unknown value
		255			unsupported variable for addressed device"
	::= { cmrwLocalMappingEntry 7 }

--------------------------------------------------------------------------------
--	CM-RW	far Clock
--------------------------------------------------------------------------------
cmrwFarClockTable OBJECT-TYPE
	SYNTAX SEQUENCE OF CmrwFarClockEntry
	ACCESS not-accessible
	STATUS mandatory
	DESCRIPTION ""
	::= { cmrwFar 3 }

cmrwFarClockEntry OBJECT-TYPE
	SYNTAX CmrwFarClockEntry
	ACCESS not-accessible
	STATUS mandatory
	DESCRIPTION ""
	INDEX { cmrwFarClockPortIndex, cmrwFarClockLinkIndex }
	::= { cmrwFarClockTable 1 }

CmrwFarClockEntry ::=
	SEQUENCE
	{
		cmrwFarClockPortIndex INTEGER,
		cmrwFarClockLinkIndex INTEGER,
		cmrwFarClockActive INTEGER,
		cmrwFarClockT3InAvailable INTEGER,
		cmrwFarClockTInterfaceAvailable INTEGER,
		cmrwFarClockUInterfaceAvailable INTEGER,
		cmrwFarClockInternalAvailable INTEGER,
		cmrwFarClockPriority OCTET STRING
	}

cmrwFarClockPortIndex OBJECT-TYPE
	SYNTAX INTEGER
	ACCESS read-only
	STATUS mandatory
	DESCRIPTION
		"This variable addresses the port number of the proxy
		and is used as index for the other elements in the Table"
	::= { cmrwFarClockEntry 1 }

cmrwFarClockLinkIndex OBJECT-TYPE
	SYNTAX INTEGER
	ACCESS read-only
	STATUS mandatory
	DESCRIPTION
		"This variable addresses the slot number of the OMI sub-rack
		and is used as index for the other elements in the Table"
	::= {cmrwFarClockEntry 2 }

cmrwFarClockActive OBJECT-TYPE
	SYNTAX INTEGER
	{
		t3in(1),
		tInterface(2),
		uInterface(3),
		internal(4),
		unknown(254),
		unsupported(255)
	}
	ACCESS read-only
	STATUS mandatory
	DESCRIPTION
		"Indicates which clock source is currently being used.
		1	T3In		Uses Clock input T3In
		2	TInterface	Taking Clock from signal on T-Interface
		3	UInterface	Taking Clock from signal on U-Interface
		4	Internal	Using internal oscillator to generate Clock
		254			unknown value
		255			unsupported variable for addressed device"
	::= { cmrwFarClockEntry 3 }

cmrwFarClockT3InAvailable OBJECT-TYPE
	SYNTAX INTEGER
	{
		false(1),
		true(2),
		unknown(254),
		unsupported(255)
	}
	ACCESS read-only
	STATUS mandatory
	DESCRIPTION
		"Reports whether Clock Input T3In is available
		1	False	Clock Input T3In not available
		2	True	Clock Input T3In available
		254		unknown value
		255		unsupported variable for addressed device"
	::= { cmrwFarClockEntry 4 }

cmrwFarClockTInterfaceAvailable OBJECT-TYPE
	SYNTAX INTEGER
	{
		false(1),
		true(2),
		unknown(254),
		unsupported(255)
	}
	ACCESS read-only
	STATUS mandatory
	DESCRIPTION
		"Reports whether a clock signal can be derrived from the signal
		on the T-Interface
		1	False	Clock signal available
		2	True	Clock signal available
		254		unknown value
		255		unsupported variable for addressed device"
	::= { cmrwFarClockEntry 5 }

cmrwFarClockUInterfaceAvailable OBJECT-TYPE
	SYNTAX INTEGER
	{
		false(1),
		true(2),
		unknown(254),
		unsupported(255)
	}
	ACCESS read-only
	STATUS mandatory
	DESCRIPTION
		"Reports whether a clock signal can be derrived from the signal
		on the U-Interface
		1	False	Clock signal available
		2	True	Clock signal available
		254		unknown value
		255		unsupported variable for addressed device"
	::= { cmrwFarClockEntry 6 }

cmrwFarClockInternalAvailable OBJECT-TYPE
	SYNTAX INTEGER
	{
		false(1),
		true(2),
		unknown(254),
		unsupported(255)
	}
	ACCESS read-only
	STATUS mandatory
	DESCRIPTION
		"Reports whether the internal oscillator is available
		1	False	oscillator not available
		2	True	oscillator available
		254		unknown value
		255		unsupported variable for addressed device"
	::= { cmrwFarClockEntry 7 }

cmrwFarClockPriority OBJECT-TYPE
	SYNTAX OCTET STRING(SIZE(4))
	ACCESS read-write
	STATUS mandatory
	DESCRIPTION
		"Used to read and set the clock priority for the different
		clock sources. The variable is an array with length 4. The
		indices correspond to the priorities (0=highest, 3=lowest).
		The following values can be contained in each position, 
		indicating which clock source has the corresponding priority:
		1	T3In		Clock Input T3In
		2	TInterface	Clock derrived from Signal at T-Interface
		3	UInterface	Clock derrived from Signal at U-Interface
		4	Internal	Internal oscillator
		254			unknown	value
		255			unsupported variable for addressed device"
	::= { cmrwFarClockEntry 8 }

--------------------------------------------------------------------------------
--	CM-RW	far 2M
--------------------------------------------------------------------------------
cmrwFar2MTable OBJECT-TYPE
	SYNTAX SEQUENCE OF CmrwFar2MEntry
	ACCESS not-accessible
	STATUS mandatory
	DESCRIPTION ""
	::= { cmrwFar 4 }

cmrwFar2MEntry OBJECT-TYPE
	SYNTAX CmrwFar2MEntry
	ACCESS not-accessible
	STATUS mandatory
	DESCRIPTION ""
	INDEX { cmrwFar2MPortIndex, cmrwFar2MLinkIndex }
	::= { cmrwFar2MTable 1 }

CmrwFar2MEntry ::=
	SEQUENCE
	{
		cmrwFar2MPortIndex INTEGER,
		cmrwFar2MLinkIndex INTEGER,
		cmrwFar2MFraming INTEGER,
		cmrwFar2MEnableT INTEGER,
		cmrwFar2MTimeslotsT INTEGER,
		cmrwFar2MIdlecodeT INTEGER,
		cmrwFar2MCrc4T INTEGER,
		cmrwFar2MCrc4U INTEGER,
		cmrwFar2MDetectAis INTEGER,
		cmrwFar2MInsertAis INTEGER,
		cmrwFar2MSaBits OCTET STRING,
		cmrwFar2MTs16Signalling INTEGER,
		cmrwFar2MIdlecodeU INTEGER,
		cmrwFar2MTs0Present INTEGER,
		cmrwFar2MCrc4V INTEGER,
		cmrwFar2MInterfaceImpedance INTEGER
	}

cmrwFar2MPortIndex OBJECT-TYPE
	SYNTAX INTEGER
	ACCESS read-only
	STATUS mandatory
	DESCRIPTION
		"This variable addresses the port number of the proxy
		and is used as index for the other elements in the Table"
	::= { cmrwFar2MEntry 1 }

cmrwFar2MLinkIndex OBJECT-TYPE
	SYNTAX INTEGER
	ACCESS read-only
	STATUS mandatory
	DESCRIPTION
		"This variable addresses the slot number of the OMI sub-rack
		and is used as index for the other elements in the Table"
	::= {cmrwFar2MEntry 2 }

cmrwFar2MFraming OBJECT-TYPE
	SYNTAX INTEGER
	{
		transparent(1),
		monitoring(2),
		termination(3),
		channelized(4),
		unknown(254),
		unsupported(255)
	}
	ACCESS read-write
	STATUS mandatory
	DESCRIPTION
		"Configures Frame Alignment
		1	Transparent	No frame or multi-frame synchronisation
		2	Monitoring	Frame and Multi-Frame synchronisation but no reinsertion of Frame
		3	Termination	Frame and Multi-Frame synchronisation and reinsertion
		4	Channelized	Frame and Multi-Frame synchronisation without transmission of timeslot 0		254			unknown value
		255			unsupported variable for addressed device"
	::= { cmrwFar2MEntry 3 }

cmrwFar2MEnableT OBJECT-TYPE
	SYNTAX INTEGER
	{
		disabled(1),
		enabled(2),
		unknown(254),
		unsupported(255)
	}
	ACCESS read-write
	STATUS mandatory
	DESCRIPTION
		"Enable or disable the G.703 interface (T-Interface)
		1	Disabled	G.703 Interface is disabled
		2	Enabled		G.703 Interface is enabled
		254			unknown value
		255			unsupported variable for addressed device"
	::= { cmrwFar2MEntry 4 }

cmrwFar2MTimeslotsT OBJECT-TYPE
	SYNTAX INTEGER
	{
		bw64(1),
		bw128(2),
		bw192(3),
		bw256(4),
		bw320(5),
		bw384(6),
		bw448(7),
		bw512(8),
		bw576(9),
		bw640(10),
		bw704(11),
		bw768(12),
		bw832(13),
		bw896(14),
		bw960(15),
		bw1024(16),
		bw1088(17),
		bw1152(18),
		bw1216(19),
		bw1280(20),
		bw1344(21),
		bw1408(22),
		bw1472(23),
		bw1536(24),
		bw1600(25),
		bw1664(26),
		bw1728(27),
		bw1792(28),
		bw1856(29),
		bw1920(30),
		bw1984(31),
		bw2048(32),
		unknown(254),
		unsupported(255)
	}
	ACCESS read-write
	STATUS mandatory
	DESCRIPTION
		"Bandwidth allocated for G.703 Interface (T-Interface) as
		a number of 64kbit/s time slots. Between 1 and 32.
		
		When reading the following values can also be returned:
		1	bw64		Bandwidth   64 kbit/s
		2	bw128		Bandwidth  128 kbit/s
		3	bw192		Bandwidth  192 kbit/s
		4	bw256		Bandwidth  256 kbit/s
		5	bw320		Bandwidth  320 kbit/s
		6	bw384		Bandwidth  384 kbit/s
		7	bw448		Bandwidth  448 kbit/s
		8	bw512		Bandwidth  512 kbit/s
		9	bw576		Bandwidth  576 kbit/s
		10	bw640		Bandwidth  640 kbit/s
		11	bw704		Bandwidth  704 kbit/s
		12	bw768		Bandwidth  768 kbit/s
		13	bw832		Bandwidth  832 kbit/s
		14	bw896		Bandwidth  896 kbit/s
		15	bw960		Bandwidth  960 kbit/s
		16	bw1024		Bandwidth 1024 kbit/s
		17	bw1088		Bandwidth 1088 kbit/s
		18	bw1152		Bandwidth 1152 kbit/s
		19	bw1216		Bandwidth 1216 kbit/s
		20	bw1280		Bandwidth 1280 kbit/s
		21	bw1344		Bandwidth 1344 kbit/s
		22	bw1408		Bandwidth 1408 kbit/s
		23	bw1472		Bandwidth 1472 kbit/s
		24	bw1536		Bandwidth 1536 kbit/s
		25	bw1600		Bandwidth 1600 kbit/s
		26	bw1664		Bandwidth 1664 kbit/s
		27	bw1728		Bandwidth 1728 kbit/s
		28	bw1792		Bandwidth 1792 kbit/s
		29	bw1856		Bandwidth 1856 kbit/s
		30	bw1920		Bandwidth 1920 kbit/s
		31	bw1984		Bandwidth 1984 kbit/s
		32	bw2048		Bandwidth 2048 kbit/s
		254			unknown value
		255			unsupported variable for addressed device"
	::= { cmrwFar2MEntry 5 }

cmrwFar2MIdlecodeT OBJECT-TYPE
	SYNTAX INTEGER
	{
		ais(1),
		es(2),
		pais(3),
		none(4),
		unknown(254),
		unsupported(255)
	}
	ACCESS read-write
	STATUS mandatory
	DESCRIPTION
		"Defines the Idle Code on the T-Interface.
		1	AIS	AIS
		2	ES	ES
		3	PAIS	PAIS
		4	None	No Idle Code 
		254		unknown value
		255		unsupported variable for addressed device"
	::= { cmrwFar2MEntry 6 }

cmrwFar2MCrc4T OBJECT-TYPE
	SYNTAX INTEGER
	{
		off(1),
		on(2),
		autoOff(3),
		unknown(254),
		unsupported(255)
	}
	ACCESS read-write
	STATUS mandatory
	DESCRIPTION
		"Defines whether CRC-4 evaluation at the T-Interface is done.
		1	Off	CRC-4 Data is not evaluated
		2	On	CRC-4 Data is evaluated, error if none present in signal
		3	AutoOff	CRC-4 Data is evaluated, if none is present, evaluation is disabled
		254		unknown value
		255		unsupported variable for addressed device"
	::= { cmrwFar2MEntry 7 }

cmrwFar2MCrc4U OBJECT-TYPE
	SYNTAX INTEGER
	{
		off(1),
		on(2),
		unknown(254),
		unsupported(255)
	}
	ACCESS read-write
	STATUS mandatory
	DESCRIPTION
		"Defines whether CRC-4 evaluation at the U-Interface is done.
		1	Off	CRC-4 Data is not evaluated
		2	On	CRC-4 Data is evaluated, error if none present in signal
		254		unknown value
		255		unsupported variable for addressed device"
	::= { cmrwFar2MEntry 8 }

cmrwFar2MDetectAis OBJECT-TYPE
	SYNTAX INTEGER
	{
		noDetect(1),
		detect(2),
		unknown(254),
		unsupported(255)
	}
	ACCESS read-write
	STATUS mandatory
	DESCRIPTION
		"Defines whether AIS detection is enabled or not
		1	NoDetect	AIS is not detected
		2	Detect		AIS is detected
		254			unknown value
		255			unsupported variable for addressed device"
	::= { cmrwFar2MEntry 9 }

cmrwFar2MInsertAis OBJECT-TYPE
	SYNTAX INTEGER
	{
		noInsertion(1),
		insertion(2),
		unknown(254),
		unsupported(255)
	}
	ACCESS read-write
	STATUS mandatory
	DESCRIPTION
		"Defines whether an AIS signal is regenerated or just passed through
		1	NoInsertion	Pass signal through
		2	Insertion	Regenerate signal
		254			unknown value
		255			unsupported variable for addressed device"
	::= { cmrwFar2MEntry 10 }

cmrwFar2MSaBits OBJECT-TYPE
	SYNTAX OCTET STRING(SIZE(6))
	ACCESS read-write
	STATUS mandatory
	DESCRIPTION
		"Contains the Sa-bit configuration. The variable is an array with length 6.
		The indicies address the Sa bits as follows:
		[0]	Sa4
		[1]	Sa5
		[2]	Sa6
		[3]	Sa7
		[4]	Sa8
		[5]	Sa6 Loop Detection
		Positions 0,3 and 4 (Sa4, Sa7, Sa8) can contain the following values:
		1	Transparent
		2	Constant Ones
		Position 1 (Sa5) can contain the following values:
		1	Transparent
		2	Constant Ones
		3	Insert
		Position 2 (Sa6) can contain the following values:
		1	Transparent
		2	Constant Ones
		3	ETSI Norm
		4	ANSI Norm
		Position 5 (Sa6 Loop Detection) can contain the following values:
		1	Loop Detection Off
		2	Loop Detection On
		
		All 6 positions can contain the values below:
		254		unknown value
		255		unsupported variable for addressed device"
	::= { cmrwFar2MEntry 11 }

cmrwFar2MTs16Signalling OBJECT-TYPE
	SYNTAX INTEGER
	{
		transparent(1),
		new(2),
		unknown(254),
		unsupported(255)
	}
	ACCESS read-write
	STATUS mandatory
	DESCRIPTION
		"Defines whether time slot 16 is passed through transparently or
		whether it is reinsertet.
		1	Transparent	Passing through TS16
		2	New		Reinserting TS16
		254			unknown value
		255			unsupported variable for addressed device"
	::= { cmrwFar2MEntry 12 }

cmrwFar2MIdlecodeU OBJECT-TYPE
	SYNTAX INTEGER
	{
		ais(1),
		es(2),
		pais(3),
		none(4),
		unknown(254),
		unsupported(255)
	}
	ACCESS read-write
	STATUS mandatory
	DESCRIPTION
		"Defines the Idle Code on the U-Interface.
		1	AIS	AIS
		2	ES	ES
		3	PAIS	PAIS
		4	none	no Idle Code
		254		unknown value
		255		unsupported variable for addressed device"
	::= { cmrwFar2MEntry 13 }

cmrwFar2MTs0Present OBJECT-TYPE
	SYNTAX INTEGER
	{
		no(1),
		yes(2),
		unknown(254),
		unsupported(255)
	}
	ACCESS read-write
	STATUS mandatory
	DESCRIPTION
		"Defines whether timeslot 0 (G.704 frame) is actually
		transmitted by the U interface.
		1	No	Timeslot 0 is re-inserted by receiver
		2	Yes	Timeslot 0 is actually sent
		254		unknown value
		255		unsupported variable for addressed device"
	::= { cmrwFar2MEntry 14 }

cmrwFar2MCrc4V OBJECT-TYPE
	SYNTAX INTEGER
	{
		off(1),
		on(2),
		unknown(254),
		unsupported(255)
	}
	ACCESS read-write
	STATUS mandatory
	DESCRIPTION
		"Defines whether CRC-4 evaluation at the V-Interfaces is done.
		1	Off	CRC-4 Data is not evaluated
		2	On		CRC-4 Data is evaluated, error if none present in signal
		254		unknown value
		255		unsupported variable for addressed device"
	::= { cmrwFar2MEntry 15 }

cmrwFar2MInterfaceImpedance OBJECT-TYPE
	SYNTAX INTEGER
	{
		ohm75(75),
		ohm120(120),
		unknown(254),
		unsupported(255)
	}
	ACCESS read-write
	STATUS mandatory
	DESCRIPTION
		"Indicates the impedance of the G.703 interface.
		75	ohm75	The impedance of the G.703 interface is 75 Ohm.
		120	ohm120	The impedance of the G.703 interface is 120 Ohm.
		254		unknown value
		255		unsupported variable for addressed device"
	::= { cmrwFar2MEntry 16 }

--------------------------------------------------------------------------------
--	CM-RW	far Data
--------------------------------------------------------------------------------
cmrwFarDataTable OBJECT-TYPE
	SYNTAX SEQUENCE OF CmrwFarDataEntry
	ACCESS not-accessible
	STATUS mandatory
	DESCRIPTION ""
	::= { cmrwFar 5 }

cmrwFarDataEntry OBJECT-TYPE
	SYNTAX CmrwFarDataEntry
	ACCESS not-accessible
	STATUS mandatory
	DESCRIPTION ""
	INDEX { cmrwFarDataPortIndex, cmrwFarDataLinkIndex }
	::= { cmrwFarDataTable 1 }

CmrwFarDataEntry ::=
	SEQUENCE
	{
		cmrwFarDataPortIndex INTEGER,
		cmrwFarDataLinkIndex INTEGER,
		cmrwFarDataEnabledD INTEGER,
		cmrwFarDataTimeslotsD INTEGER,
		cmrwFarDataIdlecodeD INTEGER,
		cmrwFarDataFastSig INTEGER,
		cmrwFarDataLine106 INTEGER,
		cmrwFarDataLine107 INTEGER,
		cmrwFarDataLine109 INTEGER,
		cmrwFarDataLine140 INTEGER,
		cmrwFarDataLine141 INTEGER,
		cmrwFarDataUseTs16ForData INTEGER,
		cmrwFarDataEndToEndSignalling INTEGER,
		cmrwFarDataDteDceMode INTEGER,
		cmrwFarDataIfSelector INTEGER		
	}

cmrwFarDataPortIndex OBJECT-TYPE
	SYNTAX INTEGER
	ACCESS read-only
	STATUS mandatory
	DESCRIPTION
		"This variable addresses the port number of the proxy
		and is used as index for the other elements in the Table"
	::= { cmrwFarDataEntry 1 }

cmrwFarDataLinkIndex OBJECT-TYPE
	SYNTAX INTEGER
	ACCESS read-only
	STATUS mandatory
	DESCRIPTION
		"This variable addresses the slot number of the OMI sub-rack
		and is used as index for the other elements in the Table"
	::= {cmrwFarDataEntry 2 }

cmrwFarDataEnabledD OBJECT-TYPE
	SYNTAX INTEGER
	{
		disabled(1),
		enabled(2),
		unknown(254),
		unsupported(255)
	}
	ACCESS read-write
	STATUS mandatory
	DESCRIPTION
		"Defines whether the Data Interface is enabled or not.
		1	Disabled	Data Interface is disabled
		2	Enabled		Data Interface is enabled
		254			unknown value
		255			unsupported variable for addressed device"
	::= { cmrwFarDataEntry 3 }

cmrwFarDataTimeslotsD OBJECT-TYPE
	SYNTAX INTEGER
	{
		bw64(1),
		bw128(2),
		bw192(3),
		bw256(4),
		bw320(5),
		bw384(6),
		bw448(7),
		bw512(8),
		bw576(9),
		bw640(10),
		bw704(11),
		bw768(12),
		bw832(13),
		bw896(14),
		bw960(15),
		bw1024(16),
		bw1088(17),
		bw1152(18),
		bw1216(19),
		bw1280(20),
		bw1344(21),
		bw1408(22),
		bw1472(23),
		bw1536(24),
		bw1600(25),
		bw1664(26),
		bw1728(27),
		bw1792(28),
		bw1856(29),
		bw1920(30),
		bw1984(31),
		bw2048(32),
		bw2112(33),
		bw2176(34),
		bw2240(35),
		bw2304(36),
		bw2368(37),
		bw2432(38),
		bw2496(39),
		bw2560(40),
		bw2624(41),
		bw2688(42),
		bw2752(43),
		bw2816(44),
		bw2880(45),
		bw2944(46),
		bw3008(47),
		bw3072(48),
		bw3136(49),
		bw3200(50),
		bw3264(51),
		bw3328(52),
		bw3392(53),
		bw3456(54),
		bw3520(55),
		bw3584(56),
		bw3648(57),
		bw3712(58),
		bw3776(59),
		bw3840(60),
		bw3904(61),
		bw3968(62),
		bw4032(63),
		bw4096(64),
		bw4160(65),
		bw4224(66),
		bw4288(67),
		bw4352(68),
		bw4416(69),
		bw4480(70),
		bw4544(71),
		bw4608(72),
		bw4672(73),
		bw4736(74),
		bw4800(75),
		bw4864(76),
		bw4928(77),
		bw4992(78),
		bw5056(79),
		bw5120(80),
		bw5184(81),
		bw5248(82),
		bw5312(83),
		bw5376(84),
		bw5440(85),
		bw5504(86),
		bw5568(87),
		bw5632(88),
		bw5696(89),
		bw5760(90),
		bw5824(91),
		bw5888(92),
		bw5952(93),
		bw6016(94),
		bw6080(95),
		bw6144(96),
		bw6208(97),
		bw6272(98),
		bw6336(99),
		bw6400(100),
		bw6464(101),
		bw6528(102),
		bw6592(103),
		bw6656(104),
		bw6720(105),
		bw6784(106),
		bw6848(107),
		bw6912(108),
		bw6976(109),
		bw7040(110),
		bw7104(111),
		bw7168(112),
		bw7232(113),
		bw7296(114),
		bw7360(115),
		bw7424(116),
		bw7488(117),
		bw7552(118),
		bw7616(119),
		bw7680(120),
		bw7744(121),
		bw7808(122),
		bw7872(123),
		bw7936(124),
		bw8000(125),
		bw8064(126),
		bw8128(127),
		bw8192(128),
		bw8256(129),
		bw8320(130),
		bw8384(131),
		bw8448(132),
		bw8512(133),
		bw8576(134),
		bw8640(135),
		bw8704(136),
		bw8768(137),
		bw8832(138),
		bw8896(139),
		bw8960(140),
		bw9024(141),
		bw9088(142),
		bw9152(143),
		bw9216(144),
		bw9280(145),
		bw9344(146),
		bw9408(147),
		bw9472(148),
		bw9536(149),
		bw9600(150),
		bw9664(151),
		bw9728(152),
		bw9792(153),
		bw9856(154),
		bw9920(155),
		bw9984(156),
		bw10048(157),
		bw10112(158),
		bw10176(159),
		bw10240(160),
		bw10304(161),
		bw10368(162),
		bw10432(163),
		bw10496(164),
		bw10560(165),
		bw10624(166),
		bw10688(167),
		bw10752(168),
		bw10816(169),
		bw10880(170),
		bw10944(171),
		bw11008(172),
		bw11072(173),
		bw11136(174),
		bw11200(175),
		bw11264(176),
		bw11328(177),
		bw11392(178),
		unknown(254),
		unsupported(255)
	}
	ACCESS read-write
	STATUS mandatory
	DESCRIPTION
		"Bandwidth allocated for G.703 Interface (T-Interface) as
		a number of 64kbit/s time slots.
		
		When reading the following values can also be returned:
		1	bw64		Bandwidth   64 kbit/s
		2	bw128		Bandwidth  128 kbit/s
		3	bw192		Bandwidth  192 kbit/s
		4	bw256		Bandwidth  256 kbit/s
		5	bw320		Bandwidth  320 kbit/s
		6	bw384		Bandwidth  384 kbit/s
		7	bw448		Bandwidth  448 kbit/s
		8	bw512		Bandwidth  512 kbit/s
		9	bw576		Bandwidth  576 kbit/s
		10	bw640		Bandwidth  640 kbit/s
		11	bw704		Bandwidth  704 kbit/s
		12	bw768		Bandwidth  768 kbit/s
		13	bw832		Bandwidth  832 kbit/s
		14	bw896		Bandwidth  896 kbit/s
		15	bw960		Bandwidth  960 kbit/s
		16	bw1024		Bandwidth 1024 kbit/s
		17	bw1088		Bandwidth 1088 kbit/s
		18	bw1152		Bandwidth 1152 kbit/s
		19	bw1216		Bandwidth 1216 kbit/s
		20	bw1280		Bandwidth 1280 kbit/s
		21	bw1344		Bandwidth 1344 kbit/s
		22	bw1408		Bandwidth 1408 kbit/s
		23	bw1472		Bandwidth 1472 kbit/s
		24	bw1536		Bandwidth 1536 kbit/s
		25	bw1600		Bandwidth 1600 kbit/s
		26	bw1664		Bandwidth 1664 kbit/s
		27	bw1728		Bandwidth 1728 kbit/s
		28	bw1792		Bandwidth 1792 kbit/s
		29	bw1856		Bandwidth 1856 kbit/s
		30	bw1920		Bandwidth 1920 kbit/s
		31	bw1984		Bandwidth 1984 kbit/s
		32	bw2048		Bandwidth 2048 kbit/s
		33	bw2112		Bandwidth 2112 kbit/s
		34	bw2176		Bandwidth 2176 kbit/s
		35	bw2240		Bandwidth 2240 kbit/s
		36	bw2304		Bandwidth 2304 kbit/s
		37	bw2368		Bandwidth 2368 kbit/s
		38	bw2432		Bandwidth 2432 kbit/s
		39	bw2496		Bandwidth 2496 kbit/s
		40	bw2560		Bandwidth 2560 kbit/s
		41	bw2624		Bandwidth 2624 kbit/s
		42	bw2688		Bandwidth 2688 kbit/s
		43	bw2752		Bandwidth 2752 kbit/s
		44	bw2816		Bandwidth 2816 kbit/s
		45	bw2880		Bandwidth 2880 kbit/s
		46	bw2944		Bandwidth 2944 kbit/s
		47	bw3008		Bandwidth 3008 kbit/s
		48	bw3072		Bandwidth 3072 kbit/s
		49	bw3136		Bandwidth 3136 kbit/s
		50	bw3200		Bandwidth 3200 kbit/s
		51	bw3264		Bandwidth 3264 kbit/s
		52	bw3328		Bandwidth 3328 kbit/s
		53	bw3392		Bandwidth 3392 kbit/s
		54	bw3456		Bandwidth 3456 kbit/s
		55	bw3520		Bandwidth 3520 kbit/s
		56	bw3584		Bandwidth 3584 kbit/s
		57	bw3648		Bandwidth 3648 kbit/s
		58	bw3712		Bandwidth 3712 kbit/s
		59	bw3776		Bandwidth 3776 kbit/s
		60	bw3840		Bandwidth 3840 kbit/s
		61	bw3904		Bandwidth 3904 kbit/s
		62	bw3968		Bandwidth 3968 kbit/s
		63	bw4032		Bandwidth 4032 kbit/s
		64	bw4096		Bandwidth 4096 kbit/s
		65	bw4160		Bandwidth 4160 kbit/s
		66	bw4224		Bandwidth 4224 kbit/s
		67	bw4288		Bandwidth 4288 kbit/s
		68	bw4352		Bandwidth 4352 kbit/s
		69	bw4416		Bandwidth 4416 kbit/s
		70	bw4480		Bandwidth 4480 kbit/s
		71	bw4544		Bandwidth 4544 kbit/s
		72	bw4608		Bandwidth 4608 kbit/s
		73	bw4672		Bandwidth 4672 kbit/s
		74	bw4736		Bandwidth 4736 kbit/s
		75	bw4800		Bandwidth 4800 kbit/s
		76	bw4864		Bandwidth 4864 kbit/s
		77	bw4928		Bandwidth 4928 kbit/s
		78	bw4992		Bandwidth 4992 kbit/s
		79	bw5056		Bandwidth 5056 kbit/s
		80	bw5120		Bandwidth 5120 kbit/s
		81	bw5184		Bandwidth 5184 kbit/s
		82	bw5248		Bandwidth 5248 kbit/s
		83	bw5312		Bandwidth 5312 kbit/s
		84	bw5376		Bandwidth 5376 kbit/s
		85	bw5440		Bandwidth 5440 kbit/s
		86	bw5504		Bandwidth 5504 kbit/s
		87	bw5568		Bandwidth 5568 kbit/s
		88	bw5632		Bandwidth 5632 kbit/s
		89	bw5696		Bandwidth 5696 kbit/s
		90	bw5760		Bandwidth 5760 kbit/s
		91	bw5824		Bandwidth 5824 kbit/s
		92	bw5888		Bandwidth 5888 kbit/s
		93	bw5952		Bandwidth 5952 kbit/s
		94	bw6016		Bandwidth 6016 kbit/s
		95	bw6080		Bandwidth 6080 kbit/s
		96	bw6144		Bandwidth 6144 kbit/s
		97	bw6208		Bandwidth 6208 kbit/s
		98	bw6272		Bandwidth 6272 kbit/s
		99	bw6336		Bandwidth 6336 kbit/s
		100	bw6400		Bandwidth 6400 kbit/s
		101	bw6464		Bandwidth 6464 kbit/s
		102	bw6528		Bandwidth 6528 kbit/s
		103	bw6592		Bandwidth 6592 kbit/s
		104	bw6656		Bandwidth 6656 kbit/s
		105	bw6720		Bandwidth 6720 kbit/s
		106	bw6784		Bandwidth 6784 kbit/s
		107	bw6848		Bandwidth 6848 kbit/s
		108	bw6912		Bandwidth 6912 kbit/s
		109	bw6976		Bandwidth 6976 kbit/s
		110	bw7040		Bandwidth 7040 kbit/s
		111	bw7104		Bandwidth 7104 kbit/s
		112	bw7168		Bandwidth 7168 kbit/s
		113	bw7232		Bandwidth 7232 kbit/s
		114	bw7296		Bandwidth 7296 kbit/s
		115	bw7360		Bandwidth 7360 kbit/s
		116	bw7424		Bandwidth 7424 kbit/s
		117	bw7488		Bandwidth 7488 kbit/s
		118	bw7552		Bandwidth 7552 kbit/s
		119	bw7616		Bandwidth 7616 kbit/s
		120	bw7680		Bandwidth 7680 kbit/s
		121	bw7744		Bandwidth 7744 kbit/s
		122	bw7808		Bandwidth 7808 kbit/s
		123	bw7872		Bandwidth 7872 kbit/s
		124	bw7936		Bandwidth 7936 kbit/s
		125	bw8000		Bandwidth 8000 kbit/s
		126	bw8064		Bandwidth 8064 kbit/s
		127	bw8128		Bandwidth 8128 kbit/s
		128	bw8192		Bandwidth 8192 kbit/s
		129	bw8256		Bandwidth 8256 kbit/s
		130	bw8320		Bandwidth 8320 kbit/s
		131	bw8384		Bandwidth 8384 kbit/s
		132	bw8448		Bandwidth 8448 kbit/s
		133	bw8512		Bandwidth 8512 kbit/s
		134	bw8576		Bandwidth 8576 kbit/s
		135	bw8640		Bandwidth 8640 kbit/s
		136	bw8704		Bandwidth 8704 kbit/s
		137	bw8768		Bandwidth 8768 kbit/s
		138	bw8832		Bandwidth 8832 kbit/s
		139	bw8896		Bandwidth 8896 kbit/s
		140	bw8960		Bandwidth 8960 kbit/s
		141	bw9024		Bandwidth 9024 kbit/s
		142	bw9088		Bandwidth 9088 kbit/s
		143	bw9152		Bandwidth 9152 kbit/s
		144	bw9216		Bandwidth 9216 kbit/s
		145	bw9280		Bandwidth 9280 kbit/s
		146	bw9344		Bandwidth 9344 kbit/s
		147	bw9408		Bandwidth 9408 kbit/s
		148	bw9472		Bandwidth 9472 kbit/s
		149	bw9536		Bandwidth 9536 kbit/s
		150	bw9600		Bandwidth 9600 kbit/s
		151	bw9664		Bandwidth 9664 kbit/s
		152	bw9728		Bandwidth 9728 kbit/s
		153	bw9792		Bandwidth 9792 kbit/s
		154	bw9856		Bandwidth 9856 kbit/s
		155	bw9920		Bandwidth 9920 kbit/s
		156	bw9984		Bandwidth 9984 kbit/s
		157	bw10048		Bandwidth 10048 kbit/s
		158	bw10112		Bandwidth 10112 kbit/s
		159	bw10176		Bandwidth 10176 kbit/s
		160	bw10240		Bandwidth 10240 kbit/s
		161	bw10304		Bandwidth 10304 kbit/s
		162	bw10368		Bandwidth 10368 kbit/s
		163	bw10432		Bandwidth 10432 kbit/s
		164	bw10496		Bandwidth 10496 kbit/s
		165	bw10560		Bandwidth 10560 kbit/s
		166	bw10624		Bandwidth 10624 kbit/s
		167	bw10688		Bandwidth 10688 kbit/s
		168	bw10752		Bandwidth 10752 kbit/s
		169	bw10816		Bandwidth 10816 kbit/s
		170	bw10880		Bandwidth 10880 kbit/s
		171	bw10944		Bandwidth 10944 kbit/s
		172	bw11008		Bandwidth 11008 kbit/s
		173	bw11072		Bandwidth 11072 kbit/s
		174	bw11136		Bandwidth 11136 kbit/s
		175	bw11200		Bandwidth 11200 kbit/s
		176	bw11264		Bandwidth 11264 kbit/s
		177	bw11328		Bandwidth 11328 kbit/s
		178	bw11392		Bandwidth 11392 kbit/s
		254			unknown value
		255			unsupported variable for addressed device"
	::= { cmrwFarDataEntry 4 }

cmrwFarDataIdlecodeD OBJECT-TYPE
	SYNTAX INTEGER
	{
		null(1),
		ais(2),
		unknown(254),
		unsupported(255)
	}
	ACCESS read-write
	STATUS mandatory
	DESCRIPTION
		"Defines the Idle Code for the Data Interface.
		1	Null	Always send 0
		2	Ais	Always send 1
		254		unknown value
		255		unsupported variable for addressed device"
	::= { cmrwFarDataEntry 5 }

cmrwFarDataFastSig OBJECT-TYPE
	SYNTAX INTEGER
	{
		off(1),
		on(2),
		unknown(254),
		unsupported(255)
	}
	ACCESS read-write
	STATUS mandatory
	DESCRIPTION
		"Defines whether Fast Signalling is used or not
		1	Off	Fast Signalling is not used
		2	On	Fast Signalling is used
		254		unknown value
		255		unsupported variable for addressed device"
	::= { cmrwFarDataEntry 6 }

cmrwFarDataLine106 OBJECT-TYPE
	SYNTAX INTEGER
	{
		auto(1),
		perm(2),
		unknown(254),
		unsupported(255)
	}
	ACCESS read-write
	STATUS mandatory
	DESCRIPTION
		"Defines whether control line 106 is set automatically or
		permanently turned on.
		1	Auto	Automatically set
		2	Perm	Permanently on
		254		unknown value
		255		unsupported variable for addressed device"
	::= { cmrwFarDataEntry 7 }

cmrwFarDataLine107 OBJECT-TYPE
	SYNTAX INTEGER
	{
		auto(1),
		perm(2),
		unknown(254),
		unsupported(255)
	}
	ACCESS read-write
	STATUS mandatory
	DESCRIPTION
		"Defines whether control line 107 is set automatically or
		permanently turned on.
		1	Auto	Automatically set
		2	Perm	Permanently on
		254		unknown value
		255		unsupported variable for addressed device"
	::= { cmrwFarDataEntry 8 }

cmrwFarDataLine109 OBJECT-TYPE
	SYNTAX INTEGER
	{
		auto(1),
		perm(2),
		unknown(254),
		unsupported(255)
	}
	ACCESS read-write
	STATUS mandatory
	DESCRIPTION
		"Defines whether control line 109 is set automatically or
		permanently turned on.
		1	Auto	Automatically set
		2	Perm	Permanently on
		254		unknown value
		255		unsupported variable for addressed device"
	::= { cmrwFarDataEntry 9 }

cmrwFarDataLine140 OBJECT-TYPE
	SYNTAX INTEGER
	{
		auto(1),
		perm(2),
		unknown(254),
		unsupported(255)
	}
	ACCESS read-write
	STATUS mandatory
	DESCRIPTION
		"Defines whether control line 140 is set automatically or
		permanently turned off.
		1	Auto	Automatically set
		2	Perm	Permanently off
		254		unknown value
		255		unsupported variable for addressed device"
	::= { cmrwFarDataEntry 10 }

cmrwFarDataLine141 OBJECT-TYPE
	SYNTAX INTEGER
	{
		auto(1),
		perm(2),
		unknown(254),
		unsupported(255)
	}
	ACCESS read-write
	STATUS mandatory
	DESCRIPTION
		"Defines whether control line 141 is set automatically or
		permanently turned off.
		1	Auto	Automatically set
		2	Perm	Permanently off
		254		unknown value
		255		unsupported variable for addressed device"
	::= { cmrwFarDataEntry 11 }

cmrwFarDataUseTs16ForData OBJECT-TYPE
	SYNTAX INTEGER
	{
		no(1),
		yes(2),
		unknown(254),
		unsupported(255)
	}
	ACCESS read-write
	STATUS mandatory
	DESCRIPTION
		"Defines whether timeslot 16 can be used for data when
		no signalling information is transmitted in it.
		1	No	Timeslot 16 is reserved even if no signalling is used
		2	Yes	Timeslot 16 is used for data if no signalling is used
		254		unknown value
		255		unsupported variable for addressed device"
	::= { cmrwFarDataEntry 12 }

cmrwFarDataEndToEndSignalling OBJECT-TYPE
	SYNTAX INTEGER
	{
		disabled(1),
		fastSig(2),
		cas(3),
		unknown(254),
		unsupported(255)
	}
	ACCESS read-write
	STATUS mandatory
	DESCRIPTION
		"Defines whether End To End Signalling is enabled.
		1	Disabled	End To End Signalling is disabled
		2	FastSig		End To End Signalling is fast signalling
		3	CAS		End To End Signalling is CAS
		254			unknown value
		255			unsupported variable for addressed device"
	::= { cmrwFarDataEntry 13 }

cmrwFarDataDteDceMode OBJECT-TYPE
	SYNTAX INTEGER
	{
		dce(1),
		dte(2),
		unknown(254),
		unsupported(255)
	}
	ACCESS read-write
	STATUS mandatory
	DESCRIPTION
		"Defines the operation mode of the data interface.
		1	DCE	Data Interface operates in DCE (Data Circuit-Terminating Equipment) mode
		2	DTE	Data Interface operates in DTE (Data Terminal Equipment) mode
		254		unknown value
		255		unsupported variable for addressed device"
	::= { cmrwFarDataEntry 14 }

cmrwFarDataIfSelector OBJECT-TYPE
	SYNTAX INTEGER
	{
		mgblEthIf(1),
		multiPurpDataIf(2),
		unknown(254),
		unsupported(255)
	}
	ACCESS read-write
	STATUS mandatory
	DESCRIPTION
		"Selects the active data Interface.
		1	mgblEthIf	Manageable Ethernet Interface is selected
		2	multiPurpDataIf	Multi Purpose Data Interface is selected
		254			unknown value
		255			unsupported variable for addressed device"
	::= { cmrwFarDataEntry 15 }

--------------------------------------------------------------------------------
--	CM-RW	far Action
--------------------------------------------------------------------------------
cmrwFarActionTable OBJECT-TYPE
	SYNTAX SEQUENCE OF CmrwFarActionEntry
	ACCESS not-accessible
	STATUS mandatory
	DESCRIPTION ""
	::= { cmrwFar 6 }

cmrwFarActionEntry OBJECT-TYPE
	SYNTAX CmrwFarActionEntry
	ACCESS not-accessible
	STATUS mandatory
	DESCRIPTION ""
	INDEX { cmrwFarActionPortIndex, cmrwFarActionLinkIndex }
	::= { cmrwFarActionTable 1 }

CmrwFarActionEntry ::=
	SEQUENCE
	{
		cmrwFarActionPortIndex INTEGER,
		cmrwFarActionLinkIndex INTEGER,
		cmrwFarActionReboot INTEGER
	}

cmrwFarActionPortIndex OBJECT-TYPE
	SYNTAX INTEGER
	ACCESS read-only
	STATUS mandatory
	DESCRIPTION
		"This variable addresses the port number of the proxy
		and is used as index for the other elements in the Table"
	::= { cmrwFarActionEntry 1 }

cmrwFarActionLinkIndex OBJECT-TYPE
	SYNTAX INTEGER
	ACCESS read-only
	STATUS mandatory
	DESCRIPTION
		"This variable addresses the slot number of the OMI sub-rack
		and is used as index for the other elements in the Table"
	::= {cmrwFarActionEntry 2 }

cmrwFarActionReboot OBJECT-TYPE
	SYNTAX INTEGER {
		passive(1),
		active(2),
		unknown(254),
		unsupported(255)
	}
	ACCESS read-write
	STATUS mandatory
	DESCRIPTION
		"Command to reboot device. The parameter specifies whether
		the firmware in the active or passive bank shall be started.
		1	Passive	Reboot using the passive firmware
		2	Active	Reboot using the active firmware
		254		unknown value
		255		unsupported variable for addressed device
		
		If the parameter 'passive' is specified but the passive
		firmware bank contains no valid code, the device reboots
		using the active firmware."
	::= { cmrwFarActionEntry 3 }

--------------------------------------------------------------------------------
--	CM-RW	Far User Data
------------------------------------------------------------------------------
cmrwFarUserDataTable OBJECT-TYPE
	SYNTAX SEQUENCE OF CmrwFarUserDataEntry
	ACCESS not-accessible
	STATUS mandatory
	DESCRIPTION ""
	::= { cmrwFar 7 }

cmrwFarUserDataEntry OBJECT-TYPE
	SYNTAX CmrwFarUserDataEntry
	ACCESS not-accessible
	STATUS mandatory
	DESCRIPTION ""
	INDEX { cmrwFarUserDataPortIndex, cmrwFarUserDataLinkIndex, cmrwFarUserDataItemIndex }
	::= { cmrwFarUserDataTable 1 }

CmrwFarUserDataEntry ::=
	SEQUENCE
	{
		cmrwFarUserDataPortIndex INTEGER,
		cmrwFarUserDataLinkIndex INTEGER,
		cmrwFarUserDataItemIndex INTEGER,
		cmrwFarUserData DisplayString
	}

cmrwFarUserDataPortIndex OBJECT-TYPE
	SYNTAX INTEGER
	ACCESS read-only
	STATUS mandatory
	DESCRIPTION
		"This variable addresses the port number of the proxy
		and is used as index for the other elements in the Table"
	::= { cmrwFarUserDataEntry 1 }

cmrwFarUserDataLinkIndex OBJECT-TYPE
	SYNTAX INTEGER
	ACCESS read-only
	STATUS mandatory
	DESCRIPTION
		"This variable addresses the slot number of the OMI sub-rack
		and is used as index for the other elements in the Table"
	::= {cmrwFarUserDataEntry 2 }

cmrwFarUserDataItemIndex OBJECT-TYPE
	SYNTAX INTEGER
	ACCESS read-only
	STATUS mandatory
	DESCRIPTION
		"This variable addresses the data field number of the user data 
		and is used as index for the other elements in the Table"
	::= {cmrwFarUserDataEntry 3 }

cmrwFarUserData OBJECT-TYPE
	SYNTAX DisplayString(SIZE(100))
	ACCESS read-write
	STATUS mandatory
	DESCRIPTION
	"User data that can be written to the device"
	::= {cmrwFarUserDataEntry 4 }

--------------------------------------------------------------------------------
--	CM-RW	Far RPS
------------------------------------------------------------------------------
cmrwFarRpsTable OBJECT-TYPE
	SYNTAX SEQUENCE OF CmrwFarRpsEntry
	ACCESS not-accessible
	STATUS mandatory
	DESCRIPTION ""
	::= { cmrwFar 8 }

cmrwFarRpsEntry OBJECT-TYPE
	SYNTAX CmrwFarRpsEntry
	ACCESS not-accessible
	STATUS mandatory
	DESCRIPTION ""
	INDEX { cmrwFarRpsPortIndex, cmrwFarRpsLinkIndex }
	::= { cmrwFarRpsTable 1 }

CmrwFarRpsEntry ::=
	SEQUENCE
	{
		cmrwFarRpsPortIndex INTEGER,
		cmrwFarRpsLinkIndex INTEGER,
		cmrwFarRps INTEGER,
		cmrwFarRpsCurrent INTEGER
	}

cmrwFarRpsPortIndex OBJECT-TYPE
	SYNTAX INTEGER
	ACCESS read-only
	STATUS mandatory
	DESCRIPTION
		"This variable addresses the port number of the proxy
		and is used as index for the other elements in the Table"
	::= { cmrwFarRpsEntry 1 }

cmrwFarRpsLinkIndex OBJECT-TYPE
	SYNTAX INTEGER
	ACCESS read-only
	STATUS mandatory
	DESCRIPTION
		"This variable addresses the slot number of the OMI sub-rack
		and is used as index for the other elements in the Table"
	::= {cmrwFarRpsEntry 2 }

cmrwFarRps OBJECT-TYPE
	SYNTAX INTEGER
	{
		inactive(1),
		active(2),
		unknown(254),
		unsupported(255)
	}
	ACCESS read-only
	STATUS mandatory
	DESCRIPTION
		"Indicates whether the Remote Power Supply is on/off.
		1	Inactive	The RPS is turned off
		2	Active		The RPS is turned on
		254			unknown value
		255			unsupported
		"
	::= {cmrwFarRpsEntry 3 }

cmrwFarRpsCurrent OBJECT-TYPE
	SYNTAX INTEGER
	{
		mA50(50),
		mA60(60),
		unknown(254),
		unsupported(255)
	}
	ACCESS read-only
	STATUS mandatory
	DESCRIPTION
		"Indicates the Remote Power Supply current.
		50	Inactive	RPS current limied to 50 mA
		60	Active		RPS current limited to 60 mA
		254			unknown value
		255			unsupported
		"
	::= {cmrwFarRpsEntry 4 }

--------------------------------------------------------------------------------
--	CM-RW	L2SwitchPort
--------------------------------------------------------------------------------
cmrwFarL2SwitchPortTable OBJECT-TYPE
	SYNTAX SEQUENCE OF CmrwFarL2SwitchPortEntry
	ACCESS not-accessible
	STATUS mandatory
	DESCRIPTION ""
	::= { cmrwFar 9 }

cmrwFarL2SwitchPortEntry OBJECT-TYPE
	SYNTAX CmrwFarL2SwitchPortEntry
	ACCESS not-accessible
	STATUS mandatory
	DESCRIPTION ""
	INDEX { cmrwFarL2SwitchPortPortIndex, cmrwFarL2SwitchPortLinkIndex, cmrwFarL2SwitchPortLanPortIndex }
	::= { cmrwFarL2SwitchPortTable 1 }

CmrwFarL2SwitchPortEntry ::=
	SEQUENCE
	{
		cmrwFarL2SwitchPortPortIndex INTEGER,
		cmrwFarL2SwitchPortLinkIndex INTEGER,
		cmrwFarL2SwitchPortLanPortIndex INTEGER,
		cmrwFarL2SwitchPortEnabled INTEGER,
		cmrwFarL2SwitchPortPhyCfg INTEGER,
		cmrwFarL2SwitchPortPhyAdvModes INTEGER,
		cmrwFarL2SwitchPortPhyCfgReadout INTEGER,
		cmrwFarL2SwitchPortAutoXover INTEGER,
		cmrwFarL2SwitchPortFlowCtrl INTEGER,
		cmrwFarL2SwitchPortRateLimit INTEGER,
		cmrwFarL2SwitchPortRateLimitCfg INTEGER
	}

cmrwFarL2SwitchPortPortIndex OBJECT-TYPE
	SYNTAX INTEGER
	ACCESS read-only
	STATUS mandatory
	DESCRIPTION
		"This variable addresses the port number of the proxy
		and is used as index for the other elements in the Table"
	::= { cmrwFarL2SwitchPortEntry 1 }

cmrwFarL2SwitchPortLinkIndex OBJECT-TYPE
	SYNTAX INTEGER
	ACCESS read-only
	STATUS mandatory
	DESCRIPTION
		"This variable addresses the slot number of the OMI sub-rack
		and is used as index for the other elements in the Table"
	::= { cmrwFarL2SwitchPortEntry 2 }

cmrwFarL2SwitchPortLanPortIndex OBJECT-TYPE
	SYNTAX INTEGER
	ACCESS read-only
	STATUS mandatory
	DESCRIPTION
		"This variable addresses the L2Switch port (LAN side)
		and is used as index for the other elements in the Table"
	::= { cmrwFarL2SwitchPortEntry 3 }

cmrwFarL2SwitchPortEnabled OBJECT-TYPE
	SYNTAX INTEGER {
		disabled(1),
		enabled(2),
		unknown(254),
		unsupported(255)
	}
	ACCESS read-write
	STATUS mandatory
	DESCRIPTION
		"Defines whether the L2Switch port is enabled or not.
		1	Disabled	L2Switch port is disabled
		2	Enabled		L2Switch port is enabled
		254	unknown
		255	unsupported"
	::= { cmrwFarL2SwitchPortEntry 4 }

cmrwFarL2SwitchPortPhyCfg OBJECT-TYPE
	SYNTAX INTEGER {
		full10(1),
		full100(2),
		half10(3),
		half100(4),
		auto(5),
		unknown(254),
		unsupported(255)
	}
	ACCESS read-write
	STATUS mandatory
	DESCRIPTION
		"Defines the ethernet phy config or allows auto negotiation.
		1	Full Duplex 10Mbps
		2	Full Duplex 100Mbps
		3	Half Duplex 10Mbps
		4	Half Duplex 100Mbps
		5	Auto Negotiation
		254	unknown
		255	unsupported"
	::= { cmrwFarL2SwitchPortEntry 5 }

cmrwFarL2SwitchPortPhyAdvModes OBJECT-TYPE
	SYNTAX INTEGER (0..1023)
	ACCESS read-write
	STATUS mandatory
	DESCRIPTION
		"Defines the phy modes to be offered during auto
		negotiation ('advertized modes').
		Bit 0	1	Full Duplex 10Mbps
		Bit 1	2	Full Duplex 100Mbps
		Bit 2	4	Half Duplex 10Mbps
		Bit 3	8	Half Duplex 100Mbps
		Bit 8	256	unknown value (ignore bits 0-7)
		Bit 9	512	unsupported variable for addressed device (ignore bits 0-7)"
	::= { cmrwFarL2SwitchPortEntry 6 }

cmrwFarL2SwitchPortPhyCfgReadout OBJECT-TYPE
	SYNTAX INTEGER {
		full10(1),
		full100(2),
		half10(3),
		half100(4),
		auto(5),
		linkdown(6),
		unknown(254),
		unsupported(255)
	}
	ACCESS read-only
	STATUS mandatory
	DESCRIPTION
		"Indicates the current ethernet phy config.
		1	Full Duplex 10Mbps
		2	Full Duplex 100Mbps
		3	Half Duplex 10Mbps
		4	Half Duplex 100Mbps
		5	Auto Negotiation
		6	Linkdown
		254	unknown
		255	unsupported"
	::= { cmrwFarL2SwitchPortEntry 7 }

cmrwFarL2SwitchPortAutoXover OBJECT-TYPE
	SYNTAX INTEGER {
		disabled(1),
		enabled(2),
		unknown(254),
		unsupported(255)
	}
	ACCESS read-write
	STATUS mandatory
	DESCRIPTION
		"Determines whether ethernet crossover (MDI/MDI-X)
		should automatically be detected and compensated
		for.
		1	Disabled	MDI
		2	Enabled		Auto MDI/MDI-X
		254	unknown
		255	unsupported"
	::= { cmrwFarL2SwitchPortEntry 8 }

cmrwFarL2SwitchPortFlowCtrl OBJECT-TYPE
	SYNTAX INTEGER {
		disabled(1),
		enabled(2),
		unknown(254),
		unsupported(255)
	}
	ACCESS read-write
	STATUS mandatory
	DESCRIPTION
		"Determines whether flow control should be performed
		on a specific port.
		1	Disabled	Flow control disabled
		2	Enabled		Flow control enabled
		254	unknown
		255	unsupported"
	::= { cmrwFarL2SwitchPortEntry 9 }

cmrwFarL2SwitchPortRateLimit OBJECT-TYPE
	SYNTAX INTEGER (0..65535)
	ACCESS read-write
	STATUS mandatory
	DESCRIPTION
		"Determines the maximum bit rate on a specific port
		in 32kbps increments. This setting can be
		overriden by the Rate Limit Cfg setting.
		32	Rate Limit 32kbps
		64	Rate Limit 64kbps
		...
		9216	Rate Limit 9216kbps (equals 4*2304 kbps)
		...
		xxx	Rate Limit xxxxkbps
		65534	unknown
		65535	unsupported"
	::= { cmrwFarL2SwitchPortEntry 10 }

cmrwFarL2SwitchPortRateLimitCfg OBJECT-TYPE
	SYNTAX INTEGER {
		unlimited(1),
		userN32k(2),
		unknown(254),
		unsupported(255)
	}
	ACCESS read-write
	STATUS mandatory
	DESCRIPTION
		"Determines the behavior of the port rate limiter.
		on a specific port
		1	Unlimited	No rate limit enforced
		2	User-Def. n*32k	User-defined value in 32k increments
		254	unknown
		255	unsupported"
	::= { cmrwFarL2SwitchPortEntry 11 }

--------------------------------------------------------------------------------
--	CM-RW	Local Multi Interfaces
--------------------------------------------------------------------------------
cmrwFarMultiIfTable OBJECT-TYPE
	SYNTAX SEQUENCE OF CmrwFarMultiIfEntry
	ACCESS not-accessible
	STATUS mandatory
	DESCRIPTION ""
	::= { cmrwFar 10 }

cmrwFarMultiIfEntry OBJECT-TYPE
	SYNTAX CmrwFarMultiIfEntry
	ACCESS not-accessible
	STATUS mandatory
	DESCRIPTION ""
	INDEX { cmrwFarMultiIfPortIndex, cmrwFarMultiIfLinkIndex, cmrwFarMultiIfInstanceIndex }
	::= { cmrwFarMultiIfTable 1 }

CmrwFarMultiIfEntry ::=
	SEQUENCE
	{
		cmrwFarMultiIfPortIndex INTEGER,
		cmrwFarMultiIfLinkIndex INTEGER,
		cmrwFarMultiIfInstanceIndex INTEGER,
		cmrwFarMultiIfUEnabled INTEGER,
		cmrwFarMultiIfVEnabled INTEGER
	}

cmrwFarMultiIfPortIndex OBJECT-TYPE
	SYNTAX INTEGER
	ACCESS read-only
	STATUS mandatory
	DESCRIPTION
		"This variable addresses the port number of the proxy
		and is used as index for the other elements in the Table"
	::= { cmrwFarMultiIfEntry 1 }

cmrwFarMultiIfLinkIndex OBJECT-TYPE
	SYNTAX INTEGER
	ACCESS read-only
	STATUS mandatory
	DESCRIPTION
		"This variable addresses the slot number of the OMI sub-rack
		and is used as index for the other elements in the Table"
	::= { cmrwFarMultiIfEntry 2 }

cmrwFarMultiIfInstanceIndex OBJECT-TYPE
	SYNTAX INTEGER
	ACCESS read-only
	STATUS mandatory
	DESCRIPTION
		"This variable addresses one of several instances
		and is used as index for the other elements in the Table.
		Instances can be
		- U interfaces 1,2,3,4...
		- V interfaces A,B,C,D...
		The numbering format is 1,2,3,4..."
	::= { cmrwFarMultiIfEntry 3 }

cmrwFarMultiIfUEnabled OBJECT-TYPE
	SYNTAX INTEGER {
		disabled(1),
		enabled(2),
		unknown(254),
		unsupported(255)
	}
	ACCESS read-write
	STATUS mandatory
	DESCRIPTION
		"Defines whether the U1,U2,U3,U4... interface is enabled or not.
		1	Disabled	Interface is disabled
		2	Enabled		Interface is enabled
		254	unknown
		255	unsupported"
	::= { cmrwFarMultiIfEntry 4 }

cmrwFarMultiIfVEnabled OBJECT-TYPE
	SYNTAX INTEGER {
		disabled(1),
		enabled(2),
		unknown(254),
		unsupported(255)
	}
	ACCESS read-write
	STATUS mandatory
	DESCRIPTION
		"Defines whether the V_A,V_B,V_C,V_D... interface is enabled or not.
		1	Disabled	Interface is disabled
		2	Enabled		Interface is enabled
		254	unknown
		255	unsupported"
	::= { cmrwFarMultiIfEntry 5 }

--------------------------------------------------------------------------------
--	CM-RW	Far L2Switch
--------------------------------------------------------------------------------
cmrwFarL2SwitchTable OBJECT-TYPE
	SYNTAX SEQUENCE OF CmrwFarL2SwitchEntry
	ACCESS not-accessible
	STATUS mandatory
	DESCRIPTION ""
	::= { cmrwFar 11 }

cmrwFarL2SwitchEntry OBJECT-TYPE
	SYNTAX CmrwFarL2SwitchEntry
	ACCESS not-accessible
	STATUS mandatory
	DESCRIPTION ""
	INDEX { cmrwFarL2SwitchPortIndex, cmrwFarL2SwitchLinkIndex }
	::= { cmrwFarL2SwitchTable 1 }

CmrwFarL2SwitchEntry ::=
	SEQUENCE
	{
		cmrwFarL2SwitchPortIndex INTEGER,
		cmrwFarL2SwitchLinkIndex INTEGER,
		cmrwFarL2SwitchHugeFrames INTEGER,
		cmrwFarL2SwitchAdaptiveFlowCtrl INTEGER,
		cmrwFarL2SwitchFrameLengthCheck INTEGER
	}

cmrwFarL2SwitchPortIndex OBJECT-TYPE
	SYNTAX INTEGER
	ACCESS read-only
	STATUS mandatory
	DESCRIPTION
		"This variable addresses the port number of the proxy
		and is used as index for the other elements in the Table"
	::= { cmrwFarL2SwitchEntry 1 }

cmrwFarL2SwitchLinkIndex OBJECT-TYPE
	SYNTAX INTEGER
	ACCESS read-only
	STATUS mandatory
	DESCRIPTION
		"This variable addresses the slot number of the OMI sub-rack
		and is used as index for the other elements in the Table"
	::= { cmrwFarL2SwitchEntry 2 }

cmrwFarL2SwitchHugeFrames OBJECT-TYPE
	SYNTAX INTEGER {
		disabled(1),
		enabled(2),
		unknown(254),
		unsupported(255)
	}
	ACCESS read-write
	STATUS mandatory
	DESCRIPTION
		"Indicates whether the Layer 2 Switch supports so-called Huge Frames
		(frames longer than 1522 bytes).
		1	Disabled	Huge frames will be discarded
		2	Enabled		Huge frames allowed
		254			unknown
		255			unsupported"
	::= { cmrwFarL2SwitchEntry 3 }

cmrwFarL2SwitchAdaptiveFlowCtrl OBJECT-TYPE
	SYNTAX INTEGER {
		disabled(1),
		enabled(2),
		unknown(254),
		unsupported(255)
	}
	ACCESS read-write
	STATUS mandatory
	DESCRIPTION
		"Indicates whether adaptive flow control on the Layer 2 Switch and on the 
		HDLC bridge is enabled (to avoid packet loss) or not.
		1	Disabled	Disable adaptive flow control
		2	Enabled		Enable adaptive flow control
		254			unknown
		255			unsupported"
	::= { cmrwFarL2SwitchEntry 4 }

cmrwFarL2SwitchFrameLengthCheck OBJECT-TYPE
	SYNTAX INTEGER {
		disabled(1),
		enabled(2),
		unknown(254),
		unsupported(255)
	}
	ACCESS read-write
	STATUS mandatory
	DESCRIPTION
		"Indicates whether frame length check on the Layer 2 Switch is enabled or not.
		1	Disabled	Disable frame length check
		2	Enabled		Enable frame length check
		254			unknown
		255			unsupported"
	::= { cmrwFarL2SwitchEntry 5 }

--------------------------------------------------------------------------------
--	CM-RW	far Mapping
--------------------------------------------------------------------------------
cmrwFarMappingTable OBJECT-TYPE
	SYNTAX SEQUENCE OF CmrwFarMappingEntry
	ACCESS not-accessible
	STATUS mandatory
	DESCRIPTION ""
	::= { cmrwFar 12 }

cmrwFarMappingEntry OBJECT-TYPE
	SYNTAX CmrwFarMappingEntry
	ACCESS not-accessible
	STATUS mandatory
	DESCRIPTION ""
	INDEX { cmrwFarMappingPortIndex, cmrwFarMappingLinkIndex }
	::= { cmrwFarMappingTable 1 }

CmrwFarMappingEntry ::=
	SEQUENCE
	{
		cmrwFarMappingPortIndex INTEGER,
		cmrwFarMappingLinkIndex INTEGER,
		cmrwFarMappingEnabled INTEGER,
		cmrwFarMappingMixedOperation INTEGER,
		cmrwFarMappingOmitSTS INTEGER,
		cmrwFarMappingSTSPosition INTEGER,
		cmrwFarMappingTxTs0 INTEGER
	}

cmrwFarMappingPortIndex OBJECT-TYPE
	SYNTAX INTEGER
	ACCESS read-only
	STATUS mandatory
	DESCRIPTION
		"This variable addresses the port number of the proxy
		and is used as index for the other elements in the Table"
	::= { cmrwFarMappingEntry 1 }

cmrwFarMappingLinkIndex OBJECT-TYPE
	SYNTAX INTEGER
	ACCESS read-only
	STATUS mandatory
	DESCRIPTION
		"This variable addresses the slot number of the OMI sub-rack
		and is used as index for the other elements in the Table"
	::= {cmrwFarMappingEntry 2 }

cmrwFarMappingEnabled OBJECT-TYPE
	SYNTAX INTEGER
	{
		disabled(1),
		enabled(2),
		unknown(254),
		unsupported(255)
	}
	ACCESS read-write
	STATUS mandatory
	DESCRIPTION
		"Defines whether Mapping is enabled or disabled.
		1	Disabled	Mapping is disabled
		2	Enabled		Mapping is enabled
		254			unknown value
		255			unsupported variable for addressed device"
	::= { cmrwFarMappingEntry 3 }

cmrwFarMappingMixedOperation OBJECT-TYPE
	SYNTAX INTEGER
	{
		disabled(1),
		enabled(2),
		unknown(254),
		unsupported(255)
	}
	ACCESS read-write
	STATUS mandatory
	DESCRIPTION
		"Defines whether Mixed Operation (Data to Structured TDM) is enabled or disabled.
		1	Disabled	Mixed Operation is disabled
		2	Enabled		Mixed Operation is enabled
		254			unknown value
		255			unsupported variable for addressed device"
	::= { cmrwFarMappingEntry 4 }

cmrwFarMappingOmitSTS OBJECT-TYPE
	SYNTAX INTEGER
	{
		transmit(1),
		omit(2),
		unknown(254),
		unsupported(255)
	}
	ACCESS read-write
	STATUS mandatory
	DESCRIPTION
		"Defines whether the Signalization Timeslot is actually being transmitted or just mapped, not transmitted.
		1	Transmit	STS is transmitted
		2	Omit		STS is mapped, but not transmitted
		254			unknown value
		255			unsupported variable for addressed device"
	::= { cmrwFarMappingEntry 5 }

cmrwFarMappingSTSPosition OBJECT-TYPE
	SYNTAX INTEGER
	{
		unchanged(1),
		tsPos1(2),
		tsPos2(3),
		tsPos3(4),
		tsPos4(5),
		tsPos5(6),
		tsPos6(7),
		tsPos7(8),
		tsPos8(9),
		tsPos9(10),
		tsPos10(11),
		tsPos11(12),
		tsPos12(13),
		tsPos13(14),
		tsPos14(15),
		tsPos15(16),
		tsPos16(17),
		tsPos17(18),
		tsPos18(19),
		tsPos19(20),
		tsPos20(21),
		tsPos21(22),
		tsPos22(23),
		tsPos23(24),
		tsPos24(25),
		tsPos25(26),
		tsPos26(27),
		tsPos27(28),
		tsPos28(29),
		tsPos29(30),
		tsPos30(31),
		tsPos31(32),
		unknown(254),
		unsupported(255)
	}
	ACCESS read-write
	STATUS mandatory
	DESCRIPTION
		"Defines the position of the Signalization Timeslot.
		1	unchanged	STS mapping is disabled
		2	tsPos1		STS position: Timeslot 1
		3	tsPos2		STS position: Timeslot 2
		4	tsPos3		STS position: Timeslot 3
		5	tsPos4		STS position: Timeslot 4
		6	tsPos5		STS position: Timeslot 5
		7	tsPos6		STS position: Timeslot 6
		8	tsPos7		STS position: Timeslot 7
		9	tsPos8		STS position: Timeslot 8
		10	tsPos9   	STS position: Timeslot 9
		11	tsPos10  	STS position: Timeslot 10
		12	tsPos11  	STS position: Timeslot 11
		13	tsPos12  	STS position: Timeslot 12
		14	tsPos13  	STS position: Timeslot 13
		15	tsPos14  	STS position: Timeslot 14
		16	tsPos15  	STS position: Timeslot 15
		17	tsPos16  	STS position: Timeslot 16
		18	tsPos17  	STS position: Timeslot 17
		19	tsPos18  	STS position: Timeslot 18
		20	tsPos19  	STS position: Timeslot 19
		21	tsPos20  	STS position: Timeslot 20
		22	tsPos21  	STS position: Timeslot 21
		23	tsPos22  	STS position: Timeslot 22
		24	tsPos23  	STS position: Timeslot 23
		25	tsPos24  	STS position: Timeslot 24
		26	tsPos25  	STS position: Timeslot 25
		27	tsPos26  	STS position: Timeslot 26
		28	tsPos27  	STS position: Timeslot 27
		29	tsPos28  	STS position: Timeslot 28
		30	tsPos29  	STS position: Timeslot 29
		31	tsPos30  	STS position: Timeslot 30
		32	tsPos31  	STS position: Timeslot 31
		254			unknown value
		255			unsupported variable for addressed device"
	::= { cmrwFarMappingEntry 6 }

cmrwFarMappingTxTs0 OBJECT-TYPE
	SYNTAX INTEGER
	{
		disabled(1),
		enabled(2),
		unknown(254),
		unsupported(255)
	}
	ACCESS read-write
	STATUS mandatory
	DESCRIPTION
		"Defines whether timeslot 0 is transmitted on the U interface.
		1	Disabled	TS0 is not transmitted
		2	Enabled		TS0 is transmitted
		254			unknown value
		255			unsupported variable for addressed device"
	::= { cmrwFarMappingEntry 7 }

--------------------------------------------------------------------------------
--	CM-RW	Setup
--------------------------------------------------------------------------------
cmrwFarSetupTable OBJECT-TYPE
	SYNTAX SEQUENCE OF CmrwFarSetupEntry
	ACCESS not-accessible
	STATUS mandatory
	DESCRIPTION ""
	::= { cmrwFar 13 }

cmrwFarSetupEntry OBJECT-TYPE
	SYNTAX CmrwFarSetupEntry
	ACCESS not-accessible
	STATUS mandatory
	DESCRIPTION ""
	INDEX { cmrwFarSetupPortIndex, cmrwFarSetupLinkIndex }
	::= { cmrwFarSetupTable 1 }

CmrwFarSetupEntry ::=
	SEQUENCE
	{
		cmrwFarSetupPortIndex INTEGER,
		cmrwFarSetupLinkIndex INTEGER,
		cmrwFarSetupCardActivation OCTET STRING,
		cmrwFarSetupCardActState OCTET STRING,
		cmrwFarSetupIfAssignment OCTET STRING
	}

cmrwFarSetupPortIndex OBJECT-TYPE
	SYNTAX INTEGER
	ACCESS read-only
	STATUS mandatory
	DESCRIPTION
		"This variable addresses the port number of the proxy
		and is used as index for the other elements in the Table"
	::= { cmrwFarSetupEntry 1 }

cmrwFarSetupLinkIndex OBJECT-TYPE
	SYNTAX INTEGER
	ACCESS read-only
	STATUS mandatory
	DESCRIPTION
		"This variable addresses the slot number of the OMI sub-rack
		and is used as index for the other elements in the Table"
	::= { cmrwFarSetupEntry 2 }

cmrwFarSetupCardActivation OBJECT-TYPE
	SYNTAX OCTET STRING(SIZE(8))
	ACCESS read-write
	STATUS mandatory
	DESCRIPTION
		"Indicates the system activation for the systems A to H on the card.
		Each byte consists of the following information for one system:
		1	Deactivated	The system is inactive
		2	Activated	The system is active
		254			unknown value
		255			unsupported variable for addressed device"
	::= { cmrwFarSetupEntry 3 }

cmrwFarSetupCardActState OBJECT-TYPE
	SYNTAX OCTET STRING(SIZE(8))
	ACCESS read-only
	STATUS mandatory
	DESCRIPTION
		"Indicates the system activation state for the systems A to H on the card .
		Each byte consists of the following information for one system:
		1	Current		The system belongs to the currently managed line
		2	Present		The system does not belong to the currently managed line
		254			unknown value
		255			unsupported variable for addressed device"
	::= { cmrwFarSetupEntry 4 }

cmrwFarSetupIfAssignment OBJECT-TYPE
	SYNTAX OCTET STRING(SIZE(4))
	ACCESS read-write
	STATUS mandatory
	DESCRIPTION
		"Indicates the assignment of the (moveable) interfaces 1..4 
		to the systems A..D on the card .
		Each byte consists of the following information for one interface:
		1	systemA		The interface is assigned to System A
		2	systemB		The interface is assigned to System B
		3	systemC		The interface is assigned to System C
		4	systemD		The interface is assigned to System D
		254			unknown value
		255			unsupported variable for addressed device"
	::= { cmrwFarSetupEntry 5 }

--------------------------------------------------------------------------------
--	CM-RW	OMI Token
--------------------------------------------------------------------------------
cmrwOmiTokenTable OBJECT-TYPE
	SYNTAX SEQUENCE OF CmrwOmiTokenEntry
	ACCESS not-accessible
	STATUS mandatory
	DESCRIPTION ""
	::= { cmrwOmi 1 }

cmrwOmiTokenEntry OBJECT-TYPE
	SYNTAX CmrwOmiTokenEntry
	ACCESS not-accessible
	STATUS mandatory
	DESCRIPTION ""
	INDEX { cmrwOmiTokenPortIndex }
	::= { cmrwOmiTokenTable 1 }

CmrwOmiTokenEntry ::=
	SEQUENCE
	{
		cmrwOmiTokenPortIndex INTEGER,
		cmrwOmiTokenResId INTEGER,
		cmrwOmiTokenTicket INTEGER,
		cmrwOmiTokenSessionId INTEGER
	}

cmrwOmiTokenPortIndex OBJECT-TYPE
	SYNTAX INTEGER
	ACCESS read-only
	STATUS mandatory
	DESCRIPTION
		"This variable addresses the port number of the proxy
		and is used as index for the other elements in the Table"
	::= { cmrwOmiTokenEntry 1 }

cmrwOmiTokenResId OBJECT-TYPE
	SYNTAX INTEGER
	{
		available(1),
		lineint(2),
		lct(3),
		unknown(254),
		unsupported(255)
	}
	ACCESS read-only
	STATUS mandatory
	DESCRIPTION
		"Indicates who is in posession of the reservation token for this
		device.
		1	Available	The token is free
		2	Lineint		The token is given to the LineIntegrator
		3	Lct		The token is given to the Local Craft Terminal (LCT)
		254			unknown value
		255			unsupported variable for the addressed device"
	::= { cmrwOmiTokenEntry 2 }

cmrwOmiTokenTicket OBJECT-TYPE
	SYNTAX INTEGER
	{
		token1(1),
		token2(2),
		token3(3),
		token4(4),
		token5(5),
		token6(6),
		token7(7),
		token8(8),
		token9(9),
		token10(10),
		notGranted(11),
		lost(12),
		notRequested(13),
		unknown(254),
		unsupported(255)
	}
	ACCESS read-only
	STATUS mandatory
	DESCRIPTION
		"Is used to request or refresh the token
		device.
		1-10	Token1-10	The token was granted/refreshed, the index helps to detect whether it has expried since last reading from this variable
		11	NotGranted	The token was not granted
		12	Lost		The token could not be refreshed
		13	NotRequested	The token has not been requested
		254			unknown value
		255			unsupported variable for the addressed device"
	::= { cmrwOmiTokenEntry 7 }

cmrwOmiTokenSessionId OBJECT-TYPE
	SYNTAX INTEGER (0..65535)
	ACCESS read-write
	STATUS mandatory
	DESCRIPTION
		"Indicates which SNMP management is in posession of the reservation token for this
		device.
		0	  Invalid	  The session value is invalid
		65535 Unsupported unsupported variable for the addressed device"
	::= { cmrwOmiTokenEntry 8 }

--------------------------------------------------------------------------------
--	CM-RW	Omi Action
--------------------------------------------------------------------------------
cmrwOmiActionTable OBJECT-TYPE
	SYNTAX SEQUENCE OF CmrwOmiActionEntry
	ACCESS not-accessible
	STATUS mandatory
	DESCRIPTION ""
	::= { cmrwOmi 6 }

cmrwOmiActionEntry OBJECT-TYPE
	SYNTAX CmrwOmiActionEntry
	ACCESS not-accessible
	STATUS mandatory
	DESCRIPTION ""
	INDEX { cmrwOmiActionPortIndex }
	::= { cmrwOmiActionTable 1 }

CmrwOmiActionEntry ::=
	SEQUENCE
	{
		cmrwOmiActionPortIndex INTEGER,
		cmrwOmiActionReboot INTEGER
	}

cmrwOmiActionPortIndex OBJECT-TYPE
	SYNTAX INTEGER
	ACCESS read-only
	STATUS mandatory
	DESCRIPTION
		"This variable addresses the port number of the proxy
		and is used as index for the other elements in the Table"
	::= { cmrwOmiActionEntry 1 }

cmrwOmiActionReboot OBJECT-TYPE
	SYNTAX INTEGER {
		passive(1),
		active(2),
		unknown(254),
		unsupported(255)
	}
	ACCESS read-write
	STATUS mandatory
	DESCRIPTION
		"Command to reboot device. The parameter specifies whether
		the firmware in the active or passive bank shall be started.
		1	Passive	Reboot using the passive firmware
		2	Active	Reboot using the active firmware
		
		If the parameter 'passive' is specified but the passive
		firmware bank contains no valid code, the device reboots
		using the active firmware."
	::= { cmrwOmiActionEntry 2 }

--------------------------------------------------------------------------------
--	CM-RW	Omi Config
--------------------------------------------------------------------------------
cmrwOmiConfigTable OBJECT-TYPE
	SYNTAX SEQUENCE OF CmrwOmiConfigEntry
	ACCESS not-accessible
	STATUS mandatory
	DESCRIPTION ""
	::= { cmrwOmi 7 }

cmrwOmiConfigEntry OBJECT-TYPE
	SYNTAX CmrwOmiConfigEntry
	ACCESS not-accessible
	STATUS mandatory
	DESCRIPTION ""
	INDEX { cmrwOmiConfigPortIndex }
	::= { cmrwOmiConfigTable 1 }

CmrwOmiConfigEntry ::=
	SEQUENCE
	{
		cmrwOmiConfigPortIndex INTEGER,
		cmrwOmiConfigVirtSlotPolling INTEGER,
		cmrwOmiNTPServer1 OCTET STRING,
		cmrwOmiNTPServer2 OCTET STRING,
		cmrwOmiSNTPClientMode INTEGER,
		cmrwOmiSNTPLocalUDPPort INTEGER,
		cmrwOmiDateTime INTEGER,
		cmrwOmiNMS1PortConfig INTEGER,
		cmrwOmiNMS1PortStatus INTEGER,
		cmrwOmiNMS1PortAutoConfig OCTET STRING,
		cmrwOmiNMS2PortConfig INTEGER,
		cmrwOmiNMS2PortStatus INTEGER,
		cmrwOmiNMS2PortAutoConfig OCTET STRING,
		cmrwOmiNMS3PortConfig INTEGER,
		cmrwOmiNMS3PortStatus INTEGER,
		cmrwOmiNMS3PortAutoConfig OCTET STRING
	}

cmrwOmiConfigPortIndex OBJECT-TYPE
	SYNTAX INTEGER
	ACCESS read-only
	STATUS mandatory
	DESCRIPTION
		"This variable addresses the port number of the proxy
		and is used as index for the other elements in the Table"
	::= { cmrwOmiConfigEntry 1 }

cmrwOmiConfigVirtSlotPolling OBJECT-TYPE
	SYNTAX INTEGER {
		disabled(1),
		enabled(2),
		unknown(254),
		unsupported(255)
	}
	ACCESS read-write
	STATUS mandatory
	DESCRIPTION
		"Is used to enable/disable the polling of the virtual slots (0x80).
		1	Disabled	The polling of the virtual slots is disabled
		2	Enabled	The polling of the virtual slots is enabled"
	::= { cmrwOmiConfigEntry 2 }

cmrwOmiNTPServer1 OBJECT-TYPE
	SYNTAX OCTET STRING(SIZE(4))
	ACCESS read-write
	STATUS mandatory
	DESCRIPTION
		"NTP Server 1"
	::= { cmrwOmiConfigEntry 3 }

cmrwOmiNTPServer2 OBJECT-TYPE
	SYNTAX OCTET STRING(SIZE(4))
	ACCESS read-write
	STATUS mandatory
	DESCRIPTION
		"NTP Server 2"
	::= { cmrwOmiConfigEntry 4 }

cmrwOmiSNTPClientMode OBJECT-TYPE
	SYNTAX INTEGER
	{
		unicast(1),
		broadcast(2),
		disable(3),
		unknown(254),
		unsupported(255)
	}
	ACCESS read-write
	STATUS mandatory
	DESCRIPTION
		"SNTP client mode:
		1	UNICAST
		2	BROADCAST
		3	DISABLED
		254 UNKNOWN
		255	UNSUPPORTED
		"
	::= { cmrwOmiConfigEntry 5 }

cmrwOmiSNTPLocalUDPPort OBJECT-TYPE
	SYNTAX INTEGER
	ACCESS read-write
	STATUS mandatory
	DESCRIPTION
		"SNTP local UDP port 1..65535"
	::= { cmrwOmiConfigEntry 6 }

cmrwOmiDateTime OBJECT-TYPE
	SYNTAX INTEGER
	ACCESS read-write
	STATUS mandatory
	DESCRIPTION
		"Unix system date (seconds elapsed since 1970-01-01)"
	::= { cmrwOmiConfigEntry 7 }

cmrwOmiNMS1PortConfig OBJECT-TYPE
	SYNTAX INTEGER
	{
		auto(1),
		full10Mbps(2),
		half10Mbps(3),
		full100Mbps(4),
		half100Mbps(5),
		unknown(254),
		unsupported(255)
	}
	ACCESS read-write
	STATUS mandatory
	DESCRIPTION
		"NMS port configuration.
		1	AUTO
		2	10 Mbps full duplex
		3	10 Mbps half duplex
		4	100 Mbps full duplex
		5	100 Mbps half duplex
		254	UNKNOWN
		255	UNSUPPORTED
		"
	::= { cmrwOmiConfigEntry 8 }

cmrwOmiNMS1PortStatus OBJECT-TYPE
	SYNTAX INTEGER
	{
		auto(1),
		full10Mbps(2),
		half10Mbps(3),
		full100Mbps(4),
		half100Mbps(5),
        linkDown(6),
		unknown(254),
		unsupported(255)
	}
	ACCESS read-only
	STATUS mandatory
	DESCRIPTION
		"NMS Port status.
		1	AUTO
		2	10 Mbps full duplex
		3	10 Mbps half duplex
		4	100 Mbps full duplex
		5	100 Mbps half duplex
        6	link down
		254	UNKNOWN
		255	UNSUPPORTED
		"
	::= { cmrwOmiConfigEntry 9 }

cmrwOmiNMS1PortAutoConfig OBJECT-TYPE
	SYNTAX OCTET STRING (SIZE(1))
	ACCESS read-write
	STATUS mandatory
	DESCRIPTION
		"NMS port auto conf:
		Bit fields: Advertised mode
		Mode is coded as follows:
		bit 0	if 1 full 10 Mbps
		bit 1	if 1 full 100 Mbps
		bit 2	if 1 half 10 Mbps
		bit 3	if 1 half 100 Mbps
		0xFE	UNKNOWN
		0xFF	UNSUPPORTED
		"
	::= { cmrwOmiConfigEntry 10 }

cmrwOmiNMS2PortConfig OBJECT-TYPE
	SYNTAX INTEGER
	{
		auto(1),
		full10Mbps(2),
		half10Mbps(3),
		full100Mbps(4),
		half100Mbps(5),
		unknown(254),
		unsupported(255)
	}
	ACCESS read-write
	STATUS mandatory
	DESCRIPTION
		"NMS port configuration.
		1	AUTO
		2	10 Mbps full duplex
		3	10 Mbps half duplex
		4	100 Mbps full duplex
		5	100 Mbps half duplex
		254	UNKNOWN
		255	UNSUPPORTED
		"
	::= { cmrwOmiConfigEntry 11}

cmrwOmiNMS2PortStatus OBJECT-TYPE
	SYNTAX INTEGER
	{
		auto(1),
		full10Mbps(2),
		half10Mbps(3),
		full100Mbps(4),
		half100Mbps(5),
        linkDown(6),
		unknown(254),
		unsupported(255)
	}
	ACCESS read-only
	STATUS mandatory
	DESCRIPTION
		"NMS Port status.
		1	AUTO
		2	10 Mbps full duplex
		3	10 Mbps half duplex
		4	100 Mbps full duplex
		5	100 Mbps half duplex
		6	link down
		254	UNKNOWN
		255	UNSUPPORTED
		"
	::= { cmrwOmiConfigEntry 12 }

cmrwOmiNMS2PortAutoConfig OBJECT-TYPE
	SYNTAX OCTET STRING (SIZE(1))
	ACCESS read-write
	STATUS mandatory
	DESCRIPTION
		"NMS port auto conf:
		Bit fields: Advertised mode
		Mode is coded as follows:
		bit 0	if 1 full 10 Mbps
		bit 1	if 1 full 100 Mbps
		bit 2	if 1 half 10 Mbps
		bit 3	if 1 half 100 Mbps
		0xFE	UNKNOWN
		0xFF	UNSUPPORTED
		"
	::= { cmrwOmiConfigEntry 13 }

cmrwOmiNMS3PortConfig OBJECT-TYPE
	SYNTAX INTEGER
	{
		auto(1),
		full10Mbps(2),
		half10Mbps(3),
		full100Mbps(4),
		half100Mbps(5),
		unknown(254),
		unsupported(255)
	}
	ACCESS read-write
	STATUS mandatory
	DESCRIPTION
		"NMS port configuration.
		1	AUTO
		2	10 Mbps full duplex
		3	10 Mbps half duplex
		4	100 Mbps full duplex
		5	100 Mbps half duplex
		254	UNKNOWN
		255	UNSUPPORTED
		"
	::= { cmrwOmiConfigEntry 14 }

cmrwOmiNMS3PortStatus OBJECT-TYPE
	SYNTAX INTEGER
	{
		auto(1),
		full10Mbps(2),
		half10Mbps(3),
		full100Mbps(4),
		half100Mbps(5),
        linkDown(6),
		unknown(254),
		unsupported(255)
	}
	ACCESS read-only
	STATUS mandatory
	DESCRIPTION
		"NMS Port status.
		1	AUTO
		2	10 Mbps full duplex
		3	10 Mbps half duplex
		4	100 Mbps full duplex
		5	100 Mbps half duplex
		6	link down
		254	UNKNOWN
		255	UNSUPPORTED
		"
	::= { cmrwOmiConfigEntry 15 }

cmrwOmiNMS3PortAutoConfig OBJECT-TYPE
	SYNTAX OCTET STRING (SIZE(1))
	ACCESS read-write
	STATUS mandatory
	DESCRIPTION
		"NMS port auto conf:
		Bit fields: Advertised mode
		Mode is coded as follows:
		bit 0	if 1 full 10 Mbps
		bit 1	if 1 full 100 Mbps
		bit 2	if 1 half 10 Mbps
		bit 3	if 1 half 100 Mbps
		0xFE	UNKNOWN
		0xFF	UNSUPPORTED
		"
	::= { cmrwOmiConfigEntry 16 }

--------------------------------------------------------------------------------
--	CM-RW	Sru Action
--------------------------------------------------------------------------------
cmrwSruActionTable OBJECT-TYPE
	SYNTAX SEQUENCE OF CmrwSruActionEntry
	ACCESS not-accessible
	STATUS mandatory
	DESCRIPTION ""
	::= { cmrwSru 1 }

cmrwSruActionEntry OBJECT-TYPE
	SYNTAX CmrwSruActionEntry
	ACCESS not-accessible
	STATUS mandatory
	DESCRIPTION ""
	INDEX { cmrwSruActionPortIndex, cmrwSruActionLinkIndex, cmrwSruActionRegIndex }
	::= { cmrwSruActionTable 1 }

CmrwSruActionEntry ::=
	SEQUENCE
	{
		cmrwSruActionPortIndex INTEGER,
		cmrwSruActionLinkIndex INTEGER,
		cmrwSruActionRegIndex INTEGER,
		cmrwSruActionReboot INTEGER
	}

cmrwSruActionPortIndex OBJECT-TYPE
	SYNTAX INTEGER
	ACCESS read-only
	STATUS mandatory
	DESCRIPTION
		"This variable addresses the port number of the proxy
		and is used as index for the other elements in the Table"
	::= { cmrwSruActionEntry 1 }

cmrwSruActionLinkIndex OBJECT-TYPE
	SYNTAX INTEGER
	ACCESS read-only
	STATUS mandatory
	DESCRIPTION
		"This variable addresses the slot number of the OMI sub-rack
		and is used as index for the other elements in the Table"
	::= { cmrwSruActionEntry 2 }

cmrwSruActionRegIndex OBJECT-TYPE
	SYNTAX INTEGER
	{
		reg11(3),
		reg12(4),
		reg21(5),
		reg22(6),
		reg31(7),
		reg32(8),
		reg41(9),
		reg42(10),
		reg51(11),
		reg52(12),
		reg61(13),
		reg62(14),
		reg71(15),
		reg72(16),
		reg81(17),
		reg82(18),
		reg13(19),
		reg14(20),
		reg23(21),
		reg24(22),
		reg33(23),
		reg34(24),
		reg43(25),
		reg44(26),
		reg53(27),
		reg54(28),
		reg63(29),
		reg64(30),
		reg73(31),
		reg74(32),
		reg83(33),
		reg84(34)
	}
	ACCESS read-only
	STATUS mandatory
	DESCRIPTION
		"This variable addresses the regenerator device and is
		used as index for the other elements in the Table"
	::= { cmrwSruActionEntry 3 }

cmrwSruActionReboot OBJECT-TYPE
	SYNTAX INTEGER {
		passive(1),
		active(2),
		unknown(254),
		unsupported(255)
	}
	ACCESS read-write
	STATUS mandatory
	DESCRIPTION
		"Command to reboot device. The parameter specifies whether
		the firmware in the active or passive bank shall be started.
		1	Passive	Reboot using the passive firmware
		2	Active	Reboot using the active firmware
		
		If the parameter 'passive' is specified but the passive
		firmware bank contains no valid code, the device reboots
		using the active firmware."
	::= { cmrwSruActionEntry 4 }

--==============================================================================
--==============================================================================
--
--      FM-RO
--
--==============================================================================
--==============================================================================
	fmro	OBJECT IDENTIFIER ::= { linksVers3 3 }

--------------------------------------------------------------------------------  
--	FM-RO	OMI
--------------------------------------------------------------------------------  
fmroOmiTable OBJECT-TYPE
	SYNTAX SEQUENCE OF FmroOmiEntry
	ACCESS not-accessible
	STATUS mandatory
	DESCRIPTION ""
	::= { fmro 1 }

fmroOmiEntry OBJECT-TYPE
	SYNTAX FmroOmiEntry
	ACCESS not-accessible
	STATUS mandatory
	DESCRIPTION ""
	INDEX { fmroOmiPortIndex }
	::= { fmroOmiTable 1 }

FmroOmiEntry ::=
	SEQUENCE
	{
		fmroOmiPortIndex INTEGER,
		fmroOmiBattery1 INTEGER,
		fmroOmiBattery2 INTEGER,
		fmroOmiSaw INTEGER,
		fmroOmiAuxMcuPower INTEGER,
		fmroOmiExtInput1 INTEGER,
		fmroOmiExtInput2 INTEGER,
		fmroOmiExtInput3 INTEGER,
		fmroOmiExtInput4 INTEGER,
		fmroOmiNMSInterface1 INTEGER,
		fmroOmiNMSInterface2 INTEGER,
		fmroOmiNMSInterface3 INTEGER,
		fmroOmiFEInterface1 INTEGER,
		fmroOmiFEInterface2 INTEGER,
		fmroOmiFEInterface3 INTEGER,
		fmroOmiFEInterface4 INTEGER,
		fmroOmiFEInterface5 INTEGER,
		fmroOmiFEInterface6 INTEGER,
		fmroOmiFEInterface7 INTEGER,
		fmroOmiFEInterface8 INTEGER,
		fmroOmiFEInterface9 INTEGER,
		fmroOmiFEInterface10 INTEGER,
		fmroOmiFEInterface11 INTEGER,
		fmroOmiFEInterface12 INTEGER,
		fmroOmiFEInterface13 INTEGER,
		fmroOmiFEInterface14 INTEGER,
		fmroOmiFEInterface15 INTEGER,
		fmroOmiFEInterface16 INTEGER,
		fmroOmiGBEUplink1 INTEGER,
		fmroOmiGBEUplink2 INTEGER,
		fmroOmiSFPLaser1 INTEGER,
		fmroOmiSFPLaser2 INTEGER,
		fmroOmiSFPInterface1 INTEGER,
		fmroOmiSFPInterface2 INTEGER
	}

fmroOmiPortIndex OBJECT-TYPE
	SYNTAX INTEGER
	ACCESS read-only
	STATUS mandatory
	DESCRIPTION
		"This variable addresses the port number of the proxy
		and is used as index for the other elements in the Table"
	::= { fmroOmiEntry 1 }

fmroOmiBattery1 OBJECT-TYPE
	SYNTAX INTEGER
	{
		none(1),
		batteryAlarm(2),
		unknown(254),
		unsupported(255)
	}
	ACCESS read-only
	STATUS mandatory
	DESCRIPTION
		"Battery alarm of the OMI card.
		1	None		No Alarm
		2	BatteryAlarm	Power failure on Battery 1
		254			unknown value
		255			unsupported variable for addressed device"
	::= { fmroOmiEntry 2 }

fmroOmiBattery2 OBJECT-TYPE
	SYNTAX INTEGER
	{
		none(1),
		batteryAlarm(2),
		unknown(254),
		unsupported(255)
	}
	ACCESS read-only
	STATUS mandatory
	DESCRIPTION
		"Battery alarm of the OMI card.
		1	None		No Alarm
		2	BatteryAlarm	Power failure on Battery 2
		254			unknown value
		255			unsupported variable for addressed device"
	::= { fmroOmiEntry 3 }

fmroOmiSaw OBJECT-TYPE
	SYNTAX INTEGER
	ACCESS read-only
	STATUS mandatory
	DESCRIPTION
		"Alarm summary of the OMI card.
		Bit 0	  1	Urgent Alarm
		Bit 1	  2	Non-urgent Alarm
		Bit 2	  4	AIS (Alarm Indication Signal)
		Bit 6	 64	unknown
		Bit 7	128	unsupported"
	::= { fmroOmiEntry 4 }

fmroOmiAuxMcuPower OBJECT-TYPE
	SYNTAX INTEGER
	{
		none(1),
		batteryAlarm(2),
		unknown(254),
		unsupported(255)
	}
	ACCESS read-only
	STATUS mandatory
	DESCRIPTION
		"Battery alarm of the OMI card.
		1	No Alarm
		2	Power failure on Auxiliary MCU battery
		254	unknown value
		255	unsupported variable for addressed device"
	::= { fmroOmiEntry 5 }

fmroOmiExtInput1 OBJECT-TYPE
	SYNTAX INTEGER
	{
		none(1),
		inputAlarm(2),
		unknown(254),
		unsupported(255)
	}
	ACCESS read-only
	STATUS mandatory
	DESCRIPTION
		"External alarm 1 of the MCU card.
		1	No Alarm
		2	External Alarm 1
		254	unknown value
		255	unsupported variable for addressed device"
	::= { fmroOmiEntry 6 }

fmroOmiExtInput2 OBJECT-TYPE
	SYNTAX INTEGER
	{
		none(1),
		inputAlarm(2),
		unknown(254),
		unsupported(255)
	}
	ACCESS read-only
	STATUS mandatory
	DESCRIPTION
		"External alarm 2 of the MCU card.
		1	No Alarm
		2	External Alarm 2
		254	unknown value
		255	unsupported variable for addressed device"
	::= { fmroOmiEntry 7 }

fmroOmiExtInput3 OBJECT-TYPE
	SYNTAX INTEGER
	{
		none(1),
		inputAlarm(2),
		unknown(254),
		unsupported(255)
	}
	ACCESS read-only
	STATUS mandatory
	DESCRIPTION
		"External alarm 3 of the MCU card.
		1	No Alarm
		2	External Alarm 3
		254	unknown value
		255	unsupported variable for addressed device"
	::= { fmroOmiEntry 8 }

fmroOmiExtInput4 OBJECT-TYPE
	SYNTAX INTEGER
	{
		none(1),
		inputAlarm(2),
		unknown(254),
		unsupported(255)
	}
	ACCESS read-only
	STATUS mandatory
	DESCRIPTION
		"External alarm of the MCU card.
		1	No Alarm
		2	External Alarm 4
		254	unknown value
		255	unsupported variable for addressed device"
	::= { fmroOmiEntry 9 }

fmroOmiNMSInterface1 OBJECT-TYPE
	SYNTAX INTEGER
	{
		none(1),
		linkdown(24),
		unknown(254),
		unsupported(255)
	}
	ACCESS read-only
	STATUS mandatory
	DESCRIPTION
		"NMS Interface 1 alarm of the MCU card.
		1	No Alarm
		24	LinkDown	No Link Detected
		254	unknown value
		255	unsupported variable for addressed device"
	::= { fmroOmiEntry 10 }

fmroOmiNMSInterface2 OBJECT-TYPE
	SYNTAX INTEGER
	{
		none(1),
		linkdown(24),
		unknown(254),
		unsupported(255)
	}
	ACCESS read-only
	STATUS mandatory
	DESCRIPTION
		"NMS Interface 2 alarm of the MCU card.
		1	No Alarm
		24	LinkDown	No Link Detected
		254	unknown value
		255	unsupported variable for addressed device"
	::= { fmroOmiEntry 11 }

fmroOmiNMSInterface3 OBJECT-TYPE
	SYNTAX INTEGER
	{
		none(1),
		linkdown(24),
		unknown(254),
		unsupported(255)
	}
	ACCESS read-only
	STATUS mandatory
	DESCRIPTION
		"NMS Interface 3 alarm of the MCU card.
		1	No Alarm
		24	LinkDown	No Link Detected
		254	unknown value
		255	unsupported variable for addressed device"
	::= { fmroOmiEntry 12 }

fmroOmiFEInterface1 OBJECT-TYPE
	SYNTAX INTEGER
	{
		none(1),
		linkdown(24),
		unknown(254),
		unsupported(255)
	}
	ACCESS read-only
	STATUS mandatory
	DESCRIPTION
		"Fast Ethernet Interface 1 alarm of the MCU card.
		1	No Alarm
		24	LinkDown	No Link Detected
		254	unknown value
		255	unsupported variable for addressed device"
	::= { fmroOmiEntry 13 }

fmroOmiFEInterface2 OBJECT-TYPE
	SYNTAX INTEGER
	{
		none(1),
		linkdown(24),
		unknown(254),
		unsupported(255)
	}
	ACCESS read-only
	STATUS mandatory
	DESCRIPTION
		"Fast Ethernet Interface 2 alarm of the MCU card.
		1	No Alarm
		24	LinkDown	No Link Detected
		254	unknown value
		255	unsupported variable for addressed device"
	::= { fmroOmiEntry 14 }

fmroOmiFEInterface3 OBJECT-TYPE
	SYNTAX INTEGER
	{
		none(1),
		linkdown(24),
		unknown(254),
		unsupported(255)
	}
	ACCESS read-only
	STATUS mandatory
	DESCRIPTION
		"Fast Ethernet Interface 3 alarm of the MCU card.
		1	No Alarm
		24	LinkDown	No Link Detected
		254	unknown value
		255	unsupported variable for addressed device"
	::= { fmroOmiEntry 15 }

fmroOmiFEInterface4 OBJECT-TYPE
	SYNTAX INTEGER
	{
		none(1),
		linkdown(24),
		unknown(254),
		unsupported(255)
	}
	ACCESS read-only
	STATUS mandatory
	DESCRIPTION
		"Fast Ethernet Interface 4 alarm of the MCU card.
		1	No Alarm
		24	LinkDown	No Link Detected
		254	unknown value
		255	unsupported variable for addressed device"
	::= { fmroOmiEntry 16 }

fmroOmiFEInterface5 OBJECT-TYPE
	SYNTAX INTEGER
	{
		none(1),
		linkdown(24),
		unknown(254),
		unsupported(255)
	}
	ACCESS read-only
	STATUS mandatory
	DESCRIPTION
		"Fast Ethernet Interface 5 alarm of the MCU card.
		1	No Alarm
		24	LinkDown	No Link Detected
		254	unknown value
		255	unsupported variable for addressed device"
	::= { fmroOmiEntry 17 }

fmroOmiFEInterface6 OBJECT-TYPE
	SYNTAX INTEGER
	{
		none(1),
		linkdown(24),
		unknown(254),
		unsupported(255)
	}
	ACCESS read-only
	STATUS mandatory
	DESCRIPTION
		"Fast Ethernet Interface 6 alarm of the MCU card.
		1	No Alarm
		24	LinkDown	No Link Detected
		254	unknown value
		255	unsupported variable for addressed device"
	::= { fmroOmiEntry 18 }

fmroOmiFEInterface7 OBJECT-TYPE
	SYNTAX INTEGER
	{
		none(1),
		linkdown(24),
		unknown(254),
		unsupported(255)
	}
	ACCESS read-only
	STATUS mandatory
	DESCRIPTION
		"Fast Ethernet Interface 7 alarm of the MCU card.
		1	No Alarm
		24	LinkDown	No Link Detected
		254	unknown value
		255	unsupported variable for addressed device"
	::= { fmroOmiEntry 19 }

fmroOmiFEInterface8 OBJECT-TYPE
	SYNTAX INTEGER
	{
		none(1),
		linkdown(24),
		unknown(254),
		unsupported(255)
	}
	ACCESS read-only
	STATUS mandatory
	DESCRIPTION
		"Fast Ethernet Interface 8 alarm of the MCU card.
		1	No Alarm
		24	LinkDown	No Link Detected
		254	unknown value
		255	unsupported variable for addressed device"
	::= { fmroOmiEntry 20 }

fmroOmiFEInterface9 OBJECT-TYPE
	SYNTAX INTEGER
	{
		none(1),
		linkdown(24),
		unknown(254),
		unsupported(255)
	}
	ACCESS read-only
	STATUS mandatory
	DESCRIPTION
		"Fast Ethernet Interface 9 alarm of the MCU card.
		1	No Alarm
		24	LinkDown	No Link Detected
		254	unknown value
		255	unsupported variable for addressed device"
	::= { fmroOmiEntry 21 }

fmroOmiFEInterface10 OBJECT-TYPE
	SYNTAX INTEGER
	{
		none(1),
		linkdown(24),
		unknown(254),
		unsupported(255)
	}
	ACCESS read-only
	STATUS mandatory
	DESCRIPTION
		"Fast Ethernet Interface 10 alarm of the MCU card.
		1	No Alarm
		24	LinkDown	No Link Detected
		254	unknown value
		255	unsupported variable for addressed device"
	::= { fmroOmiEntry 22 }

fmroOmiFEInterface11 OBJECT-TYPE
	SYNTAX INTEGER
	{
		none(1),
		linkdown(24),
		unknown(254),
		unsupported(255)
	}
	ACCESS read-only
	STATUS mandatory
	DESCRIPTION
		"Fast Ethernet Interface 11 alarm of the MCU card.
		1	No Alarm
		24	LinkDown	No Link Detected
		254	unknown value
		255	unsupported variable for addressed device"
	::= { fmroOmiEntry 23 }

fmroOmiFEInterface12 OBJECT-TYPE
	SYNTAX INTEGER
	{
		none(1),
		linkdown(24),
		unknown(254),
		unsupported(255)
	}
	ACCESS read-only
	STATUS mandatory
	DESCRIPTION
		"Fast Ethernet Interface 12 alarm of the MCU card.
		1	No Alarm
		24	LinkDown	No Link Detected
		254	unknown value
		255	unsupported variable for addressed device"
	::= { fmroOmiEntry 24 }

fmroOmiFEInterface13 OBJECT-TYPE
	SYNTAX INTEGER
	{
		none(1),
		linkdown(24),
		unknown(254),
		unsupported(255)
	}
	ACCESS read-only
	STATUS mandatory
	DESCRIPTION
		"Fast Ethernet Interface 13 alarm of the MCU card.
		1	No Alarm
		24	LinkDown	No Link Detected
		254	unknown value
		255	unsupported variable for addressed device"
	::= { fmroOmiEntry 25 }

fmroOmiFEInterface14 OBJECT-TYPE
	SYNTAX INTEGER
	{
		none(1),
		linkdown(24),
		unknown(254),
		unsupported(255)
	}
	ACCESS read-only
	STATUS mandatory
	DESCRIPTION
		"Fast Ethernet Interface 14 alarm of the MCU card.
		1	No Alarm
		24	LinkDown	No Link Detected
		254	unknown value
		255	unsupported variable for addressed device"
	::= { fmroOmiEntry 26 }

fmroOmiFEInterface15 OBJECT-TYPE
	SYNTAX INTEGER
	{
		none(1),
		linkdown(24),
		unknown(254),
		unsupported(255)
	}
	ACCESS read-only
	STATUS mandatory
	DESCRIPTION
		"Fast Ethernet Interface 15 alarm of the MCU card.
		1	No Alarm
		24	LinkDown	No Link Detected
		254	unknown value
		255	unsupported variable for addressed device"
	::= { fmroOmiEntry 27 }

fmroOmiFEInterface16 OBJECT-TYPE
	SYNTAX INTEGER
	{
		none(1),
		linkdown(24),
		unknown(254),
		unsupported(255)
	}
	ACCESS read-only
	STATUS mandatory
	DESCRIPTION
		"Fast Ethernet Interface 16 alarm of the MCU card.
		1	No Alarm
		24	LinkDown	No Link Detected
		254	unknown value
		255	unsupported variable for addressed device"
	::= { fmroOmiEntry 28 }

fmroOmiGBEUplink1 OBJECT-TYPE
	SYNTAX INTEGER
	{
		none(1),
		linkdown(24),
		unknown(254),
		unsupported(255)
	}
	ACCESS read-only
	STATUS mandatory
	DESCRIPTION
		"GBE 1 link down alarm of the MCU card.
		1	No Alarm
		24	LinkDown	No Link Detected
		254	unknown value
		255	unsupported variable for addressed device"
	::= { fmroOmiEntry 29 }

fmroOmiGBEUplink2 OBJECT-TYPE
	SYNTAX INTEGER
	{
		none(1),
		linkdown(24),
		unknown(254),
		unsupported(255)
	}
	ACCESS read-only
	STATUS mandatory
	DESCRIPTION
		"GBE 2 link down alarm of the MCU card.
		1	No Alarm
		24	LinkDown	No Link Detected
		254	unknown value
		255	unsupported variable for addressed device"
	::= { fmroOmiEntry 30 }

fmroOmiSFPLaser1 OBJECT-TYPE
	SYNTAX INTEGER
	{
		none(1),
		alarm(10),
		unknown(254),
		unsupported(255)
	}
	ACCESS read-only
	STATUS mandatory
	DESCRIPTION
		"SFP 1 laser alarm of the MCU card.
		1	No Alarm
		10	Alarm	Alarm present
		254	unknown value
		255	unsupported variable for addressed device"
	::= { fmroOmiEntry 31 }

fmroOmiSFPLaser2 OBJECT-TYPE
	SYNTAX INTEGER
	{
		none(1),
		alarm(10),
		unknown(254),
		unsupported(255)
	}
	ACCESS read-only
	STATUS mandatory
	DESCRIPTION
		"SFP 2 laser alarm of the MCU card.
		1	No Alarm
		10	Alarm	Alarm present
		254	unknown value
		255	unsupported variable for addressed device"
	::= { fmroOmiEntry 32 }

fmroOmiSFPInterface1 OBJECT-TYPE
	SYNTAX INTEGER
	{
		none(1),
		los(9),
		unknown(254),
		unsupported(255)
	}
	ACCESS read-only
	STATUS mandatory
	DESCRIPTION
		"SFP 1 interface alarm of the MCU card
		1	No Alarm
		9	LOS	Loss of Signal
		254	unknown value
		255	unsupported variable for addressed device"
	::= { fmroOmiEntry 33 }

fmroOmiSFPInterface2 OBJECT-TYPE
	SYNTAX INTEGER
	{
		none(1),
		los(9),
		unknown(254),
		unsupported(255)
	}
	ACCESS read-only
	STATUS mandatory
	DESCRIPTION
		"SFP 2 interface alarm of the MCU card.
		1	No Alarm
		9	LOS	Loss of Signal
		254	unknown value
		255	unsupported variable for addressed device"
	::= { fmroOmiEntry 34 }

--------------------------------------------------------------------------------  
--	FM-RO	Local HTU
--------------------------------------------------------------------------------  
fmroHtuLocalTable OBJECT-TYPE
	SYNTAX SEQUENCE OF FmroHtuLocalEntry
	ACCESS not-accessible
	STATUS mandatory
	DESCRIPTION ""
	::= { fmro 2 }

fmroHtuLocalEntry OBJECT-TYPE
	SYNTAX FmroHtuLocalEntry
	ACCESS not-accessible
	STATUS mandatory
	DESCRIPTION ""
	INDEX { fmroHtuLocalPortIndex, fmroHtuLocalLinkIndex }
	::= { fmroHtuLocalTable 1 }	

FmroHtuLocalEntry ::=
	SEQUENCE
	{
		fmroHtuLocalPortIndex INTEGER,
		fmroHtuLocalLinkIndex INTEGER,
		fmroHtuLocalU1 INTEGER,
		fmroHtuLocalU2 INTEGER,
		fmroHtuLocalU INTEGER,
		fmroHtuLocalT INTEGER,
		fmroHtuLocalDC INTEGER,
		fmroHtuLocalDN INTEGER,
		fmroHtuLocalEquipment INTEGER,
		fmroHtuLocalLosD INTEGER,
		fmroHtuLocalT3In INTEGER,
		fmroHtuLocalRps INTEGER,
		fmroHtuLocalRta INTEGER,
		fmroHtuLocalPowerfail INTEGER,
		fmroHtuLocalT3Out INTEGER,
		fmroHtuLocalLaser INTEGER,
		fmroHtuLocalAlarmSummary INTEGER,
		fmroHtuLocalPowerfailCpe INTEGER,
		fmroHtuLocalU3 INTEGER,
		fmroHtuLocalU4 INTEGER,
		fmroHtuLocalRps2 INTEGER,
		fmroHtuLocalRps3 INTEGER,
		fmroHtuLocalRps4 INTEGER,
		fmroHtuLocalVA INTEGER,
		fmroHtuLocalVB INTEGER,
		fmroHtuLocalVC INTEGER,
		fmroHtuLocalVD INTEGER,
		fmroHtuLocalMcsCha INTEGER,
		fmroHtuLocalMcsChb INTEGER,
		fmroHtuLocalMcsChc INTEGER,
		fmroHtuLocalMcsChd INTEGER,
		fmroHtuLocalMcsRemCha INTEGER,
		fmroHtuLocalMcsRemChb INTEGER,
		fmroHtuLocalMcsRemChc INTEGER,
		fmroHtuLocalMcsRemChd INTEGER,
		fmroHtuLocalMcs INTEGER,
		fmroHtuLocalL2SwitchWanRx INTEGER,
		fmroHtuLocalL2SwitchWanTx INTEGER,
		fmroHtuLocalL2SwitchLanPort1 INTEGER,
		fmroHtuLocalL2SwitchLanPort2 INTEGER,
		fmroHtuLocalL2SwitchLanPort3 INTEGER,
		fmroHtuLocalL2SwitchLanPort4 INTEGER,
		fmroHtuLocalL2SwitchBPLPort1 INTEGER,
		fmroHtuLocalUo INTEGER,
		fmroHtuLocalUo1 INTEGER,
		fmroHtuLocalUo2 INTEGER,
		fmroHtuLocalUA INTEGER,
		fmroHtuLocalUB INTEGER,
		fmroHtuLocalUC INTEGER,
		fmroHtuLocalUD INTEGER,
		fmroHtuLocalLosDB INTEGER,
		fmroHtuLocalLosDC INTEGER,
		fmroHtuLocalLosDD INTEGER,
		fmroHtuLocalSFP1 INTEGER,
		fmroHtuLocalSFP2 INTEGER
	}

fmroHtuLocalPortIndex OBJECT-TYPE
	SYNTAX INTEGER
	ACCESS read-only
	STATUS mandatory
	DESCRIPTION
		"This variable addresses the port number of the proxy
		and is used as index for the other elements in the Table"
	::= { fmroHtuLocalEntry 1 }

fmroHtuLocalLinkIndex OBJECT-TYPE
	SYNTAX INTEGER
	ACCESS read-only
	STATUS mandatory
	DESCRIPTION
		"This variable addresses the slot number of the OMI sub-rack
		and is used as index for the other elements in the Table"
	::= { fmroHtuLocalEntry 2 }

fmroHtuLocalU1 OBJECT-TYPE
	SYNTAX INTEGER
	{
		none(1),
		ber6(4),
		ber3(5),
		los(9),
		losw(19),
		unknown(254),
		unsupported(255)
	}
	ACCESS read-only
	STATUS mandatory
	DESCRIPTION
		"HDSL Error on Path 1
		 1	None	No Alarm
		 4	BER6	Bit Error Ratio 10^-6
		 5	BER3	Bit Error Ratio 10^-3
		 9	LOS	Loss of Signal
		 19	LOSW	Loss of SDSL synchronistation
		 254		Unknown value
		 255		Unsupported variable for addressed device"
	::= { fmroHtuLocalEntry 3 }

fmroHtuLocalU2 OBJECT-TYPE
	SYNTAX INTEGER
	{
		none(1),
		ber6(4),
		ber3(5),
		los(9),
		losw(19),
		unknown(254),
		unsupported(255)
	}
	ACCESS read-only
	STATUS mandatory
	DESCRIPTION
		"HDSL Error on Path 2
		 1	None	No Alarm
		 4	BER6	Bit Error Ratio 10^-6
		 5	BER3	Bit Error Ratio 10^-3
		 9	LOS	Loss of Signal
		 19	LOSW	Loss of SDSL synchronistation
		 254		Unknown value
		 255		Unsupported variable for addressed device"
	::= { fmroHtuLocalEntry 4 }

fmroHtuLocalU OBJECT-TYPE
	SYNTAX INTEGER
	{
		none(1),
		hpo(2),
		fpo(3),
		ber6(4),
		ber3(5),
		ais(7),
		lfa(8),
		los(9),
		rai(11),
		bwNotAvail(18),
		unknown(254),
		unsupported(255)
	}
	ACCESS read-only
	STATUS mandatory
	DESCRIPTION
		"Error in 2MB Signal on HDSL Path
		 1	None		No Alarm
		 4	BER6		Bit Error Ratio 10^-6
		 5	BER3		Bit Error Ratio 10^-3
		 7	AIS		Alarm Indication Signal
		 8	LFA		Loss of Frame Alignment
		 9	LOS		Loss of Signal
		 10	RAI		Remote Alarm Indication
		 18	BwNotAvail	Bandwidth not available
		 254			Unknown value
		 255			Unsupported variable for addressed device"
	::= { fmroHtuLocalEntry 5 }

fmroHtuLocalT OBJECT-TYPE
	SYNTAX INTEGER
	{
		none(1),
		ber6(4),
		ber3(5),
		ais(7),
		lfa(8),
		los(9),
		rai(11),
		unknown(254),
		unsupported(255)
	}
	ACCESS read-only
	STATUS mandatory
	DESCRIPTION
		"Error on the G.703 Interface
		 1	None	No Alarm
		 4	BER6	Bit Error Ratio 10^-6
		 5	BER3	Bit Error Ratio 10^-3
		 7	AIS	Alarm Indication Signal
		 8	LFA	Loss of Frame Alignment
		 9	LOS	Loss of Signal
		 11	RAI	Remote Alarm Indication
		 254		Unknown value
		 255		Unsupported variable for addressed device"
	::= { fmroHtuLocalEntry 6 }

fmroHtuLocalDC OBJECT-TYPE
	SYNTAX INTEGER
	{
		none(1),
		loa(6),
		unknown(254),
		unsupported(255)
	}
	ACCESS read-only
	STATUS mandatory
	DESCRIPTION
		"Error on the Data interface (Transmit signal)
		 1	None	No Alarm
		 6	LOA	Loss of Activity
		 254		Unknown value
		 255		Unsupported variable for addressed device"
	::= { fmroHtuLocalEntry 7 }

fmroHtuLocalDN OBJECT-TYPE
	SYNTAX INTEGER
	{
		none(1),
		loa(6),
		unknown(254),
		unsupported(255)
	}
	ACCESS read-only
	STATUS mandatory
	DESCRIPTION
		"Error on the Data interface (Receive signal)
		 1	None	No Alarm
		 6	LOA	Loss of Activity
		 254		Unknown value
		 255		Unsupported variable for addressed device"
	::= { fmroHtuLocalEntry 8 }

fmroHtuLocalEquipment OBJECT-TYPE
	SYNTAX INTEGER
	{
		none(1),
		alarm(10),
		xfw(25),
		unknown(254),
		unsupported(255)
	}
	ACCESS read-only
	STATUS mandatory
	DESCRIPTION
		"Equipment Alarm
		 1	None	No Alarm
		 10	Alarm	Alarm present
		 25	XFW	Firmware Mismatch
		 254		Unknown value
		 255		Unsupported variable for addressed device"
	::= { fmroHtuLocalEntry 9 }

fmroHtuLocalLosD OBJECT-TYPE
	SYNTAX INTEGER
	{
		none(1),
		alarm(10),
		unknown(254),
		unsupported(255)
	}
	ACCESS read-only
	STATUS mandatory
	DESCRIPTION
		"LOS-D Error State
		 1	None	No Alarm
		 10	Alarm	Alarm present
		 254		Unknown value
		 255		Unsupported variable for addressed device"
	::= { fmroHtuLocalEntry 10 }

fmroHtuLocalT3In OBJECT-TYPE
	SYNTAX INTEGER
	{
		none(1),
		los(9),
		unknown(254),
		unsupported(255)
	}
	ACCESS read-only
	STATUS mandatory
	DESCRIPTION
		"Loss of Clock on T3In
		 1	None	No Alarm
		 9	LOS	Loss of Clock Signal an T3In
		 254		Unknown value
		 255		Unsupported variable for addressed device"
	::= { fmroHtuLocalEntry 11 }

fmroHtuLocalRps OBJECT-TYPE
	SYNTAX INTEGER
	{
		none(1),
		ucr12(12),
		ucr1(13),
		ucr2(14),
		ovr(15),
		nosym(16),
		defect(17),
		unknown(254),
		unsupported(255)
	}
	ACCESS read-only
	STATUS mandatory
	DESCRIPTION
		"Remote Power Supply Error State
		 1	None	No Alarm
		 12	UCR12	Undercurrent on HDSL Path 1 and 2
		 13	UCR1	Undercurrent on HDSL Path 1
		 14	UCR2	Undercurrent on HDSL Path 2
		 15	OVR	Overload
		 16	NOSYM	Unsymetrical Load
		 17	DEFECT	Defect on Module
		 254		Unknown value
		 255		Unsupported variable for addressed device"
	::= { fmroHtuLocalEntry 12 }

fmroHtuLocalRta OBJECT-TYPE
	SYNTAX INTEGER
	{
		none(1),
		alarm(10),
		unknown(254),
		unsupported(255)
	}
	ACCESS read-only
	STATUS mandatory
	DESCRIPTION
		"Remote Terminal Alarm Error State
		 1	None	No Alarm
		 10	Alarm	Alarm present
		 254		Unknown value
		 255		Unsupported variable for addressed device"
	::= { fmroHtuLocalEntry 13 }

fmroHtuLocalPowerfail OBJECT-TYPE
	SYNTAX INTEGER
	{
		none(1),
		alarm(10),
		unknown(254),
		unsupported(255)
	}
	ACCESS read-only
	STATUS mandatory
	DESCRIPTION
		"Remote Device Powerfailure Alarm. If this alarm occurs the
		remote device has lost all power and cannot be reached any
		longer.
		 1	None	No Alarm
		 10	Alarm	Alarm present
		 254		Unknown value
		 255		Unsupported variable for addressed device"
	::= { fmroHtuLocalEntry 14 }

fmroHtuLocalT3Out OBJECT-TYPE
	SYNTAX INTEGER
	{
		none(1),
		los(9),
		unknown(254),
		unsupported(255)
	}
	ACCESS read-only
	STATUS mandatory
	DESCRIPTION
		"No Clock Signal available for T3Out
		 1	None	No Alarm
		 9	LOS	Loss of Clock Signal on T3Out
		 254		Unknown value
		 255		Unsupported variable for addressed device"
	::= { fmroHtuLocalEntry 15 }

fmroHtuLocalLaser OBJECT-TYPE
	SYNTAX INTEGER
	{
		none(1),
		alarm(10),
		unknown(254),
		unsupported(255)
	}
	ACCESS read-only
	STATUS mandatory
	DESCRIPTION
		"Laser aging alarm
		 1	None	No Alarm
		 10	Alarm	Laser reaching critical age
		 254		Unknown value
		 255		Unsupported variable for addressed device"
	::= { fmroHtuLocalEntry 16 }

fmroHtuLocalAlarmSummary OBJECT-TYPE
	SYNTAX INTEGER (0..255)
	ACCESS read-only
	STATUS mandatory
	DESCRIPTION
		"Contains the alarm summary of the link. This value is bit coded:
		Bit	Value
		 0	1	UA		Urgent alarm
		 1	2	NUA		Non urgent alarm
		 2  	4	AIS		Alarm indication signal
		
		A value of 0 means no alarm"
	::= { fmroHtuLocalEntry 17 }

fmroHtuLocalPowerfailCpe OBJECT-TYPE
	SYNTAX INTEGER
	{
		none(1),
		alarm(10),
		unknown(254),
		unsupported(255)
	}
	ACCESS read-only
	STATUS mandatory
	DESCRIPTION
		"Remote Device Local Power Loss Alarm. If this Alarm
		is active, the device has lost its local power supply
		but is still powered over the transmission line (using
		a remote power supply (RPS).
		 1	None	No Alarm
		 10	Alarm	Alarm present
		 254		Unknown value
		 255		Unsupported variable for addressed device"
	::= { fmroHtuLocalEntry 18 }

fmroHtuLocalU3 OBJECT-TYPE
	SYNTAX INTEGER
	{
		none(1),
		ber6(4),
		ber3(5),
		los(9),
		losw(19),
		unknown(254),
		unsupported(255)
	}
	ACCESS read-only
	STATUS mandatory
	DESCRIPTION
		"xDSL Error on Path 3
		 1	None	No Alarm
		 4	BER6	Bit Error Ratio 10^-6
		 5	BER3	Bit Error Ratio 10^-3
		 9	LOS	Loss of Signal
		 19	LOSW	Loss of SDSL synchronistation
		 254		Unknown value
		 255		Unsupported variable for addressed device"
	::= { fmroHtuLocalEntry 19 }

fmroHtuLocalU4 OBJECT-TYPE
	SYNTAX INTEGER
	{
		none(1),
		ber6(4),
		ber3(5),
		los(9),
		losw(19),
		unknown(254),
		unsupported(255)
	}
	ACCESS read-only
	STATUS mandatory
	DESCRIPTION
		"xDSL Error on Path 4
		 1	None	No Alarm
		 4	BER6	Bit Error Ratio 10^-6
		 5	BER3	Bit Error Ratio 10^-3
		 9	LOS	Loss of Signal
		 19	LOSW		Loss of SDSL synchronistation
		 254		Unknown value
		 255		Unsupported variable for addressed device"
	::= { fmroHtuLocalEntry 20 }

fmroHtuLocalRps2 OBJECT-TYPE
	SYNTAX INTEGER
	{
		none(1),
		ucr1(13),
		ovr(15),
		nosym(16),
		defect(17),
		unknown(254),
		unsupported(255)
	}
	ACCESS read-only
	STATUS mandatory
	DESCRIPTION
		"Remote Power Supply Error State on Path 2
		 1	None	No Alarm
		 13	UCR1	Undercurrent on current Path
		 15	OVR	Overload
		 16	NOSYM	Unsymetrical Load
		 17	DEFECT	Defect on Module
		 254		Unknown value
		 255		Unsupported variable for addressed device"
	::= { fmroHtuLocalEntry 21 }

fmroHtuLocalRps3 OBJECT-TYPE
	SYNTAX INTEGER
	{
		none(1),
		ucr1(13),
		ovr(15),
		nosym(16),
		defect(17),
		unknown(254),
		unsupported(255)
	}
	ACCESS read-only
	STATUS mandatory
	DESCRIPTION
		"Remote Power Supply Error State on Path 3
		 1	None	No Alarm
		 13	UCR1	Undercurrent on current Path
		 15	OVR	Overload
		 16	NOSYM	Unsymetrical Load
		 17	DEFECT	Defect on Module
		 254		Unknown value
		 255		Unsupported variable for addressed device"
	::= { fmroHtuLocalEntry 22 }

fmroHtuLocalRps4 OBJECT-TYPE
	SYNTAX INTEGER
	{
		none(1),
		ucr1(13),
		ovr(15),
		nosym(16),
		defect(17),
		unknown(254),
		unsupported(255)
	}
	ACCESS read-only
	STATUS mandatory
	DESCRIPTION
		"Remote Power Supply Error State on Path 4
		 1	None	No Alarm
		 13	UCR1	Undercurrent on current Path
		 15	OVR	Overload
		 16	NOSYM	Unsymetrical Load
		 17	DEFECT	Defect on Module
		 254		Unknown value
		 255		Unsupported variable for addressed device"
	::= { fmroHtuLocalEntry 23 }

fmroHtuLocalVA OBJECT-TYPE
	SYNTAX INTEGER
	{
		none(1),
		ber6(4),
		ber3(5),
		ais(7),
		lfa(8),
		los(9),
		rai(11),
		unknown(254),
		unsupported(255)
	}
	ACCESS read-only
	STATUS mandatory
	DESCRIPTION
		"Error on the G.703 Interface
		 1	None	No Alarm
		 4	BER6	Bit Error Ratio 10^-6
		 5	BER3	Bit Error Ratio 10^-3
		 7	AIS	Alarm Indication Signal
		 8	LFA	Loss of Frame Alignment
		 9	LOS	Loss of Signal
		 11	RAI	Remote Alarm Indication
		 254		Unknown value
		 255		Unsupported variable for addressed device"
	::= { fmroHtuLocalEntry 24 }

fmroHtuLocalVB OBJECT-TYPE
	SYNTAX INTEGER
	{
		none(1),
		ber6(4),
		ber3(5),
		ais(7),
		lfa(8),
		los(9),
		rai(11),
		unknown(254),
		unsupported(255)
	}
	ACCESS read-only
	STATUS mandatory
	DESCRIPTION
		"Error on the G.703 Interface
		 1	None	No Alarm
		 4	BER6	Bit Error Ratio 10^-6
		 5	BER3	Bit Error Ratio 10^-3
		 7	AIS	Alarm Indication Signal
		 8	LFA	Loss of Frame Alignment
		 9	LOS	Loss of Signal
		 11	RAI	Remote Alarm Indication
		 254		Unknown value
		 255		Unsupported variable for addressed device"
	::= { fmroHtuLocalEntry 25 }

fmroHtuLocalVC OBJECT-TYPE
	SYNTAX INTEGER
	{
		none(1),
		ber6(4),
		ber3(5),
		ais(7),
		lfa(8),
		los(9),
		rai(11),
		unknown(254),
		unsupported(255)
	}
	ACCESS read-only
	STATUS mandatory
	DESCRIPTION
		"Error on the G.703 Interface
		 1	None	No Alarm
		 4	BER6	Bit Error Ratio 10^-6
		 5	BER3	Bit Error Ratio 10^-3
		 7	AIS	Alarm Indication Signal
		 8	LFA	Loss of Frame Alignment
		 9	LOS	Loss of Signal
		 11	RAI	Remote Alarm Indication
		 254		Unknown value
		 255		Unsupported variable for addressed device"
	::= { fmroHtuLocalEntry 26 }

fmroHtuLocalVD OBJECT-TYPE
	SYNTAX INTEGER
	{
		none(1),
		ber6(4),
		ber3(5),
		ais(7),
		lfa(8),
		los(9),
		rai(11),
		unknown(254),
		unsupported(255)
	}
	ACCESS read-only
	STATUS mandatory
	DESCRIPTION
		"Error on the G.703 Interface
		 1	None	No Alarm
		 4	BER6	Bit Error Ratio 10^-6
		 5	BER3	Bit Error Ratio 10^-3
		 7	AIS	Alarm Indication Signal
		 8	LFA	Loss of Frame Alignment
		 9	LOS	Loss of Signal
		 11	RAI	Remote Alarm Indication
		 254		Unknown value
		 255		Unsupported variable for addressed device"
	::= { fmroHtuLocalEntry 27 }

fmroHtuLocalMcsCha OBJECT-TYPE
	SYNTAX INTEGER
	{
		none(1),
		ber6(4),
		ber3(5),
		lom(21),
		unknown(254),
		unsupported(255)
	}
	ACCESS read-only
	STATUS mandatory
	DESCRIPTION
		"Error on the MCS Channel a
		 1	None	No Alarm
		 4	BER6	Bit Error Ratio 10^-6
		 5	BER3	Bit Error Ratio 10^-3
		 21	LOM	Loss Of MCS sync
		 254		Unknown value
		 255		Unsupported variable for addressed device"
	::= { fmroHtuLocalEntry 28 }

fmroHtuLocalMcsChb OBJECT-TYPE
	SYNTAX INTEGER
	{
		none(1),
		ber6(4),
		ber3(5),
		lom(21),
		unknown(254),
		unsupported(255)
	}
	ACCESS read-only
	STATUS mandatory
	DESCRIPTION
		"Error on the MCS Channel b
		 1	None	No Alarm
		 4	BER6	Bit Error Ratio 10^-6
		 5	BER3	Bit Error Ratio 10^-3
		 21	LOM	Loss Of MCS sync
		 254		Unknown value
		 255		Unsupported variable for addressed device"
	::= { fmroHtuLocalEntry 29 }

fmroHtuLocalMcsChc OBJECT-TYPE
	SYNTAX INTEGER
	{
		none(1),
		ber6(4),
		ber3(5),
		lom(21),
		unknown(254),
		unsupported(255)
	}
	ACCESS read-only
	STATUS mandatory
	DESCRIPTION
		"Error on the MCS Channel c
		 1	None	No Alarm
		 4	BER6	Bit Error Ratio 10^-6
		 5	BER3	Bit Error Ratio 10^-3
		 21	LOM	Loss Of MCS sync
		 254		Unknown value
		 255		Unsupported variable for addressed device"
	::= { fmroHtuLocalEntry 30 }

fmroHtuLocalMcsChd OBJECT-TYPE
	SYNTAX INTEGER
	{
		none(1),
		ber6(4),
		ber3(5),
		lom(21),
		unknown(254),
		unsupported(255)
	}
	ACCESS read-only
	STATUS mandatory
	DESCRIPTION
		"Error on the MCS Channel d
		 1	None	No Alarm
		 4	BER6	Bit Error Ratio 10^-6
		 5	BER3	Bit Error Ratio 10^-3
		 21	LOM	Loss Of MCS sync
		 254		Unknown value
		 255		Unsupported variable for addressed device"
	::= { fmroHtuLocalEntry 31 }

fmroHtuLocalMcsRemCha OBJECT-TYPE
	SYNTAX INTEGER
	{
		none(1),
		lom(21),
		unknown(254),
		unsupported(255)
	}
	ACCESS read-only
	STATUS mandatory
	DESCRIPTION
		"Error on the MCS Remote Channel a
		 1	None	No Alarm
		 21	LOM	Loss Of MCS sync
		 254		Unknown value
		 255		Unsupported variable for addressed device"
	::= { fmroHtuLocalEntry 32 }

fmroHtuLocalMcsRemChb OBJECT-TYPE
	SYNTAX INTEGER
	{
		none(1),
		lom(21),
		unknown(254),
		unsupported(255)
	}
	ACCESS read-only
	STATUS mandatory
	DESCRIPTION
		"Error on the MCS Remote Channel b
		 1	None	No Alarm
		 21	LOM	Loss Of MCS sync
		 254		Unknown value
		 255		Unsupported variable for addressed device"
	::= { fmroHtuLocalEntry 33 }

fmroHtuLocalMcsRemChc OBJECT-TYPE
	SYNTAX INTEGER
	{
		none(1),
		lom(21),
		unknown(254),
		unsupported(255)
	}
	ACCESS read-only
	STATUS mandatory
	DESCRIPTION
		"Error on the MCS Remote Channel c
		 1	None	No Alarm
		 21	LOM	Loss Of MCS sync
		 254		Unknown value
		 255		Unsupported variable for addressed device"
	::= { fmroHtuLocalEntry 34 }

fmroHtuLocalMcsRemChd OBJECT-TYPE
	SYNTAX INTEGER
	{
		none(1),
		lom(21),
		unknown(254),
		unsupported(255)
	}
	ACCESS read-only
	STATUS mandatory
	DESCRIPTION
		"Error on the MCS Remote Channel d
		 1	None	No Alarm
		 21	LOM	Loss Of MCS sync
		 254		Unknown value
		 255		Unsupported variable for addressed device"
	::= { fmroHtuLocalEntry 35 }

fmroHtuLocalMcs OBJECT-TYPE
	SYNTAX INTEGER
	{
		none(1),
		lom(21),
		plom(22),
		unknown(254),
		unsupported(255)
	}
	ACCESS read-only
	STATUS mandatory
	DESCRIPTION
		"Error on the entire MCS System
		 1	None	No Alarm
		 21	LOM	Loss Of MCS sync
		 22	PLOM	Partial Loss Of MCS sync
		 254		Unknown value
		 255		Unsupported variable for addressed device"
	::= { fmroHtuLocalEntry 36 }

fmroHtuLocalL2SwitchWanRx OBJECT-TYPE
	SYNTAX INTEGER
	{
		none(1),
		loa(6),
		unknown(254),
		unsupported(255)
	}
	ACCESS read-only
	STATUS mandatory
	DESCRIPTION
		"Error on the L2Switch WAN interface (Receive signal)
		 1	None	No Alarm
		 6	LOA	Loss Of Activity
		 254		Unknown value
		 255		Unsupported variable for addressed device"
	::= { fmroHtuLocalEntry 37 }

fmroHtuLocalL2SwitchWanTx OBJECT-TYPE
	SYNTAX INTEGER
	{
		none(1),
		loa(6),
		mir(23),
		unknown(254),
		unsupported(255)
	}
	ACCESS read-only
	STATUS mandatory
	DESCRIPTION
		"Error on the L2Switch WAN interface (Transmit signal)
		 1	None	No Alarm
		 6	LOA	Loss Of Activity
		 23	MIR	Maximum Information Rate
		 254		Unknown value
		 255		Unsupported variable for addressed device"
	::= { fmroHtuLocalEntry 38 }

fmroHtuLocalL2SwitchLanPort1 OBJECT-TYPE
	SYNTAX INTEGER
	{
		none(1),
		linkdown(24),
		lfp(27),
		unknown(254),
		unsupported(255)
	}
	ACCESS read-only
	STATUS mandatory
	DESCRIPTION
		"Error on the L2Switch LAN Port 1
		 1	None		No Alarm
		 24	LinkDown	No Link Detected
		 27	LFP		Link Failure Propagation
		 254			Unknown value
		 255			Unsupported variable for addressed device"
	::= { fmroHtuLocalEntry 39 }

fmroHtuLocalL2SwitchLanPort2 OBJECT-TYPE
	SYNTAX INTEGER
	{
		none(1),
		linkdown(24),
		lfp(27),
		unknown(254),
		unsupported(255)
	}
	ACCESS read-only
	STATUS mandatory
	DESCRIPTION
		"Error on the L2Switch LAN Port 2
		 1	None		No Alarm
		 24	LinkDown	No Link Detected
		 27	LFP		Link Failure Propagation
		 254			Unknown value
		 255			Unsupported variable for addressed device"
	::= { fmroHtuLocalEntry 40 }

fmroHtuLocalL2SwitchLanPort3 OBJECT-TYPE
	SYNTAX INTEGER
	{
		none(1),
		linkdown(24),
		lfp(27),
		unknown(254),
		unsupported(255)
	}
	ACCESS read-only
	STATUS mandatory
	DESCRIPTION
		"Error on the L2Switch LAN Port 3
		 1	None		No Alarm
		 24	LinkDown	No Link Detected
		 27	LFP		Link Failure Propagation
		 254			Unknown value
		 255			Unsupported variable for addressed device"
	::= { fmroHtuLocalEntry 41 }

fmroHtuLocalL2SwitchLanPort4 OBJECT-TYPE
	SYNTAX INTEGER
	{
		none(1),
		linkdown(24),
		lfp(27),
		unknown(254),
		unsupported(255)
	}
	ACCESS read-only
	STATUS mandatory
	DESCRIPTION
		"Error on the L2Switch LAN Port 4
		 1	None		No Alarm
		 24	LinkDown	No Link Detected
		 27	LFP		Link Failure Propagation
		 254			Unknown value
		 255			Unsupported variable for addressed device"
	::= { fmroHtuLocalEntry 42 }

fmroHtuLocalL2SwitchBPLPort1 OBJECT-TYPE
	SYNTAX INTEGER
	{
		none(1),
		linkdown(24),
		lfp(27),
		unknown(254),
		unsupported(255)
	}
	ACCESS read-only
	STATUS mandatory
	DESCRIPTION
		"Error on the L2Switch Backplane Port 1
		 1	None		No Alarm
		 24	LinkDown	No Link Detected
		 27	LFP		Link Failure Propagation
		 254			Unknown value
		 255			Unsupported variable for addressed device"
	::= { fmroHtuLocalEntry 43 }

fmroHtuLocalUo OBJECT-TYPE
	SYNTAX INTEGER
	{
		none(1),
		los(9),
		failUo1(28),
		failUo2(29),
		unknown(254),
		unsupported(255)
	}
	ACCESS read-only
	STATUS mandatory
	DESCRIPTION
		"Error on the optical link
		 1	None		No Alarm
		 9	LOS		Loss of Signal
		 28	FAIL_UO1	Line protection fail on Uo1
		 29	FAIL_UO2	Line protection fail on Uo2
		 254			Unknown value
		 255			Unsupported variable for addressed device"
	::= { fmroHtuLocalEntry 44 }

fmroHtuLocalUo1 OBJECT-TYPE
	SYNTAX INTEGER
	{
		none(1),
		ber6(4),
		ber3(5),
		lfa(8),
		los(9),
		rai(11),
		unknown(254),
		unsupported(255)
	}
	ACCESS read-only
	STATUS mandatory
	DESCRIPTION
		"Error on first optical interface
		 1	None		No Alarm
		 4	BER6		Bit Error Ratio 10^-6
		 5	BER3		Bit Error Ratio 10^-3
		 8	LFA		Loss of Frame Alignment
		 9	LOS		Loss of Signal
		 11	RAI		Remote Alarm Indication
		 254			Unknown value
		 255			Unsupported variable for addressed device"
	::= { fmroHtuLocalEntry 45 }

fmroHtuLocalUo2 OBJECT-TYPE
	SYNTAX INTEGER
	{
		none(1),
		ber6(4),
		ber3(5),
		lfa(8),
		los(9),
		rai(11),
		unknown(254),
		unsupported(255)
	}
	ACCESS read-only
	STATUS mandatory
	DESCRIPTION
		"Error on second optical interface
		 1	None		No Alarm
		 4	BER6		Bit Error Ratio 10^-6
		 5	BER3		Bit Error Ratio 10^-3
		 8	LFA		Loss of Frame Alignment
		 9	LOS		Loss of Signal
		 11	RAI		Remote Alarm Indication
		 254			Unknown value
		 255			Unsupported variable for addressed device"
	::= { fmroHtuLocalEntry 46 }

fmroHtuLocalUA OBJECT-TYPE
	SYNTAX INTEGER
	{
		none(1),
		ber6(4),
		ber3(5),
		ais(7),
		lfa(8),
		los(9),
		rai(11),
		unknown(254),
		unsupported(255)
	}
	ACCESS read-only
	STATUS mandatory
	DESCRIPTION
		"Error in 2MB Signal (Framer A) on transmission side
		 1	None		No Alarm
		 4	BER6		Bit Error Ratio 10^-6
		 5	BER3		Bit Error Ratio 10^-3
		 7	AIS		Alarm Indication Signal
		 8	LFA		Loss of Frame Alignment
		 9	LOS		Loss of Signal
		 11	RAI		Remote Alarm Indication
		 254			Unknown value
		 255			Unsupported variable for addressed device"
	::= { fmroHtuLocalEntry 47 }

fmroHtuLocalUB OBJECT-TYPE
	SYNTAX INTEGER
	{
		none(1),
		ber6(4),
		ber3(5),
		ais(7),
		lfa(8),
		los(9),
		rai(11),
		unknown(254),
		unsupported(255)
	}
	ACCESS read-only
	STATUS mandatory
	DESCRIPTION
		"Error in 2MB Signal (Framer B) on transmission side
		 1	None		No Alarm
		 4	BER6		Bit Error Ratio 10^-6
		 5	BER3		Bit Error Ratio 10^-3
		 7	AIS		Alarm Indication Signal
		 8	LFA		Loss of Frame Alignment
		 9	LOS		Loss of Signal
		 11	RAI		Remote Alarm Indication
		 254			Unknown value
		 255			Unsupported variable for addressed device"
	::= { fmroHtuLocalEntry 48 }

fmroHtuLocalUC OBJECT-TYPE
	SYNTAX INTEGER
	{
		none(1),
		ber6(4),
		ber3(5),
		ais(7),
		lfa(8),
		los(9),
		rai(11),
		unknown(254),
		unsupported(255)
	}
	ACCESS read-only
	STATUS mandatory
	DESCRIPTION
		"Error in 2MB Signal (Framer C) on transmission side
		 1	None		No Alarm
		 4	BER6		Bit Error Ratio 10^-6
		 5	BER3		Bit Error Ratio 10^-3
		 7	AIS		Alarm Indication Signal
		 8	LFA		Loss of Frame Alignment
		 9	LOS		Loss of Signal
		 11	RAI		Remote Alarm Indication
		 254			Unknown value
		 255			Unsupported variable for addressed device"
	::= { fmroHtuLocalEntry 49 }

fmroHtuLocalUD OBJECT-TYPE
	SYNTAX INTEGER
	{
		none(1),
		ber6(4),
		ber3(5),
		ais(7),
		lfa(8),
		los(9),
		rai(11),
		unknown(254),
		unsupported(255)
	}
	ACCESS read-only
	STATUS mandatory
	DESCRIPTION
		"Error in 2MB Signal (Framer D) on transmission side
		 1	None		No Alarm
		 4	BER6		Bit Error Ratio 10^-6
		 5	BER3		Bit Error Ratio 10^-3
		 7	AIS		Alarm Indication Signal
		 8	LFA		Loss of Frame Alignment
		 9	LOS		Loss of Signal
		 11	RAI		Remote Alarm Indication
		 254			Unknown value
		 255			Unsupported variable for addressed device"
	::= { fmroHtuLocalEntry 50 }

fmroHtuLocalLosDB OBJECT-TYPE
	SYNTAX INTEGER
	{
		none(1),
		alarm(10),
		unknown(254),
		unsupported(255)
	}
	ACCESS read-only
	STATUS mandatory
	DESCRIPTION
		"LOS-D (Framer B) Error State
		 1	None	No Alarm
		 10	Alarm	Alarm present
		 254		Unknown value
		 255		Unsupported variable for addressed device"
	::= { fmroHtuLocalEntry 51 }

fmroHtuLocalLosDC OBJECT-TYPE
	SYNTAX INTEGER
	{
		none(1),
		alarm(10),
		unknown(254),
		unsupported(255)
	}
	ACCESS read-only
	STATUS mandatory
	DESCRIPTION
		"LOS-D (Framer C) Error State
		 1	None	No Alarm
		 10	Alarm	Alarm present
		 254		Unknown value
		 255		Unsupported variable for addressed device"
	::= { fmroHtuLocalEntry 52 }

fmroHtuLocalLosDD OBJECT-TYPE
	SYNTAX INTEGER
	{
		none(1),
		alarm(10),
		unknown(254),
		unsupported(255)
	}
	ACCESS read-only
	STATUS mandatory
	DESCRIPTION
		"LOS-D (Framer D) Error State
		 1	None	No Alarm
		 10	Alarm	Alarm present
		 254		Unknown value
		 255		Unsupported variable for addressed device"
	::= { fmroHtuLocalEntry 53 }

fmroHtuLocalSFP1 OBJECT-TYPE
	SYNTAX INTEGER
	{
		none(1),
		txfault(30),
		invalid(31),
		missing(32),
		unknown(254),
		unsupported(255)
	}
	ACCESS read-only
	STATUS mandatory
	DESCRIPTION
		"Error on first SFP modul
		 1	None		No Alarm
		 30	Tx fault	Transmit laser fault
		 31	Invalid		Invalid SFP modul equipped
		 32	Missing		No SFP modul equipped
		 254			Unknown value
		 255			Unsupported variable for addressed device"
	::= { fmroHtuLocalEntry 54 }

fmroHtuLocalSFP2 OBJECT-TYPE
	SYNTAX INTEGER
	{
		none(1),
		txfault(30),
		invalid(31),
		missing(32),
		unknown(254),
		unsupported(255)
	}
	ACCESS read-only
	STATUS mandatory
	DESCRIPTION
		"Error on second SFP modul
		 1	None		No Alarm
		 30	Tx fault	Transmit laser fault
		 31	Invalid		Invalid SFP modul equipped
		 32	Missing		No SFP modul equipped
		 254			Unknown value
		 255			Unsupported variable for addressed device"
	::= { fmroHtuLocalEntry 55 }

--------------------------------------------------------------------------------  
--	FM-RO	Far HTU
--------------------------------------------------------------------------------  
fmroHtuFarTable OBJECT-TYPE
	SYNTAX SEQUENCE OF FmroHtuFarEntry
	ACCESS not-accessible
	STATUS mandatory
	DESCRIPTION ""
	::= { fmro 3 }

fmroHtuFarEntry OBJECT-TYPE
	SYNTAX FmroHtuFarEntry
	ACCESS not-accessible
	STATUS mandatory
	DESCRIPTION ""
	INDEX { fmroHtuFarPortIndex, fmroHtuFarLinkIndex }
	::= { fmroHtuFarTable 1 }	

FmroHtuFarEntry ::=
	SEQUENCE
	{
		fmroHtuFarPortIndex INTEGER,
		fmroHtuFarLinkIndex INTEGER,
		fmroHtuFarU1 INTEGER,
		fmroHtuFarU2 INTEGER,
		fmroHtuFarU INTEGER,
		fmroHtuFarT INTEGER,
		fmroHtuFarDC INTEGER,
		fmroHtuFarDN INTEGER,
		fmroHtuFarEquipment INTEGER,
		fmroHtuFarLosD INTEGER,
		fmroHtuFarT3In INTEGER,
		fmroHtuFarRps INTEGER,
		fmroHtuFarRta INTEGER,
		fmroHtuFarPowerfail INTEGER,
		fmroHtuFarT3Out INTEGER,
		fmroHtuFarLaser INTEGER,
		fmroHtuFarPowerfailCpe INTEGER,
		fmroHtuFarU3 INTEGER,
		fmroHtuFarU4 INTEGER,
		fmroHtuFarRps2 INTEGER,
		fmroHtuFarRps3 INTEGER,
		fmroHtuFarRps4 INTEGER,
		fmroHtuFarVSlave INTEGER,
		fmroHtuFarTSlave INTEGER,
		fmroHtuFarDCSlave INTEGER,
		fmroHtuFarDNSlave INTEGER,
		fmroHtuFarVA INTEGER,
		fmroHtuFarVB INTEGER,
		fmroHtuFarVC INTEGER,
		fmroHtuFarVD INTEGER,
		fmroHtuFarMcsCha INTEGER,
		fmroHtuFarMcsChb INTEGER,
		fmroHtuFarMcsChc INTEGER,
		fmroHtuFarMcsChd INTEGER,
		fmroHtuFarMcsRemCha INTEGER,
		fmroHtuFarMcsRemChb INTEGER,
		fmroHtuFarMcsRemChc INTEGER,
		fmroHtuFarMcsRemChd INTEGER,
		fmroHtuFarMcs INTEGER,
		fmroHtuFarL2SwitchWanRx INTEGER,
		fmroHtuFarL2SwitchWanTx INTEGER,
		fmroHtuFarL2SwitchLanPort1 INTEGER,
		fmroHtuFarL2SwitchLanPort2 INTEGER,
		fmroHtuFarL2SwitchLanPort3 INTEGER,
		fmroHtuFarL2SwitchLanPort4 INTEGER,
		fmroHtuFarL2SwitchBPLPort1 INTEGER,
		fmroHtuFarUo INTEGER,
		fmroHtuFarUo1 INTEGER,
		fmroHtuFarUo2 INTEGER,
		fmroHtuFarUA INTEGER,
		fmroHtuFarUB INTEGER,
		fmroHtuFarUC INTEGER,
		fmroHtuFarUD INTEGER,
		fmroHtuFarLosDB INTEGER,
		fmroHtuFarLosDC INTEGER,
		fmroHtuFarLosDD INTEGER,
		fmroHtuFarSFP1 INTEGER,
		fmroHtuFarSFP2 INTEGER
	}

fmroHtuFarPortIndex OBJECT-TYPE
	SYNTAX INTEGER
	ACCESS read-only
	STATUS mandatory
	DESCRIPTION
		"This variable addresses the port number of the proxy
		and is used as index for the other elements in the Table"
	::= { fmroHtuFarEntry 1 }

fmroHtuFarLinkIndex OBJECT-TYPE
	SYNTAX INTEGER
	ACCESS read-only
	STATUS mandatory
	DESCRIPTION
		"This variable addresses the slot number of the OMI sub-rack
		and is used as index for the other elements in the Table"
	::= { fmroHtuFarEntry 2 }

fmroHtuFarU1 OBJECT-TYPE
	SYNTAX INTEGER
	{
		none(1),
		ber6(4),
		ber3(5),
		los(9),
		losw(19),
		unknown(254),
		unsupported(255)
	}
	ACCESS read-only
	STATUS mandatory
	DESCRIPTION
		"HDSL Error on Path 1
		  1	None	No Alarm
		  4	BER6	Bit Error Ratio 10^-6
		  5	BER3	Bit Error Ratio 10^-3
		  9	LOS	Loss of Signal
		 19	LOSW	Loss of SDSL synchronistation
		 254		Unknown value
		 255		Unsupported variable for addressed device"
	::= { fmroHtuFarEntry 3 }

fmroHtuFarU2 OBJECT-TYPE
	SYNTAX INTEGER
	{
		none(1),
		ber6(4),
		ber3(5),
		los(9),
		losw(19),
		unknown(254),
		unsupported(255)
	}
	ACCESS read-only
	STATUS mandatory
	DESCRIPTION
		"HDSL Error on Path 2
		 1	None	No Alarm
		 4	BER6	Bit Error Ratio 10^-6
		 5	BER3	Bit Error Ratio 10^-3
		 9	LOS	Loss of Signal
		 19	LOSW	Loss of SDSL synchronistation
		 254		Unknown value
		 255		Unsupported variable for addressed device"
	::= { fmroHtuFarEntry 4 }

fmroHtuFarU OBJECT-TYPE
	SYNTAX INTEGER
	{
		none(1),
		hpo(2),
		fpo(3),
		ber6(4),
		ber3(5),
		ais(7),
		lfa(8),
		los(9),
		rai(11),
		bwNotAvail(18),
		unknown(254),
		unsupported(255)
	}
	ACCESS read-only
	STATUS mandatory
	DESCRIPTION
		"Error in 2MB Signal on HDSL Path
		 1	None		No Alarm
		 4	BER6		Bit Error Ratio 10^-6
		 5	BER3		Bit Error Ratio 10^-3
		 7	AIS		Alarm Indication Signal
		 8	LFA		Loss of Frame Alignment
		 9	LOS		Loss of Signal
		 11	RAI		Remote Alarm Indication
		 18	BwNotAvail	Bandwidth not available
		 254			Unknown value
		 255			Unsupported variable for addressed device"
	::= { fmroHtuFarEntry 5 }

fmroHtuFarT OBJECT-TYPE
	SYNTAX INTEGER
	{
		none(1),
		ber6(4),
		ber3(5),
		ais(7),
		lfa(8),
		los(9),
		rai(11),
		unknown(254),
		unsupported(255)
	}
	ACCESS read-only
	STATUS mandatory
	DESCRIPTION
		"Error on the G.703 Interface
		 1	None	No Alarm
		 4	BER6	Bit Error Ratio 10^-6
		 5	BER3	Bit Error Ratio 10^-3
		 7	AIS	Alarm Indication Signal
		 8	LFA	Loss of Frame Alignment
		 9	LOS	Loss of Signal
		 11	RAI	Remote Alarm Indication
		 254		Unknown value
		 255		Unsupported variable for addressed device"
	::= { fmroHtuFarEntry 6 }

fmroHtuFarDC OBJECT-TYPE
	SYNTAX INTEGER
	{
		none(1),
		loa(6),
		unknown(254),
		unsupported(255)
	}
	ACCESS read-only
	STATUS mandatory
	DESCRIPTION
		"Error on the Data interface (Transmit signal)
		 1	None	No Alarm
		 6	LOA	Loss of Activity
		 254		Unknown value
		 255		Unsupported variable for addressed device"
	::= { fmroHtuFarEntry 7 }

fmroHtuFarDN OBJECT-TYPE
	SYNTAX INTEGER
	{
		none(1),
		loa(6),
		unknown(254),
		unsupported(255)
	}
	ACCESS read-only
	STATUS mandatory
	DESCRIPTION
		"Error on the Data interface (Receive signal)
		 1	None	No Alarm
		 6	LOA	Loss of Activity
		 254		Unknown value
		 255		Unsupported variable for addressed device"
	::= { fmroHtuFarEntry 8 }

fmroHtuFarEquipment OBJECT-TYPE
	SYNTAX INTEGER
	{
		none(1),
		alarm(10),
		unknown(254),
		unsupported(255)
	}
	ACCESS read-only
	STATUS mandatory
	DESCRIPTION
		"Equipment Alarm
		 1	None	No Alarm
		 10	Alarm	Alarm present
		 254		Unknown value
		 255		Unsupported variable for addressed device"
	::= { fmroHtuFarEntry 9 }

fmroHtuFarLosD OBJECT-TYPE
	SYNTAX INTEGER
	{
		none(1),
		alarm(10),
		unknown(254),
		unsupported(255)
	}
	ACCESS read-only
	STATUS mandatory
	DESCRIPTION
		"LOS-D Error State
		 1	None	No Alarm
		 10	Alarm	Alarm present
		 254		Unknown value
		 255		Unsupported variable for addressed device"
	::= { fmroHtuFarEntry 10 }

fmroHtuFarT3In OBJECT-TYPE
	SYNTAX INTEGER
	{
		none(1),
		los(9),
		unknown(254),
		unsupported(255)
	}
	ACCESS read-only
	STATUS mandatory
	DESCRIPTION
		"Loss of Clock on T3In
		 1	None	No Alarm
		 9	LOS	Loss of Clock Signal on T3In
		 254		Unknown value
		 255		Unsupported variable for addressed device"
	::= { fmroHtuFarEntry 11 }

fmroHtuFarRps OBJECT-TYPE
	SYNTAX INTEGER
	{
		none(1),
		ucr12(12),
		ucr1(13),
		ucr2(14),
		ovr(15),
		nosym(16),
		defect(17),
		unknown(254),
		unsupported(255)
	}
	ACCESS read-only
	STATUS mandatory
	DESCRIPTION
		"Remote Power Supply Error State
		 1	None	No Alarm
		 12	UCR12	Undercurrent on HDSL Path 1 and 2
		 13	UCR1	Undercurrent on HDSL Path 1
		 14	UCR2	Undercurrent on HDSL Path 2
		 15	OVR	Overload
		 16	NOSYM	Unsymetrical Load
		 17	DEFECT	Defect on Module
		 254		Unknown value
		 255		Unsupported variable for addressed device"
	::= { fmroHtuFarEntry 12 }

fmroHtuFarRta OBJECT-TYPE
	SYNTAX INTEGER
	{
		none(1),
		alarm(10),
		unknown(254),
		unsupported(255)
	}
	ACCESS read-only
	STATUS mandatory
	DESCRIPTION
		"Remote Terminal Alarm Error State
		 1	None	No Alarm
		 10	Alarm	Alarm present
		 254		Unknown value
		 255		Unsupported variable for addressed device"
	::= { fmroHtuFarEntry 13 }

fmroHtuFarPowerfail OBJECT-TYPE
	SYNTAX INTEGER
	{
		none(1),
		alarm(10),
		unknown(254),
		unsupported(255)
	}
	ACCESS read-only
	STATUS mandatory
	DESCRIPTION
		"Remote Device Powerfailure Alarm
		 1	None	No Alarm
		 10	Alarm	Alarm present
		 254		Unknown value
		 255		Unsupported variable for addressed device"
	::= { fmroHtuFarEntry 14 }

fmroHtuFarT3Out OBJECT-TYPE
	SYNTAX INTEGER
	{
		none(1),
		los(9),
		unknown(254),
		unsupported(255)
	}
	ACCESS read-only
	STATUS mandatory
	DESCRIPTION
		"No Clock Signal available for T3Out
		 1	None	No Alarm
		 9	LOS	Loss of Clock Signal on T3Out
		 254		Unknown value
		 255		Unsupported variable for addressed device"
	::= { fmroHtuFarEntry 15 }

fmroHtuFarLaser OBJECT-TYPE
	SYNTAX INTEGER
	{
		none(1),
		alarm(10),
		unknown(254),
		unsupported(255)
	}
	ACCESS read-only
	STATUS mandatory
	DESCRIPTION
		"Laser aging alarm
		 1	None	No Alarm
		 10	Alarm	Laser reaching critcal age
		 254		Unknown value
		 255		Unsupported variable for addressed device"
	::= { fmroHtuFarEntry 16 }

fmroHtuFarPowerfailCpe OBJECT-TYPE
	SYNTAX INTEGER
	{
		none(1),
		alarm(10),
		unknown(254),
		unsupported(255)
	}
	ACCESS read-only
	STATUS mandatory
	DESCRIPTION
		"Remote Device Local Power Loss Alarm. If this Alarm
		is active, the device has lost its local power supply
		but is still powered over the transmission line (using
		a remote power supply (RPS).
		 1	None	No Alarm
		 10	Alarm	Alarm present
		 254		Unknown value
		 255		Unsupported variable for addressed device"
	::= { fmroHtuFarEntry 17 }

fmroHtuFarU3 OBJECT-TYPE
	SYNTAX INTEGER
	{
		none(1),
		ber6(4),
		ber3(5),
		los(9),
		losw(19),
		unknown(254),
		unsupported(255)
	}
	ACCESS read-only
	STATUS mandatory
	DESCRIPTION
		"xDSL Error on Path 3
		 1	None	No Alarm
		 4	BER6	Bit Error Ratio 10^-6
		 5	BER3	Bit Error Ratio 10^-3
		 9	LOS	Loss of Signal
		 19	LOSW	Loss of SDSL synchronistation
		 254		Unknown value
		 255		Unsupported variable for addressed device"
	::= { fmroHtuFarEntry 18 }

fmroHtuFarU4 OBJECT-TYPE
	SYNTAX INTEGER
	{
		none(1),
		ber6(4),
		ber3(5),
		los(9),
		losw(19),
		unknown(254),
		unsupported(255)
	}
	ACCESS read-only
	STATUS mandatory
	DESCRIPTION
		"xDSL Error on Path 4
		 1	None	No Alarm
		 4	BER6	Bit Error Ratio 10^-6
		 5	BER3	Bit Error Ratio 10^-3
		 9	LOS	Loss of Signal
		 19	LOSW		Loss of SDSL synchronistation
		 254		Unknown value
		 255		Unsupported variable for addressed device"
	::= { fmroHtuFarEntry 19 }

fmroHtuFarRps2 OBJECT-TYPE
	SYNTAX INTEGER
	{
		none(1),
		ucr1(13),
		ovr(15),
		nosym(16),
		defect(17),
		unknown(254),
		unsupported(255)
	}
	ACCESS read-only
	STATUS mandatory
	DESCRIPTION
		"Remote Power Supply Error State on Path 2
		 1	None	No Alarm
		 13	UCR1	Undercurrent on current Path
		 15	OVR	Overload
		 16	NOSYM	Unsymetrical Load
		 17	DEFECT	Defect on Module
		 254		Unknown value
		 255		Unsupported variable for addressed device"
	::= { fmroHtuFarEntry 20 }

fmroHtuFarRps3 OBJECT-TYPE
	SYNTAX INTEGER
	{
		none(1),
		ucr1(13),
		ovr(15),
		nosym(16),
		defect(17),
		unknown(254),
		unsupported(255)
	}
	ACCESS read-only
	STATUS mandatory
	DESCRIPTION
		"Remote Power Supply Error State on Path 3
		 1	None	No Alarm
		 13	UCR1	Undercurrent on current Path
		 15	OVR	Overload
		 16	NOSYM	Unsymetrical Load
		 17	DEFECT	Defect on Module
		 254		Unknown value
		 255		Unsupported variable for addressed device"
	::= { fmroHtuFarEntry 21 }

fmroHtuFarRps4 OBJECT-TYPE
	SYNTAX INTEGER
	{
		none(1),
		ucr1(13),
		ovr(15),
		nosym(16),
		defect(17),
		unknown(254),
		unsupported(255)
	}
	ACCESS read-only
	STATUS mandatory
	DESCRIPTION
		"Remote Power Supply Error State on Path 4
		 1	None	No Alarm
		 13	UCR1	Undercurrent on current Path
		 15	OVR	Overload
		 16	NOSYM	Unsymetrical Load
		 17	DEFECT	Defect on Module
		 254		Unknown value
		 255		Unsupported variable for addressed device"
	::= { fmroHtuFarEntry 22 }

fmroHtuFarVSlave OBJECT-TYPE
	SYNTAX INTEGER
	{
		none(1),
		ber6(4),
		ber3(5),
		ais(7),
		lfa(8),
		los(9),
		rai(11),
		nsp(20),
		unknown(254),
		unsupported(255)
	}
	ACCESS read-only
	STATUS mandatory
	DESCRIPTION
		"Error on the V-Interface on the slave device
		 1	None	No Alarm
		 4	BER6	Bit Error Ratio 10^-6
		 5	BER3	Bit Error Ratio 10^-3
		 7	AIS	Alarm Indication Signal
		 8	LFA	Loss of Frame Alignment
		 9	LOS	Loss of Signal
		 10	RAI	Remote Alarm Indication
		 20	NSP		No Slave Present (GTU with slave support)
		 254		Unknown value
		 255		Unsupported variable for addressed device"
	::= { fmroHtuFarEntry 23 }

fmroHtuFarTSlave OBJECT-TYPE
	SYNTAX INTEGER
	{
		none(1),
		ber6(4),
		ber3(5),
		ais(7),
		lfa(8),
		los(9),
		rai(11),
		unknown(254),
		unsupported(255)
	}
	ACCESS read-only
	STATUS mandatory
	DESCRIPTION
		"Error on the T-Interface on the slave device
		 1	None	No Alarm
		 4	BER6	Bit Error Ratio 10^-6
		 5	BER3	Bit Error Ratio 10^-3
		 7	AIS	Alarm Indication Signal
		 8	LFA	Loss of Frame Alignment
		 9	LOS	Loss of Signal
		 11	RAI	Remote Alarm Indication
		 254		Unknown value
		 255		Unsupported variable for addressed device"
	::= { fmroHtuFarEntry 24 }

fmroHtuFarDCSlave OBJECT-TYPE
	SYNTAX INTEGER
	{
		none(1),
		loa(6),
		unknown(254),
		unsupported(255)
	}
	ACCESS read-only
	STATUS mandatory
	DESCRIPTION
		"Error on the Data interface (Transmit signal) on the slave device
		 1	None	No Alarm
		 6	LOA	Loss of Activity
		 254		Unknown value
		 255		Unsupported variable for addressed device"
	::= { fmroHtuFarEntry 25 }

fmroHtuFarDNSlave OBJECT-TYPE
	SYNTAX INTEGER
	{
		none(1),
		loa(6),
		unknown(254),
		unsupported(255)
	}
	ACCESS read-only
	STATUS mandatory
	DESCRIPTION
		"Error on the Data interface (Receive signal) on the slave device
		 1	None	No Alarm
		 6	LOA	Loss of Activity
		 254		Unknown value
		 255		Unsupported variable for addressed device"
	::= { fmroHtuFarEntry 26 }

fmroHtuFarVA OBJECT-TYPE
	SYNTAX INTEGER
	{
		none(1),
		ber6(4),
		ber3(5),
		ais(7),
		lfa(8),
		los(9),
		rai(11),
		unknown(254),
		unsupported(255)
	}
	ACCESS read-only
	STATUS mandatory
	DESCRIPTION
		"Error on the G.703 Interface
		 1	None	No Alarm
		 4	BER6	Bit Error Ratio 10^-6
		 5	BER3	Bit Error Ratio 10^-3
		 7	AIS	Alarm Indication Signal
		 8	LFA	Loss of Frame Alignment
		 9	LOS	Loss of Signal
		 11	RAI	Remote Alarm Indication
		 254		Unknown value
		 255		Unsupported variable for addressed device"
	::= { fmroHtuFarEntry 27 }

fmroHtuFarVB OBJECT-TYPE
	SYNTAX INTEGER
	{
		none(1),
		ber6(4),
		ber3(5),
		ais(7),
		lfa(8),
		los(9),
		rai(11),
		unknown(254),
		unsupported(255)
	}
	ACCESS read-only
	STATUS mandatory
	DESCRIPTION
		"Error on the G.703 Interface
		 1	None	No Alarm
		 4	BER6	Bit Error Ratio 10^-6
		 5	BER3	Bit Error Ratio 10^-3
		 7	AIS	Alarm Indication Signal
		 8	LFA	Loss of Frame Alignment
		 9	LOS	Loss of Signal
		 11	RAI	Remote Alarm Indication
		 254		Unknown value
		 255		Unsupported variable for addressed device"
	::= { fmroHtuFarEntry 28 }

fmroHtuFarVC OBJECT-TYPE
	SYNTAX INTEGER
	{
		none(1),
		ber6(4),
		ber3(5),
		ais(7),
		lfa(8),
		los(9),
		rai(11),
		unknown(254),
		unsupported(255)
	}
	ACCESS read-only
	STATUS mandatory
	DESCRIPTION
		"Error on the G.703 Interface
		 1	None	No Alarm
		 4	BER6	Bit Error Ratio 10^-6
		 5	BER3	Bit Error Ratio 10^-3
		 7	AIS	Alarm Indication Signal
		 8	LFA	Loss of Frame Alignment
		 9	LOS	Loss of Signal
		 11	RAI	Remote Alarm Indication
		 254		Unknown value
		 255		Unsupported variable for addressed device"
	::= { fmroHtuFarEntry 29 }

fmroHtuFarVD OBJECT-TYPE
	SYNTAX INTEGER
	{
		none(1),
		ber6(4),
		ber3(5),
		ais(7),
		lfa(8),
		los(9),
		rai(11),
		unknown(254),
		unsupported(255)
	}
	ACCESS read-only
	STATUS mandatory
	DESCRIPTION
		"Error on the G.703 Interface
		 1	None	No Alarm
		 4	BER6	Bit Error Ratio 10^-6
		 5	BER3	Bit Error Ratio 10^-3
		 7	AIS	Alarm Indication Signal
		 8	LFA	Loss of Frame Alignment
		 9	LOS	Loss of Signal
		 11	RAI	Remote Alarm Indication
		 254		Unknown value
		 255		Unsupported variable for addressed device"
	::= { fmroHtuFarEntry 30 }

fmroHtuFarMcsCha OBJECT-TYPE
	SYNTAX INTEGER
	{
		none(1),
		ber6(4),
		ber3(5),
		lom(21),
		unknown(254),
		unsupported(255)
	}
	ACCESS read-only
	STATUS mandatory
	DESCRIPTION
		"Error on the MCS Channel a
		 1	None	No Alarm
		 4	BER6	Bit Error Ratio 10^-6
		 5	BER3	Bit Error Ratio 10^-3
		 21	LOM	Loss Of MCS sync
		 254		Unknown value
		 255		Unsupported variable for addressed device"
	::= { fmroHtuFarEntry 31 }

fmroHtuFarMcsChb OBJECT-TYPE
	SYNTAX INTEGER
	{
		none(1),
		ber6(4),
		ber3(5),
		lom(21),
		unknown(254),
		unsupported(255)
	}
	ACCESS read-only
	STATUS mandatory
	DESCRIPTION
		"Error on the MCS Channel b
		 1	None	No Alarm
		 4	BER6	Bit Error Ratio 10^-6
		 5	BER3	Bit Error Ratio 10^-3
		 21	LOM	Loss Of MCS sync
		 254		Unknown value
		 255		Unsupported variable for addressed device"
	::= { fmroHtuFarEntry 32 }

fmroHtuFarMcsChc OBJECT-TYPE
	SYNTAX INTEGER
	{
		none(1),
		ber6(4),
		ber3(5),
		lom(21),
		unknown(254),
		unsupported(255)
	}
	ACCESS read-only
	STATUS mandatory
	DESCRIPTION
		"Error on the MCS Channel c
		 1	None	No Alarm
		 4	BER6	Bit Error Ratio 10^-6
		 5	BER3	Bit Error Ratio 10^-3
		 21	LOM	Loss Of MCS sync
		 254		Unknown value
		 255		Unsupported variable for addressed device"
	::= { fmroHtuFarEntry 33 }

fmroHtuFarMcsChd OBJECT-TYPE
	SYNTAX INTEGER
	{
		none(1),
		ber6(4),
		ber3(5),
		lom(21),
		unknown(254),
		unsupported(255)
	}
	ACCESS read-only
	STATUS mandatory
	DESCRIPTION
		"Error on the MCS Channel d
		 1	None	No Alarm
		 4	BER6	Bit Error Ratio 10^-6
		 5	BER3	Bit Error Ratio 10^-3
		 21	LOM	Loss Of MCS sync
		 254		Unknown value
		 255		Unsupported variable for addressed device"
	::= { fmroHtuFarEntry 34 }

fmroHtuFarMcsRemCha OBJECT-TYPE
	SYNTAX INTEGER
	{
		none(1),
		lom(21),
		unknown(254),
		unsupported(255)
	}
	ACCESS read-only
	STATUS mandatory
	DESCRIPTION
		"Error on the MCS Remote Channel a
		 1	None	No Alarm
		 21	LOM	Loss Of MCS sync
		 254		Unknown value
		 255		Unsupported variable for addressed device"
	::= { fmroHtuFarEntry 35 }

fmroHtuFarMcsRemChb OBJECT-TYPE
	SYNTAX INTEGER
	{
		none(1),
		lom(21),
		unknown(254),
		unsupported(255)
	}
	ACCESS read-only
	STATUS mandatory
	DESCRIPTION
		"Error on the MCS Remote Channel b
		 1	None	No Alarm
		 21	LOM	Loss Of MCS sync
		 254		Unknown value
		 255		Unsupported variable for addressed device"
	::= { fmroHtuFarEntry 36 }

fmroHtuFarMcsRemChc OBJECT-TYPE
	SYNTAX INTEGER
	{
		none(1),
		lom(21),
		unknown(254),
		unsupported(255)
	}
	ACCESS read-only
	STATUS mandatory
	DESCRIPTION
		"Error on the MCS Remote Channel c
		 1	None	No Alarm
		 21	LOM	Loss Of MCS sync
		 254		Unknown value
		 255		Unsupported variable for addressed device"
	::= { fmroHtuFarEntry 37 }

fmroHtuFarMcsRemChd OBJECT-TYPE
	SYNTAX INTEGER
	{
		none(1),
		lom(21),
		unknown(254),
		unsupported(255)
	}
	ACCESS read-only
	STATUS mandatory
	DESCRIPTION
		"Error on the MCS Remote Channel d
		 1	None	No Alarm
		 21	LOM	Loss Of MCS sync
		 254		Unknown value
		 255		Unsupported variable for addressed device"
	::= { fmroHtuFarEntry 38 }

fmroHtuFarMcs OBJECT-TYPE
	SYNTAX INTEGER
	{
		none(1),
		lom(21),
		plom(22),
		unknown(254),
		unsupported(255)
	}
	ACCESS read-only
	STATUS mandatory
	DESCRIPTION
		"Error on the entire MCS System
		 1	None	No Alarm
		 21	LOM	Loss Of MCS sync
		 22	PLOM	Partial Loss Of MCS sync
		 254		Unknown value
		 255		Unsupported variable for addressed device"
	::= { fmroHtuFarEntry 39 }

fmroHtuFarL2SwitchWanRx OBJECT-TYPE
	SYNTAX INTEGER
	{
		none(1),
		loa(6),
		unknown(254),
		unsupported(255)
	}
	ACCESS read-only
	STATUS mandatory
	DESCRIPTION
		"Error on the L2Switch WAN interface (Receive signal)
		 1	None	No Alarm
		 6	LOA	Loss Of Activity
		 254		Unknown value
		 255		Unsupported variable for addressed device"
	::= { fmroHtuFarEntry 40 }

fmroHtuFarL2SwitchWanTx OBJECT-TYPE
	SYNTAX INTEGER
	{
		none(1),
		loa(6),
		mir(23),
		unknown(254),
		unsupported(255)
	}
	ACCESS read-only
	STATUS mandatory
	DESCRIPTION
		"Error on the L2Switch WAN interface (Transmit signal)
		 1	None	No Alarm
		 6	LOA	Loss Of Activity
		 23	MIR	Maximum Information Rate
		 254		Unknown value
		 255		Unsupported variable for addressed device"
	::= { fmroHtuFarEntry 41 }

fmroHtuFarL2SwitchLanPort1 OBJECT-TYPE
	SYNTAX INTEGER
	{
		none(1),
		linkdown(24),
		lfp(27),
		unknown(254),
		unsupported(255)
	}
	ACCESS read-only
	STATUS mandatory
	DESCRIPTION
		"Error on the L2Switch LAN Port 1
		 1	None		No Alarm
		 24	LinkDown	No Link Detected
		 27	LFP		Link Failure Propagation
		 254			Unknown value
		 255			Unsupported variable for addressed device"
	::= { fmroHtuFarEntry 42 }

fmroHtuFarL2SwitchLanPort2 OBJECT-TYPE
	SYNTAX INTEGER
	{
		none(1),
		linkdown(24),
		lfp(27),
		unknown(254),
		unsupported(255)
	}
	ACCESS read-only
	STATUS mandatory
	DESCRIPTION
		"Error on the L2Switch LAN Port 2
		 1	None		No Alarm
		 24	LinkDown	No Link Detected
		 27	LFP		Link Failure Propagation
		 254			Unknown value
		 255			Unsupported variable for addressed device"
	::= { fmroHtuFarEntry 43 }

fmroHtuFarL2SwitchLanPort3 OBJECT-TYPE
	SYNTAX INTEGER
	{
		none(1),
		linkdown(24),
		lfp(27),
		unknown(254),
		unsupported(255)
	}
	ACCESS read-only
	STATUS mandatory
	DESCRIPTION
		"Error on the L2Switch LAN Port 3
		 1	None		No Alarm
		 24	LinkDown	No Link Detected
		 27	LFP		Link Failure Propagation
		 254			Unknown value
		 255			Unsupported variable for addressed device"
	::= { fmroHtuFarEntry 44 }

fmroHtuFarL2SwitchLanPort4 OBJECT-TYPE
	SYNTAX INTEGER
	{
		none(1),
		linkdown(24),
		lfp(27),
		unknown(254),
		unsupported(255)
	}
	ACCESS read-only
	STATUS mandatory
	DESCRIPTION
		"Error on the L2Switch LAN Port 4
		 1	None		No Alarm
		 24	LinkDown	No Link Detected
		 27	LFP		Link Failure Propagation
		 254			Unknown value
		 255			Unsupported variable for addressed device"
	::= { fmroHtuFarEntry 45 }

fmroHtuFarL2SwitchBPLPort1 OBJECT-TYPE
	SYNTAX INTEGER
	{
		none(1),
		linkdown(24),
		lfp(27),
		unknown(254),
		unsupported(255)
	}
	ACCESS read-only
	STATUS mandatory
	DESCRIPTION
		"Error on the L2Switch Backplane Port 1
		 1	None		No Alarm
		 24	LinkDown	No Link Detected
		 27	LFP		Link Failure Propagation
		 254			Unknown value
		 255			Unsupported variable for addressed device"
	::= { fmroHtuFarEntry 46 }

fmroHtuFarUo OBJECT-TYPE
	SYNTAX INTEGER
	{
		none(1),
		los(9),
		failUo1(28),
		failUo2(29),
		unknown(254),
		unsupported(255)
	}
	ACCESS read-only
	STATUS mandatory
	DESCRIPTION
		"Error on the optical link
		 1	None		No Alarm
		 9	LOS		Loss of Signal
		 28	FAIL_UO1	Line protection fail on Uo1
		 29	FAIL_UO2	Line protection fail on Uo2
		 254			Unknown value
		 255			Unsupported variable for addressed device"
	::= { fmroHtuFarEntry 47 }

fmroHtuFarUo1 OBJECT-TYPE
	SYNTAX INTEGER
	{
		none(1),
		ber6(4),
		ber3(5),
		lfa(8),
		los(9),
		rai(11),
		unknown(254),
		unsupported(255)
	}
	ACCESS read-only
	STATUS mandatory
	DESCRIPTION
		"Error on first optical interface
		 1	None		No Alarm
		 4	BER6		Bit Error Ratio 10^-6
		 5	BER3		Bit Error Ratio 10^-3
		 8	LFA		Loss of Frame Alignment
		 9	LOS		Loss of Signal
		 11	RAI		Remote Alarm Indication
		 254			Unknown value
		 255			Unsupported variable for addressed device"
	::= { fmroHtuFarEntry 48 }

fmroHtuFarUo2 OBJECT-TYPE
	SYNTAX INTEGER
	{
		none(1),
		ber6(4),
		ber3(5),
		lfa(8),
		los(9),
		rai(11),
		unknown(254),
		unsupported(255)
	}
	ACCESS read-only
	STATUS mandatory
	DESCRIPTION
		"Error on second optical interface
		 1	None		No Alarm
		 4	BER6		Bit Error Ratio 10^-6
		 5	BER3		Bit Error Ratio 10^-3
		 8	LFA		Loss of Frame Alignment
		 9	LOS		Loss of Signal
		 11	RAI		Remote Alarm Indication
		 254			Unknown value
		 255			Unsupported variable for addressed device"
	::= { fmroHtuFarEntry 49 }

fmroHtuFarUA OBJECT-TYPE
	SYNTAX INTEGER
	{
		none(1),
		ber6(4),
		ber3(5),
		ais(7),
		lfa(8),
		rai(11),
		unknown(254),
		unsupported(255)
	}
	ACCESS read-only
	STATUS mandatory
	DESCRIPTION
		"Error in 2MB Signal (Framer A) on transmission side
		 1	None		No Alarm
		 4	BER6		Bit Error Ratio 10^-6
		 5	BER3		Bit Error Ratio 10^-3
		 7	AIS		Alarm Indication Signal
		 8	LFA		Loss of Frame Alignment
		 11	RAI		Remote Alarm Indication
		 254			Unknown value
		 255			Unsupported variable for addressed device"
	::= { fmroHtuFarEntry 50 }

fmroHtuFarUB OBJECT-TYPE
	SYNTAX INTEGER
	{
		none(1),
		ber6(4),
		ber3(5),
		ais(7),
		lfa(8),
		rai(11),
		unknown(254),
		unsupported(255)
	}
	ACCESS read-only
	STATUS mandatory
	DESCRIPTION
		"Error in 2MB Signal (Framer B) on transmission side
		 1	None		No Alarm
		 4	BER6		Bit Error Ratio 10^-6
		 5	BER3		Bit Error Ratio 10^-3
		 7	AIS		Alarm Indication Signal
		 8	LFA		Loss of Frame Alignment
		 11	RAI		Remote Alarm Indication
		 254			Unknown value
		 255			Unsupported variable for addressed device"
	::= { fmroHtuFarEntry 51 }

fmroHtuFarUC OBJECT-TYPE
	SYNTAX INTEGER
	{
		none(1),
		ber6(4),
		ber3(5),
		ais(7),
		lfa(8),
		rai(11),
		unknown(254),
		unsupported(255)
	}
	ACCESS read-only
	STATUS mandatory
	DESCRIPTION
		"Error in 2MB Signal (Framer C) on transmission side
		 1	None		No Alarm
		 4	BER6		Bit Error Ratio 10^-6
		 5	BER3		Bit Error Ratio 10^-3
		 7	AIS		Alarm Indication Signal
		 8	LFA		Loss of Frame Alignment
		 11	RAI		Remote Alarm Indication
		 254			Unknown value
		 255			Unsupported variable for addressed device"
	::= { fmroHtuFarEntry 52 }

fmroHtuFarUD OBJECT-TYPE
	SYNTAX INTEGER
	{
		none(1),
		ber6(4),
		ber3(5),
		ais(7),
		lfa(8),
		rai(11),
		unknown(254),
		unsupported(255)
	}
	ACCESS read-only
	STATUS mandatory
	DESCRIPTION
		"Error in 2MB Signal (Framer D) on transmission side
		 1	None		No Alarm
		 4	BER6		Bit Error Ratio 10^-6
		 5	BER3		Bit Error Ratio 10^-3
		 7	AIS		Alarm Indication Signal
		 8	LFA		Loss of Frame Alignment
		 11	RAI		Remote Alarm Indication
		 254			Unknown value
		 255			Unsupported variable for addressed device"
	::= { fmroHtuFarEntry 53 }

fmroHtuFarLosDB OBJECT-TYPE
	SYNTAX INTEGER
	{
		none(1),
		alarm(10),
		unknown(254),
		unsupported(255)
	}
	ACCESS read-only
	STATUS mandatory
	DESCRIPTION
		"LOS-D (Framer B) Error State
		 1	None	No Alarm
		 10	Alarm	Alarm present
		 254		Unknown value
		 255		Unsupported variable for addressed device"
	::= { fmroHtuFarEntry 54 }

fmroHtuFarLosDC OBJECT-TYPE
	SYNTAX INTEGER
	{
		none(1),
		alarm(10),
		unknown(254),
		unsupported(255)
	}
	ACCESS read-only
	STATUS mandatory
	DESCRIPTION
		"LOS-D (Framer C) Error State
		 1	None	No Alarm
		 10	Alarm	Alarm present
		 254		Unknown value
		 255		Unsupported variable for addressed device"
	::= { fmroHtuFarEntry 55 }

fmroHtuFarLosDD OBJECT-TYPE
	SYNTAX INTEGER
	{
		none(1),
		alarm(10),
		unknown(254),
		unsupported(255)
	}
	ACCESS read-only
	STATUS mandatory
	DESCRIPTION
		"LOS-D (Framer D) Error State
		 1	None	No Alarm
		 10	Alarm	Alarm present
		 254		Unknown value
		 255		Unsupported variable for addressed device"
	::= { fmroHtuFarEntry 56 }

fmroHtuFarSFP1 OBJECT-TYPE
	SYNTAX INTEGER
	{
		none(1),
		txfault(30),
		invalid(31),
		missing(32),
		unknown(254),
		unsupported(255)
	}
	ACCESS read-only
	STATUS mandatory
	DESCRIPTION
		"Error on first SFP modul
		 1	None		No Alarm
		 30	Tx fault	Transmit laser fault
		 31	Invalid		Invalid SFP modul equipped
		 32	Missing		No SFP modul equipped
		 254			Unknown value
		 255			Unsupported variable for addressed device"
	::= { fmroHtuFarEntry 57 }

fmroHtuFarSFP2 OBJECT-TYPE
	SYNTAX INTEGER
	{
		none(1),
		txfault(30),
		invalid(31),
		missing(32),
		unknown(254),
		unsupported(255)
	}
	ACCESS read-only
	STATUS mandatory
	DESCRIPTION
		"Error on second SFP modul
		 1	None		No Alarm
		 30	Tx fault	Transmit laser fault
		 31	Invalid		Invalid SFP modul equipped
		 32	Missing		No SFP modul equipped
		 254			Unknown value
		 255			Unsupported variable for addressed device"
	::= { fmroHtuFarEntry 58 }

--------------------------------------------------------------------------------  
--	FM-RO	Regenerator
--------------------------------------------------------------------------------  
fmroRegTable OBJECT-TYPE
	SYNTAX SEQUENCE OF FmroRegEntry
	ACCESS not-accessible
	STATUS mandatory
	DESCRIPTION ""
	::= { fmro 4 }

fmroRegEntry OBJECT-TYPE
	SYNTAX FmroRegEntry
	ACCESS not-accessible
	STATUS mandatory
	DESCRIPTION ""
	INDEX { fmroRegPortIndex, fmroRegLinkIndex, fmroRegSectionIndex }
	::= { fmroRegTable 1 }

FmroRegEntry ::=
	SEQUENCE
	{
		fmroRegPortIndex INTEGER,
		fmroRegLinkIndex INTEGER,
		fmroRegSectionIndex INTEGER,
		fmroRegU1L INTEGER,
		fmroRegU2L INTEGER,
		fmroRegU1N INTEGER,
		fmroRegU2N INTEGER,
		fmroRegEquipment1 INTEGER,
		fmroRegEquipment2 INTEGER
	}

fmroRegPortIndex OBJECT-TYPE
	SYNTAX INTEGER
	ACCESS read-only
	STATUS mandatory
	DESCRIPTION
		"This variable addresses the port number of the proxy
		and is used as index for the other elements in the Table"
	::= { fmroRegEntry 1 }

fmroRegLinkIndex OBJECT-TYPE
	SYNTAX INTEGER
	ACCESS read-only
	STATUS mandatory
	DESCRIPTION
		"This variable addresses the slot number of the OMI sub-rack
		and is used as index for the other elements in the Table"
	::= { fmroRegEntry 2 }

fmroRegSectionIndex OBJECT-TYPE
	SYNTAX INTEGER
	{
		sectionA(1),
		sectionB(2)
	}
	ACCESS read-only
	STATUS mandatory
	DESCRIPTION
		"Defines which Section of Regenerators is to be queried.
		Ulaf+ Version 1.0 only supports the first section.
		1	sectionA	First section
		2	sectionB	Second section"
	::= { fmroRegEntry 3 }

fmroRegU1L OBJECT-TYPE
	SYNTAX INTEGER
	{
		none(1),
		ber6(4),
		ber3(5),
		los(9),
		losw(19),
		unknown(254),
		unsupported(255)
	}
	ACCESS read-only
	STATUS mandatory
	DESCRIPTION
		"Regenerator Error on HDSL Path 1 to LT
		 1	None	No Alarm
		 4	BER6	Bit Error Ratio 10^-6
		 5	BER3	Bit Error Ratio 10^-3
		 9	LOS	Loss of Signal
		 19	LOSW	Loss of SDSL synchronistation
		 254		Unknown value
		 255		Unsupported variable for addressed device"
	::= { fmroRegEntry 4 }

fmroRegU2L OBJECT-TYPE
	SYNTAX INTEGER
	{
		none(1),
		ber6(4),
		ber3(5),
		los(9),
		losw(19),
		unknown(254),
		unsupported(255)
	}
	ACCESS read-only
	STATUS mandatory
	DESCRIPTION
		"Regenerator Error on HDSL Path 2 to LT
		 1	None	No Alarm
		 4	BER6	Bit Error Ratio 10^-6
		 5	BER3	Bit Error Ratio 10^-3
		 9	LOS	Loss of Signal
		 19	LOSW	Loss of SDSL synchronistation
		 254		Unknown value
		 255		Unsupported variable for addressed device"
	::= { fmroRegEntry 5 }

fmroRegU1N OBJECT-TYPE
	SYNTAX INTEGER
	{
		none(1),
		ber6(4),
		ber3(5),
		los(9),
		losw(19),
		unknown(254),
		unsupported(255)
	}
	ACCESS read-only
	STATUS mandatory
	DESCRIPTION
		"Regenerator Error on HDSL Path 1 to NT
		 1	None	No Alarm
		 4	BER6	Bit Error Ratio 10^-6
		 5	BER3	Bit Error Ratio 10^-3
		 9	LOS	Loss of Signal
		 19	LOSW	Loss of SDSL synchronistation
		 254		Unknown value
		 255		Unsupported variable for addressed device"
	::= { fmroRegEntry 6 }

fmroRegU2N OBJECT-TYPE
	SYNTAX INTEGER
	{
		none(1),
		ber6(4),
		ber3(5),
		los(9),
		losw(19),
		unknown(254),
		unsupported(255)
	}
	ACCESS read-only
	STATUS mandatory
	DESCRIPTION
		"Regenerator Error on HDSL Path 2 to NT
		 1	None	No Alarm
		 4	BER6	Bit Error Ratio 10^-6
		 5	BER3	Bit Error Ratio 10^-3
		 9	LOS	Loss of Signal
		 19	LOSW	Loss of SDSL synchronistation
		 254		Unknown value
		 255		Unsupported variable for addressed device"
	::= { fmroRegEntry 7 }

fmroRegEquipment1 OBJECT-TYPE
	SYNTAX INTEGER
	{
		none(1),
		alarm(10),
		unknown(254),
		unsupported(255)
	}
	ACCESS read-only
	STATUS mandatory
	DESCRIPTION
		"Equipment Alarm in Regenerator in HDSL Path 1
		 1	None	No Alarm
		 10	Alarm	Equipment Alarm present
		 254		Unknown value
		 255		Unsupported variable for addressed device"
	::= { fmroRegEntry 8 }

fmroRegEquipment2 OBJECT-TYPE
	SYNTAX INTEGER
	{
		none(1),
		alarm(10),
		unknown(254),
		unsupported(255)
	}
	ACCESS read-only
	STATUS mandatory
	DESCRIPTION
		"Equipment Alarm in Regenerator in HDSL Path 2
		 1	None	No Alarm
		 10	Alarm	Equipment Alarm present
		 254		Unknown value
		 255		Unsupported variable for addressed device"
	::= { fmroRegEntry 9 }

--------------------------------------------------------------------------------  
--	FM-RO	Local Led State
--------------------------------------------------------------------------------  
fmroLocalLedStateTable OBJECT-TYPE
	SYNTAX SEQUENCE OF FmroLocalLedStateEntry
	ACCESS not-accessible
	STATUS mandatory
	DESCRIPTION ""
	::= { fmro 5 }
	
fmroLocalLedStateEntry OBJECT-TYPE
	SYNTAX FmroLocalLedStateEntry
	ACCESS not-accessible
	STATUS mandatory
	DESCRIPTION ""
	INDEX { fmroLocalLedStatePortIndex, fmroLocalLedStateLinkIndex }
	::= { fmroLocalLedStateTable 1 }

FmroLocalLedStateEntry ::=
	SEQUENCE
	{
		fmroLocalLedStatePortIndex INTEGER,
		fmroLocalLedStateLinkIndex INTEGER,
		fmroLocalLedState1 INTEGER,
		fmroLocalLedState2 INTEGER,
		fmroLocalLedState3 INTEGER,
		fmroLocalLedState4 INTEGER,
		fmroLocalLedState5 INTEGER,
		fmroLocalLedState6 INTEGER,
		fmroLocalLedState7 INTEGER,
		fmroLocalLedState8 INTEGER,
		fmroLocalLedState9 INTEGER,
		fmroLocalLedState10 INTEGER,
		fmroLocalLedColor1 INTEGER,
		fmroLocalLedColor2 INTEGER,
		fmroLocalLedColor3 INTEGER,
		fmroLocalLedColor4 INTEGER,
		fmroLocalLedColor5 INTEGER,
		fmroLocalLedColor6 INTEGER,
		fmroLocalLedColor7 INTEGER,
		fmroLocalLedColor8 INTEGER,
		fmroLocalLedColor9 INTEGER,
		fmroLocalLedColor10 INTEGER,
		fmroLocalLedState11 INTEGER,
		fmroLocalLedState12 INTEGER,
		fmroLocalLedState13 INTEGER,
		fmroLocalLedState14 INTEGER,
		fmroLocalLedState15 INTEGER,
		fmroLocalLedState16 INTEGER,
		fmroLocalLedState17 INTEGER,
		fmroLocalLedState18 INTEGER,
		fmroLocalLedState19 INTEGER,
		fmroLocalLedState20 INTEGER,
		fmroLocalLedColor11 INTEGER,
		fmroLocalLedColor12 INTEGER,
		fmroLocalLedColor13 INTEGER,
		fmroLocalLedColor14 INTEGER,
		fmroLocalLedColor15 INTEGER,
		fmroLocalLedColor16 INTEGER,
		fmroLocalLedColor17 INTEGER,
		fmroLocalLedColor18 INTEGER,
		fmroLocalLedColor19 INTEGER,
		fmroLocalLedColor20 INTEGER
	}

fmroLocalLedStatePortIndex OBJECT-TYPE
	SYNTAX INTEGER
	ACCESS read-only
	STATUS mandatory
	DESCRIPTION
		"This variable addresses the port number of the proxy
		and is used as index for the other elements in the Table"
	::= { fmroLocalLedStateEntry 1 }

fmroLocalLedStateLinkIndex OBJECT-TYPE
	SYNTAX INTEGER
	ACCESS read-only
	STATUS mandatory
	DESCRIPTION
		"This variable addresses the slot number of the OMI sub-rack
		and is used as index for the other elements in the Table"
	::= { fmroLocalLedStateEntry 2 }

fmroLocalLedState1 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED1 of the device.
		HTU: Loop / Maintenance
		1	Off
		2	On
		3	Blinking pattern 1
		4	Blinking pattern 2
		5	Blinking pattern 3
		6	Blinking pattern 4
		7	Blinking pattern 5"
	::= { fmroLocalLedStateEntry 3 }

fmroLocalLedState2 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED2 of the device.
		HTU: LOS/LFA-U
		1	Off
		2	On
		3	Blinking pattern 1
		4	Blinking pattern 2
		5	Blinking pattern 3
		6	Blinking pattern 4
		7	Blinking pattern 5"
	::= { fmroLocalLedStateEntry 4 }

fmroLocalLedState3 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED3 of the device.
		HTU: LOS/LFA-T
		1	Off
		2	On
		3	Blinking pattern 1
		4	Blinking pattern 2
		5	Blinking pattern 3
		6	Blinking pattern 4
		7	Blinking pattern 5"
	::= { fmroLocalLedStateEntry 5 }

fmroLocalLedState4 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED4 of the device.
		HTU: AIS-U
		1	Off
		2	On
		3	Blinking pattern 1
		4	Blinking pattern 2
		5	Blinking pattern 3
		6	Blinking pattern 4
		7	Blinking pattern 5"
	::= { fmroLocalLedStateEntry 6 }

fmroLocalLedState5 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED5 of the device.
		HTU: BER6-U
		1	Off
		2	On
		3	Blinking pattern 1
		4	Blinking pattern 2
		5	Blinking pattern 3
		6	Blinking pattern 4
		7	Blinking pattern 5"
	::= { fmroLocalLedStateEntry 7 }

fmroLocalLedState6 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED6 of the device.
		HTU: PRA (Desktop only)
		1	Off
		2	On
		3	Blinking pattern 1
		4	Blinking pattern 2
		5	Blinking pattern 3
		6	Blinking pattern 4
		7	Blinking pattern 5"
	::= { fmroLocalLedStateEntry 8 }

fmroLocalLedState7 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED7 of the device.
		HTU: LOA-R (Desktop only)
		1	Off
		2	On
		3	Blinking pattern 1
		4	Blinking pattern 2
		5	Blinking pattern 3
		6	Blinking pattern 4
		7	Blinking pattern 5"
	::= { fmroLocalLedStateEntry 9 }

fmroLocalLedState8 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED8 of the device.
		HTU: LOA-T (Desktop only)
		1	Off
		2	On
		3	Blinking pattern 1
		4	Blinking pattern 2
		5	Blinking pattern 3
		6	Blinking pattern 4
		7	Blinking pattern 5"
	::= { fmroLocalLedStateEntry 10 }

fmroLocalLedState9 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED9 of the device.
		1	Off
		2	On
		3	Blinking pattern 1
		4	Blinking pattern 2
		5	Blinking pattern 3
		6	Blinking pattern 4
		7	Blinking pattern 5"
	::= { fmroLocalLedStateEntry 11 }

fmroLocalLedState10 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED10 of the device.
		1	Off
		2	On
		3	Blinking pattern 1
		4	Blinking pattern 2
		5	Blinking pattern 3
		6	Blinking pattern 4
		7	Blinking pattern 5"
	::= { fmroLocalLedStateEntry 12 }

fmroLocalLedColor1 OBJECT-TYPE
	SYNTAX INTEGER
	{
		ledBlack(1),
		ledYellow(2),
		ledRed(3),
		ledGreen(4),
		unknown(254),
		unsupported(255)
	}
	ACCESS read-only
	STATUS mandatory
	DESCRIPTION
	"Color of LED1 of the device.
	1  LED color is black
	2  LED color is yellow
	3  LED color is red
	4  LED color is green"
	::= { fmroLocalLedStateEntry 13 }

fmroLocalLedColor2 OBJECT-TYPE
   SYNTAX INTEGER
   {
      ledBlack(1),
      ledYellow(2),
      ledRed(3),
      ledGreen(4),
      unknown(254),
      unsupported(255)
   }
   ACCESS read-only
   STATUS mandatory
   DESCRIPTION
      "Color of LED2 of the device.
      1  LED color is black
      2  LED color is yellow
      3  LED color is red
      4  LED color is green"
   ::= { fmroLocalLedStateEntry 14 }

fmroLocalLedColor3 OBJECT-TYPE
   SYNTAX INTEGER
   {
      ledBlack(1),
      ledYellow(2),
      ledRed(3),
      ledGreen(4),
      unknown(254),
      unsupported(255)
   }
   ACCESS read-only
   STATUS mandatory
   DESCRIPTION
      "Color of LED3 of the device.
      1  LED color is black
      2  LED color is yellow
      3  LED color is red
      4  LED color is green"
   ::= { fmroLocalLedStateEntry 15 }

fmroLocalLedColor4 OBJECT-TYPE
   SYNTAX INTEGER
   {
      ledBlack(1),
      ledYellow(2),
      ledRed(3),
      ledGreen(4),
      unknown(254),
      unsupported(255)
   }
   ACCESS read-only
   STATUS mandatory
   DESCRIPTION
      "Color of LED4 of the device.
      1  LED color is black
      2  LED color is yellow
      3  LED color is red
      4  LED color is green"
   ::= { fmroLocalLedStateEntry 16 }

fmroLocalLedColor5 OBJECT-TYPE
   SYNTAX INTEGER
   {
      ledBlack(1),
      ledYellow(2),
      ledRed(3),
      ledGreen(4),
      unknown(254),
      unsupported(255)
   }
   ACCESS read-only
   STATUS mandatory
   DESCRIPTION
      "Color of LED5 of the device.
      1  LED color is black
      2  LED color is yellow
      3  LED color is red
      4  LED color is green"
   ::= { fmroLocalLedStateEntry 17 }

fmroLocalLedColor6 OBJECT-TYPE
   SYNTAX INTEGER
   {
      ledBlack(1),
      ledYellow(2),
      ledRed(3),
      ledGreen(4),
      unknown(254),
      unsupported(255)
   }
   ACCESS read-only
   STATUS mandatory
   DESCRIPTION
      "Color of LED6 of the device.
      1  LED color is black
      2  LED color is yellow
      3  LED color is red
      4  LED color is green"
   ::= { fmroLocalLedStateEntry 18 }

fmroLocalLedColor7 OBJECT-TYPE
   SYNTAX INTEGER
   {
      ledBlack(1),
      ledYellow(2),
      ledRed(3),
      ledGreen(4),
      unknown(254),
      unsupported(255)
   }
   ACCESS read-only
   STATUS mandatory
   DESCRIPTION
      "Color of LED7 of the device.
      1  LED color is black
      2  LED color is yellow
      3  LED color is red
      4  LED color is green"
   ::= { fmroLocalLedStateEntry 19 }

fmroLocalLedColor8 OBJECT-TYPE
   SYNTAX INTEGER
   {
      ledBlack(1),
      ledYellow(2),
      ledRed(3),
      ledGreen(4),
      unknown(254),
      unsupported(255)
   }
   ACCESS read-only
   STATUS mandatory
   DESCRIPTION
      "Color of LED8 of the device.
      1  LED color is black
      2  LED color is yellow
      3  LED color is red
      4  LED color is green"
   ::= { fmroLocalLedStateEntry 20 }

fmroLocalLedColor9 OBJECT-TYPE
   SYNTAX INTEGER
   {
      ledBlack(1),
      ledYellow(2),
      ledRed(3),
      ledGreen(4),
      unknown(254),
      unsupported(255)
   }
   ACCESS read-only
   STATUS mandatory
   DESCRIPTION
      "Color of LED9 of the device.
      1  LED color is black
      2  LED color is yellow
      3  LED color is red
      4  LED color is green"
   ::= { fmroLocalLedStateEntry 21 }

fmroLocalLedColor10 OBJECT-TYPE
   SYNTAX INTEGER
   {
      ledBlack(1),
      ledYellow(2),
      ledRed(3),
      ledGreen(4),
      unknown(254),
      unsupported(255)
   }
   ACCESS read-only
   STATUS mandatory
   DESCRIPTION
      "Color of LED10 of the device.
      1  LED color is black
      2  LED color is yellow
      3  LED color is red
      4  LED color is green"
   ::= { fmroLocalLedStateEntry 22 }

fmroLocalLedState11 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED11 of the device.
		1	Off
		2	On
		3	Blinking pattern 1
		4	Blinking pattern 2
		5	Blinking pattern 3
		6	Blinking pattern 4
		7	Blinking pattern 5"
	::= { fmroLocalLedStateEntry 23 }

fmroLocalLedState12 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED12 of the device.
		1	Off
		2	On
		3	Blinking pattern 1
		4	Blinking pattern 2
		5	Blinking pattern 3
		6	Blinking pattern 4
		7	Blinking pattern 5"
	::= { fmroLocalLedStateEntry 24 }

fmroLocalLedState13 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED13 of the device.
		1	Off
		2	On
		3	Blinking pattern 1
		4	Blinking pattern 2
		5	Blinking pattern 3
		6	Blinking pattern 4
		7	Blinking pattern 5"
	::= { fmroLocalLedStateEntry 25 }

fmroLocalLedState14 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED14 of the device.
		1	Off
		2	On
		3	Blinking pattern 1
		4	Blinking pattern 2
		5	Blinking pattern 3
		6	Blinking pattern 4
		7	Blinking pattern 5"
	::= { fmroLocalLedStateEntry 26 }

fmroLocalLedState15 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED15 of the device.
		1	Off
		2	On
		3	Blinking pattern 1
		4	Blinking pattern 2
		5	Blinking pattern 3
		6	Blinking pattern 4
		7	Blinking pattern 5"
	::= { fmroLocalLedStateEntry 27 }

fmroLocalLedState16 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED16 of the device.
		1	Off
		2	On
		3	Blinking pattern 1
		4	Blinking pattern 2
		5	Blinking pattern 3
		6	Blinking pattern 4
		7	Blinking pattern 5"
	::= { fmroLocalLedStateEntry 28 }

fmroLocalLedState17 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED17 of the device.
		1	Off
		2	On
		3	Blinking pattern 1
		4	Blinking pattern 2
		5	Blinking pattern 3
		6	Blinking pattern 4
		7	Blinking pattern 5"
	::= { fmroLocalLedStateEntry 29 }

fmroLocalLedState18 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED18 of the device.
		1	Off
		2	On
		3	Blinking pattern 1
		4	Blinking pattern 2
		5	Blinking pattern 3
		6	Blinking pattern 4
		7	Blinking pattern 5"
	::= { fmroLocalLedStateEntry 30 }

fmroLocalLedState19 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED19 of the device.
		1	Off
		2	On
		3	Blinking pattern 1
		4	Blinking pattern 2
		5	Blinking pattern 3
		6	Blinking pattern 4
		7	Blinking pattern 5"
	::= { fmroLocalLedStateEntry 31 }

fmroLocalLedState20 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED20 of the device.
		1	Off
		2	On
		3	Blinking pattern 1
		4	Blinking pattern 2
		5	Blinking pattern 3
		6	Blinking pattern 4
		7	Blinking pattern 5"
	::= { fmroLocalLedStateEntry 32 }

fmroLocalLedColor11 OBJECT-TYPE
	SYNTAX INTEGER
	{
		ledBlack(1),
		ledYellow(2),
		ledRed(3),
		ledGreen(4),
		unknown(254),
		unsupported(255)
	}
	ACCESS read-only
	STATUS mandatory
	DESCRIPTION
	"Color of LED11 of the device.
	1  LED color is black
	2  LED color is yellow
	3  LED color is red
	4  LED color is green"
	::= { fmroLocalLedStateEntry 33 }

fmroLocalLedColor12 OBJECT-TYPE
	SYNTAX INTEGER
	{
		ledBlack(1),
		ledYellow(2),
		ledRed(3),
		ledGreen(4),
		unknown(254),
		unsupported(255)
	}
	ACCESS read-only
	STATUS mandatory
	DESCRIPTION
	"Color of LED12 of the device.
	1  LED color is black
	2  LED color is yellow
	3  LED color is red
	4  LED color is green"
	::= { fmroLocalLedStateEntry 34 }

fmroLocalLedColor13 OBJECT-TYPE
	SYNTAX INTEGER
	{
		ledBlack(1),
		ledYellow(2),
		ledRed(3),
		ledGreen(4),
		unknown(254),
		unsupported(255)
	}
	ACCESS read-only
	STATUS mandatory
	DESCRIPTION
	"Color of LED13 of the device.
	1  LED color is black
	2  LED color is yellow
	3  LED color is red
	4  LED color is green"
	::= { fmroLocalLedStateEntry 35 }

fmroLocalLedColor14 OBJECT-TYPE
	SYNTAX INTEGER
	{
		ledBlack(1),
		ledYellow(2),
		ledRed(3),
		ledGreen(4),
		unknown(254),
		unsupported(255)
	}
	ACCESS read-only
	STATUS mandatory
	DESCRIPTION
	"Color of LED14 of the device.
	1  LED color is black
	2  LED color is yellow
	3  LED color is red
	4  LED color is green"
	::= { fmroLocalLedStateEntry 36 }

fmroLocalLedColor15 OBJECT-TYPE
	SYNTAX INTEGER
	{
		ledBlack(1),
		ledYellow(2),
		ledRed(3),
		ledGreen(4),
		unknown(254),
		unsupported(255)
	}
	ACCESS read-only
	STATUS mandatory
	DESCRIPTION
	"Color of LED15 of the device.
	1  LED color is black
	2  LED color is yellow
	3  LED color is red
	4  LED color is green"
	::= { fmroLocalLedStateEntry 37 }

fmroLocalLedColor16 OBJECT-TYPE
	SYNTAX INTEGER
	{
		ledBlack(1),
		ledYellow(2),
		ledRed(3),
		ledGreen(4),
		unknown(254),
		unsupported(255)
	}
	ACCESS read-only
	STATUS mandatory
	DESCRIPTION
	"Color of LED16 of the device.
	1  LED color is black
	2  LED color is yellow
	3  LED color is red
	4  LED color is green"
	::= { fmroLocalLedStateEntry 38 }

fmroLocalLedColor17 OBJECT-TYPE
	SYNTAX INTEGER
	{
		ledBlack(1),
		ledYellow(2),
		ledRed(3),
		ledGreen(4),
		unknown(254),
		unsupported(255)
	}
	ACCESS read-only
	STATUS mandatory
	DESCRIPTION
	"Color of LED17 of the device.
	1  LED color is black
	2  LED color is yellow
	3  LED color is red
	4  LED color is green"
	::= { fmroLocalLedStateEntry 39 }

fmroLocalLedColor18 OBJECT-TYPE
	SYNTAX INTEGER
	{
		ledBlack(1),
		ledYellow(2),
		ledRed(3),
		ledGreen(4),
		unknown(254),
		unsupported(255)
	}
	ACCESS read-only
	STATUS mandatory
	DESCRIPTION
	"Color of LED18 of the device.
	1  LED color is black
	2  LED color is yellow
	3  LED color is red
	4  LED color is green"
	::= { fmroLocalLedStateEntry 40 }

fmroLocalLedColor19 OBJECT-TYPE
	SYNTAX INTEGER
	{
		ledBlack(1),
		ledYellow(2),
		ledRed(3),
		ledGreen(4),
		unknown(254),
		unsupported(255)
	}
	ACCESS read-only
	STATUS mandatory
	DESCRIPTION
	"Color of LED19 of the device.
	1  LED color is black
	2  LED color is yellow
	3  LED color is red
	4  LED color is green"
	::= { fmroLocalLedStateEntry 41 }

fmroLocalLedColor20 OBJECT-TYPE
	SYNTAX INTEGER
	{
		ledBlack(1),
		ledYellow(2),
		ledRed(3),
		ledGreen(4),
		unknown(254),
		unsupported(255)
	}
	ACCESS read-only
	STATUS mandatory
	DESCRIPTION
	"Color of LED20 of the device.
	1  LED color is black
	2  LED color is yellow
	3  LED color is red
	4  LED color is green"
	::= { fmroLocalLedStateEntry 42 }

--------------------------------------------------------------------------------  
--	FM-RO	Far Led State
--------------------------------------------------------------------------------  
fmroFarLedStateTable OBJECT-TYPE
	SYNTAX SEQUENCE OF FmroFarLedStateEntry
	ACCESS not-accessible
	STATUS mandatory
	DESCRIPTION ""
	::= { fmro 6 }

fmroFarLedStateEntry OBJECT-TYPE
	SYNTAX FmroFarLedStateEntry
	ACCESS not-accessible
	STATUS mandatory
	DESCRIPTION ""
	INDEX { fmroFarLedStatePortIndex, fmroFarLedStateLinkIndex }
	::= { fmroFarLedStateTable 1 }

FmroFarLedStateEntry ::=
	SEQUENCE
	{
		fmroFarLedStatePortIndex INTEGER,
		fmroFarLedStateLinkIndex INTEGER,
		fmroFarLedState1 INTEGER,
		fmroFarLedState2 INTEGER,
		fmroFarLedState3 INTEGER,
		fmroFarLedState4 INTEGER,
		fmroFarLedState5 INTEGER,
		fmroFarLedState6 INTEGER,
		fmroFarLedState7 INTEGER,
		fmroFarLedState8 INTEGER,
		fmroFarLedState9 INTEGER,
		fmroFarLedState10 INTEGER,
		fmroFarLedColor1 INTEGER,
		fmroFarLedColor2 INTEGER,
		fmroFarLedColor3 INTEGER,
		fmroFarLedColor4 INTEGER,
		fmroFarLedColor5 INTEGER,
		fmroFarLedColor6 INTEGER,
		fmroFarLedColor7 INTEGER,
		fmroFarLedColor8 INTEGER,
		fmroFarLedColor9 INTEGER,
		fmroFarLedColor10 INTEGER,
		fmroFarLedState11 INTEGER,
		fmroFarLedState12 INTEGER,
		fmroFarLedState13 INTEGER,
		fmroFarLedState14 INTEGER,
		fmroFarLedState15 INTEGER,
		fmroFarLedState16 INTEGER,
		fmroFarLedState17 INTEGER,
		fmroFarLedState18 INTEGER,
		fmroFarLedState19 INTEGER,
		fmroFarLedState20 INTEGER,
		fmroFarLedColor11 INTEGER,
		fmroFarLedColor12 INTEGER,
		fmroFarLedColor13 INTEGER,
		fmroFarLedColor14 INTEGER,
		fmroFarLedColor15 INTEGER,
		fmroFarLedColor16 INTEGER,
		fmroFarLedColor17 INTEGER,
		fmroFarLedColor18 INTEGER,
		fmroFarLedColor19 INTEGER,
		fmroFarLedColor20 INTEGER
	}

fmroFarLedStatePortIndex OBJECT-TYPE
	SYNTAX INTEGER
	ACCESS read-only
	STATUS mandatory
	DESCRIPTION
		"This variable addresses the port number of the proxy
		and is used as index for the other elements in the Table"
	::= { fmroFarLedStateEntry 1 }

fmroFarLedStateLinkIndex OBJECT-TYPE
	SYNTAX INTEGER
	ACCESS read-only
	STATUS mandatory
	DESCRIPTION
		"This variable addresses the slot number of the OMI sub-rack
		and is used as index for the other elements in the Table"
	::= { fmroFarLedStateEntry 2 }

fmroFarLedState1 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED1 of the device.
		HTU: Loop / Maintenance
		1	Off
		2	On
		3	Blinking pattern 1
		4	Blinking pattern 2
		5	Blinking pattern 3
		6	Blinking pattern 4
		7	Blinking pattern 5"
	::= { fmroFarLedStateEntry 3 }

fmroFarLedState2 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED2 of the device.
		HTU: LOS/LFA-U
		1	Off
		2	On
		3	Blinking pattern 1
		4	Blinking pattern 2
		5	Blinking pattern 3
		6	Blinking pattern 4
		7	Blinking pattern 5"
	::= { fmroFarLedStateEntry 4 }

fmroFarLedState3 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED3 of the device.
		HTU: LOS/LFA-T
		1	Off
		2	On
		3	Blinking pattern 1
		4	Blinking pattern 2
		5	Blinking pattern 3
		6	Blinking pattern 4
		7	Blinking pattern 5"
	::= { fmroFarLedStateEntry 5 }

fmroFarLedState4 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED4 of the device.
		HTU: AIS-U
		1	Off
		2	On
		3	Blinking pattern 1
		4	Blinking pattern 2
		5	Blinking pattern 3
		6	Blinking pattern 4
		7	Blinking pattern 5"
	::= { fmroFarLedStateEntry 6 }

fmroFarLedState5 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED5 of the device.
		HTU: BER6-U
		1	Off
		2	On
		3	Blinking pattern 1
		4	Blinking pattern 2
		5	Blinking pattern 3
		6	Blinking pattern 4
		7	Blinking pattern 5"
	::= { fmroFarLedStateEntry 7 }

fmroFarLedState6 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED6 of the device.
		HTU: PRA (Desktop only)
		1	Off
		2	On
		3	Blinking pattern 1
		4	Blinking pattern 2
		5	Blinking pattern 3
		6	Blinking pattern 4
		7	Blinking pattern 5"
	::= { fmroFarLedStateEntry 8 }

fmroFarLedState7 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED7 of the device.
		HTU: LOA-R (Desktop only)
		1	Off
		2	On
		3	Blinking pattern 1
		4	Blinking pattern 2
		5	Blinking pattern 3
		6	Blinking pattern 4
		7	Blinking pattern 5"
	::= { fmroFarLedStateEntry 9 }

fmroFarLedState8 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED8 of the device.
		HTU: LOA-T (Desktop only)
		1	Off
		2	On
		3	Blinking pattern 1
		4	Blinking pattern 2
		5	Blinking pattern 3
		6	Blinking pattern 4
		7	Blinking pattern 5"
	::= { fmroFarLedStateEntry 10 }

fmroFarLedState9 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED9 of the device.
		1	Off
		2	On
		3	Blinking pattern 1
		4	Blinking pattern 2
		5	Blinking pattern 3
		6	Blinking pattern 4
		7	Blinking pattern 5"
	::= { fmroFarLedStateEntry 11 }

fmroFarLedState10 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED10 of the device.
		1	Off
		2	On
		3	Blinking pattern 1
		4	Blinking pattern 2
		5	Blinking pattern 3
		6	Blinking pattern 4
		7	Blinking pattern 5"
	::= { fmroFarLedStateEntry 12 }

fmroFarLedColor1 OBJECT-TYPE
   SYNTAX INTEGER
   {
      ledBlack(1),
      ledYellow(2),
      ledRed(3),
      ledGreen(4),
      unknown(254),
      unsupported(255)
   }
   ACCESS read-only
   STATUS mandatory
   DESCRIPTION
      "Color of LED1 of the device.
      1  LED color is black
      2  LED color is yellow
      3  LED color is red
      4  LED color is green"
   ::= { fmroFarLedStateEntry 13 }

fmroFarLedColor2 OBJECT-TYPE
   SYNTAX INTEGER
   {
      ledBlack(1),
      ledYellow(2),
      ledRed(3),
      ledGreen(4),
      unknown(254),
      unsupported(255)
   }
   ACCESS read-only
   STATUS mandatory
   DESCRIPTION
      "Color of LED2 of the device.
      1  LED color is black
      2  LED color is yellow
      3  LED color is red
      4  LED color is green"
   ::= { fmroFarLedStateEntry 14 }

fmroFarLedColor3 OBJECT-TYPE
   SYNTAX INTEGER
   {
      ledBlack(1),
      ledYellow(2),
      ledRed(3),
      ledGreen(4),
      unknown(254),
      unsupported(255)
   }
   ACCESS read-only
   STATUS mandatory
   DESCRIPTION
      "Color of LED3 of the device.
      1  LED color is black
      2  LED color is yellow
      3  LED color is red
      4  LED color is green"
   ::= { fmroFarLedStateEntry 15 }

fmroFarLedColor4 OBJECT-TYPE
   SYNTAX INTEGER
   {
      ledBlack(1),
      ledYellow(2),
      ledRed(3),
      ledGreen(4),
      unknown(254),
      unsupported(255)
   }
   ACCESS read-only
   STATUS mandatory
   DESCRIPTION
      "Color of LED4 of the device.
      1  LED color is black
      2  LED color is yellow
      3  LED color is red
      4  LED color is green"
   ::= { fmroFarLedStateEntry 16 }

fmroFarLedColor5 OBJECT-TYPE
   SYNTAX INTEGER
   {
      ledBlack(1),
      ledYellow(2),
      ledRed(3),
      ledGreen(4),
      unknown(254),
      unsupported(255)
   }
   ACCESS read-only
   STATUS mandatory
   DESCRIPTION
      "Color of LED5 of the device.
      1  LED color is black
      2  LED color is yellow
      3  LED color is red
      4  LED color is green"
   ::= { fmroFarLedStateEntry 17 }

fmroFarLedColor6 OBJECT-TYPE
   SYNTAX INTEGER
   {
      ledBlack(1),
      ledYellow(2),
      ledRed(3),
      ledGreen(4),
      unknown(254),
      unsupported(255)
   }
   ACCESS read-only
   STATUS mandatory
   DESCRIPTION
      "Color of LED6 of the device.
      1  LED color is black
      2  LED color is yellow
      3  LED color is red
      4  LED color is green"
   ::= { fmroFarLedStateEntry 18 }

fmroFarLedColor7 OBJECT-TYPE
   SYNTAX INTEGER
   {
      ledBlack(1),
      ledYellow(2),
      ledRed(3),
      ledGreen(4),
      unknown(254),
      unsupported(255)
   }
   ACCESS read-only
   STATUS mandatory
   DESCRIPTION
      "Color of LED7 of the device.
      1  LED color is black
      2  LED color is yellow
      3  LED color is red
      4  LED color is green"
   ::= { fmroFarLedStateEntry 19 }

fmroFarLedColor8 OBJECT-TYPE
   SYNTAX INTEGER
   {
      ledBlack(1),
      ledYellow(2),
      ledRed(3),
      ledGreen(4),
      unknown(254),
      unsupported(255)
   }
   ACCESS read-only
   STATUS mandatory
   DESCRIPTION
      "Color of LED8 of the device.
      1  LED color is black
      2  LED color is yellow
      3  LED color is red
      4  LED color is green"
   ::= { fmroFarLedStateEntry 20 }

fmroFarLedColor9 OBJECT-TYPE
   SYNTAX INTEGER
   {
      ledBlack(1),
      ledYellow(2),
      ledRed(3),
      ledGreen(4),
      unknown(254),
      unsupported(255)
   }
   ACCESS read-only
   STATUS mandatory
   DESCRIPTION
      "Color of LED9 of the device.
      1  LED color is black
      2  LED color is yellow
      3  LED color is red
      4  LED color is green"
   ::= { fmroFarLedStateEntry 21 }

fmroFarLedColor10 OBJECT-TYPE
   SYNTAX INTEGER
   {
      ledBlack(1),
      ledYellow(2),
      ledRed(3),
      ledGreen(4),
      unknown(254),
      unsupported(255)
   }
   ACCESS read-only
   STATUS mandatory
   DESCRIPTION
      "Color of LED10 of the device.
      1  LED color is black
      2  LED color is yellow
      3  LED color is red
      4  LED color is green"
   ::= { fmroFarLedStateEntry 22 }

fmroFarLedState11 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED11 of the device.
		1	Off
		2	On
		3	Blinking pattern 1
		4	Blinking pattern 2
		5	Blinking pattern 3
		6	Blinking pattern 4
		7	Blinking pattern 5"
	::= { fmroFarLedStateEntry 23 }

fmroFarLedState12 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED12 of the device.
		1	Off
		2	On
		3	Blinking pattern 1
		4	Blinking pattern 2
		5	Blinking pattern 3
		6	Blinking pattern 4
		7	Blinking pattern 5"
	::= { fmroFarLedStateEntry 24 }

fmroFarLedState13 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED13 of the device.
		1	Off
		2	On
		3	Blinking pattern 1
		4	Blinking pattern 2
		5	Blinking pattern 3
		6	Blinking pattern 4
		7	Blinking pattern 5"
	::= { fmroFarLedStateEntry 25 }

fmroFarLedState14 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED14 of the device.
		1	Off
		2	On
		3	Blinking pattern 1
		4	Blinking pattern 2
		5	Blinking pattern 3
		6	Blinking pattern 4
		7	Blinking pattern 5"
	::= { fmroFarLedStateEntry 26 }

fmroFarLedState15 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED15 of the device.
		1	Off
		2	On
		3	Blinking pattern 1
		4	Blinking pattern 2
		5	Blinking pattern 3
		6	Blinking pattern 4
		7	Blinking pattern 5"
	::= { fmroFarLedStateEntry 27 }

fmroFarLedState16 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED16 of the device.
		1	Off
		2	On
		3	Blinking pattern 1
		4	Blinking pattern 2
		5	Blinking pattern 3
		6	Blinking pattern 4
		7	Blinking pattern 5"
	::= { fmroFarLedStateEntry 28 }

fmroFarLedState17 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED17 of the device.
		1	Off
		2	On
		3	Blinking pattern 1
		4	Blinking pattern 2
		5	Blinking pattern 3
		6	Blinking pattern 4
		7	Blinking pattern 5"
	::= { fmroFarLedStateEntry 29 }

fmroFarLedState18 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED18 of the device.
		1	Off
		2	On
		3	Blinking pattern 1
		4	Blinking pattern 2
		5	Blinking pattern 3
		6	Blinking pattern 4
		7	Blinking pattern 5"
	::= { fmroFarLedStateEntry 30 }

fmroFarLedState19 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED19 of the device.
		1	Off
		2	On
		3	Blinking pattern 1
		4	Blinking pattern 2
		5	Blinking pattern 3
		6	Blinking pattern 4
		7	Blinking pattern 5"
	::= { fmroFarLedStateEntry 31 }

fmroFarLedState20 OBJECT-TYPE
	SYNTAX INTEGER
	{
		ledOff(1),
		ledOn(2),
		ledBlink1(3),
		ledBlink2(4),
		ledBlink3(5),
		ledBlink4(6),
		ledBlink5(7),
		unknown(254),
		unsupported(255)
	}
	ACCESS read-only
	STATUS mandatory
	DESCRIPTION
		"State of LED20 of the device.
		1	Off
		2	On
		3	Blinking pattern 1
		4	Blinking pattern 2
		5	Blinking pattern 3
		6	Blinking pattern 4
		7	Blinking pattern 5"
	::= { fmroFarLedStateEntry 32 }

fmroFarLedColor11 OBJECT-TYPE
	SYNTAX INTEGER
	{
		ledBlack(1),
		ledYellow(2),
		ledRed(3),
		ledGreen(4),
		unknown(254),
		unsupported(255)
	}
	ACCESS read-only
	STATUS mandatory
	DESCRIPTION
	"Color of LED11 of the device.
	1  LED color is black
	2  LED color is yellow
	3  LED color is red
	4  LED color is green"
	::= { fmroFarLedStateEntry 33 }

fmroFarLedColor12 OBJECT-TYPE
	SYNTAX INTEGER
	{
		ledBlack(1),
		ledYellow(2),
		ledRed(3),
		ledGreen(4),
		unknown(254),
		unsupported(255)
	}
	ACCESS read-only
	STATUS mandatory
	DESCRIPTION
	"Color of LED12 of the device.
	1  LED color is black
	2  LED color is yellow
	3  LED color is red
	4  LED color is green"
	::= { fmroFarLedStateEntry 34 }

fmroFarLedColor13 OBJECT-TYPE
	SYNTAX INTEGER
	{
		ledBlack(1),
		ledYellow(2),
		ledRed(3),
		ledGreen(4),
		unknown(254),
		unsupported(255)
	}
	ACCESS read-only
	STATUS mandatory
	DESCRIPTION
	"Color of LED13 of the device.
	1  LED color is black
	2  LED color is yellow
	3  LED color is red
	4  LED color is green"
	::= { fmroFarLedStateEntry 35 }

fmroFarLedColor14 OBJECT-TYPE
	SYNTAX INTEGER
	{
		ledBlack(1),
		ledYellow(2),
		ledRed(3),
		ledGreen(4),
		unknown(254),
		unsupported(255)
	}
	ACCESS read-only
	STATUS mandatory
	DESCRIPTION
	"Color of LED14 of the device.
	1  LED color is black
	2  LED color is yellow
	3  LED color is red
	4  LED color is green"
	::= { fmroFarLedStateEntry 36 }

fmroFarLedColor15 OBJECT-TYPE
	SYNTAX INTEGER
	{
		ledBlack(1),
		ledYellow(2),
		ledRed(3),
		ledGreen(4),
		unknown(254),
		unsupported(255)
	}
	ACCESS read-only
	STATUS mandatory
	DESCRIPTION
	"Color of LED15 of the device.
	1  LED color is black
	2  LED color is yellow
	3  LED color is red
	4  LED color is green"
	::= { fmroFarLedStateEntry 37 }

fmroFarLedColor16 OBJECT-TYPE
	SYNTAX INTEGER
	{
		ledBlack(1),
		ledYellow(2),
		ledRed(3),
		ledGreen(4),
		unknown(254),
		unsupported(255)
	}
	ACCESS read-only
	STATUS mandatory
	DESCRIPTION
	"Color of LED16 of the device.
	1  LED color is black
	2  LED color is yellow
	3  LED color is red
	4  LED color is green"
	::= { fmroFarLedStateEntry 38 }

fmroFarLedColor17 OBJECT-TYPE
	SYNTAX INTEGER
	{
		ledBlack(1),
		ledYellow(2),
		ledRed(3),
		ledGreen(4),
		unknown(254),
		unsupported(255)
	}
	ACCESS read-only
	STATUS mandatory
	DESCRIPTION
	"Color of LED17 of the device.
	1  LED color is black
	2  LED color is yellow
	3  LED color is red
	4  LED color is green"
	::= { fmroFarLedStateEntry 39 }

fmroFarLedColor18 OBJECT-TYPE
	SYNTAX INTEGER
	{
		ledBlack(1),
		ledYellow(2),
		ledRed(3),
		ledGreen(4),
		unknown(254),
		unsupported(255)
	}
	ACCESS read-only
	STATUS mandatory
	DESCRIPTION
	"Color of LED18 of the device.
	1  LED color is black
	2  LED color is yellow
	3  LED color is red
	4  LED color is green"
	::= { fmroFarLedStateEntry 40 }

fmroFarLedColor19 OBJECT-TYPE
	SYNTAX INTEGER
	{
		ledBlack(1),
		ledYellow(2),
		ledRed(3),
		ledGreen(4),
		unknown(254),
		unsupported(255)
	}
	ACCESS read-only
	STATUS mandatory
	DESCRIPTION
	"Color of LED19 of the device.
	1  LED color is black
	2  LED color is yellow
	3  LED color is red
	4  LED color is green"
	::= { fmroFarLedStateEntry 41 }

fmroFarLedColor20 OBJECT-TYPE
	SYNTAX INTEGER
	{
		ledBlack(1),
		ledYellow(2),
		ledRed(3),
		ledGreen(4),
		unknown(254),
		unsupported(255)
	}
	ACCESS read-only
	STATUS mandatory
	DESCRIPTION
	"Color of LED20 of the device.
	1  LED color is black
	2  LED color is yellow
	3  LED color is red
	4  LED color is green"
	::= { fmroFarLedStateEntry 42 }

--------------------------------------------------------------------------------  
--	FM-RO	Omi Led State
--------------------------------------------------------------------------------  
fmroOmiLedStateTable OBJECT-TYPE
	SYNTAX SEQUENCE OF FmroOmiLedStateEntry
	ACCESS not-accessible
	STATUS mandatory
	DESCRIPTION ""
	::= { fmro 7 }
	
fmroOmiLedStateEntry OBJECT-TYPE
	SYNTAX FmroOmiLedStateEntry
	ACCESS not-accessible
	STATUS mandatory
	DESCRIPTION ""
	INDEX { fmroOmiLedStatePortIndex }
	::= { fmroOmiLedStateTable 1 }

FmroOmiLedStateEntry ::=
	SEQUENCE
	{
		fmroOmiLedStatePortIndex INTEGER,
		fmroOmiLedState1 INTEGER,
		fmroOmiLedState2 INTEGER,
		fmroOmiLedState3 INTEGER,
		fmroOmiLedState4 INTEGER,
		fmroOmiLedState5 INTEGER,
		fmroOmiLedState6 INTEGER,
		fmroOmiLedState7 INTEGER,
		fmroOmiLedState8 INTEGER,
		fmroOmiLedState9 INTEGER,
		fmroOmiLedState10 INTEGER,
		fmroOmiLedState11 INTEGER,
		fmroOmiLedState12 INTEGER,
		fmroOmiLedState13 INTEGER,
		fmroOmiLedState14 INTEGER,
		fmroOmiLedState15 INTEGER,
		fmroOmiLedState16 INTEGER,
		fmroOmiLedColor1 INTEGER,
		fmroOmiLedColor2 INTEGER,
		fmroOmiLedColor3 INTEGER,
		fmroOmiLedColor4 INTEGER,
		fmroOmiLedColor5 INTEGER,
		fmroOmiLedColor6 INTEGER,
		fmroOmiLedColor7 INTEGER,
		fmroOmiLedColor8 INTEGER,
		fmroOmiLedColor9 INTEGER,
		fmroOmiLedColor10 INTEGER,
		fmroOmiLedColor11 INTEGER,
		fmroOmiLedColor12 INTEGER,
		fmroOmiLedColor13 INTEGER,
		fmroOmiLedColor14 INTEGER,
		fmroOmiLedColor15 INTEGER,
		fmroOmiLedColor16 INTEGER
	}

fmroOmiLedStatePortIndex OBJECT-TYPE
	SYNTAX INTEGER
	ACCESS read-only
	STATUS mandatory
	DESCRIPTION
		"This variable addresses the port number of the proxy
		and is used as index for the other elements in the Table"
	::= { fmroOmiLedStateEntry 1 }

fmroOmiLedState1 OBJECT-TYPE
	SYNTAX INTEGER
	{
		ledOff(1),
		ledOn(2),
		ledBlink1(3),
		ledBlink2(4),
		ledBlink3(5),
		unknown(254),
		unsupported(255)
	}
	ACCESS read-only
	STATUS mandatory
	DESCRIPTION
		"State of LED1 of the OMI: Urgent Alarm
		1	Off
		2	On
		3	Blinking pattern 1
		3	Blinking pattern 2
		4	Blinking pattern 3"
	::= { fmroOmiLedStateEntry 3 }

fmroOmiLedState2 OBJECT-TYPE
	SYNTAX INTEGER
	{
		ledOff(1),
		ledOn(2),
		ledBlink1(3),
		ledBlink2(4),
		ledBlink3(5),
		unknown(254),
		unsupported(255)
	}
	ACCESS read-only
	STATUS mandatory
	DESCRIPTION
		"State of LED2 of the OMI: Non-Urgent Alarm
		1	Off
		2	On
		3	Blinking pattern 1
		3	Blinking pattern 2
		4	Blinking pattern 3"
	::= { fmroOmiLedStateEntry 4 }

fmroOmiLedState3 OBJECT-TYPE
	SYNTAX INTEGER
	{
		ledOff(1),
		ledOn(2),
		ledBlink1(3),
		ledBlink2(4),
		ledBlink3(5),
		unknown(254),
		unsupported(255)
	}
	ACCESS read-only
	STATUS mandatory
	DESCRIPTION
		"State of LED3 of the OMI: Acknowledged Alarm
		1	Off
		2	On
		3	Blinking pattern 1
		3	Blinking pattern 2
		4	Blinking pattern 3"
	::= { fmroOmiLedStateEntry 5 }

fmroOmiLedState4 OBJECT-TYPE
	SYNTAX INTEGER
	{
		ledOff(1),
		ledOn(2),
		ledBlink1(3),
		ledBlink2(4),
		ledBlink3(5),
		unknown(254),
		unsupported(255)
	}
	ACCESS read-only
	STATUS mandatory
	DESCRIPTION
		"State of LED4 of the OMI
		1	Off
		2	On
		3	Blinking pattern 1
		3	Blinking pattern 2
		4	Blinking pattern 3"
	::= { fmroOmiLedStateEntry 6 }

fmroOmiLedState5 OBJECT-TYPE
	SYNTAX INTEGER
	{
		ledOff(1),
		ledOn(2),
		ledBlink1(3),
		ledBlink2(4),
		ledBlink3(5),
		unknown(254),
		unsupported(255)
	}
	ACCESS read-only
	STATUS mandatory
	DESCRIPTION
		"State of LED5 of the OMI
		1	Off
		2	On
		3	Blinking pattern 1
		3	Blinking pattern 2
		4	Blinking pattern 3"
	::= { fmroOmiLedStateEntry 7 }

fmroOmiLedState6 OBJECT-TYPE
	SYNTAX INTEGER
	{
		ledOff(1),
		ledOn(2),
		ledBlink1(3),
		ledBlink2(4),
		ledBlink3(5),
		unknown(254),
		unsupported(255)
	}
	ACCESS read-only
	STATUS mandatory
	DESCRIPTION
		"State of LED6 of the OMI
		1	Off
		2	On
		3	Blinking pattern 1
		3	Blinking pattern 2
		4	Blinking pattern 3"
	::= { fmroOmiLedStateEntry 8 }

fmroOmiLedState7 OBJECT-TYPE
	SYNTAX INTEGER
	{
		ledOff(1),
		ledOn(2),
		ledBlink1(3),
		ledBlink2(4),
		ledBlink3(5),
		unknown(254),
		unsupported(255)
	}
	ACCESS read-only
	STATUS mandatory
	DESCRIPTION
		"State of LED7 of the OMI
		1	Off
		2	On
		3	Blinking pattern 1
		3	Blinking pattern 2
		4	Blinking pattern 3"
	::= { fmroOmiLedStateEntry 9 }

fmroOmiLedState8 OBJECT-TYPE
	SYNTAX INTEGER
	{
		ledOff(1),
		ledOn(2),
		ledBlink1(3),
		ledBlink2(4),
		ledBlink3(5),
		unknown(254),
		unsupported(255)
	}
	ACCESS read-only
	STATUS mandatory
	DESCRIPTION
		"State of LED8 of the OMI
		1	Off
		2	On
		3	Blinking pattern 1
		3	Blinking pattern 2
		4	Blinking pattern 3"
	::= { fmroOmiLedStateEntry 10 }

fmroOmiLedState9 OBJECT-TYPE
	SYNTAX INTEGER
	{
		ledOff(1),
		ledOn(2),
		ledBlink1(3),
		ledBlink2(4),
		ledBlink3(5),
		unknown(254),
		unsupported(255)
	}
	ACCESS read-only
	STATUS mandatory
	DESCRIPTION
		"State of LED9 of the OMI
		1	Off
		2	On
		3	Blinking pattern 1
		3	Blinking pattern 2
		4	Blinking pattern 3"
	::= { fmroOmiLedStateEntry 11 }

fmroOmiLedState10 OBJECT-TYPE
	SYNTAX INTEGER
	{
		ledOff(1),
		ledOn(2),
		ledBlink1(3),
		ledBlink2(4),
		ledBlink3(5),
		unknown(254),
		unsupported(255)
	}
	ACCESS read-only
	STATUS mandatory
	DESCRIPTION
		"State of LED10 of the OMI
		1	Off
		2	On
		3	Blinking pattern 1
		3	Blinking pattern 2
		4	Blinking pattern 3"
	::= { fmroOmiLedStateEntry 12 }

fmroOmiLedState11 OBJECT-TYPE
	SYNTAX INTEGER
	{
		ledOff(1),
		ledOn(2),
		ledBlink1(3),
		ledBlink2(4),
		ledBlink3(5),
		unknown(254),
		unsupported(255)
	}
	ACCESS read-only
	STATUS mandatory
	DESCRIPTION
		"State of LED11 of the OMI
		1	Off
		2	On
		3	Blinking pattern 1
		3	Blinking pattern 2
		4	Blinking pattern 3"
	::= { fmroOmiLedStateEntry 13 }

fmroOmiLedState12 OBJECT-TYPE
	SYNTAX INTEGER
	{
		ledOff(1),
		ledOn(2),
		ledBlink1(3),
		ledBlink2(4),
		ledBlink3(5),
		unknown(254),
		unsupported(255)
	}
	ACCESS read-only
	STATUS mandatory
	DESCRIPTION
		"State of LED12 of the OMI
		1	Off
		2	On
		3	Blinking pattern 1
		3	Blinking pattern 2
		4	Blinking pattern 3"
	::= { fmroOmiLedStateEntry 14 }

fmroOmiLedState13 OBJECT-TYPE
	SYNTAX INTEGER
	{
		ledOff(1),
		ledOn(2),
		ledBlink1(3),
		ledBlink2(4),
		ledBlink3(5),
		unknown(254),
		unsupported(255)
	}
	ACCESS read-only
	STATUS mandatory
	DESCRIPTION
		"State of LED13 of the OMI
		1	Off
		2	On
		3	Blinking pattern 1
		3	Blinking pattern 2
		4	Blinking pattern 3"
	::= { fmroOmiLedStateEntry 15 }

fmroOmiLedState14 OBJECT-TYPE
	SYNTAX INTEGER
	{
		ledOff(1),
		ledOn(2),
		ledBlink1(3),
		ledBlink2(4),
		ledBlink3(5),
		unknown(254),
		unsupported(255)
	}
	ACCESS read-only
	STATUS mandatory
	DESCRIPTION
		"State of LED14 of the OMI
		1	Off
		2	On
		3	Blinking pattern 1
		3	Blinking pattern 2
		4	Blinking pattern 3"
	::= { fmroOmiLedStateEntry 16 }

fmroOmiLedState15 OBJECT-TYPE
	SYNTAX INTEGER
	{
		ledOff(1),
		ledOn(2),
		ledBlink1(3),
		ledBlink2(4),
		ledBlink3(5),
		unknown(254),
		unsupported(255)
	}
	ACCESS read-only
	STATUS mandatory
	DESCRIPTION
		"State of LED15 of the OMI
		1	Off
		2	On
		3	Blinking pattern 1
		3	Blinking pattern 2
		4	Blinking pattern 3"
	::= { fmroOmiLedStateEntry 17 }

fmroOmiLedState16 OBJECT-TYPE
	SYNTAX INTEGER
	{
		ledOff(1),
		ledOn(2),
		ledBlink1(3),
		ledBlink2(4),
		ledBlink3(5),
		unknown(254),
		unsupported(255)
	}
	ACCESS read-only
	STATUS mandatory
	DESCRIPTION
		"State of LED16 of the OMI
		1	Off
		2	On
		3	Blinking pattern 1
		3	Blinking pattern 2
		4	Blinking pattern 3"
	::= { fmroOmiLedStateEntry 18 }

fmroOmiLedColor1 OBJECT-TYPE
	SYNTAX INTEGER
	{
		ledBlack(1),
		ledYellow(2),
		ledRed(3),
		ledGreen(4),
		unknown(254),
		unsupported(255)
	}
	ACCESS read-only
	STATUS mandatory
	DESCRIPTION
	"Color of LED1 of the device.
	1  LED color is black
	2  LED color is yellow
	3  LED color is red
	4  LED color is green"
	::= { fmroOmiLedStateEntry 19 }

fmroOmiLedColor2 OBJECT-TYPE
	SYNTAX INTEGER
	{
		ledBlack(1),
		ledYellow(2),
		ledRed(3),
		ledGreen(4),
		unknown(254),
		unsupported(255)
	}
	ACCESS read-only
	STATUS mandatory
	DESCRIPTION
	"Color of LED2 of the device.
	1  LED color is black
	2  LED color is yellow
	3  LED color is red
	4  LED color is green"
	::= { fmroOmiLedStateEntry 20 }
fmroOmiLedColor3 OBJECT-TYPE
	SYNTAX INTEGER
	{
		ledBlack(1),
		ledYellow(2),
		ledRed(3),
		ledGreen(4),
		unknown(254),
		unsupported(255)
	}
	ACCESS read-only
	STATUS mandatory
	DESCRIPTION
	"Color of LED3 of the device.
	1  LED color is black
	2  LED color is yellow
	3  LED color is red
	4  LED color is green"
	::= { fmroOmiLedStateEntry 21 }
fmroOmiLedColor4 OBJECT-TYPE
	SYNTAX INTEGER
	{
		ledBlack(1),
		ledYellow(2),
		ledRed(3),
		ledGreen(4),
		unknown(254),
		unsupported(255)
	}
	ACCESS read-only
	STATUS mandatory
	DESCRIPTION
	"Color of LED4 of the device.
	1  LED color is black
	2  LED color is yellow
	3  LED color is red
	4  LED color is green"
	::= { fmroOmiLedStateEntry 22 }
fmroOmiLedColor5 OBJECT-TYPE
	SYNTAX INTEGER
	{
		ledBlack(1),
		ledYellow(2),
		ledRed(3),
		ledGreen(4),
		unknown(254),
		unsupported(255)
	}
	ACCESS read-only
	STATUS mandatory
	DESCRIPTION
	"Color of LED5 of the device.
	1  LED color is black
	2  LED color is yellow
	3  LED color is red
	4  LED color is green"
	::= { fmroOmiLedStateEntry 23 }
fmroOmiLedColor6 OBJECT-TYPE
	SYNTAX INTEGER
	{
		ledBlack(1),
		ledYellow(2),
		ledRed(3),
		ledGreen(4),
		unknown(254),
		unsupported(255)
	}
	ACCESS read-only
	STATUS mandatory
	DESCRIPTION
	"Color of LED6 of the device.
	1  LED color is black
	2  LED color is yellow
	3  LED color is red
	4  LED color is green"
	::= { fmroOmiLedStateEntry 24 }
fmroOmiLedColor7 OBJECT-TYPE
	SYNTAX INTEGER
	{
		ledBlack(1),
		ledYellow(2),
		ledRed(3),
		ledGreen(4),
		unknown(254),
		unsupported(255)
	}
	ACCESS read-only
	STATUS mandatory
	DESCRIPTION
	"Color of LED7 of the device.
	1  LED color is black
	2  LED color is yellow
	3  LED color is red
	4  LED color is green"
	::= { fmroOmiLedStateEntry 25 }
fmroOmiLedColor8 OBJECT-TYPE
	SYNTAX INTEGER
	{
		ledBlack(1),
		ledYellow(2),
		ledRed(3),
		ledGreen(4),
		unknown(254),
		unsupported(255)
	}
	ACCESS read-only
	STATUS mandatory
	DESCRIPTION
	"Color of LED8 of the device.
	1  LED color is black
	2  LED color is yellow
	3  LED color is red
	4  LED color is green"
	::= { fmroOmiLedStateEntry 26 }
fmroOmiLedColor9 OBJECT-TYPE
	SYNTAX INTEGER
	{
		ledBlack(1),
		ledYellow(2),
		ledRed(3),
		ledGreen(4),
		unknown(254),
		unsupported(255)
	}
	ACCESS read-only
	STATUS mandatory
	DESCRIPTION
	"Color of LED9 of the device.
	1  LED color is black
	2  LED color is yellow
	3  LED color is red
	4  LED color is green"
	::= { fmroOmiLedStateEntry 27 }
fmroOmiLedColor10 OBJECT-TYPE
	SYNTAX INTEGER
	{
		ledBlack(1),
		ledYellow(2),
		ledRed(3),
		ledGreen(4),
		unknown(254),
		unsupported(255)
	}
	ACCESS read-only
	STATUS mandatory
	DESCRIPTION
	"Color of LED10 of the device.
	1  LED color is black
	2  LED color is yellow
	3  LED color is red
	4  LED color is green"
	::= { fmroOmiLedStateEntry 28 }
fmroOmiLedColor11 OBJECT-TYPE
	SYNTAX INTEGER
	{
		ledBlack(1),
		ledYellow(2),
		ledRed(3),
		ledGreen(4),
		unknown(254),
		unsupported(255)
	}
	ACCESS read-only
	STATUS mandatory
	DESCRIPTION
	"Color of LED11 of the device.
	1  LED color is black
	2  LED color is yellow
	3  LED color is red
	4  LED color is green"
	::= { fmroOmiLedStateEntry 29 }
fmroOmiLedColor12 OBJECT-TYPE
	SYNTAX INTEGER
	{
		ledBlack(1),
		ledYellow(2),
		ledRed(3),
		ledGreen(4),
		unknown(254),
		unsupported(255)
	}
	ACCESS read-only
	STATUS mandatory
	DESCRIPTION
	"Color of LED12 of the device.
	1  LED color is black
	2  LED color is yellow
	3  LED color is red
	4  LED color is green"
	::= { fmroOmiLedStateEntry 30 }
fmroOmiLedColor13 OBJECT-TYPE
	SYNTAX INTEGER
	{
		ledBlack(1),
		ledYellow(2),
		ledRed(3),
		ledGreen(4),
		unknown(254),
		unsupported(255)
	}
	ACCESS read-only
	STATUS mandatory
	DESCRIPTION
	"Color of LED13 of the device.
	1  LED color is black
	2  LED color is yellow
	3  LED color is red
	4  LED color is green"
	::= { fmroOmiLedStateEntry 31 }
fmroOmiLedColor14 OBJECT-TYPE
	SYNTAX INTEGER
	{
		ledBlack(1),
		ledYellow(2),
		ledRed(3),
		ledGreen(4),
		unknown(254),
		unsupported(255)
	}
	ACCESS read-only
	STATUS mandatory
	DESCRIPTION
	"Color of LED14 of the device.
	1  LED color is black
	2  LED color is yellow
	3  LED color is red
	4  LED color is green"
	::= { fmroOmiLedStateEntry 32 }
fmroOmiLedColor15 OBJECT-TYPE
	SYNTAX INTEGER
	{
		ledBlack(1),
		ledYellow(2),
		ledRed(3),
		ledGreen(4),
		unknown(254),
		unsupported(255)
	}
	ACCESS read-only
	STATUS mandatory
	DESCRIPTION
	"Color of LED15 of the device.
	1  LED color is black
	2  LED color is yellow
	3  LED color is red
	4  LED color is green"
	::= { fmroOmiLedStateEntry 33 }
fmroOmiLedColor16 OBJECT-TYPE
	SYNTAX INTEGER
	{
		ledBlack(1),
		ledYellow(2),
		ledRed(3),
		ledGreen(4),
		unknown(254),
		unsupported(255)
	}
	ACCESS read-only
	STATUS mandatory
	DESCRIPTION
	"Color of LED16 of the device.
	1  LED color is black
	2  LED color is yellow
	3  LED color is red
	4  LED color is green"
	::= { fmroOmiLedStateEntry 34 }


--------------------------------------------------------------------------------
--	FM-RO	Threshold alarms
--------------------------------------------------------------------------------
fmroThresholdTable OBJECT-TYPE
	SYNTAX SEQUENCE OF FmroThresholdEntry
	ACCESS not-accessible
	STATUS mandatory
	DESCRIPTION ""
	::= { fmro 8 }

fmroThresholdEntry OBJECT-TYPE
	SYNTAX FmroThresholdEntry
	ACCESS not-accessible
	STATUS mandatory
	DESCRIPTION ""
	INDEX { fmroThresholdPortIndex, fmroThresholdLinkIndex, fmroThresholdCounterIndex }
	::= { fmroThresholdTable 1 }

FmroThresholdEntry ::=
	SEQUENCE
	{
		fmroThresholdPortIndex INTEGER,
		fmroThresholdLinkIndex INTEGER,
		fmroThresholdCounterIndex INTEGER,
		fmroThresholdAlarms OCTET STRING
	}

fmroThresholdPortIndex OBJECT-TYPE
	SYNTAX INTEGER
	ACCESS read-only
	STATUS mandatory
	DESCRIPTION
		"This variable addresses the port number of the proxy
		and is used as index for the other elements in the Table"
	::= { fmroThresholdEntry 1 }

fmroThresholdLinkIndex OBJECT-TYPE
	SYNTAX INTEGER
	ACCESS read-only
	STATUS mandatory
	DESCRIPTION
		"This variable addresses the slot number of the OMI sub-rack
		and is used as index for the other elements in the Table"
	::= { fmroThresholdEntry 2 }

fmroThresholdCounterIndex OBJECT-TYPE
	SYNTAX INTEGER
	ACCESS read-only
	STATUS mandatory
	DESCRIPTION
		"This variable addresses the performance counter of a link
		and is used as index for the other elements in the Table
		The following values are foreseen:
		5	LT	Wire pair 1	Direction NT
		6	Reg1	Wire pair 1	Direction LT
		7	Reg1	Wire pair 1	Direction NT
		8	NT	Wire pair 1	Direction LT
		9	LT	Wire pair 2	Direction NT
		10	Reg1	Wire pair 2	Direction LT
		11	Reg1	Wire pair 2	Direction NT
		12	NT	Wire pair 2	Direction LT
		15	Reg2	Wire pair 1	Direction LT
		16	Reg2	Wire pair 1	Direction NT
		17	Reg2	Wire pair 2	Direction LT
		18	Reg2	Wire pair 2	Direction NT
		19	Reg3	Wire pair 1	Direction LT
		20	Reg3	Wire pair 1	Direction NT
		21	Reg4	Wire pair 1	Direction LT
		22	Reg4	Wire pair 1	Direction NT
		23	Reg5	Wire pair 1	Direction LT
		24	Reg5	Wire pair 1	Direction NT
		25	Reg6	Wire pair 1	Direction LT
		26	Reg6	Wire pair 1	Direction NT
		27	Reg7	Wire pair 1	Direction LT
		28	Reg7	Wire pair 1	Direction NT
		29	Reg8	Wire pair 1	Direction LT
		30	Reg8	Wire pair 1	Direction NT
		31	Reg3	Wire pair 2	Direction LT
		32	Reg3	Wire pair 2	Direction NT
		33	Reg4	Wire pair 2	Direction LT
		34	Reg4	Wire pair 2	Direction NT
		35	Reg5	Wire pair 2	Direction LT
		36	Reg5	Wire pair 2	Direction NT
		37	Reg6	Wire pair 2	Direction LT
		38	Reg6	Wire pair 2	Direction NT
		39	Reg7	Wire pair 2	Direction LT
		40	Reg7	Wire pair 2	Direction NT
		41	Reg8	Wire pair 2	Direction LT
		42	Reg8	Wire pair 2	Direction NT
		43	Reg1	Wire pair 3	Direction LT
		44	Reg1	Wire pair 3	Direction NT
		45	Reg2	Wire pair 3	Direction LT
		46	Reg2	Wire pair 3	Direction NT
		47	Reg3	Wire pair 3	Direction LT
		48	Reg3	Wire pair 3	Direction NT
		49	Reg4	Wire pair 3	Direction LT
		50	Reg4	Wire pair 3	Direction NT
		51	Reg5	Wire pair 3	Direction LT
		52	Reg5	Wire pair 3	Direction NT
		53	Reg6	Wire pair 3 Direction LT
		54	Reg6	Wire pair 3	Direction NT
		55	Reg7	Wire pair 3	Direction LT
		56	Reg7	Wire pair 3	Direction NT
		57	Reg8	Wire pair 3	Direction LT
		58	Reg8	Wire pair 3	Direction NT
		59	Reg1	Wire pair 4	Direction LT
		60	Reg1	Wire pair 4	Direction NT
		61	Reg2	Wire pair 4	Direction LT
		62	Reg2	Wire pair 4	Direction NT
		63	Reg3	Wire pair 4	Direction LT
		64	Reg3	Wire pair 4	Direction NT
		65	Reg4	Wire pair 4	Direction LT
		66	Reg4	Wire pair 4	Direction NT
		67	Reg5	Wire pair 4	Direction LT
		68	Reg5	Wire pair 4	Direction NT
		69	Reg6	Wire pair 4	Direction LT
		70	Reg6	Wire pair 4	Direction NT
		71	Reg7	Wire pair 4	Direction LT
		72	Reg7	Wire pair 4	Direction NT
		73	Reg8	Wire pair 4	Direction LT
		74	Reg8	Wire pair 4	Direction NT
		75	LT	Wire pair 3	Direction NT
		76	NT	Wire pair 3	Direction LT
		77	LT	Wire pair 4	Direction NT
		78	NT	Wire pair 4	Direction LT"
	::= { fmroThresholdEntry 3 }

fmroThresholdAlarms OBJECT-TYPE
	SYNTAX OCTET STRING(SIZE(2))
	ACCESS read-only
	STATUS mandatory
	DESCRIPTION
		"Indicates whether the Attenuation and SNR Threshold at this
		point has been reached or crossed
		
		Byte 0
			1		None			No Attenuation Threshold Alarm
			10		Att_Alarm	Attenuation Threshold Alarm present
			254					Unknown value
			255					Unsupported variable for addressed device
		Byte 1
			1		None			No SNR Threshold Alarm
			10		Snr_Alarm	SNR Threshold Alarm present
			254					Unknown value
			255					Unsupported variable for addressed device"
	::= { fmroThresholdEntry 4 }

--------------------------------------------------------------------------------
--	FM-RO	Detail Alarms
--------------------------------------------------------------------------------
fmroAlarmLogTable OBJECT-TYPE
	SYNTAX SEQUENCE OF FmroAlarmLogEntry
	ACCESS not-accessible
	STATUS mandatory
	DESCRIPTION ""
	::= { fmro 9 }

fmroAlarmLogEntry OBJECT-TYPE
	SYNTAX FmroAlarmLogEntry
	ACCESS not-accessible
	STATUS mandatory
	DESCRIPTION ""
	INDEX { fmroAlarmLogPortIndex, fmroAlarmLogLinkIndex, fmroAlarmLogBlockIndex }
	::= { fmroAlarmLogTable 1 }

FmroAlarmLogEntry ::=
	SEQUENCE
	{
		fmroAlarmLogPortIndex INTEGER,
		fmroAlarmLogLinkIndex INTEGER,
		fmroAlarmLogBlockIndex INTEGER,
		fmroAlarmLogLatestDataFieldNumber INTEGER,
		fmroAlarmLogCurrentTime INTEGER,
		fmroAlarmLogInformation OCTET STRING
	}

fmroAlarmLogPortIndex OBJECT-TYPE
	SYNTAX INTEGER
	ACCESS read-only
	STATUS mandatory
	DESCRIPTION
		"This variable addresses the port number of the proxy
		and is used as index for the other elements in the Table"
	::= { fmroAlarmLogEntry 1 }

fmroAlarmLogLinkIndex OBJECT-TYPE
	SYNTAX INTEGER
	ACCESS read-only
	STATUS mandatory
	DESCRIPTION
		"This variable addresses the slot number of the OMI sub-rack
		and is used as index for the other elements in the Table"
	::= { fmroAlarmLogEntry 2 }

fmroAlarmLogBlockIndex OBJECT-TYPE
	SYNTAX INTEGER (1..4)
	ACCESS read-only
	STATUS mandatory
	DESCRIPTION
		"This variable addresses the alarm log block number of a link
		and is used as index for the other elements in the Table
		Foreseen values are:
		1	Alarm Log Entries 1..25
		2	Alarm Log Entries 26..50
		3	Alarm Log Entries 51..75
		4	Alarm Log Entries 76..100"
	::= { fmroAlarmLogEntry 3 }

fmroAlarmLogLatestDataFieldNumber OBJECT-TYPE
	SYNTAX INTEGER (1..100)
	ACCESS read-only
	STATUS mandatory
	DESCRIPTION
		"This variable addresses the latest alarm log entry
		 254		Unknown value
		 255		Unsupported variable for addressed device"
	::= { fmroAlarmLogEntry 4 }

fmroAlarmLogCurrentTime OBJECT-TYPE
	SYNTAX INTEGER
	ACCESS read-only
	STATUS mandatory
	DESCRIPTION
		"This variable contains the current time in seconds since power up
		 0xfffffffe	Unknown value
		 0xffffffff	Unsupported variable for addressed device"
	::= { fmroAlarmLogEntry 5 }

fmroAlarmLogInformation OBJECT-TYPE
	SYNTAX OCTET STRING(SIZE(176))
	ACCESS read-only
	STATUS mandatory
	DESCRIPTION
		"Contains the alarm log entries in blocks of 25 entries where
		each entry is 7 bytes long. Each entry has the following format:
		Byte(s)	Range	Content
		1..4		Event time in seconds since power up
		5	0..21	Interface at which the event occurred
		6	0..18	Error which occurred at the interface
		7		Event Details
		
		The interfaces are coded as follows:
		 0	U1			Transmission Interface Wire pair 1
		 1	U2			Transmission Interface Wire pair 2
		 2	U			Transmission Interface
		 3	T			G.703 Interface
		 4	DC			Data Interface Direction Customer
		 5	DN			Data Interface Direction Network
		 6				Equipment
		 7	LOSD
		 8	T4OUT			Loss of Signal for clock output
		 9	T3IN			Loss of Signal for clock input
		10	RPS			Remote Power Supply
		11	RTA	
		12				Powerfail
		13		
		14	REG1UL			Regenerator on wire pair 1, direction LT
		15	REG2UL			Regenerator on wire pair 2, direction LT
		16	REG1UN			Regenerator on wire pair 1, direction NT
		17	REG2UN			Regenerator on wire pair 2, direction NT
		18	REG1E			Regenerator on wire pair 1
		19	REG2E			Regenerator on wire pair 2
		20	LASER			Laser ageing on OTU
		21				Powerfail CPE
		22	THRES_ATT		Attenuation Threshold Alarm
		23	THRES_ATT_REG_U1L	Attenuation Threshold Alarm at the Regenerator on wire pair 1, direction LT
		24	THRES_ATT_REG_U2L	Attenuation Threshold Alarm at the Regenerator on wire pair 2, direction LT
		25	THRES_ATT_REG_U1N	Attenuation Threshold Alarm at the Regenerator on wire pair 1, direction NT
		26	THRES_ATT_REG_U2N	Attenuation Threshold Alarm at the Regenerator on wire pair 2, direction NT
		27	THRES_SNR		SNR Threshold Alarm
		28	THRES_SNR_REG_U1L	SNR Threshold Alarm at the Regenerator on wire pair 1, direction LT
		29	THRES_SNR_REG_U2L	SNR Threshold Alarm at the Regenerator on wire pair 2, direction LT
		30	THRES_SNR_REG_U1N	SNR Threshold Alarm at the Regenerator on wire pair 1, direction NT
		31	THRES_SNR_REG_U2N	SNR Threshold Alarm at the Regenerator on wire pair 2, direction NT
		32	U3			Transmission Interface Wire pair 3
		33	U4			Transmission Interface Wire pair 4
		34	RPS2			Remote Power Supply on wire pair 2
		35	RPS3			Remote Power Supply on wire pair 3
		36	RPS4			Remote Power Supply on wire pair 4
		37	REG3UL			Regenerator on wire pair 3, direction LT
		38	REG4UL			Regenerator on wire pair 4, direction LT
		39	REG3UN			Regenerator on wire pair 3, direction NT
		40	REG4UN			Regenerator on wire pair 4, direction NT
		41	REG3E			Regenerator on wire pair 3
		42	REG4E			Regenerator on wire pair 4
		43	THRES_ATT1		Attenuation Threshold Alarm on wire pair 1
		44	THRES_ATT2		Attenuation Threshold Alarm on wire pair 2
		45	THRES_ATT3		Attenuation Threshold Alarm on wire pair 3
		46	THRES_ATT4		Attenuation Threshold Alarm on wire pair 4
		47	THRES_ATT_REG_U3L	Attenuation Threshold Alarm at the Regenerator on wire pair 3, direction LT
		48	THRES_ATT_REG_U4L	Attenuation Threshold Alarm at the Regenerator on wire pair 4, direction LT
		49	THRES_ATT_REG_U3N	Attenuation Threshold Alarm at the Regenerator on wire pair 3, direction NT
		50	THRES_ATT_REG_U4N	Attenuation Threshold Alarm at the Regenerator on wire pair 4, direction NT
		51	THRES_SNR1		SNR Threshold Alarm on wire pair 1
		52	THRES_SNR2		SNR Threshold Alarm on wire pair 2
		53	THRES_SNR3		SNR Threshold Alarm on wire pair 3
		54	THRES_SNR4		SNR Threshold Alarm on wire pair 4
		55	THRES_SNR_REG_U3L	SNR Threshold Alarm at the Regenerator on wire pair 3, direction LT
		56	THRES_SNR_REG_U4L	SNR Threshold Alarm at the Regenerator on wire pair 4, direction LT
		57	THRES_SNR_REG_U3N	SNR Threshold Alarm at the Regenerator on wire pair 3, direction NT
		58	THRES_SNR_REG_U4N	SNR Threshold Alarm at the Regenerator on wire pair 4, direction NT
		59	V_SL			V-Interface on the slave device
		60	T_SL			T-Interface on the slave device
		61	DC_SL			Data Interface Direction Customer on the slave device
		62	DN_SL			Data Interface Direction Network on the slave device
		63	VA			VA Interface
		64	VB			VB Interface
		65	VC			VC Interface
		66	VD			VD Interface
		67	MCSa			MCS channel a
		68	MCSb			MCS channel b
		69	MCSc			MCS channel c
		70	MCSd			MCS channel d
		71	MCSa_FarEnd		MCS channel a, far end
		72	MCSb_FarEnd		MCS channel b, far end
		73	MCSc_FarEnd		MCS channel c, far end
		74	MCSd_FarEnd		MCS channel d, far end
		75	MCS			MCS
		76	WAN_RX			WAN Rx
		77	WAN_TX			WAN Tx
		78	ETH_P1			Ethernet Port 1
		79	ETH_P2			Ethernet Port 2
		80	ETH_P3			Ethernet Port 3
		81	ETH_P4			Ethernet Port 4
		82	EXT_AL_1		External Alarm 1
		83	EXT_AL_2		External Alarm 2
		84	EXT_AL_3		External Alarm 3

		The Errors which can occur are coded as follows:
		 0	NONE	No alarm
		 1	HPO	Half partial operation
		 2	FPO	Full partial operation
		 3	BER6	Bit error ratio 10^-6
		 4	BER3	Bit error ratio 10^-3
		 5	LOA	Loss of activity
		 6	AIS	Alarm indication signal
		 7	LFA	Loss of frame alignment
		 8	LOS	Loss of signal
		 9	AON	Alarm
		10	RAI	Remote alarm indication
		11	UCR12	Undercurrent on wire pair 1 & 2
		12	UCR1	Undercurrent on wire pair 1
		13	UCR2	Undercurrent on wire pair 2
		14	OVR	Overload
		15	NOSYM	Asymmetry
		16	DEFECT	
		17	BNA	Bandwidth not available
		18	LOSW	Loss of Synchronisation
		
		The Event Details are bit coded as follows:
		Bit	Value	Content
		0..1	  0	Non-Urgent Alarm
			  1	Urgent Alarm
			  2	No Alarm
			  3	No Alarm
			  
		2	  4	-
		
		3	  8	LT/NT Alaem (clear) / Reg Alarm (set)
		
		4..6	 	If Bit 3 is set
			 000	Regenerator Section 1
			 001	Regenerator Section 2
			 010	Regenerator Section 3
			 011	Regenerator Section 4
			 100	Regenerator Section 5
			 101	Regenerator Section 6
			 110	Regenerator Section 7
			 111	Regenerator Section 8
			 
		7		If Bit 3 is clear
			128	LT (clear) / NT (set)

		Byte 176 contains a value specifying the validity of the
		result of a read operation:
		1	Ok	Values returned are valid
		254		unknown values
		255		unsupported variable for addressed device"
	::= { fmroAlarmLogEntry 6 }

--------------------------------------------------------------------------------  
--	FM-RO	SRU
--------------------------------------------------------------------------------  
fmroSruTable OBJECT-TYPE
	SYNTAX SEQUENCE OF FmroSruEntry
	ACCESS not-accessible
	STATUS mandatory
	DESCRIPTION ""
	::= { fmro 10 }

fmroSruEntry OBJECT-TYPE
	SYNTAX FmroSruEntry
	ACCESS not-accessible
	STATUS mandatory
	DESCRIPTION ""
	INDEX { fmroSruPortIndex, fmroSruLinkIndex, fmroSruSectionIndex }
	::= { fmroSruTable 1 }

FmroSruEntry ::=
	SEQUENCE
	{
		fmroSruPortIndex INTEGER,
		fmroSruLinkIndex INTEGER,
		fmroSruSectionIndex INTEGER,
		fmroSruU1L INTEGER,
		fmroSruU2L INTEGER,
		fmroSruU1N INTEGER,
		fmroSruU2N INTEGER,
		fmroSruEquipment1 INTEGER,
		fmroSruEquipment2 INTEGER,
		fmroSruU3L INTEGER,
		fmroSruU4L INTEGER,
		fmroSruU3N INTEGER,
		fmroSruU4N INTEGER,
		fmroSruEquipment3 INTEGER,
		fmroSruEquipment4 INTEGER
	}

fmroSruPortIndex OBJECT-TYPE
	SYNTAX INTEGER
	ACCESS read-only
	STATUS mandatory
	DESCRIPTION
		"This variable addresses the port number of the proxy
		and is used as index for the other elements in the Table"
	::= { fmroSruEntry 1 }

fmroSruLinkIndex OBJECT-TYPE
	SYNTAX INTEGER
	ACCESS read-only
	STATUS mandatory
	DESCRIPTION
		"This variable addresses the slot number of the OMI sub-rack
		and is used as index for the other elements in the Table"
	::= { fmroSruEntry 2 }

fmroSruSectionIndex OBJECT-TYPE
	SYNTAX INTEGER
	{
		section1(1),
		section2(2),
		section3(3),
		section4(4),
		section5(5),
		section6(6),
		section7(7),
		section8(8)
	}
	ACCESS read-only
	STATUS mandatory
	DESCRIPTION
		"Defines which Section of Regenerators is to be queried.
		Ulaf+ Version 1.0 only supports the first section.
		1	section1	First section
		2	section2	Second section
		3	section3	Third section
		4	section4	Fourth section
		5	section5	Fifth section
		6	section6	Sixth section
		7	section7	Seventh section
		8	section8	Eighth section"
	::= { fmroSruEntry 3 }

fmroSruU1L OBJECT-TYPE
	SYNTAX INTEGER
	{
		none(1),
		ber6(4),
		ber3(5),
		los(9),
		losw(19),
		unknown(254),
		unsupported(255)
	}
	ACCESS read-only
	STATUS mandatory
	DESCRIPTION
		"Regenerator Error on SHDSL Path 1 to LT
		 1	None	No Alarm
		 4	BER6	Bit Error Ratio 10^-6
		 5	BER3	Bit Error Ratio 10^-3
		 9	LOS	Loss of Signal
		 19	LOSW	Loss of SHDSL synchronistation
		 254		Unknown value
		 255		Unsupported variable for addressed device"
	::= { fmroSruEntry 4 }

fmroSruU2L OBJECT-TYPE
	SYNTAX INTEGER
	{
		none(1),
		ber6(4),
		ber3(5),
		los(9),
		losw(19),
		unknown(254),
		unsupported(255)
	}
	ACCESS read-only
	STATUS mandatory
	DESCRIPTION
		"Regenerator Error on SHDSL Path 2 to LT
		 1	None	No Alarm
		 4	BER6	Bit Error Ratio 10^-6
		 5	BER3	Bit Error Ratio 10^-3
		 9	LOS	Loss of Signal
		 19	LOSW	Loss of SHDSL synchronistation
		 254		Unknown value
		 255		Unsupported variable for addressed device"
	::= { fmroSruEntry 5 }

fmroSruU1N OBJECT-TYPE
	SYNTAX INTEGER
	{
		none(1),
		ber6(4),
		ber3(5),
		los(9),
		losw(19),
		unknown(254),
		unsupported(255)
	}
	ACCESS read-only
	STATUS mandatory
	DESCRIPTION
		"Regenerator Error on SHDSL Path 1 to NT
		 1	None	No Alarm
		 4	BER6	Bit Error Ratio 10^-6
		 5	BER3	Bit Error Ratio 10^-3
		 9	LOS	Loss of Signal
		 19	LOSW	Loss of SHDSL synchronistation
		 254		Unknown value
		 255		Unsupported variable for addressed device"
	::= { fmroSruEntry 6 }

fmroSruU2N OBJECT-TYPE
	SYNTAX INTEGER
	{
		none(1),
		ber6(4),
		ber3(5),
		los(9),
		losw(19),
		unknown(254),
		unsupported(255)
	}
	ACCESS read-only
	STATUS mandatory
	DESCRIPTION
		"Regenerator Error on SHDSL Path 2 to NT
		 1	None	No Alarm
		 4	BER6	Bit Error Ratio 10^-6
		 5	BER3	Bit Error Ratio 10^-3
		 9	LOS	Loss of Signal
		 19	LOSW	Loss of SHDSL synchronistation
		 254		Unknown value
		 255		Unsupported variable for addressed device"
	::= { fmroSruEntry 7 }

fmroSruEquipment1 OBJECT-TYPE
	SYNTAX INTEGER
	{
		none(1),
		alarm(10),
		unknown(254),
		unsupported(255)
	}
	ACCESS read-only
	STATUS mandatory
	DESCRIPTION
		"Equipment Alarm in Regenerator in SHDSL Path 1
		 1	None	No Alarm
		 10	Alarm	Equipment Alarm present
		 254		Unknown value
		 255		Unsupported variable for addressed device"
	::= { fmroSruEntry 8 }

fmroSruEquipment2 OBJECT-TYPE
	SYNTAX INTEGER
	{
		none(1),
		alarm(10),
		unknown(254),
		unsupported(255)
	}
	ACCESS read-only
	STATUS mandatory
	DESCRIPTION
		"Equipment Alarm in Regenerator in SHDSL Path 2
		 1	None	No Alarm
		 10	Alarm	Equipment Alarm present
		 254		Unknown value
		 255		Unsupported variable for addressed device"
	::= { fmroSruEntry 9 }

fmroSruU3L OBJECT-TYPE
	SYNTAX INTEGER
	{
		none(1),
		ber6(4),
		ber3(5),
		los(9),
		losw(19),
		unknown(254),
		unsupported(255)
	}
	ACCESS read-only
	STATUS mandatory
	DESCRIPTION
		"Regenerator Error on xDSL Path 3 to LT
		 1	None	No Alarm
		 4	BER6	Bit Error Ratio 10^-6
		 5	BER3	Bit Error Ratio 10^-3
		 9	LOS	Loss of Signal
		 19	LOSW	Loss of SDSL synchronistation
		 254		Unknown value
		 255		Unsupported variable for addressed device"
	::= { fmroSruEntry 10 }

fmroSruU4L OBJECT-TYPE
	SYNTAX INTEGER
	{
		none(1),
		ber6(4),
		ber3(5),
		los(9),
		losw(19),
		unknown(254),
		unsupported(255)
	}
	ACCESS read-only
	STATUS mandatory
	DESCRIPTION
		"Regenerator Error on xDSL Path 4 to LT
		 1	None	No Alarm
		 4	BER6	Bit Error Ratio 10^-6
		 5	BER3	Bit Error Ratio 10^-3
		 9	LOS	Loss of Signal
		 19	LOSW	Loss of SDSL synchronistation
		 254		Unknown value
		 255		Unsupported variable for addressed device"
	::= { fmroSruEntry 11 }

fmroSruU3N OBJECT-TYPE
	SYNTAX INTEGER
	{
		none(1),
		ber6(4),
		ber3(5),
		los(9),
		losw(19),
		unknown(254),
		unsupported(255)
	}
	ACCESS read-only
	STATUS mandatory
	DESCRIPTION
		"Regenerator Error on xDSL Path 3 to NT
		 1	None	No Alarm
		 4	BER6	Bit Error Ratio 10^-6
		 5	BER3	Bit Error Ratio 10^-3
		 9	LOS	Loss of Signal
		 19	LOSW	Loss of SDSL synchronistation
		 254		Unknown value
		 255		Unsupported variable for addressed device"
	::= { fmroSruEntry 12 }

fmroSruU4N OBJECT-TYPE
	SYNTAX INTEGER
	{
		none(1),
		ber6(4),
		ber3(5),
		los(9),
		losw(19),
		unknown(254),
		unsupported(255)
	}
	ACCESS read-only
	STATUS mandatory
	DESCRIPTION
		"Regenerator Error on xDSL Path 4 to NT
		 1	None	No Alarm
		 4	BER6	Bit Error Ratio 10^-6
		 5	BER3	Bit Error Ratio 10^-3
		 9	LOS	Loss of Signal
		 19	LOSW	Loss of SDSL synchronistation
		 254		Unknown value
		 255		Unsupported variable for addressed device"
	::= { fmroSruEntry 13 }

fmroSruEquipment3 OBJECT-TYPE
	SYNTAX INTEGER
	{
		none(1),
		alarm(10),
		unknown(254),
		unsupported(255)
	}
	ACCESS read-only
	STATUS mandatory
	DESCRIPTION
		"Equipment Alarm in Regenerator in xDSL Path 3
		 1	None	No Alarm
		 10	Alarm	Equipment Alarm present
		 254		Unknown value
		 255		Unsupported variable for addressed device"
	::= { fmroSruEntry 14 }

fmroSruEquipment4 OBJECT-TYPE
	SYNTAX INTEGER
	{
		none(1),
		alarm(10),
		unknown(254),
		unsupported(255)
	}
	ACCESS read-only
	STATUS mandatory
	DESCRIPTION
		"Equipment Alarm in Regenerator in xDSL Path 4
		 1	None	No Alarm
		 10	Alarm	Equipment Alarm present
		 254		Unknown value
		 255		Unsupported variable for addressed device"
	::= { fmroSruEntry 15 }

--------------------------------------------------------------------------------  
--	FM-RO	CES PW
--------------------------------------------------------------------------------  
fmroCesPwTable OBJECT-TYPE
	SYNTAX SEQUENCE OF FmroCesPwEntry
	ACCESS not-accessible
	STATUS mandatory
	DESCRIPTION ""
	::= { fmro 11 }

fmroCesPwEntry OBJECT-TYPE
	SYNTAX FmroCesPwEntry
	ACCESS not-accessible
	STATUS mandatory
	DESCRIPTION ""
	INDEX { fmroCesPwPortIndex, fmroCesPwLinkIndex, fmroCesPwIndex }
	::= { fmroCesPwTable 1 }

FmroCesPwEntry ::=
	SEQUENCE
	{
		fmroCesPwPortIndex INTEGER,
		fmroCesPwLinkIndex INTEGER,
		fmroCesPwIndex INTEGER,
		fmroCesPwTdm INTEGER,
		fmroCesPwEth INTEGER
	}

fmroCesPwPortIndex OBJECT-TYPE
	SYNTAX INTEGER
	ACCESS read-only
	STATUS mandatory
	DESCRIPTION
		"This variable addresses the port number of the proxy
		and is used as index for the other elements in the Table"
	::= { fmroCesPwEntry 1 }

fmroCesPwLinkIndex OBJECT-TYPE
	SYNTAX INTEGER
	ACCESS read-only
	STATUS mandatory
	DESCRIPTION
		"This variable addresses the slot number of the sub-rack
		and is used as index for the other elements in the Table"
	::= { fmroCesPwEntry 2 }

fmroCesPwIndex OBJECT-TYPE
	SYNTAX INTEGER
	ACCESS read-only
	STATUS mandatory
	DESCRIPTION
		"This variable addresses the pseudo wire"
	::= { fmroCesPwEntry 3 }

fmroCesPwTdm OBJECT-TYPE
	SYNTAX INTEGER
	{
		none(1),
		ais(7),
		los(9),
		unknown(254),
		unsupported(255)
	}
	ACCESS read-only
	STATUS mandatory
	DESCRIPTION
		"Alarm on TDM interface of given pseudo wire:
		 1	None	No Alarm
		 7	AIS	Alarm Indication Signal
		 9	LOS	Loss of Signal
		 254		Unknown value
		 255		Unsupported variable for addressed device"
	::= { fmroCesPwEntry 4 }

fmroCesPwEth OBJECT-TYPE
	SYNTAX INTEGER
	{
		none(1),
		ais(7),
		rai(11),
		are(33),
		lof(34),
		unknown(254),
		unsupported(255)
	}
	ACCESS read-only
	STATUS mandatory
	DESCRIPTION
		"Alarm on Ethernet interface of given pseudo wire:
		 1	None	No Alarm
		 7	AIS	Alarm Indication Signal
		 11	RAI	Remote	Alarm Indication
		 33	ARE	Address Resolution Error (no MAC address resolved)
		 34	LOF	Loss of Frames
		 254		Unknown value
		 255		Unsupported variable for addressed device"
	::= { fmroCesPwEntry 5 }

--------------------------------------------------------------------------------  
--	FM-RO	CES
--------------------------------------------------------------------------------  
fmroCesTable OBJECT-TYPE
	SYNTAX SEQUENCE OF FmroCesEntry
	ACCESS not-accessible
	STATUS mandatory
	DESCRIPTION ""
	::= { fmro 12 }

fmroCesEntry OBJECT-TYPE
	SYNTAX FmroCesEntry
	ACCESS not-accessible
	STATUS mandatory
	DESCRIPTION ""
	INDEX { fmroCesPortIndex, fmroCesLinkIndex }
	::= { fmroCesTable 1 }

FmroCesEntry ::=
	SEQUENCE
	{
		fmroCesPortIndex INTEGER,
		fmroCesLinkIndex INTEGER,
		fmroCesClockIn INTEGER
	}

fmroCesPortIndex OBJECT-TYPE
	SYNTAX INTEGER
	ACCESS read-only
	STATUS mandatory
	DESCRIPTION
		"This variable addresses the port number of the proxy
		and is used as index for the other elements in the Table"
	::= { fmroCesEntry 1 }

fmroCesLinkIndex OBJECT-TYPE
	SYNTAX INTEGER
	ACCESS read-only
	STATUS mandatory
	DESCRIPTION
		"This variable addresses the slot number of the sub-rack
		and is used as index for the other elements in the Table"
	::= { fmroCesEntry 2 }

fmroCesClockIn OBJECT-TYPE
	SYNTAX INTEGER
	{
		none(1),
		los(9),
		unknown(254),
		unsupported(255)
	}
	ACCESS read-only
	STATUS mandatory
	DESCRIPTION
		"Alarm on the CES clock in interface:
		 1	None	No Alarm
		 9	LOS	Loss of Signal
		 254		Unknown value
		 255		Unsupported variable for addressed device"
	::= { fmroCesEntry 3 }

--==============================================================================
--==============================================================================
--
--      FM-RW
--
--==============================================================================
--==============================================================================
	fmrw	OBJECT IDENTIFIER ::= { linksVers3 4 }

--------------------------------------------------------------------------------
--	FM-RW	Sub-sections
--------------------------------------------------------------------------------
	fmrwLoop		OBJECT IDENTIFIER ::= { fmrw 1 }
	fmrwMask		OBJECT IDENTIFIER ::= { fmrw 2 }
	fmrwTrap		OBJECT IDENTIFIER ::= { fmrw 3 }
-- next line defined below
--	fmrwThresholdTable	OBJECT IDENTIFIER ::= { fmrw 4 }
--
	fmrwActions		OBJECT IDENTIFIER ::= { fmrw 5 }
	fmrwConfig		OBJECT IDENTIFIER ::= { fmrw 6 }

--------------------------------------------------------------------------------
--	FM-RW	Loops local
--------------------------------------------------------------------------------
fmrwLoopLocalTable OBJECT-TYPE
	SYNTAX SEQUENCE OF FmrwLoopLocalEntry
	ACCESS not-accessible
	STATUS mandatory
	DESCRIPTION ""
	::= { fmrwLoop 1 }

fmrwLoopLocalEntry OBJECT-TYPE
	SYNTAX FmrwLoopLocalEntry
	ACCESS not-accessible
	STATUS mandatory
	DESCRIPTION ""
	INDEX { fmrwLoopLocalPortIndex, fmrwLoopLocalLinkIndex }
	::= { fmrwLoopLocalTable 1 }

FmrwLoopLocalEntry ::= 
	SEQUENCE
	{
		fmrwLoopLocalPortIndex INTEGER,
		fmrwLoopLocalLinkIndex INTEGER,
		fmrwLoopLocalLoop3a INTEGER,
		fmrwLoopLocalLoop2b INTEGER,
		fmrwLoopLocalLoop3c INTEGER,
		fmrwLoopLocalLoopReg1A INTEGER,
		fmrwLoopLocalLoopReg2A INTEGER,
		fmrwLoopLocalLoopReg1B INTEGER,
		fmrwLoopLocalLoopReg2B INTEGER,
		fmrwLoopLocalLoop2Reg1A INTEGER,
		fmrwLoopLocalLoop2Reg2A INTEGER,
		fmrwLoopLocalLoop2Reg1B INTEGER,
		fmrwLoopLocalLoop2Reg2B INTEGER,
		fmrwLoopLocalLoopReg31 INTEGER,
		fmrwLoopLocalLoopReg32 INTEGER,
		fmrwLoopLocalLoopReg41 INTEGER,
		fmrwLoopLocalLoopReg42 INTEGER,
		fmrwLoopLocalLoopReg51 INTEGER,
		fmrwLoopLocalLoopReg52 INTEGER,
		fmrwLoopLocalLoopReg61 INTEGER,
		fmrwLoopLocalLoopReg62 INTEGER,
		fmrwLoopLocalLoopReg71 INTEGER,
		fmrwLoopLocalLoopReg72 INTEGER,
		fmrwLoopLocalLoopReg81 INTEGER,
		fmrwLoopLocalLoopReg82 INTEGER,
		fmrwLoopLocalLoop2Reg31 INTEGER,
		fmrwLoopLocalLoop2Reg32 INTEGER,
		fmrwLoopLocalLoop2Reg41 INTEGER,
		fmrwLoopLocalLoop2Reg42 INTEGER,
		fmrwLoopLocalLoop2Reg51 INTEGER,
		fmrwLoopLocalLoop2Reg52 INTEGER,
		fmrwLoopLocalLoop2Reg61 INTEGER,
		fmrwLoopLocalLoop2Reg62 INTEGER,
		fmrwLoopLocalLoop2Reg71 INTEGER,
		fmrwLoopLocalLoop2Reg72 INTEGER,
		fmrwLoopLocalLoop2Reg81 INTEGER,
		fmrwLoopLocalLoop2Reg82 INTEGER,
		fmrwLoopLocalLoopReg13 INTEGER,
		fmrwLoopLocalLoopReg14 INTEGER,
		fmrwLoopLocalLoopReg23 INTEGER,
		fmrwLoopLocalLoopReg24 INTEGER,
		fmrwLoopLocalLoopReg33 INTEGER,
		fmrwLoopLocalLoopReg34 INTEGER,
		fmrwLoopLocalLoopReg43 INTEGER,
		fmrwLoopLocalLoopReg44 INTEGER,
		fmrwLoopLocalLoopReg53 INTEGER,
		fmrwLoopLocalLoopReg54 INTEGER,
		fmrwLoopLocalLoopReg63 INTEGER,
		fmrwLoopLocalLoopReg64 INTEGER,
		fmrwLoopLocalLoopReg73 INTEGER,
		fmrwLoopLocalLoopReg74 INTEGER,
		fmrwLoopLocalLoopReg83 INTEGER,
		fmrwLoopLocalLoopReg84 INTEGER,
		fmrwLoopLocalLoop2Reg13 INTEGER,
		fmrwLoopLocalLoop2Reg14 INTEGER,
		fmrwLoopLocalLoop2Reg23 INTEGER,
		fmrwLoopLocalLoop2Reg24 INTEGER,
		fmrwLoopLocalLoop2Reg33 INTEGER,
		fmrwLoopLocalLoop2Reg34 INTEGER,
		fmrwLoopLocalLoop2Reg43 INTEGER,
		fmrwLoopLocalLoop2Reg44 INTEGER,
		fmrwLoopLocalLoop2Reg53 INTEGER,
		fmrwLoopLocalLoop2Reg54 INTEGER,
		fmrwLoopLocalLoop2Reg63 INTEGER,
		fmrwLoopLocalLoop2Reg64 INTEGER,
		fmrwLoopLocalLoop2Reg73 INTEGER,
		fmrwLoopLocalLoop2Reg74 INTEGER,
		fmrwLoopLocalLoop2Reg83 INTEGER,
		fmrwLoopLocalLoop2Reg84 INTEGER,
		fmrwLoopLocalLoop3a2 INTEGER,
		fmrwLoopLocalLoop3a3 INTEGER,
		fmrwLoopLocalLoop3a4 INTEGER,
		fmrwLoopLocalLoop2b2 INTEGER,
		fmrwLoopLocalLoop2b3 INTEGER,
		fmrwLoopLocalLoop2b4 INTEGER,
		fmrwLoopLocalLoopMcs INTEGER,
		fmrwLoopLocalLoop2bData INTEGER,
		fmrwLoopLocalLoop2bEth INTEGER,
		fmrwLoopLocalLoop2bDataFar INTEGER
	}

fmrwLoopLocalPortIndex OBJECT-TYPE
	SYNTAX INTEGER
	ACCESS read-only
	STATUS mandatory
	DESCRIPTION
		"This variable addresses the port number of the proxy
		and is used as index for the other elements in the Table"
	::= { fmrwLoopLocalEntry 1 }

fmrwLoopLocalLinkIndex OBJECT-TYPE
	SYNTAX INTEGER
	ACCESS read-only
	STATUS mandatory
	DESCRIPTION
		"This variable addresses the slot number of the OMI sub-rack
		and is used as index for the other elements in the Table"
	::= { fmrwLoopLocalEntry 2 }

fmrwLoopLocalLoop3a OBJECT-TYPE
	SYNTAX INTEGER (0..1023)
	ACCESS read-write
	STATUS mandatory
	DESCRIPTION
		"State of Loop 3a. The readable value is bit coded as follows:
		Bit 0	1	STATE		physical loop state
		Bit 3	8	TMN_LOCAL	Loop command by local management
		Bit 4	16	DIP		Loop command by local switch
		Bit 7	128	Sa6-Bit		Loop command by Sa6-bit
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  3	8	TMN_LOCAL	Sets/Clears the Loop on the LT or the NT Local"
	::= { fmrwLoopLocalEntry 3 }

fmrwLoopLocalLoop2b OBJECT-TYPE
	SYNTAX INTEGER (0..1023)
	ACCESS read-write
	STATUS mandatory
	DESCRIPTION
		"State of Loop 2b. The readable value is bit coded as follows:
		Bit 0	1	STATE		physical loop state
		Bit 3	8	TMN_LOCAL	Loop command by local management
		Bit 4	16	DIP		Loop command by local switch
		Bit 5	32	L140		Loop command by control line 140
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  3	8	TMN_LOCAL	Sets the Loop on the LT or the NT Local"
	::= { fmrwLoopLocalEntry 4 }

fmrwLoopLocalLoop3c OBJECT-TYPE
	SYNTAX INTEGER (0..1023)
	ACCESS read-write
	STATUS mandatory
	DESCRIPTION
		"State of Loop 3c. The readable value is bit coded as follows:
		Bit 0	1	STATE		physical loop state
		Bit 3	8	TMN_LOCAL	Loop command by local management
		Bit 4	16	DIP		Loop command by local switch
		Bit 6	64	L141		Loop command by control line 141
		Bit 7	128	Sa6-Bit		Loop command by Sa6-bit
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  3	8	TMN_LOCAL	Sets the Loop on the LT or the NT Local"
	::= { fmrwLoopLocalEntry 5 }

fmrwLoopLocalLoopReg1A OBJECT-TYPE
	SYNTAX INTEGER (0..1023)
	ACCESS read-write
	STATUS mandatory
	DESCRIPTION
		"State of Regenerator Loop in wire pair 1 (first section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 6 }

fmrwLoopLocalLoopReg2A OBJECT-TYPE
	SYNTAX INTEGER (0..1023)
	ACCESS read-write
	STATUS mandatory
	DESCRIPTION
		"State of Regenerator Loop in wire pair 2 (first section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 7 }

fmrwLoopLocalLoopReg1B OBJECT-TYPE
	SYNTAX INTEGER (0..1023)
	ACCESS read-write
	STATUS mandatory
	DESCRIPTION
		"State of Regenerator Loop in wire pair 1 (second section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 8 }

fmrwLoopLocalLoopReg2B OBJECT-TYPE
	SYNTAX INTEGER (0..1023)
	ACCESS read-write
	STATUS mandatory
	DESCRIPTION
		"State of Regenerator Loop in wire pair 2 (second section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 9 }

fmrwLoopLocalLoop2Reg1A OBJECT-TYPE
	SYNTAX INTEGER (0..1023)
	ACCESS read-write
	STATUS mandatory
	DESCRIPTION
		"State of Regenerator Loop 2 in wire pair 1 (first section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 10 }

fmrwLoopLocalLoop2Reg2A OBJECT-TYPE
	SYNTAX INTEGER (0..1023)
	ACCESS read-write
	STATUS mandatory
	DESCRIPTION
		"State of Regenerator Loop 2 in wire pair 2 (first section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 11 }

fmrwLoopLocalLoop2Reg1B OBJECT-TYPE
	SYNTAX INTEGER (0..1023)
	ACCESS read-write
	STATUS mandatory
	DESCRIPTION
		"State of Regenerator Loop 2 in wire pair 1 (second section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 12 }

fmrwLoopLocalLoop2Reg2B OBJECT-TYPE
	SYNTAX INTEGER (0..1023)
	ACCESS read-write
	STATUS mandatory
	DESCRIPTION
		"State of Regenerator Loop 2 in wire pair 2 (second section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 13 }

fmrwLoopLocalLoopReg31 OBJECT-TYPE
	SYNTAX INTEGER (0..1023)
	ACCESS read-write
	STATUS mandatory
	DESCRIPTION
		"State of Regenerator Loop 2 in wire pair 1 (third section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 14 }

fmrwLoopLocalLoopReg32 OBJECT-TYPE
	SYNTAX INTEGER (0..1023)
	ACCESS read-write
	STATUS mandatory
	DESCRIPTION
		"State of Regenerator Loop 2 in wire pair 2 (third section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 15 }

fmrwLoopLocalLoopReg41 OBJECT-TYPE
	SYNTAX INTEGER (0..1023)
	ACCESS read-write
	STATUS mandatory
	DESCRIPTION
		"State of Regenerator Loop 2 in wire pair 1 (fourth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 16 }

fmrwLoopLocalLoopReg42 OBJECT-TYPE
	SYNTAX INTEGER (0..1023)
	ACCESS read-write
	STATUS mandatory
	DESCRIPTION
		"State of Regenerator Loop 2 in wire pair 2 (fourth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 17 }

fmrwLoopLocalLoopReg51 OBJECT-TYPE
	SYNTAX INTEGER (0..1023)
	ACCESS read-write
	STATUS mandatory
	DESCRIPTION
		"State of Regenerator Loop 2 in wire pair 1 (fifth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 18 }

fmrwLoopLocalLoopReg52 OBJECT-TYPE
	SYNTAX INTEGER (0..1023)
	ACCESS read-write
	STATUS mandatory
	DESCRIPTION
		"State of Regenerator Loop 2 in wire pair 2 (fifth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 19 }

fmrwLoopLocalLoopReg61 OBJECT-TYPE
	SYNTAX INTEGER (0..1023)
	ACCESS read-write
	STATUS mandatory
	DESCRIPTION
		"State of Regenerator Loop 2 in wire pair 1 (sixth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 20 }

fmrwLoopLocalLoopReg62 OBJECT-TYPE
	SYNTAX INTEGER (0..1023)
	ACCESS read-write
	STATUS mandatory
	DESCRIPTION
		"State of Regenerator Loop 2 in wire pair 2 (sixth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 21 }

fmrwLoopLocalLoopReg71 OBJECT-TYPE
	SYNTAX INTEGER (0..1023)
	ACCESS read-write
	STATUS mandatory
	DESCRIPTION
		"State of Regenerator Loop 2 in wire pair 1 (seventh section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 22 }

fmrwLoopLocalLoopReg72 OBJECT-TYPE
	SYNTAX INTEGER (0..1023)
	ACCESS read-write
	STATUS mandatory
	DESCRIPTION
		"State of Regenerator Loop 2 in wire pair 2 (seventh section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 23 }

fmrwLoopLocalLoopReg81 OBJECT-TYPE
	SYNTAX INTEGER (0..1023)
	ACCESS read-write
	STATUS mandatory
	DESCRIPTION
		"State of Regenerator Loop 2 in wire pair 1 (eighth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 24 }

fmrwLoopLocalLoopReg82 OBJECT-TYPE
	SYNTAX INTEGER (0..1023)
	ACCESS read-write
	STATUS mandatory
	DESCRIPTION
		"State of Regenerator Loop 2 in wire pair 2 (eighth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 25 }

fmrwLoopLocalLoop2Reg31 OBJECT-TYPE
	SYNTAX INTEGER (0..1023)
	ACCESS read-write
	STATUS mandatory
	DESCRIPTION
		"State of Regenerator Loop 2 in wire pair 1 (third section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 26 }

fmrwLoopLocalLoop2Reg32 OBJECT-TYPE
	SYNTAX INTEGER (0..1023)
	ACCESS read-write
	STATUS mandatory
	DESCRIPTION
		"State of Regenerator Loop 2 in wire pair 2 (third section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 27 }

fmrwLoopLocalLoop2Reg41 OBJECT-TYPE
	SYNTAX INTEGER (0..1023)
	ACCESS read-write
	STATUS mandatory
	DESCRIPTION
		"State of Regenerator Loop 2 in wire pair 1 (fourth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 28 }

fmrwLoopLocalLoop2Reg42 OBJECT-TYPE
	SYNTAX INTEGER (0..1023)
	ACCESS read-write
	STATUS mandatory
	DESCRIPTION
		"State of Regenerator Loop 2 in wire pair 2 (fourth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 29 }

fmrwLoopLocalLoop2Reg51 OBJECT-TYPE
	SYNTAX INTEGER (0..1023)
	ACCESS read-write
	STATUS mandatory
	DESCRIPTION
		"State of Regenerator Loop 2 in wire pair 1 (fifth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 30 }

fmrwLoopLocalLoop2Reg52 OBJECT-TYPE
	SYNTAX INTEGER (0..1023)
	ACCESS read-write
	STATUS mandatory
	DESCRIPTION
		"State of Regenerator Loop 2 in wire pair 2 (fifth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 31 }

fmrwLoopLocalLoop2Reg61 OBJECT-TYPE
	SYNTAX INTEGER (0..1023)
	ACCESS read-write
	STATUS mandatory
	DESCRIPTION
		"State of Regenerator Loop 2 in wire pair 1 (sixth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 32 }

fmrwLoopLocalLoop2Reg62 OBJECT-TYPE
	SYNTAX INTEGER (0..1023)
	ACCESS read-write
	STATUS mandatory
	DESCRIPTION
		"State of Regenerator Loop 2 in wire pair 2 (sixth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 33 }

fmrwLoopLocalLoop2Reg71 OBJECT-TYPE
	SYNTAX INTEGER (0..1023)
	ACCESS read-write
	STATUS mandatory
	DESCRIPTION
		"State of Regenerator Loop 2 in wire pair 1 (seventh section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 34 }

fmrwLoopLocalLoop2Reg72 OBJECT-TYPE
	SYNTAX INTEGER (0..1023)
	ACCESS read-write
	STATUS mandatory
	DESCRIPTION
		"State of Regenerator Loop 2 in wire pair 2 (seventh section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 35 }

fmrwLoopLocalLoop2Reg81 OBJECT-TYPE
	SYNTAX INTEGER (0..1023)
	ACCESS read-write
	STATUS mandatory
	DESCRIPTION
		"State of Regenerator Loop 2 in wire pair 1 (eigtht section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 36 }

fmrwLoopLocalLoop2Reg82 OBJECT-TYPE
	SYNTAX INTEGER (0..1023)
	ACCESS read-write
	STATUS mandatory
	DESCRIPTION
		"State of Regenerator Loop 2 in wire pair 2 (eighth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 37 }

fmrwLoopLocalLoopReg13 OBJECT-TYPE
	SYNTAX INTEGER (0..1023)
	ACCESS read-write
	STATUS mandatory
	DESCRIPTION
		"State of Regenerator Loop in wire pair 3 (first section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 38 }

fmrwLoopLocalLoopReg14 OBJECT-TYPE
	SYNTAX INTEGER (0..1023)
	ACCESS read-write
	STATUS mandatory
	DESCRIPTION
		"State of Regenerator Loop in wire pair 4 (first section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 39 }

fmrwLoopLocalLoopReg23 OBJECT-TYPE
	SYNTAX INTEGER (0..1023)
	ACCESS read-write
	STATUS mandatory
	DESCRIPTION
		"State of Regenerator Loop in wire pair 3 (second section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 40 }

fmrwLoopLocalLoopReg24 OBJECT-TYPE
	SYNTAX INTEGER (0..1023)
	ACCESS read-write
	STATUS mandatory
	DESCRIPTION
		"State of Regenerator Loop in wire pair 4 (second section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 41 }

fmrwLoopLocalLoopReg33 OBJECT-TYPE
	SYNTAX INTEGER (0..1023)
	ACCESS read-write
	STATUS mandatory
	DESCRIPTION
		"State of Regenerator Loop in wire pair 3 (third section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 42 }

fmrwLoopLocalLoopReg34 OBJECT-TYPE
	SYNTAX INTEGER (0..1023)
	ACCESS read-write
	STATUS mandatory
	DESCRIPTION
		"State of Regenerator Loop in wire pair 4 (third section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 43 }

fmrwLoopLocalLoopReg43 OBJECT-TYPE
	SYNTAX INTEGER (0..1023)
	ACCESS read-write
	STATUS mandatory
	DESCRIPTION
		"State of Regenerator Loop in wire pair 3 (fourth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 44 }

fmrwLoopLocalLoopReg44 OBJECT-TYPE
	SYNTAX INTEGER (0..1023)
	ACCESS read-write
	STATUS mandatory
	DESCRIPTION
		"State of Regenerator Loop in wire pair 4 (fourth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 45 }

fmrwLoopLocalLoopReg53 OBJECT-TYPE
	SYNTAX INTEGER (0..1023)
	ACCESS read-write
	STATUS mandatory
	DESCRIPTION
		"State of Regenerator Loop in wire pair 3 (fifth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 46 }

fmrwLoopLocalLoopReg54 OBJECT-TYPE
	SYNTAX INTEGER (0..1023)
	ACCESS read-write
	STATUS mandatory
	DESCRIPTION
		"State of Regenerator Loop in wire pair 4 (fifth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 47 }

fmrwLoopLocalLoopReg63 OBJECT-TYPE
	SYNTAX INTEGER (0..1023)
	ACCESS read-write
	STATUS mandatory
	DESCRIPTION
		"State of Regenerator Loop in wire pair 3 (sixth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 48 }

fmrwLoopLocalLoopReg64 OBJECT-TYPE
	SYNTAX INTEGER (0..1023)
	ACCESS read-write
	STATUS mandatory
	DESCRIPTION
		"State of Regenerator Loop in wire pair 4 (sixth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 49 }

fmrwLoopLocalLoopReg73 OBJECT-TYPE
	SYNTAX INTEGER (0..1023)
	ACCESS read-write
	STATUS mandatory
	DESCRIPTION
		"State of Regenerator Loop in wire pair 3 (seventh section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 50 }

fmrwLoopLocalLoopReg74 OBJECT-TYPE
	SYNTAX INTEGER (0..1023)
	ACCESS read-write
	STATUS mandatory
	DESCRIPTION
		"State of Regenerator Loop in wire pair 4 (seventh section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 51 }

fmrwLoopLocalLoopReg83 OBJECT-TYPE
	SYNTAX INTEGER (0..1023)
	ACCESS read-write
	STATUS mandatory
	DESCRIPTION
		"State of Regenerator Loop in wire pair 3 (eighth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 52 }

fmrwLoopLocalLoopReg84 OBJECT-TYPE
	SYNTAX INTEGER (0..1023)
	ACCESS read-write
	STATUS mandatory
	DESCRIPTION
		"State of Regenerator Loop in wire pair 4 (eighth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 53 }

fmrwLoopLocalLoop2Reg13 OBJECT-TYPE
	SYNTAX INTEGER (0..1023)
	ACCESS read-write
	STATUS mandatory
	DESCRIPTION
		"State of Regenerator Loop 2 in wire pair 3 (first section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 54 }

fmrwLoopLocalLoop2Reg14 OBJECT-TYPE
	SYNTAX INTEGER (0..1023)
	ACCESS read-write
	STATUS mandatory
	DESCRIPTION
		"State of Regenerator Loop 2 in wire pair 4 (first section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 55 }

fmrwLoopLocalLoop2Reg23 OBJECT-TYPE
	SYNTAX INTEGER (0..1023)
	ACCESS read-write
	STATUS mandatory
	DESCRIPTION
		"State of Regenerator Loop 2 in wire pair 3 (second section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 56 }

fmrwLoopLocalLoop2Reg24 OBJECT-TYPE
	SYNTAX INTEGER (0..1023)
	ACCESS read-write
	STATUS mandatory
	DESCRIPTION
		"State of Regenerator Loop 2 in wire pair 4 (second section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 57 }

fmrwLoopLocalLoop2Reg33 OBJECT-TYPE
	SYNTAX INTEGER (0..1023)
	ACCESS read-write
	STATUS mandatory
	DESCRIPTION
		"State of Regenerator Loop 2 in wire pair 3 (third section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 58 }

fmrwLoopLocalLoop2Reg34 OBJECT-TYPE
	SYNTAX INTEGER (0..1023)
	ACCESS read-write
	STATUS mandatory
	DESCRIPTION
		"State of Regenerator Loop 2 in wire pair 4 (third section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 59 }

fmrwLoopLocalLoop2Reg43 OBJECT-TYPE
	SYNTAX INTEGER (0..1023)
	ACCESS read-write
	STATUS mandatory
	DESCRIPTION
		"State of Regenerator Loop 2 in wire pair 3 (fourth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 60 }

fmrwLoopLocalLoop2Reg44 OBJECT-TYPE
	SYNTAX INTEGER (0..1023)
	ACCESS read-write
	STATUS mandatory
	DESCRIPTION
		"State of Regenerator Loop 2 in wire pair 4 (fourth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 61 }

fmrwLoopLocalLoop2Reg53 OBJECT-TYPE
	SYNTAX INTEGER (0..1023)
	ACCESS read-write
	STATUS mandatory
	DESCRIPTION
		"State of Regenerator Loop 2 in wire pair 3 (fifth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 62 }

fmrwLoopLocalLoop2Reg54 OBJECT-TYPE
	SYNTAX INTEGER (0..1023)
	ACCESS read-write
	STATUS mandatory
	DESCRIPTION
		"State of Regenerator Loop 2 in wire pair 4 (fifth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 63 }

fmrwLoopLocalLoop2Reg63 OBJECT-TYPE
	SYNTAX INTEGER (0..1023)
	ACCESS read-write
	STATUS mandatory
	DESCRIPTION
		"State of Regenerator Loop 2 in wire pair 3 (sixth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 64 }

fmrwLoopLocalLoop2Reg64 OBJECT-TYPE
	SYNTAX INTEGER (0..1023)
	ACCESS read-write
	STATUS mandatory
	DESCRIPTION
		"State of Regenerator Loop 2 in wire pair 4 (sixth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 65 }

fmrwLoopLocalLoop2Reg73 OBJECT-TYPE
	SYNTAX INTEGER (0..1023)
	ACCESS read-write
	STATUS mandatory
	DESCRIPTION
		"State of Regenerator Loop 2 in wire pair 3 (seventh section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 66 }

fmrwLoopLocalLoop2Reg74 OBJECT-TYPE
	SYNTAX INTEGER (0..1023)
	ACCESS read-write
	STATUS mandatory
	DESCRIPTION
		"State of Regenerator Loop 2 in wire pair 4 (seventh section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 67 }

fmrwLoopLocalLoop2Reg83 OBJECT-TYPE
	SYNTAX INTEGER (0..1023)
	ACCESS read-write
	STATUS mandatory
	DESCRIPTION
		"State of Regenerator Loop 2 in wire pair 3 (eigtht section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 68 }

fmrwLoopLocalLoop2Reg84 OBJECT-TYPE
	SYNTAX INTEGER (0..1023)
	ACCESS read-write
	STATUS mandatory
	DESCRIPTION
		"State of Regenerator Loop 2 in wire pair 4 (eighth section).
		The readable value is bit coded as follows:
		Bit 0	1	STATE		physical loop state
		Bit 1	2	EOC_TMN		Loop command via EOC by management
		Bit 8	256	unknown value (ignore bits 0-7)
		Bit 9	512	unsupported variable for addressed device (ignore bits 0-7)
		
		The STATE bit shows whether the loop is currently active or not. Bit 1
		shows whether the loop command has been issued by the management system.
		
		When setting a loop, the following applies:
		Bit  1	2	EOC_TMN		Sets the Loop on the Regenerator"
	::= { fmrwLoopLocalEntry 69 }

fmrwLoopLocalLoop3a2 OBJECT-TYPE
	SYNTAX INTEGER (0..1023)
	ACCESS read-write
	STATUS mandatory
	DESCRIPTION
		"State of Loop 3a2. The readable value is bit coded as follows:
		Bit 0	1	STATE		physical loop state
		Bit 3	8	TMN_LOCAL	Loop command by local management
		Bit 4	16	DIP		Loop command by local switch
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  3	8	TMN_LOCAL	Sets/Clears the Loop on the LT or the NT Local"
	::= { fmrwLoopLocalEntry 70 }

fmrwLoopLocalLoop3a3 OBJECT-TYPE
	SYNTAX INTEGER (0..1023)
	ACCESS read-write
	STATUS mandatory
	DESCRIPTION
		"State of Loop 3a3. The readable value is bit coded as follows:
		Bit 0	1	STATE		physical loop state
		Bit 3	8	TMN_LOCAL	Loop command by local management
		Bit 4	16	DIP		Loop command by local switch
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  3	8	TMN_LOCAL	Sets/Clears the Loop on the LT or the NT Local"
	::= { fmrwLoopLocalEntry 71 }

fmrwLoopLocalLoop3a4 OBJECT-TYPE
	SYNTAX INTEGER (0..1023)
	ACCESS read-write
	STATUS mandatory
	DESCRIPTION
		"State of Loop 3a4. The readable value is bit coded as follows:
		Bit 0	1	STATE		physical loop state
		Bit 3	8	TMN_LOCAL	Loop command by local management
		Bit 4	16	DIP		Loop command by local switch
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  3	8	TMN_LOCAL	Sets/Clears the Loop on the LT or the NT Local"
	::= { fmrwLoopLocalEntry 72 }

fmrwLoopLocalLoop2b2 OBJECT-TYPE
	SYNTAX INTEGER (0..1023)
	ACCESS read-write
	STATUS mandatory
	DESCRIPTION
		"State of Loop 2b2. The readable value is bit coded as follows:
		Bit 0	1	STATE		physical loop state
		Bit 3	8	TMN_LOCAL	Loop command by local management
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  3	8	TMN_LOCAL	Sets the Loop on the LT or the NT Local"
	::= { fmrwLoopLocalEntry 73 }

fmrwLoopLocalLoop2b3 OBJECT-TYPE
	SYNTAX INTEGER (0..1023)
	ACCESS read-write
	STATUS mandatory
	DESCRIPTION
		"State of Loop 2b3. The readable value is bit coded as follows:
		Bit 0	1	STATE		physical loop state
		Bit 3	8	TMN_LOCAL	Loop command by local management
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  3	8	TMN_LOCAL	Sets the Loop on the LT or the NT Local"
	::= { fmrwLoopLocalEntry 74 }

fmrwLoopLocalLoop2b4 OBJECT-TYPE
	SYNTAX INTEGER (0..1023)
	ACCESS read-write
	STATUS mandatory
	DESCRIPTION
		"State of Loop 2b4. The readable value is bit coded as follows:
		Bit 0	1	STATE		physical loop state
		Bit 3	8	TMN_LOCAL	Loop command by local management
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  3	8	TMN_LOCAL	Sets the Loop on the LT or the NT Local"
	::= { fmrwLoopLocalEntry 75 }

fmrwLoopLocalLoopMcs OBJECT-TYPE
	SYNTAX INTEGER (0..2047)
	ACCESS read-write
	STATUS mandatory
	DESCRIPTION
		"State of MCS Loop. The readable value is bit coded as follows:
		Bit 0	1	STATE		physical loop state
		Bit 3	8	TMN_LOCAL	Loop command by local management
		Bit 8	256	unknown value (ignore other bits)
		Bit 9	512	unsupported variable for addressed device (ignore other bits)
		Bit 10	1024	MCS		Loop command by MCS
		
		The STATE bit shows whether the loop is currently active or not. Bits 2-7 and 10 
		show which sources have issued the loop command. If at least one of them is
		active, the device will try to set the loop.
		For some modes of operation or with certain combinations of modules some
		loop sources might not be available.
		
		When setting a loop, the following applies:
		Bit  3	8	TMN_LOCAL	Sets the Loop on the LT or the NT Local"
	::= { fmrwLoopLocalEntry 76 }

fmrwLoopLocalLoop2bData OBJECT-TYPE
	SYNTAX INTEGER (0..1023)
	ACCESS read-write
	STATUS mandatory
	DESCRIPTION
		"State of Loop 2bData. The readable value is bit coded as follows:
		Bit 0	1	STATE		physical loop state
		Bit 3	8	TMN_LOCAL	Loop command by local management
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  3	8	TMN_LOCAL	Sets the Loop on the LT or the NT Local"
	::= { fmrwLoopLocalEntry 77 }

fmrwLoopLocalLoop2bEth OBJECT-TYPE
	SYNTAX INTEGER (0..1023)
	ACCESS read-write
	STATUS mandatory
	DESCRIPTION
		"State of Loop 2bEth. The readable value is bit coded as follows:
		Bit 0	1	STATE		physical loop state
		Bit 3	8	TMN_LOCAL	Loop command by local management
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  3	8	TMN_LOCAL	Sets the Loop on the LT or the NT Local"
	::= { fmrwLoopLocalEntry 78 }

fmrwLoopLocalLoop2bDataFar OBJECT-TYPE
	SYNTAX INTEGER (0..1023)
	ACCESS read-write
	STATUS mandatory
	DESCRIPTION
		"State of Loop 2bDataFar. The readable value is bit coded as follows:
		Bit 0	1	STATE		physical loop state
		Bit 3	8	TMN_LOCAL	Loop command by local management
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  3	8	TMN_LOCAL	Sets the Loop on the LT or the NT Local"
	::= { fmrwLoopLocalEntry 79 }

--------------------------------------------------------------------------------
--	FM-RW	Loops far
--------------------------------------------------------------------------------
fmrwLoopFarTable OBJECT-TYPE
	SYNTAX SEQUENCE OF FmrwLoopFarEntry
	ACCESS not-accessible
	STATUS mandatory
	DESCRIPTION ""
	::= { fmrwLoop 2 }

fmrwLoopFarEntry OBJECT-TYPE
	SYNTAX FmrwLoopFarEntry
	ACCESS not-accessible
	STATUS mandatory
	DESCRIPTION ""
	INDEX { fmrwLoopFarPortIndex, fmrwLoopFarLinkIndex }
	::= { fmrwLoopFarTable 1 }

FmrwLoopFarEntry ::= 
	SEQUENCE
	{
		fmrwLoopFarPortIndex INTEGER,
		fmrwLoopFarLinkIndex INTEGER,
		fmrwLoopFarLoop3a INTEGER,
		fmrwLoopFarLoop2b INTEGER,
		fmrwLoopFarLoop3c INTEGER,
		fmrwLoopFarLoop2bSlave INTEGER,
		fmrwLoopFarLoop2b2 INTEGER,
		fmrwLoopFarLoop2b3 INTEGER,
		fmrwLoopFarLoop2b4 INTEGER,
		fmrwLoopFarLoopMcs INTEGER,
		fmrwLoopFarLoop2bData INTEGER,
		fmrwLoopFarLoop2bEth INTEGER,
		fmrwLoopFarLoop2bDataFar INTEGER
	}

fmrwLoopFarPortIndex OBJECT-TYPE
	SYNTAX INTEGER
	ACCESS read-only
	STATUS mandatory
	DESCRIPTION
		"This variable addresses the port number of the proxy
		and is used as index for the other elements in the Table"
	::= { fmrwLoopFarEntry 1 }

fmrwLoopFarLinkIndex OBJECT-TYPE
	SYNTAX INTEGER
	ACCESS read-only
	STATUS mandatory
	DESCRIPTION
		"This variable addresses the slot number of the OMI sub-rack
		and is used as index for the other elements in the Table"
	::= { fmrwLoopFarEntry 2 }

fmrwLoopFarLoop3a OBJECT-TYPE
	SYNTAX INTEGER (0..1023)
	ACCESS read-write
	STATUS mandatory
	DESCRIPTION
		"State of Loop 3a. The readable value is bit coded as follows:
		Bit 0	1	STATE		physical loop state
		Bit 1	2	EOC_TMN		Loop command via EOC by management
		Bit 3	8	TMN_LOCAL	Loop command by local management
		Bit 4	16	DIP		Loop command by local switch
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  1	4	EOC_TMN		Sets the Loop on the NT
		Bit  3	8	TMN_LOCAL	Sets the Loop on the LT or the NT Local"
	::= { fmrwLoopFarEntry 3 }

fmrwLoopFarLoop2b OBJECT-TYPE
	SYNTAX INTEGER (0..1023)
	ACCESS read-write
	STATUS mandatory
	DESCRIPTION
		"State of Loop 2b. The readable value is bit coded as follows:
		Bit 0	1	STATE		physical loop state
		Bit 1	2	EOC_TMN		Loop command via EOC by management
		Bit 2	4	EOC_DIP		Loop command via EOC by switch
		Bit 3	8	TMN_LOCAL	Loop command by local management
		Bit 4	16	DIP		Loop command by local switch
		Bit 5	32	L140		Loop command by control line 140
		Bit 7	128	Sa6-Bit		Loop command by Sa6-bit
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  1	4	EOC_TMN		Sets the Loop on the NT
		Bit  3	8	TMN_LOCAL	Sets the Loop on the LT or the NT Local"
	::= { fmrwLoopFarEntry 4 }

fmrwLoopFarLoop3c OBJECT-TYPE
	SYNTAX INTEGER (0..1023)
	ACCESS read-write
	STATUS mandatory
	DESCRIPTION
		"State of Loop 3c. The readable value is bit coded as follows:
		Bit 0	1	STATE		physical loop state
		Bit 1	2	EOC_TMN		Loop command via EOC by management
		Bit 3	8	TMN_LOCAL	Loop command by local management
		Bit 4	16	DIP		Loop command by local switch
		Bit 6	64	L141		Loop command by control line 141
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  1	4	EOC_TMN		Sets the Loop on the NT
		Bit  3	8	TMN_LOCAL	Sets the Loop on the LT or the NT Local"
	::= { fmrwLoopFarEntry 5 }

fmrwLoopFarLoop2bSlave OBJECT-TYPE
	SYNTAX INTEGER (0..1023)
	ACCESS read-write
	STATUS mandatory
	DESCRIPTION
		"State of Loop 2b on the slave device. The readable value is bit coded as follows:
		Bit 0	1	STATE		physical loop state
		Bit 3	8	TMN_LOCAL	Loop command via EOC by management
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  1	2	EOC_TMN		Sets the Loop 2b on the slave device"
	::= { fmrwLoopFarEntry 6 }

fmrwLoopFarLoop2b2 OBJECT-TYPE
	SYNTAX INTEGER (0..1023)
	ACCESS read-write
	STATUS mandatory
	DESCRIPTION
		"State of Loop 2b2. The readable value is bit coded as follows:
		Bit 0	1	STATE		physical loop state
		Bit 1	2	EOC_TMN		Loop command via EOC by management
		Bit 3	8	TMN_LOCAL	Loop command by local management
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  1	4	EOC_TMN		Sets the Loop on the NT
		Bit  3	8	TMN_LOCAL	Sets the Loop on the LT or the NT Local"
	::= { fmrwLoopFarEntry 7 }

fmrwLoopFarLoop2b3 OBJECT-TYPE
	SYNTAX INTEGER (0..1023)
	ACCESS read-write
	STATUS mandatory
	DESCRIPTION
		"State of Loop 2b3. The readable value is bit coded as follows:
		Bit 0	1	STATE		physical loop state
		Bit 1	2	EOC_TMN		Loop command via EOC by management
		Bit 3	8	TMN_LOCAL	Loop command by local management
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  1	4	EOC_TMN		Sets the Loop on the NT
		Bit  3	8	TMN_LOCAL	Sets the Loop on the LT or the NT Local"
	::= { fmrwLoopFarEntry 8 }

fmrwLoopFarLoop2b4 OBJECT-TYPE
	SYNTAX INTEGER (0..1023)
	ACCESS read-write
	STATUS mandatory
	DESCRIPTION
		"State of Loop 2b4. The readable value is bit coded as follows:
		Bit 0	1	STATE		physical loop state
		Bit 1	2	EOC_TMN		Loop command via EOC by management
		Bit 3	8	TMN_LOCAL	Loop command by local management
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  1	4	EOC_TMN		Sets the Loop on the NT
		Bit  3	8	TMN_LOCAL	Sets the Loop on the LT or the NT Local"
	::= { fmrwLoopFarEntry 9 }

fmrwLoopFarLoopMcs OBJECT-TYPE
	SYNTAX INTEGER (0..2047)
	ACCESS read-write
	STATUS mandatory
	DESCRIPTION
		"State of MCS Loop. The readable value is bit coded as follows:
		Bit 0	1	STATE		physical loop state
		Bit 1	2	EOC_TMN		Loop command via EOC by management
		Bit 2	4	EOC_DIP		Loop command via EOC by switch
		Bit 3	8	TMN_LOCAL	Loop command by local management
		Bit 4	16	DIP		Loop command by local switch
		Bit 8	256	unknown value (ignore other bits)
		Bit 9	512	unsupported variable for addressed device (ignore other bits)
		Bit 10	1024	MCS		Loop command by MCS
		
		The STATE bit shows whether the loop is currently active or not. Bits 2-7 and 10 
		show which sources have issued the loop command. If at least one of them is
		active, the device will try to set the loop.
		For some modes of operation or with certain combinations of modules some
		loop sources might not be available.
		
		When setting a loop, the following applies:
		Bit  1	4	EOC_TMN		Sets the Loop on the NT
		Bit  3	8	TMN_LOCAL	Sets the Loop on the LT or the NT Local"
	::= { fmrwLoopFarEntry 19 }

fmrwLoopFarLoop2bData OBJECT-TYPE
	SYNTAX INTEGER (0..1023)
	ACCESS read-write
	STATUS mandatory
	DESCRIPTION
		"State of Loop 2bData. The readable value is bit coded as follows:
		Bit 0	1	STATE		physical loop state
		Bit 1	2	EOC_TMN		Loop command via EOC by management
		Bit 3	8	TMN_LOCAL	Loop command by local management
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  1	4	EOC_TMN		Sets the Loop on the NT
		Bit  3	8	TMN_LOCAL	Sets the Loop on the LT or the NT Local"
	::= { fmrwLoopFarEntry 20 }

fmrwLoopFarLoop2bEth OBJECT-TYPE
	SYNTAX INTEGER (0..1023)
	ACCESS read-write
	STATUS mandatory
	DESCRIPTION
		"State of Loop 2bEth. The readable value is bit coded as follows:
		Bit 0	1	STATE		physical loop state
		Bit 1	2	EOC_TMN		Loop command via EOC by management
		Bit 3	8	TMN_LOCAL	Loop command by local management
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  1	4	EOC_TMN		Sets the Loop on the NT
		Bit  3	8	TMN_LOCAL	Sets the Loop on the LT or the NT Local"
	::= { fmrwLoopFarEntry 21 }

fmrwLoopFarLoop2bDataFar OBJECT-TYPE
	SYNTAX INTEGER (0..1023)
	ACCESS read-write
	STATUS mandatory
	DESCRIPTION
		"State of Loop 2bDataFar. The readable value is bit coded as follows:
		Bit 0	1	STATE		physical loop state
		Bit 1	2	EOC_TMN		Loop command via EOC by management
		Bit 3	8	TMN_LOCAL	Loop command by local management
		Bit 8	256	unknown value (ignore bits 0-7)
		Bit 9	512	unsupported variable for addressed device (ignore bits 0-7)
		
		The STATE bit shows whether the loop is currently active or not. Bits 2-7 
		show which sources have issued the loop command. If at least one of them is
		active, the device will try to set the loop.
		For some modes of operation or with certain combinations of modules some
		loop sources might not be available.
		
		When setting a loop, the following applies:
		Bit  1	4	EOC_TMN		Sets the Loop on the NT
		Bit  3	8	TMN_LOCAL	Sets the Loop on the LT or the NT Local"
	::= { fmrwLoopFarEntry 22 }

--------------------------------------------------------------------------------
--	FM-RW	Loop Config
--------------------------------------------------------------------------------
fmrwLoopConfigTable OBJECT-TYPE
	SYNTAX SEQUENCE OF FmrwLoopConfigEntry
	ACCESS not-accessible
	STATUS mandatory
	DESCRIPTION ""
	::= { fmrwLoop 3 }

fmrwLoopConfigEntry OBJECT-TYPE
	SYNTAX FmrwLoopConfigEntry
	ACCESS not-accessible
	STATUS mandatory
	DESCRIPTION ""
	INDEX { fmrwLoopConfigPortIndex, fmrwLoopConfigLinkIndex }
	::= { fmrwLoopConfigTable 1 }

FmrwLoopConfigEntry ::= 
	SEQUENCE
	{
		fmrwLoopConfigPortIndex INTEGER,
		fmrwLoopConfigLinkIndex INTEGER,
		fmrwLoopConfigAllowRbertLoop INTEGER,
		fmrwLoopConfigTransparentLoops INTEGER
	}
	
fmrwLoopConfigPortIndex OBJECT-TYPE
	SYNTAX INTEGER
	ACCESS read-only
	STATUS mandatory
	DESCRIPTION
		"This variable addresses the port number of the proxy
		and is used as index for the other elements in the Table"
	::= { fmrwLoopConfigEntry 1 }

fmrwLoopConfigLinkIndex OBJECT-TYPE
	SYNTAX INTEGER
	ACCESS read-only
	STATUS mandatory
	DESCRIPTION
		"This variable addresses the slot number of the OMI sub-rack
		and is used as index for the other elements in the Table"
	::= { fmrwLoopConfigEntry 2 }

fmrwLoopConfigAllowRbertLoop OBJECT-TYPE
	SYNTAX INTEGER {
		notAllowed(1),
		allowed(2),
		unknown(254),
		unsupported(255)
	}
	ACCESS read-write
	STATUS mandatory
	DESCRIPTION
		"Specifies whether a remote MCS-equipped unit is allowd to
		activate an MCS loop on this line or not.
		1	Not Allowed	MCS loop activation by management only
		2	Allowed		MCS loop activation by MCS bit pattern allowed
		254			unknown value
		255			unsupported variable for addressed device"
	::= { fmrwLoopConfigEntry 3 }
		
fmrwLoopConfigTransparentLoops OBJECT-TYPE
	SYNTAX INTEGER {
		nonTransparent(1),
		transparent(2),
		unknown(254),
		unsupported(255)
	}
	ACCESS read-write
	STATUS mandatory
	DESCRIPTION
		"Specifies whether the loops are configured transparent or not.
		1	Non Transparent	The loops are configured as non transparent
		2	Transparent	The loops are configured as transparent 
		254			unknown value
		255			unsupported variable for addressed device"
	::= { fmrwLoopConfigEntry 4 }
		
--------------------------------------------------------------------------------
--	FM-RW	Htu Lt Mask
--------------------------------------------------------------------------------
fmrwHtuLtMaskTable OBJECT-TYPE
	SYNTAX SEQUENCE OF FmrwHtuLtMaskEntry
	ACCESS not-accessible
	STATUS mandatory
	DESCRIPTION ""
	::= { fmrwMask 1 }

fmrwHtuLtMaskEntry OBJECT-TYPE
	SYNTAX FmrwHtuLtMaskEntry
	ACCESS not-accessible
	STATUS mandatory
	DESCRIPTION ""
	INDEX { fmrwHtuLtMaskPortIndex, fmrwHtuLtMaskLinkIndex }
	::= { fmrwHtuLtMaskTable 1 }

FmrwHtuLtMaskEntry ::=
	SEQUENCE
	{
		fmrwHtuLtMaskPortIndex INTEGER,
		fmrwHtuLtMaskLinkIndex INTEGER,
		fmrwHtuLtMask OCTET STRING,
		fmrwStuLtMask OCTET STRING,
		fmrwStu4LtMask OCTET STRING
	}

fmrwHtuLtMaskPortIndex OBJECT-TYPE
	SYNTAX INTEGER
	ACCESS read-only
	STATUS mandatory
	DESCRIPTION
		"This variable addresses the port number of the proxy
		and is used as index for the other elements in the Table"
	::= { fmrwHtuLtMaskEntry 1 }

fmrwHtuLtMaskLinkIndex OBJECT-TYPE
	SYNTAX INTEGER
	ACCESS read-only
	STATUS mandatory
	DESCRIPTION
		"This variable addresses the slot number of the OMI sub-rack
		and is used as index for the other elements in the Table"
	::= { fmrwHtuLtMaskEntry 2 }

fmrwHtuLtMask OBJECT-TYPE
	SYNTAX OCTET STRING(SIZE(9))
	ACCESS read-write
	STATUS mandatory
	DESCRIPTION
		"Alarm Severity Mask and Alarm Suppression Mask for LT Alarms.
		 
		 This variable only returns meaningful values if the management
		 system is connected to an LT device. If it is connected to an
		 NT device on the local interface, this variable will return
		 'NotLt' as result.
		 
		 This variable is an 8 byte octet string. Bytes 0-3 contain the
		 alarm suppression mask, bytes 4-7 contain the severity map.
		 The masks are bit coded. If a bit in the suppression mask is set,
		 the corresponding alarm has the severity defined by the severity
		 mask. If the bit in the suppression mask is zero, the corresponding
		 alarm has no severity (i.e. has no influence on the alarm summary).
		 If a bit in the severity mask is set, the corresponding alarm is
		 considered to be 'Urgent', if it is zero, the alarm is 'Non-Urgent'.
		 The alarms are coded as follows:
		 
		 Suppression	Severity	Alarm
		 Byte 0		Byte 4
		 	bit 0		bit 0		LOS-U
		 	bit 1		bit 1		LFA-U
		 	bit 2		bit 2		AIS-U
		 	bit 3		bit 3		HPO-U
		 	bit 4		bit 4		FPO-U
		 	bit 5		bit 5		RAI-U
		 	bit 6		bit 6		BER3-U
		 	bit 7		bit 7		BER6-U
		 Byte 1		Byte 5
		 	bit 0		bit 0		LOS-U1
		 	bit 1		bit 1		BER3-U1
		 	bit 2		bit 2		BER6-U1
		 	bit 3		bit 3		LOS-U2
		 	bit 4		bit 4		BER3-U2
		 	bit 5		bit 5		BER6-U2
		 	bit 6		bit 6		LOS-T
		 	bit 7		bit 7		LFA-T
		 Byte 2		Byte 6
		 	bit 0		bit 0		AIS-T
		 	bit 1		bit 1		RAI-T
		 	bit 2		bit 2		BER3-T
		 	bit 3		bit 3		BER6-T
		 	bit 4		bit 4		LOAR-D
		 	bit 5		bit 5		LOAT-D
		 	bit 6		bit 6		Equipment
		 	bit 7		bit 7		A-LOS
		 Byte 3		Byte 7
		 	bit 0		bit 0		LOS-T3
		 	bit 1		bit 1		A-RTA
		 	bit 2		bit 2		Powerfail
		 	bit 3		bit 3		unused
		 	bit 4		bit 4		unused
		 	bit 5		bit 5		unused
		 	bit 6		bit 6		unused
		 	bit 7		bit 7		unused
		 
		 Byte 8 contains a value specifying the validity of the
		 result of a read operation:
		 1	Ok	Values returned are valid
		 2	NotLt	The local device is not an LT
		 254		unknown values
		 255		unsupported variable for addressed device"
	::= { fmrwHtuLtMaskEntry 3 }

fmrwStuLtMask OBJECT-TYPE
	SYNTAX OCTET STRING(SIZE(11))
	ACCESS read-write
	STATUS mandatory
	DESCRIPTION
		"Alarm Severity Mask and Alarm Suppression Mask for LT Alarms.
		 
		 This variable only returns meaningful values if the management
		 system is connected to an LT device. If it is connected to an
		 NT device on the local interface, this variable will return
		 'NotLt' as result.
		 
		 This variable is an 10 byte octet string. Bytes 0-4 contain the
		 alarm suppression mask, bytes 5-9 contain the severity map.
		 The masks are bit coded. If a bit in the suppression mask is set,
		 the corresponding alarm has the severity defined by the severity
		 mask. If the bit in the suppression mask is zero, the corresponding
		 alarm has no severity (i.e. has no influence on the alarm summary).
		 If a bit in the severity mask is set, the corresponding alarm is
		 considered to be 'Urgent', if it is zero, the alarm is 'Non-Urgent'.
		 The alarms are coded as follows:
		 
		 Suppression	Severity	Alarm
		 Byte 0		Byte 5
		 	bit 0		bit 0		LOS-U
		 	bit 1		bit 1		LFA-U
		 	bit 2		bit 2		AIS-U
		 	bit 3		bit 3		HPO-U
		 	bit 4		bit 4		FPO-U
		 	bit 5		bit 5		RAI-U
		 	bit 6		bit 6		BER3-U
		 	bit 7		bit 7		BER6-U
		 Byte 1		Byte 6
		 	bit 0		bit 0		LOS-U1
		 	bit 1		bit 1		BER3-U1
		 	bit 2		bit 2		BER6-U1
		 	bit 3		bit 3		LOS-U2
		 	bit 4		bit 4		BER3-U2
		 	bit 5		bit 5		BER6-U2
		 	bit 6		bit 6		LOS-T
		 	bit 7		bit 7		LFA-T
		 Byte 2		Byte 7
		 	bit 0		bit 0		AIS-T
		 	bit 1		bit 1		RAI-T
		 	bit 2		bit 2		BER3-T
		 	bit 3		bit 3		BER6-T
		 	bit 4		bit 4		LOAR-D
		 	bit 5		bit 5		LOAT-D
		 	bit 6		bit 6		Equipment
		 	bit 7		bit 7		A-LOS
		 Byte 3		Byte 8
		 	bit 0		bit 0		LOS-T3
		 	bit 1		bit 1		A-RTA
		 	bit 2		bit 2		Powerfail
		 	bit 3		bit 3		U-Bandwidth unavailable
		 	bit 4		bit 4		LOSW-U1
		 	bit 5		bit 5		LOSW-U2
		 	bit 6		bit 6		Powerfail CPE
		 	bit 7		bit 7		TD-ATT-U1
		 Byte 4		Byte 9
		 	bit 0		bit 0		TD-SNR-U1
		 	bit 1		bit 1		TD-ATT-U2
		 	bit 2		bit 2		TD-SNR-U2
		 	bit 3		bit 3		reserved
		 	bit 4		bit 4		reserved
		 	bit 5		bit 5		XFW
		 	bit 6		bit 6		unused
		 	bit 7		bit 7		unused
		 
		 Byte 10 contains a value specifying the validity of the
		 result of a read operation:
		 1	Ok	Values returned are valid
		 2	NotLt	The local device is not an LT
		 254		unknown values
		 255		unsupported variable for addressed device"
	::= { fmrwHtuLtMaskEntry 4 }

fmrwStu4LtMask OBJECT-TYPE
	SYNTAX OCTET STRING(SIZE(9))
	ACCESS read-write
	STATUS mandatory
	DESCRIPTION
		"Alarm Severity Mask and Alarm Suppression Mask for LT Alarms.
		 
		 This variable only returns meaningful values if the management
		 system is connected to an LT device. If it is connected to an
		 NT device on the local interface, this variable will return
		 'NotLt' as result.
		 
		 This variable is an 8 byte octet string. Bytes 0-3 contain the
		 alarm suppression mask, bytes 4-7 contain the severity map.
		 The masks are bit coded. If a bit in the suppression mask is set,
		 the corresponding alarm has the severity defined by the severity
		 mask. If the bit in the suppression mask is zero, the corresponding
		 alarm has no severity (i.e. has no influence on the alarm summary).
		 If a bit in the severity mask is set, the corresponding alarm is
		 considered to be 'Urgent', if it is zero, the alarm is 'Non-Urgent'.
		 The alarms are coded as follows:
		 
		 Suppression	Severity	Alarm
		 Byte 0		Byte 4
		 	bit 0		bit 0		LOS-U1
		 	bit 1		bit 1		BER3-U1
		 	bit 2		bit 2		BER6-U1
		 	bit 3		bit 3		LOSW-U1
		 	bit 4		bit 4		LOS-V_A
		 	bit 5		bit 5		LFA-V_A
		 	bit 6		bit 6		AIS-V_A
		 	bit 7		bit 7		RAI-V_A
		 Byte 1		Byte 5
		 	bit 0		bit 0		BER3-V_A
		 	bit 1		bit 1		BER6-V_A
		 	bit 2		bit 2		LOAR-WAN
		 	bit 3		bit 3		LOAT-WAN
		 	bit 4		bit 4		MIR-WAN
		 	bit 5		bit 5		LINKDOWN-P1
		 	bit 6		bit 6		Equipment
		 	bit 7		bit 7		A-LOS
		 Byte 2		Byte 6
		 	bit 0		bit 0		Powerfail CPE
		 	bit 1		bit 1		TD-ATT-U1
		 	bit 2		bit 2		TD-SNR-U1
		 	bit 3		bit 3		LOM-MCSx
		 	bit 4		bit 4		BER3-MCSx
		 	bit 5		bit 5		BER6-MCSx
		 	bit 6		bit 6		LOM-FARMCSx
		 	bit 7		bit 7		LOM
		 Byte 3		Byte 7
		 	bit 0		bit 0		PLOM
		 	bit 1		bit 1		LOS-T3
		 	bit 2		bit 2		Powerfail
		 	bit 3		bit 3		XFW
		 	bit 4		bit 4		
		 	bit 5		bit 5		
		 	bit 6		bit 6		
		 	bit 7		bit 7		
		 
		 Byte 8 contains a value specifying the validity of the
		 result of a read operation:
		 1	Ok	Values returned are valid
		 2	NotLt	The local device is not an LT
		 254		unknown values
		 255		unsupported variable for addressed device"
	::= { fmrwHtuLtMaskEntry 5 }

--------------------------------------------------------------------------------
--	FM-RW	HtuNt Local Mask
--------------------------------------------------------------------------------
fmrwHtuNtMaskTable OBJECT-TYPE
	SYNTAX SEQUENCE OF FmrwHtuNtMaskEntry
	ACCESS not-accessible
	STATUS mandatory
	DESCRIPTION ""
	::= { fmrwMask 2 }

fmrwHtuNtMaskEntry OBJECT-TYPE
	SYNTAX FmrwHtuNtMaskEntry
	ACCESS not-accessible
	STATUS mandatory
	DESCRIPTION ""
	INDEX { fmrwHtuNtMaskPortIndex, fmrwHtuNtMaskLinkIndex }
	::= { fmrwHtuNtMaskTable 1 }

FmrwHtuNtMaskEntry ::=
	SEQUENCE
	{
		fmrwHtuNtMaskPortIndex INTEGER,
		fmrwHtuNtMaskLinkIndex INTEGER,
		fmrwHtuNtMask OCTET STRING,
		fmrwStuNtMask OCTET STRING,
		fmrwStu4NtMask OCTET STRING
	}

fmrwHtuNtMaskPortIndex OBJECT-TYPE
	SYNTAX INTEGER
	ACCESS read-only
	STATUS mandatory
	DESCRIPTION
		"This variable addresses the port number of the proxy
		and is used as index for the other elements in the Table"
	::= { fmrwHtuNtMaskEntry 1 }

fmrwHtuNtMaskLinkIndex OBJECT-TYPE
	SYNTAX INTEGER
	ACCESS read-only
	STATUS mandatory
	DESCRIPTION
		"This variable addresses the slot number of the OMI sub-rack
		and is used as index for the other elements in the Table"
	::= { fmrwHtuNtMaskEntry 2 }

fmrwHtuNtMask OBJECT-TYPE
	SYNTAX OCTET STRING(SIZE(9))
	ACCESS read-write
	STATUS mandatory
	DESCRIPTION
		"Alarm Severity Mask and Alarm Suppression Mask for NT Alarms.
		
		 This variable is an 8 byte octet string. Bytes 0-3 contain the
		 alarm suppression mask, bytes 4-7 contain the severity map.
		 The masks are bit coded. If a bit in the suppression mask is set,
		 the corresponding alarm has the severity defined by the severity
		 mask. If the bit in the suppression mask is zero, the corresponding
		 alarm has no severity (i.e. has no influence on the alarm summary).
		 If a bit in the severity mask is set, the corresponding alarm is
		 considered to be 'Urgent', if it is zero, the alarm is 'Non-Urgent'.
		 The alarms are coded as follows:
		 
		 Suppression	Severity	Alarm
		 Byte 0		Byte 4
		 	bit 0		bit 0		LOS-U
		 	bit 1		bit 1		LFA-U
		 	bit 2		bit 2		AIS-U
		 	bit 3		bit 3		HPO-U
		 	bit 4		bit 4		FPO-U
		 	bit 5		bit 5		RAI-U
		 	bit 6		bit 6		BER3-U
		 	bit 7		bit 7		BER6-U
		 Byte 1		Byte 5
		 	bit 0		bit 0		LOS-U1
		 	bit 1		bit 1		BER3-U1
		 	bit 2		bit 2		BER6-U1
		 	bit 3		bit 3		LOS-U2
		 	bit 4		bit 4		BER3-U2
		 	bit 5		bit 5		BER6-U2
		 	bit 6		bit 6		LOS-T
		 	bit 7		bit 7		LFA-T
		 Byte 2		Byte 6
		 	bit 0		bit 0		AIS-T
		 	bit 1		bit 1		RAI-T
		 	bit 2		bit 2		BER3-T
		 	bit 3		bit 3		BER6-T
		 	bit 4		bit 4		LOAR-D
		 	bit 5		bit 5		LOAT-D
		 	bit 6		bit 6		Equipment
		 	bit 7		bit 7		A-LOS
		 Byte 3		Byte 7
		 	bit 0		bit 0		LOS-T4
		 	bit 1		bit 1		unused
		 	bit 2		bit 2		unused
		 	bit 3		bit 3		unused
		 	bit 4		bit 4		unused
		 	bit 5		bit 5		unused
		 	bit 6		bit 6		unused
		 	bit 7		bit 7		unused
		 
		 Byte 8 contains a value specifying the validity of the
		 result of a read operation:
		 1	Ok	Values returned are valid
		 254		unknown values
		 255		unsupported variable for addressed device"
	::= { fmrwHtuNtMaskEntry 3 }

fmrwStuNtMask OBJECT-TYPE
	SYNTAX OCTET STRING(SIZE(11))
	ACCESS read-write
	STATUS mandatory
	DESCRIPTION
		"Alarm Severity Mask and Alarm Suppression Mask for NT Alarms.
		
		 This variable is an 10 byte octet string. Bytes 0-4 contain the
		 alarm suppression mask, bytes 5-9 contain the severity map.
		 The masks are bit coded. If a bit in the suppression mask is set,
		 the corresponding alarm has the severity defined by the severity
		 mask. If the bit in the suppression mask is zero, the corresponding
		 alarm has no severity (i.e. has no influence on the alarm summary).
		 If a bit in the severity mask is set, the corresponding alarm is
		 considered to be 'Urgent', if it is zero, the alarm is 'Non-Urgent'.
		 The alarms are coded as follows:
		 
		 Suppression	Severity	Alarm
		 Byte 0		Byte 5
		 	bit 0		bit 0		LOS-U
		 	bit 1		bit 1		LFA-U
		 	bit 2		bit 2		AIS-U
		 	bit 3		bit 3		HPO-U
		 	bit 4		bit 4		FPO-U
		 	bit 5		bit 5		RAI-U
		 	bit 6		bit 6		BER3-U
		 	bit 7		bit 7		BER6-U
		 Byte 1		Byte 6
		 	bit 0		bit 0		LOS-U1
		 	bit 1		bit 1		BER3-U1
		 	bit 2		bit 2		BER6-U1
		 	bit 3		bit 3		LOS-U2
		 	bit 4		bit 4		BER3-U2
		 	bit 5		bit 5		BER6-U2
		 	bit 6		bit 6		LOS-T
		 	bit 7		bit 7		LFA-T
		 Byte 2		Byte 7
		 	bit 0		bit 0		AIS-T
		 	bit 1		bit 1		RAI-T
		 	bit 2		bit 2		BER3-T
		 	bit 3		bit 3		BER6-T
		 	bit 4		bit 4		LOAR-D
		 	bit 5		bit 5		LOAT-D
		 	bit 6		bit 6		Equipment
		 	bit 7		bit 7		A-LOS
		 Byte 3		Byte 8
		 	bit 0		bit 0		LOS-T4
		 	bit 1		bit 1		U-Bandwidth unavailable
		 	bit 2		bit 2		LOSW-U1
		 	bit 3		bit 3		LOSW-U2
		 	bit 4		bit 4		Powerfail CPE
		 	bit 5		bit 5		TD-ATT-U1
		 	bit 6		bit 6		TD-SNR-U1
		 	bit 7		bit 7		TD-ATT-U2
		 Byte 4		Byte 9
		 	bit 0		bit 0		TD-SNR-U2
		 	bit 1		bit 1		unused
		 	bit 2		bit 2		unused
		 	bit 3		bit 3		unused
		 	bit 4		bit 4		unused
		 	bit 5		bit 5		unused
		 	bit 6		bit 6		unused
		 	bit 7		bit 7		unused
		 
		 Byte 10 contains a value specifying the validity of the
		 result of a read operation:
		 1	Ok	Values returned are valid
		 254		unknown values
		 255		unsupported variable for addressed device"
	::= { fmrwHtuNtMaskEntry 4 }

fmrwStu4NtMask OBJECT-TYPE
	SYNTAX OCTET STRING(SIZE(9))
	ACCESS read-write
	STATUS mandatory
	DESCRIPTION
		"Alarm Severity Mask and Alarm Suppression Mask for NT Alarms.
		 
		 This variable only returns meaningful values if the management
		 system is connected to an LT device. If it is connected to an
		 NT device on the local interface, this variable will return
		 'NotLt' as result.
		 
		 This variable is an 8 byte octet string. Bytes 0-3 contain the
		 alarm suppression mask, bytes 4-7 contain the severity map.
		 The masks are bit coded. If a bit in the suppression mask is set,
		 the corresponding alarm has the severity defined by the severity
		 mask. If the bit in the suppression mask is zero, the corresponding
		 alarm has no severity (i.e. has no influence on the alarm summary).
		 If a bit in the severity mask is set, the corresponding alarm is
		 considered to be 'Urgent', if it is zero, the alarm is 'Non-Urgent'.
		 The alarms are coded as follows:
		 
		 Suppression	Severity	Alarm
		 Byte 0		Byte 4
		 	bit 0		bit 0		LOS-U1
		 	bit 1		bit 1		BER3-U1
		 	bit 2		bit 2		BER6-U1
		 	bit 3		bit 3		LOSW-U1
		 	bit 4		bit 4		LOS-V_A
		 	bit 5		bit 5		LFA-V_A
		 	bit 6		bit 6		AIS-V_A
		 	bit 7		bit 7		RAI-V_A
		 Byte 1		Byte 5
		 	bit 0		bit 0		BER3-V_A
		 	bit 1		bit 1		BER6-V_A
		 	bit 2		bit 2		LOAR-WAN
		 	bit 3		bit 3		LOAT-WAN
		 	bit 4		bit 4		MIR-WAN
		 	bit 5		bit 5		LINKDOWN-P1
		 	bit 6		bit 6		Equipment
		 	bit 7		bit 7		A-LOS
		 Byte 2		Byte 6
		 	bit 0		bit 0		TD-ATT-U1
		 	bit 1		bit 1		TD-SNR-U1
		 	bit 2		bit 2		LOM-MCSx
		 	bit 3		bit 3		BER3-MCSx
		 	bit 4		bit 4		BER6-MCSx
		 	bit 5		bit 5		LOM-FARMCSx
		 	bit 6		bit 6		LOM
		 	bit 7		bit 7		PLOM
		 Byte 3		Byte 7
		 	bit 0		bit 0		Powerfail
		 	bit 1		bit 1		
		 	bit 2		bit 2		
		 	bit 3		bit 3		
		 	bit 4		bit 4		
		 	bit 5		bit 5		
		 	bit 6		bit 6		
		 	bit 7		bit 7		
		 
		 Byte 8 contains a value specifying the validity of the
		 result of a read operation:
		 1	Ok	Values returned are valid
		 254		unknown values
		 255		unsupported variable for addressed device"
	::= { fmrwHtuNtMaskEntry 5 }

--------------------------------------------------------------------------------
--	FM-RW	Rps Mask
--------------------------------------------------------------------------------
fmrwRpsMaskTable OBJECT-TYPE
	SYNTAX SEQUENCE OF FmrwRpsMaskEntry
	ACCESS not-accessible
	STATUS mandatory
	DESCRIPTION ""
	::= { fmrwMask 4 }

fmrwRpsMaskEntry OBJECT-TYPE
	SYNTAX FmrwRpsMaskEntry
	ACCESS not-accessible
	STATUS mandatory
	DESCRIPTION ""
	INDEX { fmrwRpsMaskPortIndex, fmrwRpsMaskLinkIndex }
	::= { fmrwRpsMaskTable 1 }

FmrwRpsMaskEntry ::=
	SEQUENCE
	{
		fmrwRpsMaskPortIndex INTEGER,
		fmrwRpsMaskLinkIndex INTEGER,
		fmrwRpsMask OCTET STRING
	}

fmrwRpsMaskPortIndex OBJECT-TYPE
	SYNTAX INTEGER
	ACCESS read-only
	STATUS mandatory
	DESCRIPTION
		"This variable addresses the port number of the proxy
		and is used as index for the other elements in the Table"
	::= { fmrwRpsMaskEntry 1 }

fmrwRpsMaskLinkIndex OBJECT-TYPE
	SYNTAX INTEGER
	ACCESS read-only
	STATUS mandatory
	DESCRIPTION
		"This variable addresses the slot number of the OMI sub-rack
		and is used as index for the other elements in the Table"
	::= { fmrwRpsMaskEntry 2 }

fmrwRpsMask OBJECT-TYPE
	SYNTAX OCTET STRING(SIZE(3))
	ACCESS read-write
	STATUS mandatory
	DESCRIPTION
		"Alarm Severity Mask and Alarm Suppression Mask for Remote Power Supply (RPS).
		
		 This variable only returns meaningful values if the management
		 system is connected to an LT device. If it is connected to an
		 NT device on the local interface, this variable will return
		 'NotLt' as result.
		 
		 This variable is an 2 byte octet string. Byte 0 contains the
		 alarm suppression mask, byte 1 contains the severity map.
		 The masks are bit coded. If a bit in the suppression mask is set,
		 the corresponding alarm has the severity defined by the severity
		 mask. If the bit in the suppression mask is zero, the corresponding
		 alarm has no severity (i.e. has no influence on the alarm summary).
		 If a bit in the severity mask is set, the corresponding alarm is
		 considered to be 'Urgent', if it is zero, the alarm is 'Non-Urgent'.
		 The alarms are coded as follows:
		 
		 Suppression	Severity	Alarm
		 Byte 0		Byte 1
		 	bit 0		bit 0		UCR12
		 	bit 1		bit 1		UCR1
		 	bit 2		bit 2		UCR2
		 	bit 3		bit 3		OVR
		 	bit 4		bit 4		NOSYM
		 	bit 5		bit 5		DEFECT
		 	bit 6		bit 6		unused
		 	bit 7		bit 7		unused
		 
		 Byte 2 contains a value specifying the validity of the
		 result of a read operation:
		 1	Ok	Values returned are valid
		 2	NotLt	The local device is not an LT
		 254		unknown values
		 255		unsupported variable for addressed device"
	::= { fmrwRpsMaskEntry 3 }

--------------------------------------------------------------------------------
--	FM-RW	Regen Section A Mask
--------------------------------------------------------------------------------
fmrwRegAMaskTable OBJECT-TYPE
	SYNTAX SEQUENCE OF FmrwRegAMaskEntry
	ACCESS not-accessible
	STATUS mandatory
	DESCRIPTION ""
	::= { fmrwMask 5 }

fmrwRegAMaskEntry OBJECT-TYPE
	SYNTAX FmrwRegAMaskEntry
	ACCESS not-accessible
	STATUS mandatory
	DESCRIPTION ""
	INDEX { fmrwRegAMaskPortIndex, fmrwRegAMaskLinkIndex }
	::= { fmrwRegAMaskTable 1 }

FmrwRegAMaskEntry ::=
	SEQUENCE
	{
		fmrwRegAMaskPortIndex INTEGER,
		fmrwRegAMaskLinkIndex INTEGER,
		fmrwRegAMask OCTET STRING
	}

fmrwRegAMaskPortIndex OBJECT-TYPE
	SYNTAX INTEGER
	ACCESS read-only
	STATUS mandatory
	DESCRIPTION
		"This variable addresses the port number of the proxy
		and is used as index for the other elements in the Table"
	::= { fmrwRegAMaskEntry 1 }

fmrwRegAMaskLinkIndex OBJECT-TYPE
	SYNTAX INTEGER
	ACCESS read-only
	STATUS mandatory
	DESCRIPTION
		"This variable addresses the slot number of the OMI sub-rack
		and is used as index for the other elements in the Table"
	::= { fmrwRegAMaskEntry 2 }

fmrwRegAMask OBJECT-TYPE
	SYNTAX OCTET STRING(SIZE(5))
	ACCESS read-write
	STATUS mandatory
	DESCRIPTION
		"Alarm Severity Mask and Alarm Suppression Mask for Regenerator Section A (LT side).
		
		 This variable only returns meaningful values if the management
		 system is connected to an LT device. If it is connected to an
		 NT device on the local interface, this variable will return
		 'NotLt' as result.
		 
		 This variable is a 4 byte octet string. Bytes 0-1 contain the
		 alarm suppression mask, bytes 2-3 contain the severity map.
		 The masks are bit coded. If a bit in the suppression mask is set,
		 the corresponding alarm has the severity defined by the severity
		 mask. If the bit in the suppression mask is zero, the corresponding
		 alarm has no severity (i.e. has no influence on the alarm summary).
		 If a bit in the severity mask is set, the corresponding alarm is
		 considered to be 'Urgent', if it is zero, the alarm is 'Non-Urgent'.
		 The alarms are coded as follows:
		 
		 Suppression	Severity	Alarm
		 Byte 0		Byte 2
		 	bit 0		bit 0		LOS-R1L
		 	bit 1		bit 1		BER3-R1L
		 	bit 2		bit 2		BER6-R1L
		 	bit 3		bit 3		LOS-R2L
		 	bit 4		bit 4		BER3-R2L
		 	bit 5		bit 5		BER6-R2L
		 	bit 6		bit 6		LOS-R1N
		 	bit 7		bit 7		BER3-R1N
		 Byte 1		Byte 3
		 	bit 0		bit 0		BER6-R1N
		 	bit 1		bit 1		LOS-R2N
		 	bit 2		bit 2		BER3-R2N
		 	bit 3		bit 3		BER6-R2N
		 	bit 4		bit 4		Equipment1
		 	bit 5		bit 5		Equipment2
		 	bit 6		bit 6		unused
		 	bit 7		bit 7		unused
		 
		 Byte 4 contains a value specifying the validity of the
		 result of a read operation:
		 1	Ok	Values returned are valid
		 2	NotLt	The local device is not an LT
		 254		unknown values
		 255		unsupported variable for addressed device"
	::= { fmrwRegAMaskEntry 3 }

--------------------------------------------------------------------------------
--	FM-RW	OMI Mask
--------------------------------------------------------------------------------
fmrwOmiMaskTable OBJECT-TYPE
	SYNTAX SEQUENCE OF FmrwOmiMaskEntry
	ACCESS not-accessible
	STATUS mandatory
	DESCRIPTION ""
	::= { fmrwMask 7 }

fmrwOmiMaskEntry OBJECT-TYPE
	SYNTAX FmrwOmiMaskEntry
	ACCESS not-accessible
	STATUS mandatory
	DESCRIPTION ""
	INDEX { fmrwOmiMaskPortIndex }
	::= { fmrwOmiMaskTable 1 }

FmrwOmiMaskEntry ::=
	SEQUENCE
	{
		fmrwOmiMaskPortIndex INTEGER,
		fmrwOmiMask OCTET STRING,
		fmrwOmiExtInputMask OCTET STRING,
		fmrwOmiNMSMask OCTET STRING,
		fmrwOmiFEMask OCTET STRING,
		fmrwOmiGBEMask OCTET STRING,
		fmrwOmiSFPMask OCTET STRING,
		fmrwOmiOutputMask INTEGER,
		fmrwOmiCESMask OCTET STRING
	}

fmrwOmiMaskPortIndex OBJECT-TYPE
	SYNTAX INTEGER
	ACCESS read-only
	STATUS mandatory
	DESCRIPTION
		"This variable addresses the port number of the proxy
		and is used as index for the other elements in the Table"
	::= { fmrwOmiMaskEntry 1 }

fmrwOmiMask OBJECT-TYPE
	SYNTAX OCTET STRING(SIZE(3))
	ACCESS read-write
	STATUS mandatory
	DESCRIPTION
		"Alarm Severity Mask and Alarm Suppression Mask for the OMI card.
		
		 This variable is a 2 byte octet string. Byte 0 contains the
		 alarm suppression mask, byte 1 contains the severity map.
		 The masks are bit coded. If a bit in the suppression mask is set,
		 the corresponding alarm has the severity defined by the severity
		 mask. If the bit in the suppression mask is zero, the corresponding
		 alarm has no severity (i.e. has no influence on the alarm summary).
		 If a bit in the severity mask is set, the corresponding alarm is
		 considered to be 'Urgent', if it is zero, the alarm is 'Non-Urgent'.
		 The alarms are coded as follows:
		 
		 Suppression	Severity	Alarm
		 Byte 0		Byte 1
		 	bit 0		bit 0		BAT1
		 	bit 1		bit 1		BAT2
		 	bit 2		bit 2		AUX BAT MCU
		 	bit 3		bit 3		unused
		 	bit 4		bit 4		unused
		 	bit 5		bit 5		unused
		 	bit 6		bit 6		unused
		 	bit 7		bit 7		unused
		 
		 Byte 2 contains a value specifying the validity of the
		 result of a read operation:
		 1	Ok	Values returned are valid
		 254		unknown values
		 255		unsupported variable for addressed device"
	::= { fmrwOmiMaskEntry 2 }

fmrwOmiExtInputMask OBJECT-TYPE
	SYNTAX OCTET STRING(SIZE(3))
	ACCESS read-write
	STATUS mandatory
	DESCRIPTION
		"External input alarm Severity and Suppression Mask for the MCU card.

		 Byte 0 alarm suppression mask, (bit coded: 0=masked 1= no masked)
		 Byte 1 alarm severity map (bit coded: 0=not urgent, 1=urgent)
		 The masks are bit coded. If a bit in the suppression mask is set,
		 the corresponding alarm has the severity defined by the severity
		 mask. If the bit in the suppression mask is zero, the corresponding
		 alarm has no severity (i.e. has no influence on the alarm summary).
		 If a bit in the severity mask is set, the corresponding alarm is
		 considered to be 'Urgent', if it is zero, the alarm is 'Non-Urgent'.
		 The alarm mask is bit coded as follows:

		 Suppression	Severity	Alarm
		 Byte 0		Byte 1
		 	bit 0		bit 0		EXTERNAL INPUT 1
		 	bit 1		bit 1		EXTERNAL INPUT 2
		 	bit 2		bit 2		EXTERNAL INPUT 3
		 	bit 3		bit 3		EXTERNAL INPUT 4
		 	bit 4		bit 4		unused
		 	bit 5		bit 5		unused
		 	bit 6		bit 6		unused
		 	bit 7		bit 7		unused

		 Byte 2 contains a value specifying the validity of the
		 result of a read operation:
		 1	Ok	Values returned are valid
		 254		unknown values
		 255		unsupported variable for addressed device"
	::= { fmrwOmiMaskEntry 3 }

fmrwOmiNMSMask OBJECT-TYPE
	SYNTAX OCTET STRING(SIZE(3))
	ACCESS read-write
	STATUS mandatory
	DESCRIPTION
		"NMS link alarm Severity and Suppression Mask for the MCU card.

		 Byte 0 alarm suppression mask, (bit coded: 0=masked 1= no masked)
		 Byte 1 alarm severity map (bit coded: 0=not urgent, 1=urgent)
		 The masks are bit coded. If a bit in the suppression mask is set,
		 the corresponding alarm has the severity defined by the severity
		 mask. If the bit in the suppression mask is zero, the corresponding
		 alarm has no severity (i.e. has no influence on the alarm summary).
		 If a bit in the severity mask is set, the corresponding alarm is
		 considered to be 'Urgent', if it is zero, the alarm is 'Non-Urgent'.
		 The alarm mask is bit coded as follows:

		 Suppression	Severity	Alarm
		 Byte 0		Byte 1
		 	bit 0		bit 0		NMS LINK ALARM
		 	bit 1		bit 1		unused
		 	bit 2		bit 2		unused
		 	bit 3		bit 3		unused
		 	bit 4		bit 4		unused
		 	bit 5		bit 5		unused
		 	bit 6		bit 6		unused
		 	bit 7		bit 7		unused

		 Byte 2 contains a value specifying the validity of the
		 result of a read operation:
		 1	Ok	Values returned are valid
		 254		unknown values
		 255		unsupported variable for addressed device"
	::= { fmrwOmiMaskEntry 4 }

fmrwOmiFEMask OBJECT-TYPE
	SYNTAX OCTET STRING(SIZE(3))
	ACCESS read-write
	STATUS mandatory
	DESCRIPTION
		"Fast Ethernet link alarm Severity and Suppression Mask for the MCU card.

		 Byte 0 alarm suppression mask, (bit coded: 0=masked 1= no masked)
		 Byte 1 alarm severity map (bit coded: 0=not urgent, 1=urgent)
		 The masks are bit coded. If a bit in the suppression mask is set,
		 the corresponding alarm has the severity defined by the severity
		 mask. If the bit in the suppression mask is zero, the corresponding
		 alarm has no severity (i.e. has no influence on the alarm summary).
		 If a bit in the severity mask is set, the corresponding alarm is
		 considered to be 'Urgent', if it is zero, the alarm is 'Non-Urgent'.
		 The alarm mask is bit coded as follows:

		 Suppression	Severity	Alarm
		 Byte 0		Byte 1
		 	bit 0		bit 0		FE LINK ALARM
		 	bit 1		bit 1		unused
		 	bit 2		bit 2		unused
		 	bit 3		bit 3		unused
		 	bit 4		bit 4		unused
		 	bit 5		bit 5		unused
		 	bit 6		bit 6		unused
		 	bit 7		bit 7		unused

		 Byte 2 contains a value specifying the validity of the
		 result of a read operation:
		 1	Ok	Values returned are valid
		 254		unknown values
		 255		unsupported variable for addressed device"
	::= { fmrwOmiMaskEntry 5 }

fmrwOmiGBEMask OBJECT-TYPE
	SYNTAX OCTET STRING(SIZE(3))
	ACCESS read-write
	STATUS mandatory
	DESCRIPTION
		"GigaBit Ethernet link alarm Severity and Suppression Mask for the MCU card.

		 Byte 0 alarm suppression mask, (bit coded: 0=masked 1= no masked)
		 Byte 1 alarm severity map (bit coded: 0=not urgent, 1=urgent)
		 The masks are bit coded. If a bit in the suppression mask is set,
		 the corresponding alarm has the severity defined by the severity
		 mask. If the bit in the suppression mask is zero, the corresponding
		 alarm has no severity (i.e. has no influence on the alarm summary).
		 If a bit in the severity mask is set, the corresponding alarm is
		 considered to be 'Urgent', if it is zero, the alarm is 'Non-Urgent'.
		 The alarm mask is bit coded as follows:

		 Suppression	Severity	Alarm
		 Byte 0		Byte 1
		 	bit 0		bit 0		GBE LINK ALARM
		 	bit 1		bit 1		unused
		 	bit 2		bit 2		unused
		 	bit 3		bit 3		unused
		 	bit 4		bit 4		unused
		 	bit 5		bit 5		unused
		 	bit 6		bit 6		unused
		 	bit 7		bit 7		unused

		 Byte 2 contains a value specifying the validity of the
		 result of a read operation:
		 1	Ok	Values returned are valid
		 254		unknown values
		 255		unsupported variable for addressed device"
	::= { fmrwOmiMaskEntry 6 }

fmrwOmiSFPMask OBJECT-TYPE
	SYNTAX OCTET STRING(SIZE(3))
	ACCESS read-write
	STATUS mandatory
	DESCRIPTION
		"SFP laser/interface alarm Severity and Suppression Mask for the MCU card.

		 Byte 0 alarm suppression mask, (bit coded: 0=masked 1= no masked)
		 Byte 1 alarm severity map (bit coded: 0=not urgent, 1=urgent)
		 The masks are bit coded. If a bit in the suppression mask is set,
		 the corresponding alarm has the severity defined by the severity
		 mask. If the bit in the suppression mask is zero, the corresponding
		 alarm has no severity (i.e. has no influence on the alarm summary).
		 If a bit in the severity mask is set, the corresponding alarm is
		 considered to be 'Urgent', if it is zero, the alarm is 'Non-Urgent'.
		 The alarm mask is bit coded as follows:

		 Suppression	Severity	Alarm
		 Byte 0		Byte 1
		 	bit 0		bit 0		SFP LASER ALARM
		 	bit 1		bit 1		SFP INTERFACE ALARM
		 	bit 2		bit 2		unused
		 	bit 3		bit 3		unused
		 	bit 4		bit 4		unused
		 	bit 5		bit 5		unused
		 	bit 6		bit 6		unused
		 	bit 7		bit 7		unused

		 Byte 2 contains a value specifying the validity of the
		 result of a read operation:
		 1	Ok	Values returned are valid
		 254		unknown values
		 255		unsupported variable for addressed device"
	::= { fmrwOmiMaskEntry 7 }

fmrwOmiOutputMask OBJECT-TYPE
	SYNTAX INTEGER
	{
		off(1),
		on(2),
		unknown(254),
		unsupported(255)
	}
	ACCESS read-write
	STATUS mandatory
	DESCRIPTION
		"Alarm output mask for the MCU card
		1	Alarm output Off
		2	Alarm output On
		254	unknown value
		255	unsupported variable for addressed device"
	::= { fmrwOmiMaskEntry 8 }


fmrwOmiCESMask OBJECT-TYPE
	SYNTAX OCTET STRING(SIZE(3))
	ACCESS read-write
	STATUS mandatory
	DESCRIPTION
		"CES interface alarm Severity and Suppression Mask for the MCU card.

		 Byte 0 alarm suppression mask, (bit coded: 0=masked 1= no masked)
		 Byte 1 alarm severity map (bit coded: 0=not urgent, 1=urgent)
		 The masks are bit coded. If a bit in the suppression mask is set,
		 the corresponding alarm has the severity defined by the severity
		 mask. If the bit in the suppression mask is zero, the corresponding
		 alarm has no severity (i.e. has no influence on the alarm summary).
		 If a bit in the severity mask is set, the corresponding alarm is
		 considered to be 'Urgent', if it is zero, the alarm is 'Non-Urgent'.
		 The alarm mask is bit coded as follows:

		 Suppression	Severity	Alarm
		 Byte 0		Byte 1
		 	bit 0		bit 0		LOS TDM
		 	bit 1		bit 1		ARE ETH
		 	bit 2		bit 2		LOF ETH
		 	bit 3		bit 3		LOS Clock In
		 	bit 4		bit 4		AIS TDM
		 	bit 5		bit 5		RAI ETH
		 	bit 6		bit 6		AIS ETH
		 	bit 7		bit 7		unused

		 Byte 2 contains a value specifying the validity of the
		 result of a read operation:
		 1	Ok	Values returned are valid
		 254		unknown values
		 255		unsupported variable for addressed device"
	::= { fmrwOmiMaskEntry 9 }

--------------------------------------------------------------------------------
--	FM-RW	NT Rps Mask
--------------------------------------------------------------------------------
fmrwFarRpsMaskTable OBJECT-TYPE
	SYNTAX SEQUENCE OF FmrwFarRpsMaskEntry
	ACCESS not-accessible
	STATUS mandatory
	DESCRIPTION ""
	::= { fmrwMask 8 }

fmrwFarRpsMaskEntry OBJECT-TYPE
	SYNTAX FmrwFarRpsMaskEntry
	ACCESS not-accessible
	STATUS mandatory
	DESCRIPTION ""
	INDEX { fmrwFarRpsMaskPortIndex, fmrwFarRpsMaskLinkIndex }
	::= { fmrwFarRpsMaskTable 1 }

FmrwFarRpsMaskEntry ::=
	SEQUENCE
	{
		fmrwFarRpsMaskPortIndex INTEGER,
		fmrwFarRpsMaskLinkIndex INTEGER,
		fmrwFarRpsMask OCTET STRING
	}

fmrwFarRpsMaskPortIndex OBJECT-TYPE
	SYNTAX INTEGER
	ACCESS read-only
	STATUS mandatory
	DESCRIPTION
		"This variable addresses the port number of the proxy
		and is used as index for the other elements in the Table"
	::= { fmrwFarRpsMaskEntry 1 }

fmrwFarRpsMaskLinkIndex OBJECT-TYPE
	SYNTAX INTEGER
	ACCESS read-only
	STATUS mandatory
	DESCRIPTION
		"This variable addresses the slot number of the OMI sub-rack
		and is used as index for the other elements in the Table"
	::= { fmrwFarRpsMaskEntry 2 }

fmrwFarRpsMask OBJECT-TYPE
	SYNTAX OCTET STRING(SIZE(3))
	ACCESS read-write
	STATUS mandatory
	DESCRIPTION
		"Alarm Severity Mask and Alarm Suppression Mask for Remote Power Supply (RPS).
		
		 This variable only returns meaningful values if the management
		 system is connected to an LT device. If it is connected to an
		 NT device on the local interface, this variable will return
		 'NotLt' as result.
		 
		 This variable is an 2 byte octet string. Byte 0 contains the
		 alarm suppression mask, byte 1 contains the severity map.
		 The masks are bit coded. If a bit in the suppression mask is set,
		 the corresponding alarm has the severity defined by the severity
		 mask. If the bit in the suppression mask is zero, the corresponding
		 alarm has no severity (i.e. has no influence on the alarm summary).
		 If a bit in the severity mask is set, the corresponding alarm is
		 considered to be 'Urgent', if it is zero, the alarm is 'Non-Urgent'.
		 The alarms are coded as follows:
		 
		 Suppression	Severity	Alarm
		 Byte 0		Byte 1
		 	bit 0		bit 0		UCR12
		 	bit 1		bit 1		UCR1
		 	bit 2		bit 2		UCR2
		 	bit 3		bit 3		OVR
		 	bit 4		bit 4		NOSYM
		 	bit 5		bit 5		DEFECT
		 	bit 6		bit 6		unused
		 	bit 7		bit 7		unused
		 
		 Byte 2 contains a value specifying the validity of the
		 result of a read operation:
		 1	Ok	Values returned are valid
		 254		unknown values
		 255		unsupported variable for addressed device"
	::= { fmrwFarRpsMaskEntry 3 }

--------------------------------------------------------------------------------
--	FM-RW	SRU Mask
--------------------------------------------------------------------------------
fmrwSruMaskTable OBJECT-TYPE
	SYNTAX SEQUENCE OF FmrwSruMaskEntry
	ACCESS not-accessible
	STATUS mandatory
	DESCRIPTION ""
	::= { fmrwMask 9 }

fmrwSruMaskEntry OBJECT-TYPE
	SYNTAX FmrwSruMaskEntry
	ACCESS not-accessible
	STATUS mandatory
	DESCRIPTION ""
	INDEX { fmrwSruMaskPortIndex, fmrwSruMaskLinkIndex }
	::= { fmrwSruMaskTable 1 }

FmrwSruMaskEntry ::=
	SEQUENCE
	{
		fmrwSruMaskPortIndex INTEGER,
		fmrwSruMaskLinkIndex INTEGER,
		fmrwSruMask OCTET STRING
	}

fmrwSruMaskPortIndex OBJECT-TYPE
	SYNTAX INTEGER
	ACCESS read-only
	STATUS mandatory
	DESCRIPTION
		"This variable addresses the port number of the proxy
		and is used as index for the other elements in the Table"
	::= { fmrwSruMaskEntry 1 }

fmrwSruMaskLinkIndex OBJECT-TYPE
	SYNTAX INTEGER
	ACCESS read-only
	STATUS mandatory
	DESCRIPTION
		"This variable addresses the slot number of the OMI sub-rack
		and is used as index for the other elements in the Table"
	::= { fmrwSruMaskEntry 2 }

fmrwSruMask OBJECT-TYPE
	SYNTAX OCTET STRING(SIZE(5))
	ACCESS read-write
	STATUS mandatory
	DESCRIPTION
		"Alarm Severity Mask and Alarm Suppression Mask for Regenerator Section A (LT side).
		
		 This variable only returns meaningful values if the management
		 system is connected to an LT device. If it is connected to an
		 NT device on the local interface, this variable will return
		 'NotLt' as result.
		 
		 This variable is a 4 byte octet string. Bytes 0-1 contain the
		 alarm suppression mask, bytes 2-3 contain the severity map.
		 The masks are bit coded. If a bit in the suppression mask is set,
		 the corresponding alarm has the severity defined by the severity
		 mask. If the bit in the suppression mask is zero, the corresponding
		 alarm has no severity (i.e. has no influence on the alarm summary).
		 If a bit in the severity mask is set, the corresponding alarm is
		 considered to be 'Urgent', if it is zero, the alarm is 'Non-Urgent'.
		 The alarms are coded as follows:
		 
		 Suppression	Severity	Alarm
		 Byte 0		Byte 2
		 	bit 0		bit 0		LOS-L
		 	bit 1		bit 1		BER3-L
		 	bit 2		bit 2		BER6-L
		 	bit 3		bit 3		LOS-N
		 	bit 4		bit 4		BER3-N
		 	bit 5		bit 5		BER6-N
		 	bit 6		bit 6		Equipment
		 	bit 7		bit 7		LOSW-L
		 Byte 1		Byte 3
		 	bit 0		bit 0		LOSW-N
		 	bit 1		bit 1		Thres-Att-L
		 	bit 2		bit 2		Thres-Att-N
		 	bit 3		bit 3		Thres-Snr-L
		 	bit 4		bit 4		Thres-Snr-N
		 	bit 5		bit 5		unused
		 	bit 6		bit 6		unused
		 	bit 7		bit 7		unused
		 
		 Byte 4 contains a value specifying the validity of the
		 result of a read operation:
		 1	Ok	Values returned are valid
		 2	NotLt	The local device is not an LT
		 254		unknown values
		 255		unsupported variable for addressed device"
	::= { fmrwSruMaskEntry 3 }

--------------------------------------------------------------------------------
--	FM-RW	Master GTU Mask
--------------------------------------------------------------------------------
fmrwGtuMasterMaskTable OBJECT-TYPE
	SYNTAX SEQUENCE OF FmrwGtuMasterMaskEntry
	ACCESS not-accessible
	STATUS mandatory
	DESCRIPTION ""
	::= { fmrwMask 10 }

fmrwGtuMasterMaskEntry OBJECT-TYPE
	SYNTAX FmrwGtuMasterMaskEntry
	ACCESS not-accessible
	STATUS mandatory
	DESCRIPTION ""
	INDEX { fmrwGtuMasterMaskPortIndex, fmrwGtuMasterMaskLinkIndex }
	::= { fmrwGtuMasterMaskTable 1 }

FmrwGtuMasterMaskEntry ::=
	SEQUENCE
	{
		fmrwGtuMasterMaskPortIndex INTEGER,
		fmrwGtuMasterMaskLinkIndex INTEGER,
		fmrwGtuMasterMask OCTET STRING
	}

fmrwGtuMasterMaskPortIndex OBJECT-TYPE
	SYNTAX INTEGER
	ACCESS read-only
	STATUS mandatory
	DESCRIPTION
		"This variable addresses the port number of the proxy
		and is used as index for the other elements in the Table"
	::= { fmrwGtuMasterMaskEntry 1 }

fmrwGtuMasterMaskLinkIndex OBJECT-TYPE
	SYNTAX INTEGER
	ACCESS read-only
	STATUS mandatory
	DESCRIPTION
		"This variable addresses the slot number of the OMI sub-rack
		and is used as index for the other elements in the Table"
	::= { fmrwGtuMasterMaskEntry 2 }

fmrwGtuMasterMask OBJECT-TYPE
	SYNTAX OCTET STRING(SIZE(9))
	ACCESS read-write
	STATUS mandatory
	DESCRIPTION
		"Alarm Severity Mask and Alarm Suppression Mask for Master Alarms.
		 
		 This variable only returns meaningful values if the management
		 system is connected to an LT device. If it is connected to an
		 NT device on the local interface, this variable will return
		 'NotLt' as result.
		 
		 This variable is an 8 byte octet string. Bytes 0-3 contain the
		 alarm suppression mask, bytes 4-7 contain the severity map.
		 The masks are bit coded. If a bit in the suppression mask is set,
		 the corresponding alarm has the severity defined by the severity
		 mask. If the bit in the suppression mask is zero, the corresponding
		 alarm has no severity (i.e. has no influence on the alarm summary).
		 If a bit in the severity mask is set, the corresponding alarm is
		 considered to be 'Urgent', if it is zero, the alarm is 'Non-Urgent'.
		 The alarms are coded as follows:
		 
		 Suppression	Severity	Alarm
		 Byte 0		Byte 4
		 	bit 0		bit 0		LOS-V
		 	bit 1		bit 1		LFA-V
		 	bit 2		bit 2		AIS-V
		 	bit 3		bit 3		RAI-V
		 	bit 4		bit 4		BER3-V
		 	bit 5		bit 5		BER6-V
		 	bit 6		bit 6		LOS-T
		 	bit 7		bit 7		LFA-T
		 Byte 1		Byte 5
		 	bit 0		bit 0		AIS-T
		 	bit 1		bit 1		RAI-T
		 	bit 2		bit 2		BER3-T
		 	bit 3		bit 3		BER6-T
		 	bit 4		bit 4		LOAR-D
		 	bit 5		bit 5		LOAT-D
		 	bit 6		bit 6		Equipment
		 	bit 7		bit 7		A-LOS
		 Byte 2		Byte 6
		 	bit 0		bit 0		LOS-T4	
		 	bit 1		bit 1		LOS-V-Slave
		 	bit 2		bit 2		LFA-V-Slave
		 	bit 3		bit 3		AIS-V-Slave
		 	bit 4		bit 4		RAI-V-Slave
		 	bit 5		bit 5		BER3-V-Slave
		 	bit 6		bit 6		BER6-V-Slave
		 	bit 7		bit 7		LOS-T-Slave
		 Byte 3		Byte 7
		 	bit 0		bit 0		LFA-T-Slave
		 	bit 1		bit 1		AIS-T-Slave
		 	bit 2		bit 2		RAI-T-Slave
		 	bit 3		bit 3		BER3-T-Slave
		 	bit 4		bit 4		BER6-T-Slave
		 	bit 5		bit 5		LOAR-D-Slave
		 	bit 6		bit 6		LOAT-D-Slave
		 	bit 7		bit 7		unused
		 
		 Byte 8 contains a value specifying the validity of the
		 result of a read operation:
		 1	Ok	Values returned are valid
		 2	NotLt	The local device is not an LT
		 254		unknown values
		 255		unsupported variable for addressed device"
	::= { fmrwGtuMasterMaskEntry 3 }

--------------------------------------------------------------------------------
--	FM-RW	Local Alarm Mask Configuration
--------------------------------------------------------------------------------
fmrwLocalAlarmMaskConfigTable OBJECT-TYPE
	SYNTAX SEQUENCE OF FmrwLocalAlarmMaskConfigEntry
	ACCESS not-accessible
	STATUS mandatory
	DESCRIPTION ""
	::= { fmrwMask 11 }

fmrwLocalAlarmMaskConfigEntry OBJECT-TYPE
	SYNTAX FmrwLocalAlarmMaskConfigEntry
	ACCESS not-accessible
	STATUS mandatory
	DESCRIPTION ""
	INDEX { fmrwLocalAlarmMaskConfigPortIndex, fmrwLocalAlarmMaskConfigLinkIndex }
	::= { fmrwLocalAlarmMaskConfigTable 1 }

FmrwLocalAlarmMaskConfigEntry ::=
	SEQUENCE
	{
		fmrwLocalAlarmMaskConfigPortIndex INTEGER,
		fmrwLocalAlarmMaskConfigLinkIndex INTEGER,
		fmrwLocalAlarmMaskConfigArray OCTET STRING
	}

fmrwLocalAlarmMaskConfigPortIndex OBJECT-TYPE
	SYNTAX INTEGER
	ACCESS read-only
	STATUS mandatory
	DESCRIPTION
		"This variable addresses the port number of the proxy
		and is used as index for the other elements in the Table"
	::= { fmrwLocalAlarmMaskConfigEntry 1 }

fmrwLocalAlarmMaskConfigLinkIndex OBJECT-TYPE
	SYNTAX INTEGER
	ACCESS read-only
	STATUS mandatory
	DESCRIPTION
		"This variable addresses the slot number of the OMI sub-rack
		and is used as index for the other elements in the Table"
	::= { fmrwLocalAlarmMaskConfigEntry 2 }

fmrwLocalAlarmMaskConfigArray OBJECT-TYPE
	SYNTAX OCTET STRING(SIZE(91))
	ACCESS read-write
	STATUS mandatory
	DESCRIPTION
		"Alarm Severity Mask and Alarm Suppression Mask for LT Alarms.
		 
		 This variable only returns meaningful values if the management
		 system is connected to an LT device. If it is connected to an
		 NT device on the local interface, this variable will return
		 'NotLt' as result.
		 
		 This variable is an 91 byte octet string. Bytes 0-29 contain the
		 alarm suppression mask, bytes 30-59 contain the severity mask,
		 bytes 60-89 contain the logging mask.
		 The masks are bit coded. If a bit in the suppression mask is set,
		 the corresponding alarm has the severity defined by the severity
		 mask. If the bit in the suppression mask is zero, the corresponding
		 alarm has no severity (i.e. has no influence on the alarm summary).
		 If a bit in the severity mask is set, the corresponding alarm is
		 considered to be 'Urgent', if it is zero, the alarm is 'Non-Urgent'.
		 If the bit in the logging mask is set, the corresponding alarm is
		 logged.
		 
		 Alarm mask coding for STUP/QSTUP:
		 
		 Suppression	Severity	Logging		Alarm
		 Byte 0		Byte 30		Byte 60
		  bit 0		 bit 0		 bit 0		XTU_LOS_U
		  bit 1		 bit 1		 bit 1		XTU_LFA_U
		  bit 2		 bit 2		 bit 2		XTU_AIS_U
		  bit 3		 bit 3		 bit 3		XTU_BNA_U
		  bit 4		 bit 4		 bit 4		XTU_RAI_U
		  bit 5		 bit 5		 bit 5		XTU_BER3_U
		  bit 6		 bit 6		 bit 6		XTU_BER6_U
		  bit 7		 bit 7		 bit 7		XTU_LOS_Ux
		 Byte 1		Byte 31		Byte 61
		  bit 0		 bit 0		 bit 0		XTU_LOSW_Ux
		  bit 1		 bit 1		 bit 1		XTU_BER3_Ux
		  bit 2		 bit 2		 bit 2		XTU_BER6_Ux
		  bit 3		 bit 3		 bit 3		XTU_LOS_T
		  bit 4		 bit 4		 bit 4		XTU_LFA_T
		  bit 5		 bit 5		 bit 5		XTU_AIS_T
		  bit 6		 bit 6		 bit 6		XTU_RAI_T
		  bit 7		 bit 7		 bit 7		XTU_BER3_T
		 Byte 21	Byte 32		Byte 62
		  bit 0		 bit 0		 bit 0		XTU_BER6_T
		  bit 1		 bit 1		 bit 1		XTU_LOA_RX_D
		  bit 2		 bit 2		 bit 2		XTU_LOA_TX_D
		  bit 3		 bit 3		 bit 3		XTU_EQUIPMENT
		  bit 4		 bit 4		 bit 4		XTU_LOS_T3
		  bit 5		 bit 5		 bit 5		XTU_LOS_T4
		  bit 6		 bit 6		 bit 6		XTU_P1_LINKDOWN
		  bit 7		 bit 7		 bit 7		XTU_LOA_RX_WAN
		 Byte 3		Byte 33		Byte 63
		  bit 0		 bit 0		 bit 0		XTU_LOA_TX_WAN
		  bit 1		 bit 1		 bit 1		XTU_MIR_TX_WAN
		  bit 2		 bit 2		 bit 2		XTU_LOS_D
		  bit 3		 bit 3		 bit 3		XTU_POWERFAIL
		  bit 4		 bit 4		 bit 4		XTU_REM_PWRFAIL
		  bit 5		 bit 5		 bit 5		XTU_TD_ATT
		  bit 6		 bit 6		 bit 6		XTU_TD_SNR
		  bit 7		 bit 7		 bit 7		XTU_XFW
		 Bytes 4-14	Bytes 34-44	Bytes 64-74
		  unused
		 Byte 15	Byte 45		Byte 75
		  bit 0		 bit 0		 bit 0		XRU_LOS_UL
		  bit 1		 bit 1		 bit 1		XRU_BER3_UL
		  bit 2		 bit 2		 bit 2		XRU_BER6_UL
		  bit 3		 bit 3		 bit 3		XRU_LOS_UN
		  bit 4		 bit 4		 bit 4		XRU_BER3_UN
		  bit 5		 bit 5		 bit 5		XRU_BER6_UN
		  bit 6		 bit 6		 bit 6		XRU_EQUIPMENT
		  bit 7		 bit 7		 bit 7		XRU_LOSW_UL
		 Byte 16	Byte 46		Byte 76
		  bit 0		 bit 0		 bit 0		XRU_LOSW_UN
		  bit 1		 bit 1		 bit 1		XRU_TD_ATT_UL
		  bit 2		 bit 2		 bit 2		XRU_TD_SNR_UL
		  bit 3		 bit 3		 bit 3		XRU_TD_ATT_UN
		  bit 4		 bit 4		 bit 4		XRU_TD_SNR_UN
		  bit 5		 bit 5		 bit 5		unused
		  bit 6		 bit 6		 bit 6		unused
		  bit 7		 bit 7		 bit 7		unused
		 Bytes 17-24	Bytes 47-54	Bytes 77-84
		  unused
		 Byte 25	Byte 55		Byte 85
		  bit 0		 bit 0		 bit 0		RPS_UC
		  bit 1		 bit 1		 bit 1		RPS_OC
		  bit 2		 bit 2		 bit 2		RPS_UNBAL
		  bit 3		 bit 3		 bit 3		RPS_DEFEKT
		  bit 4		 bit 4		 bit 4		unused
		  bit 5		 bit 5		 bit 5		unused
		  bit 6		 bit 6		 bit 6		unused
		  bit 7		 bit 7		 bit 7		unused
		 Bytes 26-29	Bytes 56-59	Bytes 86-89
		  unused
		 
		 Byte 90 contains a value specifying the validity of the
		 result of a read operation:
		 1	Ok	Values returned are valid
		 254		unknown values
		 255		unsupported variable for addressed device"
	::= { fmrwLocalAlarmMaskConfigEntry 3 }

--------------------------------------------------------------------------------
--	FM-RW	Far Alarm Mask Configuration
--------------------------------------------------------------------------------
fmrwFarAlarmMaskConfigTable OBJECT-TYPE
	SYNTAX SEQUENCE OF FmrwFarAlarmMaskConfigEntry
	ACCESS not-accessible
	STATUS mandatory
	DESCRIPTION ""
	::= { fmrwMask 12 }

fmrwFarAlarmMaskConfigEntry OBJECT-TYPE
	SYNTAX FmrwFarAlarmMaskConfigEntry
	ACCESS not-accessible
	STATUS mandatory
	DESCRIPTION ""
	INDEX { fmrwFarAlarmMaskConfigPortIndex, fmrwFarAlarmMaskConfigLinkIndex }
	::= { fmrwFarAlarmMaskConfigTable 1 }

FmrwFarAlarmMaskConfigEntry ::=
	SEQUENCE
	{
		fmrwFarAlarmMaskConfigPortIndex INTEGER,
		fmrwFarAlarmMaskConfigLinkIndex INTEGER,
		fmrwFarAlarmMaskConfigArray OCTET STRING
	}

fmrwFarAlarmMaskConfigPortIndex OBJECT-TYPE
	SYNTAX INTEGER
	ACCESS read-only
	STATUS mandatory
	DESCRIPTION
		"This variable addresses the port number of the proxy
		and is used as index for the other elements in the Table"
	::= { fmrwFarAlarmMaskConfigEntry 1 }

fmrwFarAlarmMaskConfigLinkIndex OBJECT-TYPE
	SYNTAX INTEGER
	ACCESS read-only
	STATUS mandatory
	DESCRIPTION
		"This variable addresses the slot number of the OMI sub-rack
		and is used as index for the other elements in the Table"
	::= { fmrwFarAlarmMaskConfigEntry 2 }

fmrwFarAlarmMaskConfigArray OBJECT-TYPE
	SYNTAX OCTET STRING(SIZE(91))
	ACCESS read-write
	STATUS mandatory
	DESCRIPTION
		"Alarm Severity Mask and Alarm Suppression Mask for NT Alarms.
		 
		 This variable is an 91 byte octet string. Bytes 0-29 contain the
		 alarm suppression mask, bytes 30-59 contain the severity mask,
		 bytes 60-89 contain the logging mask.
		 The masks are bit coded. If a bit in the suppression mask is set,
		 the corresponding alarm has the severity defined by the severity
		 mask. If the bit in the suppression mask is zero, the corresponding
		 alarm has no severity (i.e. has no influence on the alarm summary).
		 If a bit in the severity mask is set, the corresponding alarm is
		 considered to be 'Urgent', if it is zero, the alarm is 'Non-Urgent'.
		 If the bit in the logging mask is set, the corresponding alarm is
		 logged.
		 
		 Alarm mask coding for STUP/QSTUP:
		 
		 Suppression	Severity	Logging		Alarm
		 Byte 0		Byte 30		Byte 60
		  bit 0		 bit 0		 bit 0		XTU_LOS_U
		  bit 1		 bit 1		 bit 1		XTU_LFA_U
		  bit 2		 bit 2		 bit 2		XTU_AIS_U
		  bit 3		 bit 3		 bit 3		XTU_BNA_U
		  bit 4		 bit 4		 bit 4		XTU_RAI_U
		  bit 5		 bit 5		 bit 5		XTU_BER3_U
		  bit 6		 bit 6		 bit 6		XTU_BER6_U
		  bit 7		 bit 7		 bit 7		XTU_LOS_Ux
		 Byte 1		Byte 31		Byte 61
		  bit 0		 bit 0		 bit 0		XTU_LOSW_Ux
		  bit 1		 bit 1		 bit 1		XTU_BER3_Ux
		  bit 2		 bit 2		 bit 2		XTU_BER6_Ux
		  bit 3		 bit 3		 bit 3		XTU_LOS_T
		  bit 4		 bit 4		 bit 4		XTU_LFA_T
		  bit 5		 bit 5		 bit 5		XTU_AIS_T
		  bit 6		 bit 6		 bit 6		XTU_RAI_T
		  bit 7		 bit 7		 bit 7		XTU_BER3_T
		 Byte 21	Byte 32		Byte 62
		  bit 0		 bit 0		 bit 0		XTU_BER6_T
		  bit 1		 bit 1		 bit 1		XTU_LOA_RX_D
		  bit 2		 bit 2		 bit 2		XTU_LOA_TX_D
		  bit 3		 bit 3		 bit 3		XTU_EQUIPMENT
		  bit 4		 bit 4		 bit 4		XTU_LOS_T3
		  bit 5		 bit 5		 bit 5		XTU_LOS_T4
		  bit 6		 bit 6		 bit 6		XTU_P1_LINKDOWN
		  bit 7		 bit 7		 bit 7		XTU_LOA_RX_WAN
		 Byte 3		Byte 33		Byte 63
		  bit 0		 bit 0		 bit 0		XTU_LOA_TX_WAN
		  bit 1		 bit 1		 bit 1		XTU_MIR_TX_WAN
		  bit 2		 bit 2		 bit 2		XTU_LOS_D
		  bit 3		 bit 3		 bit 3		XTU_POWERFAIL
		  bit 4		 bit 4		 bit 4		XTU_REM_PWRFAIL
		  bit 5		 bit 5		 bit 5		XTU_TD_ATT
		  bit 6		 bit 6		 bit 6		XTU_TD_SNR
		  bit 7		 bit 7		 bit 7		XTU_XFW
		 Bytes 4-14	Bytes 34-44	Bytes 64-74
		  unused
		 Byte 15	Byte 45		Byte 75
		  bit 0		 bit 0		 bit 0		XRU_LOS_UL
		  bit 1		 bit 1		 bit 1		XRU_BER3_UL
		  bit 2		 bit 2		 bit 2		XRU_BER6_UL
		  bit 3		 bit 3		 bit 3		XRU_LOS_UN
		  bit 4		 bit 4		 bit 4		XRU_BER3_UN
		  bit 5		 bit 5		 bit 5		XRU_BER6_UN
		  bit 6		 bit 6		 bit 6		XRU_EQUIPMENT
		  bit 7		 bit 7		 bit 7		XRU_LOSW_UL
		 Byte 16	Byte 46		Byte 76
		  bit 0		 bit 0		 bit 0		XRU_LOSW_UN
		  bit 1		 bit 1		 bit 1		XRU_TD_ATT_UL
		  bit 2		 bit 2		 bit 2		XRU_TD_SNR_UL
		  bit 3		 bit 3		 bit 3		XRU_TD_ATT_UN
		  bit 4		 bit 4		 bit 4		XRU_TD_SNR_UN
		  bit 5		 bit 5		 bit 5		unused
		  bit 6		 bit 6		 bit 6		unused
		  bit 7		 bit 7		 bit 7		unused
		 Bytes 17-24	Bytes 47-54	Bytes 77-84
		  unused
		 Byte 25	Byte 55		Byte 85
		  bit 0		 bit 0		 bit 0		RPS_UC
		  bit 1		 bit 1		 bit 1		RPS_OC
		  bit 2		 bit 2		 bit 2		RPS_UNBAL
		  bit 3		 bit 3		 bit 3		RPS_DEFEKT
		  bit 4		 bit 4		 bit 4		unused
		  bit 5		 bit 5		 bit 5		unused
		  bit 6		 bit 6		 bit 6		unused
		  bit 7		 bit 7		 bit 7		unused
		 Bytes 26-29	Bytes 56-59	Bytes 86-89
		  unused
		 
		 Byte 90 contains a value specifying the validity of the
		 result of a read operation:
		 1	Ok	Values returned are valid
		 254		unknown values
		 255		unsupported variable for addressed device"
	::= { fmrwFarAlarmMaskConfigEntry 3 }

--------------------------------------------------------------------------------
--	FM-RW	Htu Traps
--------------------------------------------------------------------------------
fmrwHtuTrapTable OBJECT-TYPE
	SYNTAX SEQUENCE OF FmrwHtuTrapEntry
	ACCESS not-accessible
	STATUS mandatory
	DESCRIPTION ""
	::= { fmrwTrap 1 }

fmrwHtuTrapEntry OBJECT-TYPE
	SYNTAX FmrwHtuTrapEntry
	ACCESS not-accessible
	STATUS mandatory
	DESCRIPTION ""
	INDEX { fmrwHtuTrapPortIndex, fmrwHtuTrapLinkIndex }
	::= { fmrwHtuTrapTable 1 }

FmrwHtuTrapEntry ::=
	SEQUENCE
	{
		fmrwHtuTrapPortIndex INTEGER,
		fmrwHtuTrapLinkIndex INTEGER,
		fmrwHtuTrapEnable INTEGER,
		fmrwHtuTrapSuppDisAlarmTrap INTEGER
	}

fmrwHtuTrapPortIndex OBJECT-TYPE
	SYNTAX INTEGER
	ACCESS read-only
	STATUS mandatory
	DESCRIPTION
		"This variable addresses the port number of the proxy
		and is used as index for the other elements in the Table"
	::= { fmrwHtuTrapEntry 1 }

fmrwHtuTrapLinkIndex OBJECT-TYPE
	SYNTAX INTEGER
	ACCESS read-only
	STATUS mandatory
	DESCRIPTION
		"This variable addresses the slot number of the OMI sub-rack
		and is used as index for the other elements in the Table"
	::= { fmrwHtuTrapEntry 2 }

fmrwHtuTrapEnable OBJECT-TYPE
	SYNTAX INTEGER
	{
		disabled(1),
		enabled(2),
		unknown(254),
		unsupported(255)
	}
	ACCESS read-write
	STATUS mandatory
	DESCRIPTION
		"Allows the suppression of all traps from a certain device
		without altering the assigned alarm severities via the alarm
		masks. The following values are supported:
		1	Disabled	Suppress all traps
		2	Enabled	Send traps from this system
		254	Unknown value (not supported for set)
		255	Unsupported variable for addressed device (not supported for set)"
	::= { fmrwHtuTrapEntry 3 }

fmrwHtuTrapSuppDisAlarmTrap OBJECT-TYPE
	SYNTAX INTEGER
	{
		disabled(1),
		enabled(2),
		unknown(254),
		unsupported(255)
	}
	ACCESS read-write
	STATUS mandatory
	DESCRIPTION
		"Allows the suppression of alarm traps when the line's overall
		alarm summary remains 'No Alarm'. This feature is useful for
		preventing masked alarm from causing unwanted trap traffic.
		Trap generation can be suppressed entirely using the variable
		fmrwHtuTrapEnable.
		The following values are supported:
		1	Disabled	Allow all traps
		2	Enabled		Suppress trap for constant 'No Alarm' summary
		254	Unknown value (not supported for set)
		255	Unsupported variable for addressed device (not supported for set)"
	::= { fmrwHtuTrapEntry 4 }

--------------------------------------------------------------------------------
--	FM-RW	Omi Traps
--------------------------------------------------------------------------------
fmrwOmiTrapTable OBJECT-TYPE
	SYNTAX SEQUENCE OF FmrwOmiTrapEntry
	ACCESS not-accessible
	STATUS mandatory
	DESCRIPTION ""
	::= { fmrwTrap 2 }

fmrwOmiTrapEntry OBJECT-TYPE
	SYNTAX FmrwOmiTrapEntry
	ACCESS not-accessible
	STATUS mandatory
	DESCRIPTION ""
	INDEX { fmrwOmiTrapPortIndex }
	::= { fmrwOmiTrapTable 1 }

FmrwOmiTrapEntry ::=
	SEQUENCE
	{
		fmrwOmiTrapPortIndex INTEGER,
		fmrwOmiTrapEnable INTEGER,
		fmrwOmiTrapSuppDisAlarmTrap INTEGER
	}

fmrwOmiTrapPortIndex OBJECT-TYPE
	SYNTAX INTEGER
	ACCESS read-only
	STATUS mandatory
	DESCRIPTION
		"This variable addresses the port number of the proxy
		and is used as index for the other elements in the Table"
	::= { fmrwOmiTrapEntry 1 }

fmrwOmiTrapEnable OBJECT-TYPE
	SYNTAX INTEGER
	{
		disabled(1),
		enabled(2),
		unknown(254),
		unsupported(255)
	}
	ACCESS read-write
	STATUS mandatory
	DESCRIPTION
		"Allows the suppression of all traps from a certain OMI
		without altering the assigned alarm severities via the alarm
		masks. The following values are supported:
		1	Disabled	Suppress all traps originating on this OMI
		2	Enabled	Send traps from this OMI
		254	Unknown value (not supported for set)
		255	Unsupported variable for addressed device (not supported for set)
		
		Please note that the suppression mechanism only suppresses those
		traps originating on the OMI itself but not traps generated by
		line cards which are addressed through the OMI. These traps must
		be suppressed on the line cards themselves."
	::= { fmrwOmiTrapEntry 2 }

fmrwOmiTrapSuppDisAlarmTrap OBJECT-TYPE
	SYNTAX INTEGER
	{
		disabled(1),
		enabled(2),
		unknown(254),
		unsupported(255)
	}
	ACCESS read-write
	STATUS mandatory
	DESCRIPTION
      "Allows the suppression of alarm traps when the line's overall
      alarm summary remains 'No Alarm'. This feature is useful for
      preventing masked alarm from causing unwanted trap traffic.
      Trap generation can be suppressed entirely using the variable
      fmrwOmiTrapEnable.	
		1	 Disabled	Suppress all traps originating on this OMI
		2	 Enabled	Send traps from this OMI
		254 Unknown value (not supported for set)
		255 Unsupported variable for addressed device (not supported for set)"
	::= { fmrwOmiTrapEntry 3 }

--------------------------------------------------------------------------------
--	FM-RW	Thresholds
--------------------------------------------------------------------------------
fmrwThresholdTable OBJECT-TYPE
	SYNTAX SEQUENCE OF FmrwThresholdEntry
	ACCESS not-accessible
	STATUS mandatory
	DESCRIPTION ""
	::= { fmrw 4 }

fmrwThresholdEntry OBJECT-TYPE
	SYNTAX FmrwThresholdEntry
	ACCESS not-accessible
	STATUS mandatory
	DESCRIPTION ""
	INDEX { fmrwThresholdPortIndex, fmrwThresholdLinkIndex }
	::= { fmrwThresholdTable 1 }

FmrwThresholdEntry ::=
	SEQUENCE
	{
		fmrwThresholdPortIndex INTEGER,
		fmrwThresholdLinkIndex INTEGER,
		fmrwThresholdAttenuation INTEGER,
		fmrwThresholdSnr INTEGER
	}

fmrwThresholdPortIndex OBJECT-TYPE
	SYNTAX INTEGER
	ACCESS read-only
	STATUS mandatory
	DESCRIPTION
		"This variable addresses the port number of the proxy
		and is used as index for the other elements in the Table"
	::= { fmrwThresholdEntry 1 }

fmrwThresholdLinkIndex OBJECT-TYPE
	SYNTAX INTEGER
	ACCESS read-only
	STATUS mandatory
	DESCRIPTION
		"This variable addresses the slot number of the OMI sub-rack
		and is used as index for the other elements in the Table"
	::= { fmrwThresholdEntry 2 }

fmrwThresholdAttenuation OBJECT-TYPE
	SYNTAX INTEGER
	{
		disabled(1),
		att1dB(2),
		att2dB(3),
		att3dB(4),
		att4dB(5),
		att5dB(6),
		att6dB(7),
		att7dB(8),
		att8dB(9),
		att9dB(10),
		att10dB(11),
		att11dB(12),
		att12dB(13),
		att13dB(14),
		att14dB(15),
		att15dB(16),
		att16dB(17),
		att17dB(18),
		att18dB(19),
		att19dB(20),
		att20dB(21),
		att21dB(22),
		att22dB(23),
		att23dB(24),
		att24dB(25),
		att25dB(26),
		att26dB(27),
		att27dB(28),
		att28dB(29),
		att29dB(30),
		att30dB(31),
		att31dB(32),
		att32dB(33),
		att33dB(34),
		att34dB(35),
		att35dB(36),
		att36dB(37),
		att37dB(38),
		att38dB(39),
		att39dB(40),
		att40dB(41),
		att41dB(42),
		att42dB(43),
		att43dB(44),
		att44dB(45),
		att45dB(46),
		att46dB(47),
		att47dB(48),
		att48dB(49),
		att49dB(50),
		att50dB(51),
		att51dB(52),
		att52dB(53),
		att53dB(54),
		att54dB(55),
		att55dB(56),
		att56dB(57),
		att57dB(58),
		att58dB(59),
		att59dB(60),
		att60dB(61),
		att61dB(62),
		att62dB(63),
		att63dB(64),
		att64dB(65),
		att65dB(66),
		att66dB(67),
		att67dB(68),
		att68dB(69),
		att69dB(70),
		att70dB(71),
		att71dB(72),
		att72dB(73),
		att73dB(74),
		att74dB(75),
		att75dB(76),
		att76dB(77),
		att77dB(78),
		att78dB(79),
		att79dB(80),
		att80dB(81),
		att81dB(82),
		att82dB(83),
		att83dB(84),
		att84dB(85),
		att85dB(86),
		att86dB(87),
		att87dB(88),
		att88dB(89),
		att89dB(90),
		att90dB(91),
		att91dB(92),
		att92dB(93),
		att93dB(94),
		att94dB(95),
		att95dB(96),
		att96dB(97),
		att97dB(98),
		att98dB(99),
		att99dB(100),
		att100dB(101),
		att101dB(102),
		att102dB(103),
		att103dB(104),
		att104dB(105),
		att105dB(106),
		att106dB(107),
		att107dB(108),
		att108dB(109),
		att109dB(110),
		att110dB(111),
		att111dB(112),
		att112dB(113),
		att113dB(114),
		att114dB(115),
		att115dB(116),
		att116dB(117),
		att117dB(118),
		att118dB(119),
		att119dB(120),
		att120dB(121),
		att121dB(122),
		att122dB(123),
		att123dB(124),
		att124dB(125),
		att125dB(126),
		att126dB(127),
		att127dB(128),
		unknown(254),
		unsupported(255)
	}
	ACCESS read-write
	STATUS mandatory
	DESCRIPTION
		"Defines the Attenuation Threshold
		   1	disabled	Disabled
		   2	att1dB		Attenuation in dB (1..127)
		   ...			Attenuation in dB (1..127)
		   128	att127dB	Attenuation in dB (1..127)
		   254			Unknown value
		   255			Unsupported variable for addressed device"
	::= { fmrwThresholdEntry 4 }

fmrwThresholdSnr OBJECT-TYPE
	SYNTAX INTEGER
	{
		disabled(1),
		snr1dB(2),
		snr2dB(3),
		snr3dB(4),
		snr4dB(5),
		snr5dB(6),
		snr6dB(7),
		snr7dB(8),
		snr8dB(9),
		snr9dB(10),
		snr10dB(11),
		snr11dB(12),
		snr12dB(13),
		snr13dB(14),
		snr14dB(15),
		snr15dB(16),
		unknown(254),
		unsupported(255)
	}
	ACCESS read-write
	STATUS mandatory
	DESCRIPTION
		"Defines the Signal To Noise Ration (SNR) Threshold
		  1	disabled	Disabled
		  2	snr1dB		SNR Margin in db (1..15)
		  ...			SNR Margin in db (1..15)
		  16	snr15dB	SNR Margin in db (1..15)
		 254			Unknown value
		 255			Unsupported variable for addressed device"
	::= { fmrwThresholdEntry 5 }

--------------------------------------------------------------------------------
--	FM-RW	Htu Actions
--------------------------------------------------------------------------------
fmrwHtuActionTable OBJECT-TYPE
	SYNTAX SEQUENCE OF FmrwHtuActionEntry
	ACCESS not-accessible
	STATUS mandatory
	DESCRIPTION ""
	::= { fmrwActions 1 }

fmrwHtuActionEntry OBJECT-TYPE
	SYNTAX FmrwHtuActionEntry
	ACCESS not-accessible
	STATUS mandatory
	DESCRIPTION ""
	INDEX { fmrwHtuActionPortIndex, fmrwHtuActionLinkIndex }
	::= { fmrwHtuActionTable 1 }

FmrwHtuActionEntry ::=
	SEQUENCE
	{
		fmrwHtuActionPortIndex INTEGER,
		fmrwHtuActionLinkIndex INTEGER,
		fmrwHtuActionResetAlarmLog INTEGER
	}

fmrwHtuActionPortIndex OBJECT-TYPE
	SYNTAX INTEGER
	ACCESS read-only
	STATUS mandatory
	DESCRIPTION
		"This variable addresses the port number of the proxy
		and is used as index for the other elements in the Table"
	::= { fmrwHtuActionEntry 1 }

fmrwHtuActionLinkIndex OBJECT-TYPE
	SYNTAX INTEGER
	ACCESS read-only
	STATUS mandatory
	DESCRIPTION
		"This variable addresses the slot number of the OMI sub-rack
		and is used as index for the other elements in the Table"
	::= { fmrwHtuActionEntry 2 }

fmrwHtuActionResetAlarmLog OBJECT-TYPE
	SYNTAX INTEGER
	{
		reset(1),
		unknown(254),
		unsupported(255)
	}
	ACCESS read-write
	STATUS mandatory
	DESCRIPTION
		"Clears the content of the Alarm Log
		1	Reset	Clears the log
		254		Unknown value (not supported for set)
		255		Unsupported variable for addressed device (not supported for set)"
	::= { fmrwHtuActionEntry 3 }

--------------------------------------------------------------------------------
--	FM-RW	Htu Actions
--------------------------------------------------------------------------------
fmrwConfigTable OBJECT-TYPE
	SYNTAX SEQUENCE OF FmrwConfigEntry
	ACCESS not-accessible
	STATUS mandatory
	DESCRIPTION ""
	::= { fmrwConfig 1 }
	
fmrwConfigEntry OBJECT-TYPE
	SYNTAX FmrwConfigEntry
	ACCESS not-accessible
	STATUS mandatory
	DESCRIPTION ""
	INDEX { fmrwConfigPortIndex, fmrwConfigLinkIndex }
	::= { fmrwConfigTable 1 }

FmrwConfigEntry ::=
	SEQUENCE
	{
		fmrwConfigPortIndex INTEGER,
		fmrwConfigLinkIndex INTEGER,
		fmrwLocalPwrFailAlarmSupp INTEGER,
		fmrwLocalL2SwitchTestMode INTEGER,
		fmrwFarPwrFailAlarmSupp INTEGER,
		fmrwFarL2SwitchTestMode INTEGER
	}

fmrwConfigPortIndex OBJECT-TYPE
	SYNTAX INTEGER
	ACCESS read-only
	STATUS mandatory
	DESCRIPTION
		"This variable addresses the port number of the proxy
		and is used as index for the other elements in the Table"
	::= { fmrwConfigEntry 1 }

fmrwConfigLinkIndex OBJECT-TYPE
	SYNTAX INTEGER
	ACCESS read-only
	STATUS mandatory
	DESCRIPTION
		"This variable addresses the slot number of the OMI sub-rack
		and is used as index for the other elements in the Table"
	::= { fmrwConfigEntry 2 }

fmrwLocalPwrFailAlarmSupp OBJECT-TYPE
	SYNTAX INTEGER
	{
		disabled(1),
		enabled(2),
		unknown(254),
		unsupported(255)
	}
	ACCESS read-write
	STATUS mandatory
	DESCRIPTION
		"Allows the suppression of power failure alarms. In addition
		to the alarm masking provided by fmrwXtuXtMask, this feature
		actually suppresses alarm generation at all.
		1	Disabled	Allow power failure alarms
		2	Enabled		Suppress power failure alarms
		254	Unknown value (not supported for set)
		255	Unsupported variable for addressed device (not supported for set)"
	::= { fmrwConfigEntry 3 }

fmrwLocalL2SwitchTestMode OBJECT-TYPE
	SYNTAX INTEGER {
		inactive(1),
		active(2),
		unknown(254),
		unsupported(255)
	}
	ACCESS read-write
	STATUS mandatory
	DESCRIPTION
		"Defines whether the L2Switch operates in test mode
		('transparent switch') or in standard mode.
		1	Inactive	L2Switch operates in standard mode
		2	Active		L2Switch operates in test mode
		254	unknown
		255	unsupported"
	::= { fmrwConfigEntry 4 }

fmrwFarPwrFailAlarmSupp OBJECT-TYPE
	SYNTAX INTEGER
	{
		disabled(1),
		enabled(2),
		unknown(254),
		unsupported(255)
	}
	ACCESS read-write
	STATUS mandatory
	DESCRIPTION
		"Allows the suppression of power failure alarms. In addition
		to the alarm masking provided by fmrwXtuXtMask, this feature
		actually suppresses alarm generation at all.
		1	Disabled	Allow power failure alarms
		2	Enabled		Suppress power failure alarms
		254	Unknown value (not supported for set)
		255	Unsupported variable for addressed device (not supported for set)"
	::= { fmrwConfigEntry 5 }

fmrwFarL2SwitchTestMode OBJECT-TYPE
	SYNTAX INTEGER {
		inactive(1),
		active(2),
		unknown(254),
		unsupported(255)
	}
	ACCESS read-write
	STATUS mandatory
	DESCRIPTION
		"Defines whether the L2Switch operates in test mode
		('transparent switch') or in standard mode.
		1	Inactive	L2Switch operates in standard mode
		2	Active		L2Switch operates in test mode
		254	unknown
		255	unsupported"
	::= { fmrwConfigEntry 6 }

--==============================================================================
--==============================================================================
--
--      PM-RO
--
--==============================================================================
--==============================================================================
	pmro	OBJECT IDENTIFIER ::= { linksVers3 5 }

--------------------------------------------------------------------------------
--	PM-RO	HDSL Attenuation
--------------------------------------------------------------------------------
pmroHdslTable OBJECT-TYPE
	SYNTAX SEQUENCE OF PmroHdslEntry
	ACCESS not-accessible
	STATUS mandatory
	DESCRIPTION ""
	::= { pmro 1 }

pmroHdslEntry OBJECT-TYPE
	SYNTAX PmroHdslEntry
	ACCESS not-accessible
	STATUS mandatory
	DESCRIPTION ""
	INDEX { pmroHdslPortIndex, pmroHdslLinkIndex }
	::= { pmroHdslTable 1 }

PmroHdslEntry ::=
	SEQUENCE
	{
		pmroHdslPortIndex INTEGER,
		pmroHdslLinkIndex INTEGER,
		pmroHdslAttenuation1 INTEGER,
		pmroHdslAttenuation2 INTEGER,
		pmroHdslNoiseMargin1 INTEGER,
		pmroHdslNoiseMargin2 INTEGER,
		pmroHdslAttenuationNt1 INTEGER,
		pmroHdslAttenuationNt2 INTEGER,
		pmroHdslNoiseMarginNt1 INTEGER,
		pmroHdslNoiseMarginNt2 INTEGER,
		pmroHdslAttenuationReg1ALt INTEGER,
		pmroHdslAttenuationReg1ANt INTEGER,
		pmroHdslAttenuationReg2ALt INTEGER,
		pmroHdslAttenuationReg2ANt INTEGER,
		pmroHdslAttenuationReg1BLt INTEGER,
		pmroHdslAttenuationReg1BNt INTEGER,
		pmroHdslAttenuationReg2BLt INTEGER,
		pmroHdslAttenuationReg2BNt INTEGER,
		pmroHdslNoiseMarginReg1ALt INTEGER,
		pmroHdslNoiseMarginReg1ANt INTEGER,
		pmroHdslNoiseMarginReg2ALt INTEGER,
		pmroHdslNoiseMarginReg2ANt INTEGER,
		pmroHdslNoiseMarginReg1BLt INTEGER,
		pmroHdslNoiseMarginReg1BNt INTEGER,
		pmroHdslNoiseMarginReg2BLt INTEGER,
		pmroHdslNoiseMarginReg2BNt INTEGER,
		pmroHdslAttenuationReg31Lt INTEGER,
		pmroHdslAttenuationReg31Nt INTEGER,
		pmroHdslAttenuationReg32Lt INTEGER,
		pmroHdslAttenuationReg32Nt INTEGER,
		pmroHdslAttenuationReg41Lt INTEGER,
		pmroHdslAttenuationReg41Nt INTEGER,
		pmroHdslAttenuationReg42Lt INTEGER,
		pmroHdslAttenuationReg42Nt INTEGER,
		pmroHdslAttenuationReg51Lt INTEGER,
		pmroHdslAttenuationReg51Nt INTEGER,
		pmroHdslAttenuationReg52Lt INTEGER,
		pmroHdslAttenuationReg52Nt INTEGER,
		pmroHdslAttenuationReg61Lt INTEGER,
		pmroHdslAttenuationReg61Nt INTEGER,
		pmroHdslAttenuationReg62Lt INTEGER,
		pmroHdslAttenuationReg62Nt INTEGER,
		pmroHdslAttenuationReg71Lt INTEGER,
		pmroHdslAttenuationReg71Nt INTEGER,
		pmroHdslAttenuationReg72Lt INTEGER,
		pmroHdslAttenuationReg72Nt INTEGER,
		pmroHdslAttenuationReg81Lt INTEGER,
		pmroHdslAttenuationReg81Nt INTEGER,
		pmroHdslAttenuationReg82Lt INTEGER,
		pmroHdslAttenuationReg82Nt INTEGER,
		pmroHdslNoiseMarginReg31Lt INTEGER,
		pmroHdslNoiseMarginReg31Nt INTEGER,
		pmroHdslNoiseMarginReg32Lt INTEGER,
		pmroHdslNoiseMarginReg32Nt INTEGER,
		pmroHdslNoiseMarginReg41Lt INTEGER,
		pmroHdslNoiseMarginReg41Nt INTEGER,
		pmroHdslNoiseMarginReg42Lt INTEGER,
		pmroHdslNoiseMarginReg42Nt INTEGER,
		pmroHdslNoiseMarginReg51Lt INTEGER,
		pmroHdslNoiseMarginReg51Nt INTEGER,
		pmroHdslNoiseMarginReg52Lt INTEGER,
		pmroHdslNoiseMarginReg52Nt INTEGER,
		pmroHdslNoiseMarginReg61Lt INTEGER,
		pmroHdslNoiseMarginReg61Nt INTEGER,
		pmroHdslNoiseMarginReg62Lt INTEGER,
		pmroHdslNoiseMarginReg62Nt INTEGER,
		pmroHdslNoiseMarginReg71Lt INTEGER,
		pmroHdslNoiseMarginReg71Nt INTEGER,
		pmroHdslNoiseMarginReg72Lt INTEGER,
		pmroHdslNoiseMarginReg72Nt INTEGER,
		pmroHdslNoiseMarginReg81Lt INTEGER,
		pmroHdslNoiseMarginReg81Nt INTEGER,
		pmroHdslNoiseMarginReg82Lt INTEGER,
		pmroHdslNoiseMarginReg82Nt INTEGER,
		pmroHdslAttenuation3 INTEGER,
		pmroHdslAttenuation4 INTEGER,
		pmroHdslAttenuationNt3 INTEGER,
		pmroHdslAttenuationNt4 INTEGER,
		pmroHdslAttenuationReg13Lt INTEGER,
		pmroHdslAttenuationReg13Nt INTEGER,
		pmroHdslAttenuationReg14Lt INTEGER,
		pmroHdslAttenuationReg14Nt INTEGER,
		pmroHdslAttenuationReg23Lt INTEGER,
		pmroHdslAttenuationReg23Nt INTEGER,
		pmroHdslAttenuationReg24Lt INTEGER,
		pmroHdslAttenuationReg24Nt INTEGER,
		pmroHdslAttenuationReg33Lt INTEGER,
		pmroHdslAttenuationReg33Nt INTEGER,
		pmroHdslAttenuationReg34Lt INTEGER,
		pmroHdslAttenuationReg34Nt INTEGER,
		pmroHdslAttenuationReg43Lt INTEGER,
		pmroHdslAttenuationReg43Nt INTEGER,
		pmroHdslAttenuationReg44Lt INTEGER,
		pmroHdslAttenuationReg44Nt INTEGER,
		pmroHdslAttenuationReg53Lt INTEGER,
		pmroHdslAttenuationReg53Nt INTEGER,
		pmroHdslAttenuationReg54Lt INTEGER,
		pmroHdslAttenuationReg54Nt INTEGER,
		pmroHdslAttenuationReg63Lt INTEGER,
		pmroHdslAttenuationReg63Nt INTEGER,
		pmroHdslAttenuationReg64Lt INTEGER,
		pmroHdslAttenuationReg64Nt INTEGER,
		pmroHdslAttenuationReg73Lt INTEGER,
		pmroHdslAttenuationReg73Nt INTEGER,
		pmroHdslAttenuationReg74Lt INTEGER,
		pmroHdslAttenuationReg74Nt INTEGER,
		pmroHdslAttenuationReg83Lt INTEGER,
		pmroHdslAttenuationReg83Nt INTEGER,
		pmroHdslAttenuationReg84Lt INTEGER,
		pmroHdslAttenuationReg84Nt INTEGER,
		pmroHdslNoiseMargin3 INTEGER,
		pmroHdslNoiseMargin4 INTEGER,
		pmroHdslNoiseMarginNt3 INTEGER,
		pmroHdslNoiseMarginNt4 INTEGER,
		pmroHdslNoiseMarginReg13Lt INTEGER,
		pmroHdslNoiseMarginReg13Nt INTEGER,
		pmroHdslNoiseMarginReg14Lt INTEGER,
		pmroHdslNoiseMarginReg14Nt INTEGER,
		pmroHdslNoiseMarginReg23Lt INTEGER,
		pmroHdslNoiseMarginReg23Nt INTEGER,
		pmroHdslNoiseMarginReg24Lt INTEGER,
		pmroHdslNoiseMarginReg24Nt INTEGER,
		pmroHdslNoiseMarginReg33Lt INTEGER,
		pmroHdslNoiseMarginReg33Nt INTEGER,
		pmroHdslNoiseMarginReg34Lt INTEGER,
		pmroHdslNoiseMarginReg34Nt INTEGER,
		pmroHdslNoiseMarginReg43Lt INTEGER,
		pmroHdslNoiseMarginReg43Nt INTEGER,
		pmroHdslNoiseMarginReg44Lt INTEGER,
		pmroHdslNoiseMarginReg44Nt INTEGER,
		pmroHdslNoiseMarginReg53Lt INTEGER,
		pmroHdslNoiseMarginReg53Nt INTEGER,
		pmroHdslNoiseMarginReg54Lt INTEGER,
		pmroHdslNoiseMarginReg54Nt INTEGER,
		pmroHdslNoiseMarginReg63Lt INTEGER,
		pmroHdslNoiseMarginReg63Nt INTEGER,
		pmroHdslNoiseMarginReg64Lt INTEGER,
		pmroHdslNoiseMarginReg64Nt INTEGER,
		pmroHdslNoiseMarginReg73Lt INTEGER,
		pmroHdslNoiseMarginReg73Nt INTEGER,
		pmroHdslNoiseMarginReg74Lt INTEGER,
		pmroHdslNoiseMarginReg74Nt INTEGER,
		pmroHdslNoiseMarginReg83Lt INTEGER,
		pmroHdslNoiseMarginReg83Nt INTEGER,
		pmroHdslNoiseMarginReg84Lt INTEGER,
		pmroHdslNoiseMarginReg84Nt INTEGER
	}

pmroHdslPortIndex OBJECT-TYPE
	SYNTAX INTEGER
	ACCESS read-only
	STATUS mandatory
	DESCRIPTION
		"This variable addresses the port number of the proxy
		and is used as index for the other elements in the Table"
	::= { pmroHdslEntry 1 }

pmroHdslLinkIndex OBJECT-TYPE
	SYNTAX INTEGER
	ACCESS read-only
	STATUS mandatory
	DESCRIPTION
		"This variable addresses the slot number of the OMI sub-rack
		and is used as index for the other elements in the Table"
	::= { pmroHdslEntry 2 }

pmroHdslAttenuation1 OBJECT-TYPE
	SYNTAX INTEGER (0..255)
	ACCESS read-only
	STATUS mandatory
	DESCRIPTION
		"Attenuation of HDSL Path 1 at the local device
		 0-180	attenuation in steps of 0.5 dB
		 254	unknown value
		 255	unsupported variable for addressed device"
	::= { pmroHdslEntry 3 }

pmroHdslAttenuation2 OBJECT-TYPE
	SYNTAX INTEGER (0..255)
	ACCESS read-only
	STATUS mandatory
	DESCRIPTION
		"Attenuation of HDSL Path 2 at the local device
		 0-180	attenuation in steps of 0.5 dB
		 254	unknown value
		 255	unsupported variable for addressed device"
	::= { pmroHdslEntry 4 }

pmroHdslNoiseMargin1 OBJECT-TYPE
	SYNTAX INTEGER (0..255)
	ACCESS read-only
	STATUS mandatory
	DESCRIPTION
		"Noise Margin of HDSL Path 1 at the local device.
		The value is coded as a signed byte value
		 -63..63	noise margin in steps of 0.5 dB
		 126		unknown value
		 127		unsupported variable for addressed device"
	::= { pmroHdslEntry 5 }

pmroHdslNoiseMargin2 OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 6 }

pmroHdslAttenuationNt1 OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 7 }

pmroHdslAttenuationNt2 OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 8 }

pmroHdslNoiseMarginNt1 OBJECT-TYPE
	SYNTAX INTEGER (0..255)
	ACCESS read-only
	STATUS mandatory
	DESCRIPTION
		"Noise Margin of the line.
		The value is coded as a signed byte value
		 -63..63	noise margin in steps of 0.5 dB
		 126		unknown value
		 127		unsupported variable for addressed device"
	::= { pmroHdslEntry 9 }

pmroHdslNoiseMarginNt2 OBJECT-TYPE
	SYNTAX INTEGER (0..255)
	ACCESS read-only
	STATUS mandatory
	DESCRIPTION
		"Noise Margin of the line.
		The value is coded as a signed byte value
		 -63..63	noise margin in steps of 0.5 dB
		 126		unknown value
		 127		unsupported variable for addressed device"
	::= { pmroHdslEntry 10 }

pmroHdslAttenuationReg1ALt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 11 }

pmroHdslAttenuationReg1ANt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 12 }

pmroHdslAttenuationReg2ALt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 13 }

pmroHdslAttenuationReg2ANt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 14 }

pmroHdslAttenuationReg1BLt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 15 }

pmroHdslAttenuationReg1BNt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 16 }

pmroHdslAttenuationReg2BLt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 17 }

pmroHdslAttenuationReg2BNt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 18 }

pmroHdslNoiseMarginReg1ALt OBJECT-TYPE
	SYNTAX INTEGER (0..255)
	ACCESS read-only
	STATUS mandatory
	DESCRIPTION
		"Noise Margin of HDSL Path 1 at the local device.
		The value is coded as a signed byte value
		 -63..63	noise margin in steps of 0.5 dB
		 126		unknown value
		 127		unsupported variable for addressed device"
	::= { pmroHdslEntry 19 }

pmroHdslNoiseMarginReg1ANt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 20 }

pmroHdslNoiseMarginReg2ALt OBJECT-TYPE
	SYNTAX INTEGER (0..255)
	ACCESS read-only
	STATUS mandatory
	DESCRIPTION
		"Noise Margin of HDSL Path 1 at the local device.
		The value is coded as a signed byte value
		 -63..63	noise margin in steps of 0.5 dB
		 126		unknown value
		 127		unsupported variable for addressed device"
	::= { pmroHdslEntry 21 }

pmroHdslNoiseMarginReg2ANt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 22 }

pmroHdslNoiseMarginReg1BLt OBJECT-TYPE
	SYNTAX INTEGER (0..255)
	ACCESS read-only
	STATUS mandatory
	DESCRIPTION
		"Noise Margin of HDSL Path 1 at the local device.
		The value is coded as a signed byte value
		 -63..63	noise margin in steps of 0.5 dB
		 126		unknown value
		 127		unsupported variable for addressed device"
	::= { pmroHdslEntry 23 }

pmroHdslNoiseMarginReg1BNt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 24 }

pmroHdslNoiseMarginReg2BLt OBJECT-TYPE
	SYNTAX INTEGER (0..255)
	ACCESS read-only
	STATUS mandatory
	DESCRIPTION
		"Noise Margin of HDSL Path 1 at the local device.
		The value is coded as a signed byte value
		 -63..63	noise margin in steps of 0.5 dB
		 126		unknown value
		 127		unsupported variable for addressed device"
	::= { pmroHdslEntry 25 }

pmroHdslNoiseMarginReg2BNt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 26 }

pmroHdslAttenuationReg31Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 27 }

pmroHdslAttenuationReg31Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 28 }

pmroHdslAttenuationReg32Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 29 }

pmroHdslAttenuationReg32Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 30 }

pmroHdslAttenuationReg41Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 31 }

pmroHdslAttenuationReg41Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 32 }

pmroHdslAttenuationReg42Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 33 }

pmroHdslAttenuationReg42Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 34 }

pmroHdslAttenuationReg51Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 35 }

pmroHdslAttenuationReg51Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 36 }

pmroHdslAttenuationReg52Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 37 }

pmroHdslAttenuationReg52Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 38 }

pmroHdslAttenuationReg61Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 39 }

pmroHdslAttenuationReg61Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 40 }

pmroHdslAttenuationReg62Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 41 }

pmroHdslAttenuationReg62Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 42 }

pmroHdslAttenuationReg71Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 43 }

pmroHdslAttenuationReg71Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 44 }

pmroHdslAttenuationReg72Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 45 }

pmroHdslAttenuationReg72Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 46 }

pmroHdslAttenuationReg81Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 47 }

pmroHdslAttenuationReg81Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 48 }

pmroHdslAttenuationReg82Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 49 }

pmroHdslAttenuationReg82Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 50 }

pmroHdslNoiseMarginReg31Lt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 51 }

pmroHdslNoiseMarginReg31Nt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 52 }

pmroHdslNoiseMarginReg32Lt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 53 }

pmroHdslNoiseMarginReg32Nt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 54 }

pmroHdslNoiseMarginReg41Lt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 55 }

pmroHdslNoiseMarginReg41Nt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 56 }

pmroHdslNoiseMarginReg42Lt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 57 }

pmroHdslNoiseMarginReg42Nt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 58 }

pmroHdslNoiseMarginReg51Lt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 59 }

pmroHdslNoiseMarginReg51Nt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 60 }

pmroHdslNoiseMarginReg52Lt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 61 }

pmroHdslNoiseMarginReg52Nt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 62 }

pmroHdslNoiseMarginReg61Lt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 63 }

pmroHdslNoiseMarginReg61Nt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 64 }

pmroHdslNoiseMarginReg62Lt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 65 }

pmroHdslNoiseMarginReg62Nt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 66 }

pmroHdslNoiseMarginReg71Lt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 67 }

pmroHdslNoiseMarginReg71Nt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 68 }

pmroHdslNoiseMarginReg72Lt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 69 }

pmroHdslNoiseMarginReg72Nt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 70 }

pmroHdslNoiseMarginReg81Lt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 71 }

pmroHdslNoiseMarginReg81Nt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 72 }

pmroHdslNoiseMarginReg82Lt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 73 }

pmroHdslNoiseMarginReg82Nt OBJECT-TYPE
	SYNTAX INTEGER (0..255)
	ACCESS read-only
	STATUS mandatory
	DESCRIPTION
		"Noise Margin of HDSL Path 2 at the local device.
		The value is coded as a signed byte value
		 -63..63	noise margin in steps of 0.5 dB
		 126		unknown value
		 127		unsupported variable for addressed device"
	::= { pmroHdslEntry 74 }

pmroHdslAttenuation3 OBJECT-TYPE
	SYNTAX INTEGER (0..255)
	ACCESS read-only
	STATUS mandatory
	DESCRIPTION
		"Attenuation of HDSL Path 3 at the local device
		 0-180	attenuation in steps of 0.5 dB
		 254	unknown value
		 255	unsupported variable for addressed device"
	::= { pmroHdslEntry 75 }

pmroHdslAttenuation4 OBJECT-TYPE
	SYNTAX INTEGER (0..255)
	ACCESS read-only
	STATUS mandatory
	DESCRIPTION
		"Attenuation of HDSL Path 4 at the local device
		 0-180	attenuation in steps of 0.5 dB
		 254	unknown value
		 255	unsupported variable for addressed device"
	::= { pmroHdslEntry 76 }

pmroHdslAttenuationNt3 OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 77 }

pmroHdslAttenuationNt4 OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 78 }

pmroHdslAttenuationReg13Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 79 }

pmroHdslAttenuationReg13Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 80 }

pmroHdslAttenuationReg14Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 81 }

pmroHdslAttenuationReg14Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 82 }

pmroHdslAttenuationReg23Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 83 }

pmroHdslAttenuationReg23Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 84 }

pmroHdslAttenuationReg24Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 85 }

pmroHdslAttenuationReg24Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 86 }

pmroHdslAttenuationReg33Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 87 }

pmroHdslAttenuationReg33Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 88 }

pmroHdslAttenuationReg34Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 89 }

pmroHdslAttenuationReg34Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 90 }

pmroHdslAttenuationReg43Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 91 }

pmroHdslAttenuationReg43Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 92 }

pmroHdslAttenuationReg44Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 93 }

pmroHdslAttenuationReg44Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 94 }

pmroHdslAttenuationReg53Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 95 }

pmroHdslAttenuationReg53Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 96 }

pmroHdslAttenuationReg54Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 97 }

pmroHdslAttenuationReg54Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 98 }

pmroHdslAttenuationReg63Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 99 }

pmroHdslAttenuationReg63Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 100 }

pmroHdslAttenuationReg64Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 101 }

pmroHdslAttenuationReg64Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 102 }

pmroHdslAttenuationReg73Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 103 }

pmroHdslAttenuationReg73Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 104 }

pmroHdslAttenuationReg74Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 105 }

pmroHdslAttenuationReg74Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 106 }

pmroHdslAttenuationReg83Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 107 }

pmroHdslAttenuationReg83Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 108 }

pmroHdslAttenuationReg84Lt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 109 }

pmroHdslAttenuationReg84Nt OBJECT-TYPE
	SYNTAX INTEGER (0..255)
	ACCESS read-only
	STATUS mandatory
	DESCRIPTION
		"Attenuation of the line.
		 0-180	attenuation in steps of 0.5 dB
		 254	unknown value
		 255	unsupported variable for addressed device"
	::= { pmroHdslEntry 110 }

pmroHdslNoiseMargin3 OBJECT-TYPE
	SYNTAX INTEGER (0..255)
	ACCESS read-only
	STATUS mandatory
	DESCRIPTION
		"Noise Margin of HDSL Path 3 at the local device.
		The value is coded as a signed byte value
		 -63..63	noise margin in steps of 0.5 dB
		 126		unknown value
		 127		unsupported variable for addressed device"
	::= { pmroHdslEntry 111 }

pmroHdslNoiseMargin4 OBJECT-TYPE
	SYNTAX INTEGER (0..255)
	ACCESS read-only
	STATUS mandatory
	DESCRIPTION
		"Noise Margin of HDSL Path 4 at the local device.
		The value is coded as a signed byte value
		 -63..63	noise margin in steps of 0.5 dB
		 126		unknown value
		 127		unsupported variable for addressed device"
	::= { pmroHdslEntry 112 }

pmroHdslNoiseMarginNt3 OBJECT-TYPE
	SYNTAX INTEGER (0..255)
	ACCESS read-only
	STATUS mandatory
	DESCRIPTION
		"Noise Margin of the line.
		The value is coded as a signed byte value
		 -63..63	noise margin in steps of 0.5 dB
		 126		unknown value
		 127		unsupported variable for addressed device"
	::= { pmroHdslEntry 113 }

pmroHdslNoiseMarginNt4 OBJECT-TYPE
	SYNTAX INTEGER (0..255)
	ACCESS read-only
	STATUS mandatory
	DESCRIPTION
		"Noise Margin of the line.
		The value is coded as a signed byte value
		 -63..63	noise margin in steps of 0.5 dB
		 126		unknown value
		 127		unsupported variable for addressed device"
	::= { pmroHdslEntry 114 }

pmroHdslNoiseMarginReg13Lt OBJECT-TYPE
	SYNTAX INTEGER (0..255)
	ACCESS read-only
	STATUS mandatory
	DESCRIPTION
		"Noise Margin of the line.
		 0-180	attenuation in steps of 0.5 dB
		 254	unknown value
		 255	unsupported variable for addressed device"
	::= { pmroHdslEntry 115 }

pmroHdslNoiseMarginReg13Nt OBJECT-TYPE
	SYNTAX INTEGER (0..255)
	ACCESS read-only
	STATUS mandatory
	DESCRIPTION
		"Noise Margin of the line.
		 0-180	attenuation in steps of 0.5 dB
		 254	unknown value
		 255	unsupported variable for addressed device"
	::= { pmroHdslEntry 116 }

pmroHdslNoiseMarginReg14Lt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 117 }

pmroHdslNoiseMarginReg14Nt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 118 }

pmroHdslNoiseMarginReg23Lt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 119 }

pmroHdslNoiseMarginReg23Nt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 120 }

pmroHdslNoiseMarginReg24Lt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 121 }

pmroHdslNoiseMarginReg24Nt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 122 }

pmroHdslNoiseMarginReg33Lt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 123 }

pmroHdslNoiseMarginReg33Nt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 124 }

pmroHdslNoiseMarginReg34Lt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 125 }

pmroHdslNoiseMarginReg34Nt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 126 }

pmroHdslNoiseMarginReg43Lt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 127 }

pmroHdslNoiseMarginReg43Nt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 128 }

pmroHdslNoiseMarginReg44Lt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 129 }

pmroHdslNoiseMarginReg44Nt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 130 }

pmroHdslNoiseMarginReg53Lt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 131 }

pmroHdslNoiseMarginReg53Nt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 132 }

pmroHdslNoiseMarginReg54Lt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 133 }

pmroHdslNoiseMarginReg54Nt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 134 }

pmroHdslNoiseMarginReg63Lt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 135 }

pmroHdslNoiseMarginReg63Nt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 136 }

pmroHdslNoiseMarginReg64Lt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 137 }

pmroHdslNoiseMarginReg64Nt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 138 }

pmroHdslNoiseMarginReg73Lt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 139 }

pmroHdslNoiseMarginReg73Nt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 140 }

pmroHdslNoiseMarginReg74Lt OBJECT-TYPE
	SYNTAX INTEGER (0..255)
	ACCESS read-only
	STATUS mandatory
	DESCRIPTION
		"Noise Margin of the line.
		 0-180	attenuation in steps of 0.5 dB
		 254	unknown value
		 255	unsupported variable for addressed device"
	::= { pmroHdslEntry 141 }

pmroHdslNoiseMarginReg74Nt OBJECT-TYPE
	SYNTAX INTEGER (0..255)
	ACCESS read-only
	STATUS mandatory
	DESCRIPTION
		"Noise Margin of the line.
		 0-180	attenuation in steps of 0.5 dB
		 254	unknown value
		 255	unsupported variable for addressed device"
	::= { pmroHdslEntry 142 }

pmroHdslNoiseMarginReg83Lt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 143 }

pmroHdslNoiseMarginReg83Nt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 144 }

pmroHdslNoiseMarginReg84Lt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 145 }

pmroHdslNoiseMarginReg84Nt OBJECT-TYPE
	SYNTAX INTEGER (0..255)
	ACCESS read-only
	STATUS mandatory
	DESCRIPTION
		"Noise Margin of the line.
		 The value is coded as a signed byte value
		 -63..63	noise margin in steps of 0.5 dB
		 126		unknown value
		 127		unsupported variable for addressed device"
	::= { pmroHdslEntry 146 }

--------------------------------------------------------------------------------
--	PM-RO	Performance Values
--------------------------------------------------------------------------------
pmroValueTable OBJECT-TYPE
	SYNTAX SEQUENCE OF PmroValueEntry
	ACCESS not-accessible
	STATUS mandatory
	DESCRIPTION ""
	::= { pmro 2 }

pmroValueEntry OBJECT-TYPE
	SYNTAX PmroValueEntry
	ACCESS not-accessible
	STATUS mandatory
	DESCRIPTION ""
	INDEX { pmroValuePortIndex, pmroValueLinkIndex, pmroValueCounterIndex }
	::= { pmroValueTable 1 }

PmroValueEntry ::=
	SEQUENCE
	{
		pmroValuePortIndex INTEGER,
		pmroValueLinkIndex INTEGER,
		pmroValueCounterIndex INTEGER,
		pmroCounter OCTET STRING
	}

pmroValuePortIndex OBJECT-TYPE
	SYNTAX INTEGER
	ACCESS read-only
	STATUS mandatory
	DESCRIPTION
		"This variable addresses the port number of the proxy
		and is used as index for the other elements in the Table"
	::= { pmroValueEntry 1 }

pmroValueLinkIndex OBJECT-TYPE
	SYNTAX INTEGER
	ACCESS read-only
	STATUS mandatory
	DESCRIPTION
		"This variable addresses the slot number of the OMI sub-rack
		and is used as index for the other elements in the Table"
	::= { pmroValueEntry 2 }

pmroValueCounterIndex OBJECT-TYPE
	SYNTAX INTEGER
	ACCESS read-only
	STATUS mandatory
	DESCRIPTION
		"This variable addresses the performance counter of a link
		and is used as index for the other elements in the Table
		
		CRC-4
		1	LT	U-Interface
		2	NT	U-Interface
		3	LT	T-Interface incoming
		4	LT	T-Interface outgoing
		
		CRC-6
		5	LT	Wire pair 1	Direction NT
		6	RegA	Wire pair 1	Direction LT
		7	RegA	Wire pair 1	Direction NT
		8	NT	Wire pair 1	Direction LT
		9	LT	Wire pair 2	Direction NT
		10	RegA	Wire pair 2	Direction LT
		11	RegA	Wire pair 2	Direction NT
		12	NT	Wire pair 2	Direction LT"
	::= { pmroValueEntry 3 }

pmroCounter OBJECT-TYPE
	SYNTAX OCTET STRING(SIZE(96))
	ACCESS read-only
	STATUS mandatory
	DESCRIPTION
		"This octet string contains the performance data of the performance
		counter addressed through the index. The performance values are stored
		as 4 byte values, MSB first.
		
		They are mapped as follows:
		
		Byte	Interval		Variable
		
		0..3	Current 15 Minutes	Elapsed Time
		4..7	Current 15 Minutes	Block Errors
		8..11	Current 15 Minutes	Background Block Errors
		12..15	Current 15 Minutes	Errored Seconds
		16..19	Current 15 Minutes	Severely Errored Seconds
		20..23	Current 15 Minutes	Unavailable Time
		24..27	Last 15 Minutes		Elapsed Time
		28..31	Last 15 Minutes		Block Errors
		32..35	Last 15 Minutes		Background Block Errors
		36..39	Last 15 Minutes		Errored Seconds
		40..43	Last 15 Minutes		Severely Errored Seconds
		44..47	Last 15 Minutes		Unavailable Time
		48..51	Current 24 Hours	Elapsed Time
		52..55	Current 24 Hours	Block Errors
		56..59	Current 24 Hours	Background Block Errors
		60..63	Current 24 Hours	Errored Seconds
		64..67	Current 24 Hours	Severely Errored Seconds
		68..71	Current 24 Hours	Unavailable Time
		72..75	Last 24 Hours		Elapsed Time
		76..79	Last 24 Hours		Block Errors
		80..83	Last 24 Hours		Background Block Errors
		84..87	Last 24 Hours		Errored Seconds
		88..91	Last 24 Hours		Severely Errored Seconds
		92..95	Last 24 Hours		Unavailable Time
		
		The variables have the following ranges:
		15 Minute Intervals:
		ET, ES, SES, UT		0..900 Seconds
		BE, BBE			0..300'000 Errors
		
		24 Hour Intervals
		ET, ES, SES, UT		0..86'400 Seconds
		BE, BBE			0..28'800'00 Errors
		
		All Variables can contain the following values to indicate
		undefined results:
		HEX		DEC	Meaning
		0xfffffffd	(-3)	Disabled (the proxy does not store values for this link)
		0xfffffffe	(-2)	Unsupported variable for addressed device
		0xffffffff	(-1)	Unknown value"
	::= { pmroValueEntry 4 }

--------------------------------------------------------------------------------
--	PM-RO	STU Performance Values
--------------------------------------------------------------------------------
pmroStuValueTable OBJECT-TYPE
	SYNTAX SEQUENCE OF PmroStuValueEntry
	ACCESS not-accessible
	STATUS mandatory
	DESCRIPTION ""
	::= { pmro 3 }

pmroStuValueEntry OBJECT-TYPE
	SYNTAX PmroStuValueEntry
	ACCESS not-accessible
	STATUS mandatory
	DESCRIPTION ""
	INDEX { pmroStuValuePortIndex, pmroStuValueLinkIndex, pmroStuValueCounterIndex, pmroStuValueIntervalIndex }
	::= { pmroStuValueTable 1 }

PmroStuValueEntry ::=
	SEQUENCE
	{
		pmroStuValuePortIndex INTEGER,
		pmroStuValueLinkIndex INTEGER,
		pmroStuValueCounterIndex INTEGER,
		pmroStuValueIntervalIndex INTEGER,
		pmroStuCounter OCTET STRING
	}

pmroStuValuePortIndex OBJECT-TYPE
	SYNTAX INTEGER
	ACCESS read-only
	STATUS mandatory
	DESCRIPTION
		"This variable addresses the port number of the proxy
		and is used as index for the other elements in the Table"
	::= { pmroStuValueEntry 1 }

pmroStuValueLinkIndex OBJECT-TYPE
	SYNTAX INTEGER
	ACCESS read-only
	STATUS mandatory
	DESCRIPTION
		"This variable addresses the slot number of the OMI sub-rack
		and is used as index for the other elements in the Table"
	::= { pmroStuValueEntry 2 }

pmroStuValueCounterIndex OBJECT-TYPE
	SYNTAX INTEGER
	ACCESS read-only
	STATUS mandatory
	DESCRIPTION
        "This variable addresses the performance counter of a link
        and is used as index for the other elements in the Table
		
		CRC-4
        1   LT	U-Interface
        2   NT	U-Interface
        3   LT	V-Interface incoming
        4   LT	V-Interface outgoing
        13  NT	T-Interface incoming
        14  NT	T-Interface outgoing
		
        CRC-6
        5   LT      Wire pair 1	Direction NT
        6   Reg1    Wire pair 1	Direction LT
        7   Reg1    Wire pair 1	Direction NT
        8   NT      Wire pair 1	Direction LT
        9   LT      Wire pair 2	Direction NT
        10  Reg1    Wire pair 2	Direction LT
        11  Reg1    Wire pair 2	Direction NT
        12  NT      Wire pair 2	Direction LT
        
        15  Reg2    Wire pair 1	Direction LT
        16  Reg2    Wire pair 1	Direction NT
        17  Reg2    Wire pair 2	Direction LT
        18  Reg2    Wire pair 2	Direction NT
        
        19  Reg3    Wire pair 1	Direction LT
        20  Reg3    Wire pair 1	Direction NT
        21  Reg4    Wire pair 1	Direction LT
        22  Reg4    Wire pair 1	Direction NT
        23  Reg5    Wire pair 1	Direction LT
        24  Reg5    Wire pair 1	Direction NT
        25  Reg6    Wire pair 1	Direction LT
        26  Reg6    Wire pair 1	Direction NT
        27  Reg7    Wire pair 1	Direction LT
        28  Reg7    Wire pair 1	Direction NT
        29  Reg8    Wire pair 1	Direction LT
        30  Reg8    Wire pair 1	Direction NT

        31  Reg3    Wire pair 2	Direction LT
        32  Reg3    Wire pair 2	Direction NT
        33  Reg4    Wire pair 2	Direction LT
        34  Reg4    Wire pair 2	Direction NT
        35  Reg5    Wire pair 2	Direction LT
        36  Reg5    Wire pair 2	Direction NT
        37  Reg6    Wire pair 2	Direction LT
        38  Reg6    Wire pair 2	Direction NT
        39  Reg7    Wire pair 2	Direction LT
        40  Reg7    Wire pair 2	Direction NT
        41  Reg8    Wire pair 2	Direction LT
        42  Reg8    Wire pair 2	Direction NT

        43  Reg1    Wire pair 3	Direction LT
        44  Reg1    Wire pair 3	Direction NT
        45  Reg2    Wire pair 3	Direction LT
        46  Reg2    Wire pair 3	Direction NT
        47  Reg3    Wire pair 3	Direction LT
        48  Reg3    Wire pair 3	Direction NT
        49  Reg4    Wire pair 3	Direction LT
        50  Reg4    Wire pair 3	Direction NT

        59  Reg1    Wire pair 4	Direction LT
        60  Reg1    Wire pair 4	Direction NT
        61  Reg2    Wire pair 4	Direction LT
        62  Reg2    Wire pair 4	Direction NT
        63  Reg3    Wire pair 4	Direction LT
        64  Reg3    Wire pair 4	Direction NT
        65  Reg4    Wire pair 4	Direction LT
        66  Reg4    Wire pair 4	Direction NT

        75  LT      Wire pair 3 Direction NT
        76  NT      Wire pair 3 Direction LT
        77  LT      Wire pair 4 Direction NT
        78  NT      Wire pair 4 Direction LT

        FAS and BPV
        79  FAS-V/T error local
        80  BPV-V/T local
        81  FAS-T   error far
        82  BPV-T   far

        83	V_A CRC4
        84	V_A Ebit
        85	V_B CRC4
        86	V_B Ebit
        87	V_C CRC4
        88	V_C Ebit
        89	V_D CRC4
        90	V_D Ebit

        91	MCS Ch a LT
        92	MCS Ch b LT
        93	MCS Ch c LT
        94	MCS Ch d LT

        96	MCS Ch a NT
        97	MCS Ch b NT
        98	MCS Ch c NT
        99	MCS Ch d NT

       101	Far end MCS Ch a NT
       102	Far end MCS Ch b NT
       103	Far end MCS Ch c NT
       104	Far end MCS Ch d NT

       106	Far end MCS Ch a LT
       107	Far end MCS Ch b LT
       108	Far end MCS Ch c LT
       109	Far end MCS Ch d LT

       113	V_A CRC4 far
       114	V_A Ebit far
       115	V_B CRC4 far
       116	V_B Ebit far
       117	V_C CRC4 far
       118	V_C Ebit far
       119	V_D CRC4 far
       120	V_D Ebit far"
	::= { pmroStuValueEntry 3 }

pmroStuValueIntervalIndex OBJECT-TYPE
	SYNTAX INTEGER
	ACCESS read-only
	STATUS mandatory
	DESCRIPTION
		"This variable addresses the performance interval pair of a link
		and is used as index for the other elements in the Table
		The following values are supported:
		Index	Interval 1	Interval 2
		 1	Current		Last  1
		 2	Last  2		Last  3
		 3	Last  4		Last  5
		 4	Last  6		Last  7
		 5	Last  8		Last  9
		 6	Last 10		Last 11
		 7	Last 12		Last 13
		 8	Last 14		Last 15
		 9	Last 16		Last 17
		10	Last 18		Last 19
		11	Last 20		Last 21
		12	Last 22		Last 23
		13	Last 24		Last 25
		14	Last 26		Last 27
		15	Last 28		Last 29
		16	Last 30		Last 31	
		17	Last 32		unused"
	::= { pmroStuValueEntry 4 }

pmroStuCounter OBJECT-TYPE
	SYNTAX OCTET STRING(SIZE(96))
	ACCESS read-only
	STATUS mandatory
	DESCRIPTION
		"This octet string contains the performance data of the performance
		counter addressed through the index. The performance values are stored
		as 4 byte values, MSB first.
		
		They are mapped as follows:
		
		Byte	Interval		Variable
		
		0..3	Interval 1 - 15 Minutes	Elapsed Time
		4..7	Interval 1 - 15 Minutes	Block Errors
		8..11	Interval 1 - 15 Minutes	LOSW Seconds
		12..15	Interval 1 - 15 Minutes	Errored Seconds
		16..19	Interval 1 - 15 Minutes	Severely Errored Seconds
		20..23	Interval 1 - 15 Minutes	Unavailable Time
		24..27	Interval 2 - 15 Minutes	Elapsed Time
		28..31	Interval 2 - 15 Minutes	Block Errors
		32..35	Interval 2 - 15 Minutes	LOSW Seconds
		36..39	Interval 2 - 15 Minutes	Errored Seconds
		40..43	Interval 2 - 15 Minutes	Severely Errored Seconds
		44..47	Interval 2 - 15 Minutes	Unavailable Time
		48..51	Interval 1 - 24 Hours	Elapsed Time
		52..55	Interval 1 - 24 Hours	Block Errors
		56..59	Interval 1 - 24 Hours	LOSW Seconds
		60..63	Interval 1 - 24 Hours	Errored Seconds
		64..67	Interval 1 - 24 Hours	Severely Errored Seconds
		68..71	Interval 1 - 24 Hours	Unavailable Time
		72..75	Interval 2 - 24 Hours	Elapsed Time
		76..79	Interval 2 - 24 Hours	Block Errors
		80..83	Interval 2 - 24 Hours	LOSW Seconds
		84..87	Interval 2 - 24 Hours	Errored Seconds
		88..91	Interval 2 - 24 Hours	Severely Errored Seconds
		92..95	Interval 2 - 24 Hours	Unavailable Time
		
		The variables have the following ranges:
		15 Minute Intervals:
		ET, ES, SES, LOSWS, UT	0..900 Seconds
		BE			0..300'000 Errors
		
		24 Hour Intervals
		ET, ES, SES, LOSWS, UT	0..86'400 Seconds
		BE			0..28'800'00 Errors
		
		All Variables can contain the following values to indicate
		undefined results:
		HEX		DEC	Meaning
		0xfffffffd	(-3)	Disabled (the proxy does not store values for this link)
		0xfffffffe	(-2)	Unsupported variable for addressed device
		0xffffffff	(-1)	Unknown value"
	::= { pmroStuValueEntry 5 }

--------------------------------------------------------------------------------
--	PM-RO	15 min Dummy Performance Variables for APC
--------------------------------------------------------------------------------
pmroApc15Table OBJECT-TYPE
	SYNTAX SEQUENCE OF PmroApc15Entry
	ACCESS not-accessible
	STATUS mandatory
	DESCRIPTION ""
	::= { pmro 4 }

pmroApc15Entry OBJECT-TYPE
	SYNTAX PmroApc15Entry
	ACCESS not-accessible
	STATUS mandatory
	DESCRIPTION ""
	INDEX { pmroApc15PortIndex, pmroApc15LinkIndex, pmroApc15CounterIndex }
	::= { pmroApc15Table 1 }

PmroApc15Entry ::=
	SEQUENCE
	{
		pmroApc15PortIndex INTEGER,
		pmroApc15LinkIndex INTEGER,
		pmroApc15CounterIndex INTEGER,
		pmroApc15BlockErrors INTEGER,
		pmroApc15BackgroundBlockErrors INTEGER,
		pmroApc15ErroredSeconds INTEGER,
		pmroApc15SeverelyErroredSeconds INTEGER,
		pmroApc15UnavailableTime INTEGER
	}

pmroApc15PortIndex OBJECT-TYPE
	SYNTAX INTEGER
	ACCESS read-only
	STATUS mandatory
	DESCRIPTION
		"This variable addresses the port number of the proxy
		and is used as index for the other elements in the Table"
	::= { pmroApc15Entry 1 }

pmroApc15LinkIndex OBJECT-TYPE
	SYNTAX INTEGER
	ACCESS read-only
	STATUS mandatory
	DESCRIPTION
		"This variable addresses the slot number of the OMI sub-rack
		and is used as index for the other elements in the Table"
	::= { pmroApc15Entry 2 }

pmroApc15CounterIndex OBJECT-TYPE
	SYNTAX INTEGER
	ACCESS read-only
	STATUS mandatory
	DESCRIPTION
		"This variable addresses the performance counter of a link
		and is used as index for the other elements in the Table"
	::= { pmroApc15Entry 3 }

pmroApc15BlockErrors OBJECT-TYPE
	SYNTAX INTEGER
	ACCESS read-only
	STATUS mandatory
	DESCRIPTION
		"This is an unused dummy variable which is used by the Automatic
		 Performance Collection (APC) and does not exist on the proxy
		 which means that it will never be answered."
	::= { pmroApc15Entry 4 }

pmroApc15BackgroundBlockErrors OBJECT-TYPE
	SYNTAX INTEGER
	ACCESS read-only
	STATUS mandatory
	DESCRIPTION
		"This is an unused dummy variable which is used by the Automatic
		 Performance Collection (APC) and does not exist on the proxy
		 which means that it will never be answered."
	::= { pmroApc15Entry 5 }

pmroApc15ErroredSeconds OBJECT-TYPE
	SYNTAX INTEGER
	ACCESS read-only
	STATUS mandatory
	DESCRIPTION
		"This is an unused dummy variable which is used by the Automatic
		 Performance Collection (APC) and does not exist on the proxy
		 which means that it will never be answered."
	::= { pmroApc15Entry 6 }

pmroApc15SeverelyErroredSeconds OBJECT-TYPE
	SYNTAX INTEGER
	ACCESS read-only
	STATUS mandatory
	DESCRIPTION
		"This is an unused dummy variable which is used by the Automatic
		 Performance Collection (APC) and does not exist on the proxy
		 which means that it will never be answered."
	::= { pmroApc15Entry 7 }

pmroApc15UnavailableTime OBJECT-TYPE
	SYNTAX INTEGER
	ACCESS read-only
	STATUS mandatory
	DESCRIPTION
		"This is an unused dummy variable which is used by the Automatic
		 Performance Collection (APC) and does not exist on the proxy
		 which means that it will never be answered."
	::= { pmroApc15Entry 8 }

--------------------------------------------------------------------------------
--	PM-RO	24 hour Dummy Performance Variables for APC
--------------------------------------------------------------------------------
pmroApc24Table OBJECT-TYPE
	SYNTAX SEQUENCE OF PmroApc24Entry
	ACCESS not-accessible
	STATUS mandatory
	DESCRIPTION ""
	::= { pmro 5 }

pmroApc24Entry OBJECT-TYPE
	SYNTAX PmroApc24Entry
	ACCESS not-accessible
	STATUS mandatory
	DESCRIPTION ""
	INDEX { pmroApc24PortIndex, pmroApc24LinkIndex, pmroApc24CounterIndex }
	::= { pmroApc24Table 1 }

PmroApc24Entry ::=
	SEQUENCE
	{
		pmroApc24PortIndex INTEGER,
		pmroApc24LinkIndex INTEGER,
		pmroApc24CounterIndex INTEGER,
		pmroApc24BlockErrors INTEGER,
		pmroApc24BackgroundBlockErrors INTEGER,
		pmroApc24ErroredSeconds INTEGER,
		pmroApc24SeverelyErroredSeconds INTEGER,
		pmroApc24UnavailableTime INTEGER
	}

pmroApc24PortIndex OBJECT-TYPE
	SYNTAX INTEGER
	ACCESS read-only
	STATUS mandatory
	DESCRIPTION
		"This variable addresses the port number of the proxy
		and is used as index for the other elements in the Table"
	::= { pmroApc24Entry 1 }

pmroApc24LinkIndex OBJECT-TYPE
	SYNTAX INTEGER
	ACCESS read-only
	STATUS mandatory
	DESCRIPTION
		"This variable addresses the slot number of the OMI sub-rack
		and is used as index for the other elements in the Table"
	::= { pmroApc24Entry 2 }

pmroApc24CounterIndex OBJECT-TYPE
	SYNTAX INTEGER
	ACCESS read-only
	STATUS mandatory
	DESCRIPTION
		"This variable addresses the performance counter of a link
		and is used as index for the other elements in the Table"
	::= { pmroApc24Entry 3 }

pmroApc24BlockErrors OBJECT-TYPE
	SYNTAX INTEGER
	ACCESS read-only
	STATUS mandatory
	DESCRIPTION
		"This is an unused dummy variable which is used by the Automatic
		 Performance Collection (APC) and does not exist on the proxy
		 which means that it will never be answered."
	::= { pmroApc24Entry 4 }

pmroApc24BackgroundBlockErrors OBJECT-TYPE
	SYNTAX INTEGER
	ACCESS read-only
	STATUS mandatory
	DESCRIPTION
		"This is an unused dummy variable which is used by the Automatic
		 Performance Collection (APC) and does not exist on the proxy
		 which means that it will never be answered."
	::= { pmroApc24Entry 5 }

pmroApc24ErroredSeconds OBJECT-TYPE
	SYNTAX INTEGER
	ACCESS read-only
	STATUS mandatory
	DESCRIPTION
		"This is an unused dummy variable which is used by the Automatic
		 Performance Collection (APC) and does not exist on the proxy
		 which means that it will never be answered."
	::= { pmroApc24Entry 6 }

pmroApc24SeverelyErroredSeconds OBJECT-TYPE
	SYNTAX INTEGER
	ACCESS read-only
	STATUS mandatory
	DESCRIPTION
		"This is an unused dummy variable which is used by the Automatic
		 Performance Collection (APC) and does not exist on the proxy
		 which means that it will never be answered."
	::= { pmroApc24Entry 7 }

pmroApc24UnavailableTime OBJECT-TYPE
	SYNTAX INTEGER
	ACCESS read-only
	STATUS mandatory
	DESCRIPTION
		"This is an unused dummy variable which is used by the Automatic
		 Performance Collection (APC) and does not exist on the proxy
		 which means that it will never be answered."
	::= { pmroApc24Entry 8 }


--------------------------------------------------------------------------------
--	PM-RO	Bit Error Ration Measurement
--------------------------------------------------------------------------------
pmroBerTable OBJECT-TYPE
	SYNTAX SEQUENCE OF PmroBerEntry
	ACCESS not-accessible
	STATUS mandatory
	DESCRIPTION ""
	::= { pmro 6 }

pmroBerEntry OBJECT-TYPE
	SYNTAX PmroBerEntry
	ACCESS not-accessible
	STATUS mandatory
	DESCRIPTION ""
	INDEX { pmroBerPortIndex, pmroBerLinkIndex }
	::= { pmroBerTable 1 }

PmroBerEntry ::=
	SEQUENCE
	{
		pmroBerPortIndex INTEGER,
		pmroBerLinkIndex INTEGER,
		pmroBerStatus INTEGER,
		pmroBerInterval INTEGER,
		pmroBerElapsedTime INTEGER,
		pmroBerSynchLoss INTEGER,
		pmroBerNumErrs INTEGER,
		pmroBerErrorFreeSeconds INTEGER,
		pmroBerResultMcsChannelA INTEGER,
		pmroBerResultMcsChannelB INTEGER,
		pmroBerResultMcsChannelC INTEGER,
		pmroBerResultMcsChannelD INTEGER
	}

pmroBerPortIndex OBJECT-TYPE
	SYNTAX INTEGER
	ACCESS read-only
	STATUS mandatory
	DESCRIPTION
		"This variable addresses the port number of the proxy
		and is used as index for the other elements in the Table"
	::= { pmroBerEntry 1 }

pmroBerLinkIndex OBJECT-TYPE
	SYNTAX INTEGER
	ACCESS read-only
	STATUS mandatory
	DESCRIPTION
		"This variable addresses the slot number of the OMI sub-rack
		and is used as index for the other elements in the Table"
	::= { pmroBerEntry 2 }

pmroBerStatus OBJECT-TYPE
	SYNTAX INTEGER
	{
		done(1),
		running(2),
		search(3),
		failed(4),
		abort(5),
		norun(6),
		unknown(254),
		unsupported(255)
	}
	ACCESS read-only
	STATUS mandatory
	DESCRIPTION
		"State of Bit Error Ration measurement
		1	Measurement is finished
		2	Measurement is still in progress
		3	Measurement is still trying to find synchronisation
		4	Measurement failed to find synchronisation
		5	Measurement has been (aborted)
		6	Measurement has not yet been started
		254	Unknown value
		255	Unsupported variable for addressed device"
	::= { pmroBerEntry 3 }

pmroBerInterval OBJECT-TYPE
	SYNTAX INTEGER
	{
		oneMin(2),
		tenMin(3),
		oneHour(4),
		oneDay(5),
		oneMinDirV(6),
		tenMinDirV(7),
		oneHourDirV(8),
		oneDayDirV(9),
		oneMinRoundTrip(10),
		tenMinRoundTrip(11),
		oneHourRoundTrip(12),
		oneDayRoundTrip(13),
		oneMinMCS(14),
		tenMinMCS(15),
		oneHourMCS(16),
		oneDayMCS(17),
		oneMinData(18),
		tenMinData(19),
		oneHourData(20),
		oneDayData(21),
		oneMinMCSLocal(22),
		tenMinMCSLocal(23),
		oneHourMCSLocal(24),
		oneDayMCSLocal(25),
		oneMinG703If(26),
		tenMinG703If(27),
		oneHourG703If(28),
		oneDayG703If(29),
		oneMinDataIf(30),
		tenMinDataIf(31),
		oneHourDataIf(32),
		oneDayDataIf(33),
		unknown(254),
		unsupported(255)
	}
	ACCESS read-only
	STATUS mandatory
	DESCRIPTION
		"The interval of the current or last measurement
		2	OneMin            The measurement duration is/was 1 minute
		3	TenMin            The measurement duration is/was 10 minutes
		4	OneHour           The measurement duration is/was 1 hour
		5	OneDay            The measurement duration is/was 24 hours
		6	OneMinDirV        The measurement duration is/was 1 minute (direction V)
		7	TenMinDirV        The measurement duration is/was 10 minutes (direction V)
		8	OneHourDirV       The measurement duration is/was 1 hour (direction V)
		9	OneDayDirV        The measurement duration is/was 24 hours (direction V)
		10	OneMinRoundTrip   The measurement duration is/was 1 minute (round trip)
		11	TenMinRoundTrip   The measurement duration is/was 10 minutes (round trip)
		12	OneHourRoundTrip  The measurement duration is/was 1 hour (round trip)
		13	OneDayRoundTrip   The measurement duration is/was 24 hours (round trip)
		14	OneMinMCS         The measurement duration is/was 1 minute (MCS)
		15	TenMinMCS         The measurement duration is/was 10 minutes (MCS)
		16	OneHourMCS        The measurement duration is/was 1 hour (MCS)
		17	OneDayMCS         The measurement duration is/was 24 hours (MCS)
		18	OneMinData        The measurement duration is/was 1 minute (Data)
		19	TenMinData        The measurement duration is/was 10 minutes (Data)
		20	OneHourData       The measurement duration is/was 1 hour (Data)
		21	OneDayData        The measurement duration is/was 24 hours (Data)
		22	OneMinMCSLocal    The measurement duration is/was 1 minute (MCSLocal)
		23	TenMinMCSLocal    The measurement duration is/was 10 minutes (MCSLocal)
		24	OneHourMCSLocal   The measurement duration is/was 1 hour (MCSLocal)
		25	OneDayMCSLocal    The measurement duration is/was 24 hours (MCSLocal)
		26	OneMinG703If      The measurement duration is/was 1 minute (G.703 Interface)
		27	TenMinG703If      The measurement duration is/was 10 minutes (G.703 Interface)
		28	OneHourG703If     The measurement duration is/was 1 hour (G.703 Interface)
		29	OneDayG703If      The measurement duration is/was 24 hours (G.703 Interface)
		30	OneMinDataIf      The measurement duration is/was 1 minute (Data Interface)
		31	TenMinDataIf      The measurement duration is/was 10 minutes (Data Interface)
		32	OneHourDataIf     The measurement duration is/was 1 hour (Data Interface)
		33	OneDayDataIf      The measurement duration is/was 24 hours (Data Interface)
		254	Unknown value
		255	Unsupported variable for addressed device"
	::= { pmroBerEntry 4 }

pmroBerElapsedTime OBJECT-TYPE
	SYNTAX INTEGER (0..'ffffffff'h)
	ACCESS read-only
	STATUS mandatory
	DESCRIPTION
		"Elapsed time of measurement. During synchronisation (pmroBerStatus=search) this
		indicates how long the device has been searching for synchronistation. Once
		synchronisation has been found (pmroBerStatus=running), this indicates how long
		the measurement has been running.
		0..86'400	Elapsed time in seconds
		0xfffffffe	Unknown value
		0xffffffff	Unsupported variable for addressed device"
	::= { pmroBerEntry 5 }

pmroBerSynchLoss OBJECT-TYPE
	SYNTAX INTEGER (0..'ffffffff'h)
	ACCESS read-only
	STATUS mandatory
	DESCRIPTION
		"Time without synchronisation. During synchronisation (pmroBerStatus=search) this
		indicates how long the device has been searching for synchronistation and corresponds
		to pmroBerElapsedTime. Once synchronisation has been found (pmroBerStatus=running),
		this indicates how many seconds during the measurement synchronisation has been
		(temporarily) lost.
		0..86'40000	Number of seconds without synchronisation
		0xfffffffe	Unknown value
		0xffffffff	Unsupported variable for addressed device"
	::= { pmroBerEntry 6 }

pmroBerNumErrs OBJECT-TYPE
	SYNTAX INTEGER (0..'ffffffff'h)
	ACCESS read-only
	STATUS mandatory
	DESCRIPTION
		"Number of bit errors which occurred during the Bit Error Ratio measurement
		0..4'294'967'292	Effective number of errors
		0xfffffffd		More than 4'294'967'292 errors
		0xfffffffe		Unknown value
		0xffffffff		Unsupported variable for addressed device"
	::= { pmroBerEntry 7 }

pmroBerErrorFreeSeconds OBJECT-TYPE
	SYNTAX INTEGER (0..'ffffffff'h)
	ACCESS read-only
	STATUS mandatory
	DESCRIPTION
		"Number of error free seconds during the measurement. This can be used to determine
		whether errors are 'bursty', i.e. occurring only during a short period of time (when
		the number of error free seconds is close to the elapsed time) or continuous (when 
		the number of error free seconds is low).
		0..86'400		Error free seconds during measurement
		0xfffffffe	Unknown value
		0xffffffff	Unsupported variable for addressed device"
	::= { pmroBerEntry 8 }

pmroBerResultMcsChannelA OBJECT-TYPE
	SYNTAX INTEGER
	{
		notOK(1),
		ok(2),
		noPattern(3),
		unknown(254),
		unsupported(255)
	}
	ACCESS read-only
	STATUS mandatory
	DESCRIPTION
		"BER test result for MCS channel a:
		1	Test was error free on this MCS channel
		2	Test showed errors on this MCS channel
 		3	No pattern on this MCS channel found while test
 		254	Unknown value
		255	Unsupported variable for addressed device"
	::= { pmroBerEntry 9 }

pmroBerResultMcsChannelB OBJECT-TYPE
	SYNTAX INTEGER
	{
		notOK(1),
		ok(2),
		noPattern(3),
		unknown(254),
		unsupported(255)
	}
	ACCESS read-only
	STATUS mandatory
	DESCRIPTION
		"BER test result for MCS channel b:
		1	Test was error free on this MCS channel
		2	Test showed errors on this MCS channel
 		3	No pattern on this MCS channel found while test
 		254	Unknown value
		255	Unsupported variable for addressed device"
	::= { pmroBerEntry 10 }

pmroBerResultMcsChannelC OBJECT-TYPE
	SYNTAX INTEGER
	{
		notOK(1),
		ok(2),
		noPattern(3),
		unknown(254),
		unsupported(255)
	}
	ACCESS read-only
	STATUS mandatory
	DESCRIPTION
		"BER test result for MCS channel c:
		1	Test was error free on this MCS channel
		2	Test showed errors on this MCS channel
 		3	No pattern on this MCS channel found while test
 		254	Unknown value
		255	Unsupported variable for addressed device"
	::= { pmroBerEntry 11 }

pmroBerResultMcsChannelD OBJECT-TYPE
	SYNTAX INTEGER
	{
		notOK(1),
		ok(2),
		noPattern(3),
		unknown(254),
		unsupported(255)
	}
	ACCESS read-only
	STATUS mandatory
	DESCRIPTION
		"BER test result for MCS channel d:
		1	Test was error free on this MCS channel
		2	Test showed errors on this MCS channel
 		3	No pattern on this MCS channel found while test
		254	Unknown value
		255	Unsupported variable for addressed device"
	::= { pmroBerEntry 12 }

--------------------------------------------------------------------------------
--	PM-RO	Line Probing
--------------------------------------------------------------------------------
pmroLineProbeTable OBJECT-TYPE
	SYNTAX SEQUENCE OF PmroLineProbeEntry
	ACCESS not-accessible
	STATUS mandatory
	DESCRIPTION ""
	::= { pmro 7 }

pmroLineProbeEntry OBJECT-TYPE
	SYNTAX PmroLineProbeEntry
	ACCESS not-accessible
	STATUS mandatory
	DESCRIPTION ""
	INDEX { pmroLineProbePortIndex, pmroLineProbeLinkIndex }
	::= { pmroLineProbeTable 1 }

PmroLineProbeEntry ::=
	SEQUENCE
	{
		pmroLineProbePortIndex INTEGER,
		pmroLineProbeLinkIndex INTEGER,
		pmroLineProbeStatus INTEGER,
		pmroLineProbeBandwidthMask OCTET STRING,
		pmroLineProbeSNRMargin OCTET STRING,
		pmroLineProbeSNRMarginWire2 OCTET STRING,
		pmroLineProbeSNRMarginWire3 OCTET STRING,
		pmroLineProbeSNRMarginWire4 OCTET STRING
	}

pmroLineProbePortIndex OBJECT-TYPE
	SYNTAX INTEGER
	ACCESS read-only
	STATUS mandatory
	DESCRIPTION
		"This variable addresses the port number of the proxy
		and is used as index for the other elements in the Table"
	::= { pmroLineProbeEntry 1 }

pmroLineProbeLinkIndex OBJECT-TYPE
	SYNTAX INTEGER
	ACCESS read-only
	STATUS mandatory
	DESCRIPTION
		"This variable addresses the slot number of the OMI sub-rack
		and is used as index for the other elements in the Table"
	::= { pmroLineProbeEntry 2 }

pmroLineProbeStatus OBJECT-TYPE
	SYNTAX INTEGER
	{
		done(1),
		running(2),
		failed(3),
		abort(4),
		norun(5),
		unknown(254),
		unsupported(255)
	}
	ACCESS read-only
	STATUS mandatory
	DESCRIPTION
		"State of Line Probing
		1	Done	Probing is finished
		2	Running	Probing is still in progress
		3	Failed	Probing failed
		4	Abort	Probing has been aborted
		5	Norun	Probing has never been started
		254		Unknown value
		255		Unsupported variable for addressed device"
	::= { pmroLineProbeEntry 3 }

pmroLineProbeBandwidthMask OBJECT-TYPE
	SYNTAX OCTET STRING(SIZE(6))
	ACCESS read-only
	STATUS mandatory
	DESCRIPTION
		"Bandwidths used for line probing
				
		 			Bandwidth
		Byte 0
			bit  0		reserved
			bit  1		reserved
			bit  2		 192 kbit/s
			bit  3		 256 kbit/s
			bit  4		 320 kbit/s
			bit  5		 384 kbit/s
			bit  6		 448 kbit/s
			bit  7		 512 kbit/s
		Byte 1	
			bit  0		 576 kbit/s
			bit  1		 640 kbit/s
			bit  2		 704 kbit/s
			bit  3		 768 kbit/s
			bit  4		 832 kbit/s
			bit  5		 896 kbit/s
			bit  6		 960 kbit/s
			bit  7		 1024 kbit/s
		Byte 2	
			bit  0		 1088 kbit/s
			bit  1		 1152 kbit/s
			bit  2		 1216 kbit/s
			bit  3		 1280 kbit/s
			bit  4		 1344 kbit/s
			bit  5		 1408 kbit/s
			bit  6		 1472 kbit/s
			bit  7		 1536 kbit/s
		Byte 3	
			bit  0		 1600 kbit/s
			bit  1		 1664 kbit/s
			bit  2		 1728 kbit/s
			bit  3		 1792 kbit/s
			bit  4		 1856 kbit/s
			bit  5		 1920 kbit/s
			bit  6		 1984 kbit/s
			bit  7		 2048 kbit/s
		Byte 4	
			bit  0		 2112 kbit/s
			bit  1		 2176 kbit/s
			bit  2		 2240 kbit/s
			bit  3		 2304 kbit/s
			bit  4		 unused
			bit  5		 unused
			bit  6		 unused
			bit  7		 unused
		 Byte 5 contains a value specifying the validity of the
		 result of a read operation:
		 1	Ok	Values returned are valid
		 254		unknown values
		 255		unsupported variable for addressed device"
			
	::= { pmroLineProbeEntry 4 }

pmroLineProbeSNRMargin OBJECT-TYPE
	SYNTAX OCTET STRING(SIZE(36))
	ACCESS read-only
	STATUS mandatory
	DESCRIPTION
		"Each byte contains as result of the line probe the SNR margin
		 for the bandwidth corresponding to the byte number
		 
		 The value for each byte is coded as follows:
		 -127..+127	SNR margin in dB
		 -128           Unknown value"
	::= { pmroLineProbeEntry 5 }

pmroLineProbeSNRMarginWire2 OBJECT-TYPE
	SYNTAX OCTET STRING(SIZE(36))
	ACCESS read-only
	STATUS mandatory
	DESCRIPTION
		"Each byte contains as result of the line probe the SNR margin
		 for the bandwidth corresponding to the byte number
		 
		 The value for each byte is coded as follows:
		 -127..+127	SNR margin in dB
		 -128           Unknown value"
	::= { pmroLineProbeEntry 6 }

pmroLineProbeSNRMarginWire3 OBJECT-TYPE
	SYNTAX OCTET STRING(SIZE(36))
	ACCESS read-only
	STATUS mandatory
	DESCRIPTION
		"Each byte contains as result of the line probe the SNR margin
		 for the bandwidth corresponding to the byte number
		 
		 The value for each byte is coded as follows:
		 -127..+127	SNR margin in dB
		 -128           Unknown value"
	::= { pmroLineProbeEntry 7 }

pmroLineProbeSNRMarginWire4 OBJECT-TYPE
	SYNTAX OCTET STRING(SIZE(36))
	ACCESS read-only
	STATUS mandatory
	DESCRIPTION
		"Each byte contains as result of the line probe the SNR margin
		 for the bandwidth corresponding to the byte number
		 
		 The value for each byte is coded as follows:
		 -127..+127	SNR margin in dB
		 -128           Unknown value"
	::= { pmroLineProbeEntry 8 }

--------------------------------------------------------------------------------
--	PM-RO	Local L2Switch Values
--------------------------------------------------------------------------------
pmroLocalL2SwitchValueTable OBJECT-TYPE
	SYNTAX SEQUENCE OF PmroLocalL2SwitchValueEntry
	ACCESS not-accessible
	STATUS mandatory
	DESCRIPTION ""
	::= { pmro 8 }

pmroLocalL2SwitchValueEntry OBJECT-TYPE
	SYNTAX PmroLocalL2SwitchValueEntry
	ACCESS not-accessible
	STATUS mandatory
	DESCRIPTION ""
	INDEX { pmroLocalL2SwitchValuePortIndex, pmroLocalL2SwitchValueLinkIndex, pmroLocalL2SwitchValueCounterIndex }
	::= { pmroLocalL2SwitchValueTable 1 }

PmroLocalL2SwitchValueEntry ::=
	SEQUENCE
	{
		pmroLocalL2SwitchValuePortIndex INTEGER,
		pmroLocalL2SwitchValueLinkIndex INTEGER,
		pmroLocalL2SwitchValueCounterIndex INTEGER,
		pmroLocalL2SwitchRxCounter INTEGER,
		pmroLocalL2SwitchTxCounter INTEGER,
		pmroLocalL2SwitchErrCounter INTEGER
	}

pmroLocalL2SwitchValuePortIndex OBJECT-TYPE
	SYNTAX INTEGER
	ACCESS read-only
	STATUS mandatory
	DESCRIPTION
		"This variable addresses the port number of the proxy
		and is used as index for the other elements in the Table"
	::= { pmroLocalL2SwitchValueEntry 1 }

pmroLocalL2SwitchValueLinkIndex OBJECT-TYPE
	SYNTAX INTEGER
	ACCESS read-only
	STATUS mandatory
	DESCRIPTION
		"This variable addresses the slot number of the OMI sub-rack
		and is used as index for the other elements in the Table"
	::= { pmroLocalL2SwitchValueEntry 2 }

pmroLocalL2SwitchValueCounterIndex OBJECT-TYPE
	SYNTAX INTEGER
	ACCESS read-only
	STATUS mandatory
	DESCRIPTION
		"This variable addresses the performance counter of a link
		and is used as index for the other elements in the Table
		
		1	WAN Port
		2	LAN Port 1
		3	LAN Port 2
		4	LAN Port 3
		5	LAN Port 4"
	::= { pmroLocalL2SwitchValueEntry 3 }

pmroLocalL2SwitchRxCounter OBJECT-TYPE
	SYNTAX INTEGER
	ACCESS read-only
	STATUS mandatory
	DESCRIPTION
		"This value indicates the number of Rx packets / frames on a
		L2Switch port, depending on the type of port:
		
		WAN Port	Number of Frames
		LAN Port x	Number of Packets
		
		The counters count as far as the decimal equivalend of
		0xfffffffd and then roll over to 0.
		
		0xfffffffe	Unsupported value
		0xffffffff	Unknown value"
	::= { pmroLocalL2SwitchValueEntry 4 }

pmroLocalL2SwitchTxCounter OBJECT-TYPE
	SYNTAX INTEGER
	ACCESS read-only
	STATUS mandatory
	DESCRIPTION
		"This value indicates the number of Tx packets / frames on a
		L2Switch port, depending on the type of port:
		
		WAN Port	Number of Frames
		LAN Port x	Number of Packets
		
		The counters count as far as the decimal equivalend of
		0xfffffffd and then roll over to 0.
		
		0xfffffffe	Unsupported value
		0xffffffff	Unknown value"
	::= { pmroLocalL2SwitchValueEntry 5 }

pmroLocalL2SwitchErrCounter OBJECT-TYPE
	SYNTAX INTEGER
	ACCESS read-only
	STATUS mandatory
	DESCRIPTION
		"This value indicates the number of errored packets / frames on a
		L2Switch port, depending on the type of port:
		
		WAN Port	Number of Frames
		LAN Port x	Number of Packets
		
		The counters count as far as the decimal equivalend of
		0xfffffffd and then roll over to 0.
		
		0xfffffffe	Unsupported value
		0xffffffff	Unknown value"
	::= { pmroLocalL2SwitchValueEntry 6 }

--------------------------------------------------------------------------------
--	PM-RO	Far L2Switch Values
--------------------------------------------------------------------------------
pmroFarL2SwitchValueTable OBJECT-TYPE
	SYNTAX SEQUENCE OF PmroFarL2SwitchValueEntry
	ACCESS not-accessible
	STATUS mandatory
	DESCRIPTION ""
	::= { pmro 9 }

pmroFarL2SwitchValueEntry OBJECT-TYPE
	SYNTAX PmroFarL2SwitchValueEntry
	ACCESS not-accessible
	STATUS mandatory
	DESCRIPTION ""
	INDEX { pmroFarL2SwitchValuePortIndex, pmroFarL2SwitchValueLinkIndex, pmroFarL2SwitchValueCounterIndex }
	::= { pmroFarL2SwitchValueTable 1 }

PmroFarL2SwitchValueEntry ::=
	SEQUENCE
	{
		pmroFarL2SwitchValuePortIndex INTEGER,
		pmroFarL2SwitchValueLinkIndex INTEGER,
		pmroFarL2SwitchValueCounterIndex INTEGER,
		pmroFarL2SwitchRxCounter INTEGER,
		pmroFarL2SwitchTxCounter INTEGER,
		pmroFarL2SwitchErrCounter INTEGER
	}

pmroFarL2SwitchValuePortIndex OBJECT-TYPE
	SYNTAX INTEGER
	ACCESS read-only
	STATUS mandatory
	DESCRIPTION
		"This variable addresses the port number of the proxy
		and is used as index for the other elements in the Table"
	::= { pmroFarL2SwitchValueEntry 1 }

pmroFarL2SwitchValueLinkIndex OBJECT-TYPE
	SYNTAX INTEGER
	ACCESS read-only
	STATUS mandatory
	DESCRIPTION
		"This variable addresses the slot number of the OMI sub-rack
		and is used as index for the other elements in the Table"
	::= { pmroFarL2SwitchValueEntry 2 }

pmroFarL2SwitchValueCounterIndex OBJECT-TYPE
	SYNTAX INTEGER
	ACCESS read-only
	STATUS mandatory
	DESCRIPTION
		"This variable addresses the performance counter of a link
		and is used as index for the other elements in the Table
		
		1	WAN Port
		2	LAN Port 1
		3	LAN Port 2
		4	LAN Port 3
		5	LAN Port 4"
	::= { pmroFarL2SwitchValueEntry 3 }

pmroFarL2SwitchRxCounter OBJECT-TYPE
	SYNTAX INTEGER
	ACCESS read-only
	STATUS mandatory
	DESCRIPTION
		"This value indicates the number of Rx packets / frames on a
		L2Switch port, depending on the type of port:
		
		WAN Port	Number of Frames
		LAN Port x	Number of Packets
		
		The counters count as far as the decimal equivalend of
		0xfffffffd and then roll over to 0.
		
		0xfffffffe	Unsupported value
		0xffffffff	Unknown value"
	::= { pmroFarL2SwitchValueEntry 4 }

pmroFarL2SwitchTxCounter OBJECT-TYPE
	SYNTAX INTEGER
	ACCESS read-only
	STATUS mandatory
	DESCRIPTION
		"This value indicates the number of Tx packets / frames on a
		L2Switch port, depending on the type of port:
		
		WAN Port	Number of Frames
		LAN Port x	Number of Packets
		
		The counters count as far as the decimal equivalend of
		0xfffffffd and then roll over to 0.
		
		0xfffffffe	Unsupported value
		0xffffffff	Unknown value"
	::= { pmroFarL2SwitchValueEntry 5 }

pmroFarL2SwitchErrCounter OBJECT-TYPE
	SYNTAX INTEGER
	ACCESS read-only
	STATUS mandatory
	DESCRIPTION
		"This value indicates the number of errored packets / frames on a
		L2Switch port, depending on the type of port:
		
		WAN Port	Number of Frames
		LAN Port x	Number of Packets
		
		The counters count as far as the decimal equivalend of
		0xfffffffd and then roll over to 0.
		
		0xfffffffe	Unsupported value
		0xffffffff	Unknown value"
	::= { pmroFarL2SwitchValueEntry 6 }

--------------------------------------------------------------------------------
--	PM-RO	PBO Current Value
--------------------------------------------------------------------------------
pmroPBOCurrentValueTable OBJECT-TYPE
	SYNTAX SEQUENCE OF PmroPBOCurrentValueEntry
	ACCESS not-accessible
	STATUS mandatory
	DESCRIPTION ""
	::= { pmro 10 }

pmroPBOCurrentValueEntry OBJECT-TYPE
	SYNTAX PmroPBOCurrentValueEntry
	ACCESS not-accessible
	STATUS mandatory
	DESCRIPTION ""
	INDEX { pmroPBOCurrentValuePortIndex, pmroPBOCurrentValueLinkIndex }
	::= { pmroPBOCurrentValueTable 1 }

PmroPBOCurrentValueEntry ::=
	SEQUENCE
	{
		pmroPBOCurrentValuePortIndex INTEGER,
		pmroPBOCurrentValueLinkIndex INTEGER,
		pmroPBOCurrentValueLtWp1 INTEGER,
		pmroPBOCurrentValueLtWp2 INTEGER,
		pmroPBOCurrentValueNtWp1 INTEGER,
		pmroPBOCurrentValueNtWp2 INTEGER,
		pmroPBOCurrentValueReg1Wp1DirLt INTEGER,
		pmroPBOCurrentValueReg1Wp1DirNt INTEGER,
		pmroPBOCurrentValueReg1Wp2DirLt INTEGER,
		pmroPBOCurrentValueReg1Wp2DirNt INTEGER,
		pmroPBOCurrentValueReg2Wp1DirLt INTEGER,
		pmroPBOCurrentValueReg2Wp1DirNt INTEGER,
		pmroPBOCurrentValueReg2Wp2DirLt INTEGER,
		pmroPBOCurrentValueReg2Wp2DirNt INTEGER,
		pmroPBOCurrentValueReg3Wp1DirLt INTEGER,
		pmroPBOCurrentValueReg3Wp1DirNt INTEGER,
		pmroPBOCurrentValueReg3Wp2DirLt INTEGER,
		pmroPBOCurrentValueReg3Wp2DirNt INTEGER,
		pmroPBOCurrentValueReg4Wp1DirLt INTEGER,
		pmroPBOCurrentValueReg4Wp1DirNt INTEGER,
		pmroPBOCurrentValueReg4Wp2DirLt INTEGER,
		pmroPBOCurrentValueReg4Wp2DirNt INTEGER,
		pmroPBOCurrentValueReg5Wp1DirLt INTEGER,
		pmroPBOCurrentValueReg5Wp1DirNt INTEGER,
		pmroPBOCurrentValueReg5Wp2DirLt INTEGER,
		pmroPBOCurrentValueReg5Wp2DirNt INTEGER,
		pmroPBOCurrentValueReg6Wp1DirLt INTEGER,
		pmroPBOCurrentValueReg6Wp1DirNt INTEGER,
		pmroPBOCurrentValueReg6Wp2DirLt INTEGER,
		pmroPBOCurrentValueReg6Wp2DirNt INTEGER,
		pmroPBOCurrentValueReg7Wp1DirLt INTEGER,
		pmroPBOCurrentValueReg7Wp1DirNt INTEGER,
		pmroPBOCurrentValueReg7Wp2DirLt INTEGER,
		pmroPBOCurrentValueReg7Wp2DirNt INTEGER,
		pmroPBOCurrentValueReg8Wp1DirLt INTEGER,
		pmroPBOCurrentValueReg8Wp1DirNt INTEGER,
		pmroPBOCurrentValueReg8Wp2DirLt INTEGER,
		pmroPBOCurrentValueReg8Wp2DirNt INTEGER,
		pmroPBOCurrentValueLtWp3 INTEGER,
		pmroPBOCurrentValueLtWp4 INTEGER,
		pmroPBOCurrentValueNtWp3 INTEGER,
		pmroPBOCurrentValueNtWp4 INTEGER,
		pmroPBOCurrentValueReg1Wp3DirLt INTEGER,
		pmroPBOCurrentValueReg1Wp3DirNt INTEGER,
		pmroPBOCurrentValueReg1Wp4DirLt INTEGER,
		pmroPBOCurrentValueReg1Wp4DirNt INTEGER,
		pmroPBOCurrentValueReg2Wp3DirLt INTEGER,
		pmroPBOCurrentValueReg2Wp3DirNt INTEGER,
		pmroPBOCurrentValueReg2Wp4DirLt INTEGER,
		pmroPBOCurrentValueReg2Wp4DirNt INTEGER,
		pmroPBOCurrentValueReg3Wp3DirLt INTEGER,
		pmroPBOCurrentValueReg3Wp3DirNt INTEGER,
		pmroPBOCurrentValueReg3Wp4DirLt INTEGER,
		pmroPBOCurrentValueReg3Wp4DirNt INTEGER,
		pmroPBOCurrentValueReg4Wp3DirLt INTEGER,
		pmroPBOCurrentValueReg4Wp3DirNt INTEGER,
		pmroPBOCurrentValueReg4Wp4DirLt INTEGER,
		pmroPBOCurrentValueReg4Wp4DirNt INTEGER,
		pmroPBOCurrentValueReg5Wp3DirLt INTEGER,
		pmroPBOCurrentValueReg5Wp3DirNt INTEGER,
		pmroPBOCurrentValueReg5Wp4DirLt INTEGER,
		pmroPBOCurrentValueReg5Wp4DirNt INTEGER,
		pmroPBOCurrentValueReg6Wp3DirLt INTEGER,
		pmroPBOCurrentValueReg6Wp3DirNt INTEGER,
		pmroPBOCurrentValueReg6Wp4DirLt INTEGER,
		pmroPBOCurrentValueReg6Wp4DirNt INTEGER,
		pmroPBOCurrentValueReg7Wp3DirLt INTEGER,
		pmroPBOCurrentValueReg7Wp3DirNt INTEGER,
		pmroPBOCurrentValueReg7Wp4DirLt INTEGER,
		pmroPBOCurrentValueReg7Wp4DirNt INTEGER,
		pmroPBOCurrentValueReg8Wp3DirLt INTEGER,
		pmroPBOCurrentValueReg8Wp3DirNt INTEGER,
		pmroPBOCurrentValueReg8Wp4DirLt INTEGER,
		pmroPBOCurrentValueReg8Wp4DirNt INTEGER
	}

pmroPBOCurrentValuePortIndex OBJECT-TYPE
	SYNTAX INTEGER
	ACCESS read-only
	STATUS mandatory
	DESCRIPTION
		"This variable addresses the port number of the proxy
		and is used as index for the other elements in the Table"
	::= { pmroPBOCurrentValueEntry 1 }

pmroPBOCurrentValueLinkIndex OBJECT-TYPE
	SYNTAX INTEGER
	ACCESS read-only
	STATUS mandatory
	DESCRIPTION
		"This variable addresses the slot number of the OMI sub-rack
		and is used as index for the other elements in the Table"
	::= { pmroPBOCurrentValueEntry 2 }

pmroPBOCurrentValueLtWp1 OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for LT, Wire pair 1, Direction NT
		1..32		Db0..Db31	Current PBO value
		130..133	DbMin1..DbMin4	Current PBO value (negative, Power Boost).
		254				unknown value
		255				unsupported variable for addressed device
		"
	::= { pmroPBOCurrentValueEntry 3 }

pmroPBOCurrentValueLtWp2 OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for LT, Wire pair 2, Direction NT
		1..32		Db0..Db31	Current PBO value
		130..133	DbMin1..DbMin4	Current PBO value (negative, Power Boost).
		254				unknown value
		255				unsupported variable for addressed device
		"
	::= { pmroPBOCurrentValueEntry 4 }

pmroPBOCurrentValueNtWp1 OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for NT, Wire pair 1, Direction LT
		1..32		Db0..Db31	Current PBO value
		130..133	DbMin1..DbMin4	Current PBO value (negative, Power Boost).
		254				unknown value
		255				unsupported variable for addressed device
		"
	::= { pmroPBOCurrentValueEntry 5 }

pmroPBOCurrentValueNtWp2 OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for NT, Wire pair 2, Direction LT
		1..32		Db0..Db31	Current PBO value
		130..133	DbMin1..DbMin4	Current PBO value (negative, Power Boost).
		254				unknown value
		255				unsupported variable for addressed device
		"
	::= { pmroPBOCurrentValueEntry 6 }

pmroPBOCurrentValueReg1Wp1DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg1, Wire pair 1, Direction LT
		1..32		Db0..Db31	Current PBO value
		130..133	DbMin1..DbMin4	Current PBO value (negative, Power Boost).
		254				unknown value
		255				unsupported variable for addressed device
		"
	::= { pmroPBOCurrentValueEntry 7 }

pmroPBOCurrentValueReg1Wp1DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg1, Wire pair 1, Direction NT
		1..32		Db0..Db31	Current PBO value
		130..133	DbMin1..DbMin4	Current PBO value (negative, Power Boost).
		254				unknown value
		255				unsupported variable for addressed device
		"
	::= { pmroPBOCurrentValueEntry 8 }

pmroPBOCurrentValueReg1Wp2DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg1, Wire pair 2, Direction LT
		1..32		Db0..Db31	Current PBO value
		130..133	DbMin1..DbMin4	Current PBO value (negative, Power Boost).
		254				unknown value
		255				unsupported variable for addressed device
		"
	::= { pmroPBOCurrentValueEntry 9 }

pmroPBOCurrentValueReg1Wp2DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg1, Wire pair 2, Direction NT
		1..32		Db0..Db31	Current PBO value
		130..133	DbMin1..DbMin4	Current PBO value (negative, Power Boost).
		254				unknown value
		255				unsupported variable for addressed device
		"
	::= { pmroPBOCurrentValueEntry 10 }

pmroPBOCurrentValueReg2Wp1DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg2, Wire pair 1, Direction LT
		1..32		Db0..Db31	Current PBO value
		130..133	DbMin1..DbMin4	Current PBO value (negative, Power Boost).
		254				unknown value
		255				unsupported variable for addressed device
		"
	::= { pmroPBOCurrentValueEntry 11 }

pmroPBOCurrentValueReg2Wp1DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg2, Wire pair 1, Direction NT
		1..32		Db0..Db31	Current PBO value
		130..133	DbMin1..DbMin4	Current PBO value (negative, Power Boost).
		254				unknown value
		255				unsupported variable for addressed device
		"
	::= { pmroPBOCurrentValueEntry 12 }

pmroPBOCurrentValueReg2Wp2DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg2, Wire pair 2, Direction LT
		1..32		Db0..Db31	Current PBO value
		130..133	DbMin1..DbMin4	Current PBO value (negative, Power Boost).
		254				unknown value
		255				unsupported variable for addressed device
		"
	::= { pmroPBOCurrentValueEntry 13 }

pmroPBOCurrentValueReg2Wp2DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg2, Wire pair 2, Direction NT
		1..32		Db0..Db31	Current PBO value
		130..133	DbMin1..DbMin4	Current PBO value (negative, Power Boost).
		254				unknown value
		255				unsupported variable for addressed device
		"
	::= { pmroPBOCurrentValueEntry 14 }

pmroPBOCurrentValueReg3Wp1DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg3, Wire pair 1, Direction LT
		1..32		Db0..Db31	Current PBO value
		130..133	DbMin1..DbMin4	Current PBO value (negative, Power Boost).
		254				unknown value
		255				unsupported variable for addressed device
		"
	::= { pmroPBOCurrentValueEntry 15 }

pmroPBOCurrentValueReg3Wp1DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg3, Wire pair 1, Direction NT
		1..32		Db0..Db31	Current PBO value
		130..133	DbMin1..DbMin4	Current PBO value (negative, Power Boost).
		254				unknown value
		255				unsupported variable for addressed device
		"
	::= { pmroPBOCurrentValueEntry 16 }

pmroPBOCurrentValueReg3Wp2DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg3, Wire pair 2, Direction LT
		1..32		Db0..Db31	Current PBO value
		130..133	DbMin1..DbMin4	Current PBO value (negative, Power Boost).
		254				unknown value
		255				unsupported variable for addressed device
		"
	::= { pmroPBOCurrentValueEntry 17 }

pmroPBOCurrentValueReg3Wp2DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg3, Wire pair 2, Direction NT
		1..32		Db0..Db31	Current PBO value
		130..133	DbMin1..DbMin4	Current PBO value (negative, Power Boost).
		254				unknown value
		255				unsupported variable for addressed device
		"
	::= { pmroPBOCurrentValueEntry 18 }

pmroPBOCurrentValueReg4Wp1DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg4, Wire pair 1, Direction LT
		1..32		Db0..Db31	Current PBO value
		130..133	DbMin1..DbMin4	Current PBO value (negative, Power Boost).
		254				unknown value
		255				unsupported variable for addressed device
		"
	::= { pmroPBOCurrentValueEntry 19 }

pmroPBOCurrentValueReg4Wp1DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg4, Wire pair 1, Direction NT
		1..32		Db0..Db31	Current PBO value
		130..133	DbMin1..DbMin4	Current PBO value (negative, Power Boost).
		254				unknown value
		255				unsupported variable for addressed device
		"
	::= { pmroPBOCurrentValueEntry 20 }

pmroPBOCurrentValueReg4Wp2DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg4, Wire pair 2, Direction LT
		1..32		Db0..Db31	Current PBO value
		130..133	DbMin1..DbMin4	Current PBO value (negative, Power Boost).
		254				unknown value
		255				unsupported variable for addressed device
		"
	::= { pmroPBOCurrentValueEntry 21 }

pmroPBOCurrentValueReg4Wp2DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg4, Wire pair 2, Direction NT
		1..32		Db0..Db31	Current PBO value
		130..133	DbMin1..DbMin4	Current PBO value (negative, Power Boost).
		254				unknown value
		255				unsupported variable for addressed device
		"
	::= { pmroPBOCurrentValueEntry 22 }

pmroPBOCurrentValueReg5Wp1DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg5, Wire pair 1, Direction LT
		1..32		Db0..Db31	Current PBO value
		130..133	DbMin1..DbMin4	Current PBO value (negative, Power Boost).
		254				unknown value
		255				unsupported variable for addressed device
		"
	::= { pmroPBOCurrentValueEntry 23 }

pmroPBOCurrentValueReg5Wp1DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg5, Wire pair 1, Direction NT
		1..32		Db0..Db31	Current PBO value
		130..133	DbMin1..DbMin4	Current PBO value (negative, Power Boost).
		254				unknown value
		255				unsupported variable for addressed device
		"
	::= { pmroPBOCurrentValueEntry 24 }

pmroPBOCurrentValueReg5Wp2DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg5, Wire pair 2, Direction LT
		1..32		Db0..Db31	Current PBO value
		130..133	DbMin1..DbMin4	Current PBO value (negative, Power Boost).
		254				unknown value
		255				unsupported variable for addressed device
		"
	::= { pmroPBOCurrentValueEntry 25 }

pmroPBOCurrentValueReg5Wp2DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg5, Wire pair 2, Direction NT
		1..32		Db0..Db31	Current PBO value
		130..133	DbMin1..DbMin4	Current PBO value (negative, Power Boost).
		254				unknown value
		255				unsupported variable for addressed device
		"
	::= { pmroPBOCurrentValueEntry 26 }

pmroPBOCurrentValueReg6Wp1DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg6, Wire pair 1, Direction LT
		1..32		Db0..Db31	Current PBO value
		130..133	DbMin1..DbMin4	Current PBO value (negative, Power Boost).
		254				unknown value
		255				unsupported variable for addressed device
		"
	::= { pmroPBOCurrentValueEntry 27 }

pmroPBOCurrentValueReg6Wp1DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg6, Wire pair 1, Direction NT
		1..32		Db0..Db31	Current PBO value
		130..133	DbMin1..DbMin4	Current PBO value (negative, Power Boost).
		254				unknown value
		255				unsupported variable for addressed device
		"
	::= { pmroPBOCurrentValueEntry 28 }

pmroPBOCurrentValueReg6Wp2DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg6, Wire pair 2, Direction LT
		1..32		Db0..Db31	Current PBO value
		130..133	DbMin1..DbMin4	Current PBO value (negative, Power Boost).
		254				unknown value
		255				unsupported variable for addressed device
		"
	::= { pmroPBOCurrentValueEntry 29 }

pmroPBOCurrentValueReg6Wp2DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg6, Wire pair 2, Direction NT
		1..32		Db0..Db31	Current PBO value
		130..133	DbMin1..DbMin4	Current PBO value (negative, Power Boost).
		254				unknown value
		255				unsupported variable for addressed device
		"
	::= { pmroPBOCurrentValueEntry 30 }

pmroPBOCurrentValueReg7Wp1DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg7, Wire pair 1, Direction LT
		1..32		Db0..Db31	Current PBO value
		130..133	DbMin1..DbMin4	Current PBO value (negative, Power Boost).
		254				unknown value
		255				unsupported variable for addressed device
		"
	::= { pmroPBOCurrentValueEntry 31 }

pmroPBOCurrentValueReg7Wp1DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg7, Wire pair 1, Direction NT
		1..32		Db0..Db31	Current PBO value
		130..133	DbMin1..DbMin4	Current PBO value (negative, Power Boost).
		254				unknown value
		255				unsupported variable for addressed device
		"
	::= { pmroPBOCurrentValueEntry 32 }

pmroPBOCurrentValueReg7Wp2DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg7, Wire pair 2, Direction LT
		1..32		Db0..Db31	Current PBO value
		130..133	DbMin1..DbMin4	Current PBO value (negative, Power Boost).
		254				unknown value
		255				unsupported variable for addressed device
		"
	::= { pmroPBOCurrentValueEntry 33 }

pmroPBOCurrentValueReg7Wp2DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg7, Wire pair 2, Direction NT
		1..32		Db0..Db31	Current PBO value
		130..133	DbMin1..DbMin4	Current PBO value (negative, Power Boost).
		254				unknown value
		255				unsupported variable for addressed device
		"
	::= { pmroPBOCurrentValueEntry 34 }

pmroPBOCurrentValueReg8Wp1DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg8, Wire pair 1, Direction LT
		1..32		Db0..Db31	Current PBO value
		130..133	DbMin1..DbMin4	Current PBO value (negative, Power Boost).
		254				unknown value
		255				unsupported variable for addressed device
		"
	::= { pmroPBOCurrentValueEntry 35 }

pmroPBOCurrentValueReg8Wp1DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg8, Wire pair 1, Direction NT
		1..32		Db0..Db31	Current PBO value
		130..133	DbMin1..DbMin4	Current PBO value (negative, Power Boost).
		254				unknown value
		255				unsupported variable for addressed device
		"
	::= { pmroPBOCurrentValueEntry 36 }

pmroPBOCurrentValueReg8Wp2DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg8, Wire pair 2, Direction LT
		1..32		Db0..Db31	Current PBO value
		130..133	DbMin1..DbMin4	Current PBO value (negative, Power Boost).
		254				unknown value
		255				unsupported variable for addressed device
		"
	::= { pmroPBOCurrentValueEntry 37 }

pmroPBOCurrentValueReg8Wp2DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg8, Wire pair 2, Direction NT
		1..32		Db0..Db31	Current PBO value
		130..133	DbMin1..DbMin4	Current PBO value (negative, Power Boost).
		254				unknown value
		255				unsupported variable for addressed device
		"
	::= { pmroPBOCurrentValueEntry 38 }

pmroPBOCurrentValueLtWp3 OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for LT, Wire pair 3, Direction NT
		1..32		Db0..Db31	Current PBO value
		130..133	DbMin1..DbMin4	Current PBO value (negative, Power Boost).
		254				unknown value
		255				unsupported variable for addressed device
		"
	::= { pmroPBOCurrentValueEntry 39 }

pmroPBOCurrentValueLtWp4 OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for LT, Wire pair 4, Direction NT
		1..32		Db0..Db31	Current PBO value
		130..133	DbMin1..DbMin4	Current PBO value (negative, Power Boost).
		254				unknown value
		255				unsupported variable for addressed device
		"
	::= { pmroPBOCurrentValueEntry 40 }

pmroPBOCurrentValueNtWp3 OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for NT, Wire pair 3, Direction LT
		1..32		Db0..Db31	Current PBO value
		130..133	DbMin1..DbMin4	Current PBO value (negative, Power Boost).
		254				unknown value
		255				unsupported variable for addressed device
		"
	::= { pmroPBOCurrentValueEntry 41 }

pmroPBOCurrentValueNtWp4 OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for NT, Wire pair 4, Direction LT
		1..32		Db0..Db31	Current PBO value
		130..133	DbMin1..DbMin4	Current PBO value (negative, Power Boost).
		254				unknown value
		255				unsupported variable for addressed device
		"
	::= { pmroPBOCurrentValueEntry 42 }

pmroPBOCurrentValueReg1Wp3DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg1, Wire pair 3, Direction LT
		1..32		Db0..Db31	Current PBO value
		130..133	DbMin1..DbMin4	Current PBO value (negative, Power Boost).
		254				unknown value
		255				unsupported variable for addressed device
		"
	::= { pmroPBOCurrentValueEntry 43 }

pmroPBOCurrentValueReg1Wp3DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg1, Wire pair 3, Direction NT
		1..32		Db0..Db31	Current PBO value
		130..133	DbMin1..DbMin4	Current PBO value (negative, Power Boost).
		254				unknown value
		255				unsupported variable for addressed device
		"
	::= { pmroPBOCurrentValueEntry 44 }

pmroPBOCurrentValueReg1Wp4DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg1, Wire pair 4, Direction LT
		1..32		Db0..Db31	Current PBO value
		130..133	DbMin1..DbMin4	Current PBO value (negative, Power Boost).
		254				unknown value
		255				unsupported variable for addressed device
		"
	::= { pmroPBOCurrentValueEntry 45 }

pmroPBOCurrentValueReg1Wp4DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg1, Wire pair 4, Direction NT
		1..32		Db0..Db31	Current PBO value
		130..133	DbMin1..DbMin4	Current PBO value (negative, Power Boost).
		254				unknown value
		255				unsupported variable for addressed device
		"
	::= { pmroPBOCurrentValueEntry 46 }

pmroPBOCurrentValueReg2Wp3DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg2, Wire pair 3, Direction LT
		1..32		Db0..Db31	Current PBO value
		130..133	DbMin1..DbMin4	Current PBO value (negative, Power Boost).
		254				unknown value
		255				unsupported variable for addressed device
		"
	::= { pmroPBOCurrentValueEntry 47 }

pmroPBOCurrentValueReg2Wp3DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg2, Wire pair 3, Direction NT
		1..32		Db0..Db31	Current PBO value
		130..133	DbMin1..DbMin4	Current PBO value (negative, Power Boost).
		254				unknown value
		255				unsupported variable for addressed device
		"
	::= { pmroPBOCurrentValueEntry 48 }

pmroPBOCurrentValueReg2Wp4DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg2, Wire pair 4, Direction LT
		1..32		Db0..Db31	Current PBO value
		130..133	DbMin1..DbMin4	Current PBO value (negative, Power Boost).
		254				unknown value
		255				unsupported variable for addressed device
		"
	::= { pmroPBOCurrentValueEntry 49 }

pmroPBOCurrentValueReg2Wp4DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg2, Wire pair 4, Direction NT
		1..32		Db0..Db31	Current PBO value
		130..133	DbMin1..DbMin4	Current PBO value (negative, Power Boost).
		254				unknown value
		255				unsupported variable for addressed device
		"
	::= { pmroPBOCurrentValueEntry 50 }

pmroPBOCurrentValueReg3Wp3DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg3, Wire pair 3, Direction LT
		1..32		Db0..Db31	Current PBO value
		130..133	DbMin1..DbMin4	Current PBO value (negative, Power Boost).
		254				unknown value
		255				unsupported variable for addressed device
		"
	::= { pmroPBOCurrentValueEntry 51 }

pmroPBOCurrentValueReg3Wp3DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg3, Wire pair 3, Direction NT
		1..32		Db0..Db31	Current PBO value
		130..133	DbMin1..DbMin4	Current PBO value (negative, Power Boost).
		254				unknown value
		255				unsupported variable for addressed device
		"
	::= { pmroPBOCurrentValueEntry 52 }

pmroPBOCurrentValueReg3Wp4DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg3, Wire pair 4, Direction LT
		1..32		Db0..Db31	Current PBO value
		130..133	DbMin1..DbMin4	Current PBO value (negative, Power Boost).
		254				unknown value
		255				unsupported variable for addressed device
		"
	::= { pmroPBOCurrentValueEntry 53 }

pmroPBOCurrentValueReg3Wp4DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg3, Wire pair 4, Direction NT
		1..32		Db0..Db31	Current PBO value
		130..133	DbMin1..DbMin4	Current PBO value (negative, Power Boost).
		254				unknown value
		255				unsupported variable for addressed device
		"
	::= { pmroPBOCurrentValueEntry 54 }

pmroPBOCurrentValueReg4Wp3DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg4, Wire pair 3, Direction LT
		1..32		Db0..Db31	Current PBO value
		130..133	DbMin1..DbMin4	Current PBO value (negative, Power Boost).
		254				unknown value
		255				unsupported variable for addressed device
		"
	::= { pmroPBOCurrentValueEntry 55 }

pmroPBOCurrentValueReg4Wp3DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg4, Wire pair 3, Direction NT
		1..32		Db0..Db31	Current PBO value
		130..133	DbMin1..DbMin4	Current PBO value (negative, Power Boost).
		254				unknown value
		255				unsupported variable for addressed device
		"
	::= { pmroPBOCurrentValueEntry 56 }

pmroPBOCurrentValueReg4Wp4DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg4, Wire pair 4, Direction LT
		1..32		Db0..Db31	Current PBO value
		130..133	DbMin1..DbMin4	Current PBO value (negative, Power Boost).
		254				unknown value
		255				unsupported variable for addressed device
		"
	::= { pmroPBOCurrentValueEntry 57 }

pmroPBOCurrentValueReg4Wp4DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg4, Wire pair 4, Direction NT
		1..32		Db0..Db31	Current PBO value
		130..133	DbMin1..DbMin4	Current PBO value (negative, Power Boost).
		254				unknown value
		255				unsupported variable for addressed device
		"
	::= { pmroPBOCurrentValueEntry 58 }

pmroPBOCurrentValueReg5Wp3DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg5, Wire pair 3, Direction LT
		1..32		Db0..Db31	Current PBO value
		130..133	DbMin1..DbMin4	Current PBO value (negative, Power Boost).
		254				unknown value
		255				unsupported variable for addressed device
		"
	::= { pmroPBOCurrentValueEntry 59 }

pmroPBOCurrentValueReg5Wp3DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg5, Wire pair 3, Direction NT
		1..32		Db0..Db31	Current PBO value
		130..133	DbMin1..DbMin4	Current PBO value (negative, Power Boost).
		254				unknown value
		255				unsupported variable for addressed device
		"
	::= { pmroPBOCurrentValueEntry 60 }

pmroPBOCurrentValueReg5Wp4DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg5, Wire pair 4, Direction LT
		1..32		Db0..Db31	Current PBO value
		130..133	DbMin1..DbMin4	Current PBO value (negative, Power Boost).
		254				unknown value
		255				unsupported variable for addressed device
		"
	::= { pmroPBOCurrentValueEntry 61 }

pmroPBOCurrentValueReg5Wp4DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg5, Wire pair 4, Direction NT
		1..32		Db0..Db31	Current PBO value
		130..133	DbMin1..DbMin4	Current PBO value (negative, Power Boost).
		254				unknown value
		255				unsupported variable for addressed device
		"
	::= { pmroPBOCurrentValueEntry 62 }

pmroPBOCurrentValueReg6Wp3DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg6, Wire pair 3, Direction LT
		1..32		Db0..Db31	Current PBO value
		130..133	DbMin1..DbMin4	Current PBO value (negative, Power Boost).
		254				unknown value
		255				unsupported variable for addressed device
		"
	::= { pmroPBOCurrentValueEntry 63 }

pmroPBOCurrentValueReg6Wp3DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg6, Wire pair 3, Direction NT
		1..32		Db0..Db31	Current PBO value
		130..133	DbMin1..DbMin4	Current PBO value (negative, Power Boost).
		254				unknown value
		255				unsupported variable for addressed device
		"
	::= { pmroPBOCurrentValueEntry 64 }

pmroPBOCurrentValueReg6Wp4DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg6, Wire pair 4, Direction LT
		1..32		Db0..Db31	Current PBO value
		130..133	DbMin1..DbMin4	Current PBO value (negative, Power Boost).
		254				unknown value
		255				unsupported variable for addressed device
		"
	::= { pmroPBOCurrentValueEntry 65 }

pmroPBOCurrentValueReg6Wp4DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg6, Wire pair 4, Direction NT
		1..32		Db0..Db31	Current PBO value
		130..133	DbMin1..DbMin4	Current PBO value (negative, Power Boost).
		254				unknown value
		255				unsupported variable for addressed device
		"
	::= { pmroPBOCurrentValueEntry 66 }

pmroPBOCurrentValueReg7Wp3DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg7, Wire pair 3, Direction LT
		1..32		Db0..Db31	Current PBO value
		130..133	DbMin1..DbMin4	Current PBO value (negative, Power Boost).
		254				unknown value
		255				unsupported variable for addressed device
		"
	::= { pmroPBOCurrentValueEntry 67 }

pmroPBOCurrentValueReg7Wp3DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg7, Wire pair 3, Direction NT
		1..32		Db0..Db31	Current PBO value
		130..133	DbMin1..DbMin4	Current PBO value (negative, Power Boost).
		254				unknown value
		255				unsupported variable for addressed device
		"
	::= { pmroPBOCurrentValueEntry 68 }

pmroPBOCurrentValueReg7Wp4DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg7, Wire pair 4, Direction LT
		1..32		Db0..Db31	Current PBO value
		130..133	DbMin1..DbMin4	Current PBO value (negative, Power Boost).
		254				unknown value
		255				unsupported variable for addressed device
		"
	::= { pmroPBOCurrentValueEntry 69 }

pmroPBOCurrentValueReg7Wp4DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg7, Wire pair 4, Direction NT
		1..32		Db0..Db31	Current PBO value
		130..133	DbMin1..DbMin4	Current PBO value (negative, Power Boost).
		254				unknown value
		255				unsupported variable for addressed device
		"
	::= { pmroPBOCurrentValueEntry 70 }

pmroPBOCurrentValueReg8Wp3DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg8, Wire pair 3, Direction LT
		1..32		Db0..Db31	Current PBO value
		130..133	DbMin1..DbMin4	Current PBO value (negative, Power Boost).
		254				unknown value
		255				unsupported variable for addressed device
		"
	::= { pmroPBOCurrentValueEntry 71 }

pmroPBOCurrentValueReg8Wp3DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg8, Wire pair 3, Direction NT
		1..32		Db0..Db31	Current PBO value
		130..133	DbMin1..DbMin4	Current PBO value (negative, Power Boost).
		254				unknown value
		255				unsupported variable for addressed device
		"
	::= { pmroPBOCurrentValueEntry 72 }

pmroPBOCurrentValueReg8Wp4DirLt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg8, Wire pair 4, Direction LT
		1..32		Db0..Db31	Current PBO value
		130..133	DbMin1..DbMin4	Current PBO value (negative, Power Boost).
		254				unknown value
		255				unsupported variable for addressed device
		"
	::= { pmroPBOCurrentValueEntry 73 }

pmroPBOCurrentValueReg8Wp4DirNt OBJECT-TYPE
	SYNTAX INTEGER
	{  
		db0(1), db1(2), db2(3), db3(4), db4(5), db5(6), db6(7), db7(8), db8(9), db9(10), db10(11), db11(12), db12(13), db13(14), db14(15), db15(16), 
		db16(17), db17(18), db18(19), db19(20), db20(21), db21(22), db22(23), db23(24), db24(25), db25(26), db26(27), db27(28), db28(29), db29(30), db30(31), db31(32), 
		dbMin1(130), dbMin2(131), dbMin3(132), dbMin4(133), 
		unknown(254), 
		unsupported(255)
	}
	ACCESS read-only
	STATUS mandatory
	DESCRIPTION
		"The current PowerBackOff value for Reg8, Wire pair 4, Direction NT
		1..32		Db0..Db31	Current PBO value
		130..133	DbMin1..DbMin4	Current PBO value (negative, Power Boost).
		254				unknown value
		255				unsupported variable for addressed device
		"
	::= { pmroPBOCurrentValueEntry 74 }


--==============================================================================
--==============================================================================
--
--      PM-RW
--
--==============================================================================
--==============================================================================
	pmrw	OBJECT IDENTIFIER ::= { linksVers3 6 }

--------------------------------------------------------------------------------
--	PM-RW	PM Reset and BER Measurement Starting
--------------------------------------------------------------------------------
pmrwActionTable OBJECT-TYPE
	SYNTAX SEQUENCE OF PmrwActionEntry
	ACCESS not-accessible
	STATUS mandatory
	DESCRIPTION ""
	::= { pmrw 1 }

pmrwActionEntry OBJECT-TYPE
	SYNTAX PmrwActionEntry
	ACCESS not-accessible
	STATUS mandatory
	DESCRIPTION ""
	INDEX { pmrwActionPortIndex, pmrwActionLinkIndex }
	::= { pmrwActionTable 1 }

PmrwActionEntry ::=
	SEQUENCE
	{
		pmrwActionPortIndex INTEGER,
		pmrwActionLinkIndex INTEGER,
		pmrwActionResetPM INTEGER,
		pmrwActionBerStart INTEGER,
		pmrwActionProbingStart OCTET STRING,
		pmrwActionResetPMPacket INTEGER
	}

pmrwActionPortIndex OBJECT-TYPE
	SYNTAX INTEGER
	ACCESS read-only
	STATUS mandatory
	DESCRIPTION
		"This variable addresses the port number of the proxy
		and is used as index for the other elements in the Table"
	::= { pmrwActionEntry 1 }

pmrwActionLinkIndex OBJECT-TYPE
	SYNTAX INTEGER
	ACCESS read-only
	STATUS mandatory
	DESCRIPTION
		"This variable addresses the slot number of the OMI sub-rack
		and is used as index for the other elements in the Table"
	::= { pmrwActionEntry 2 }


pmrwActionResetPM OBJECT-TYPE
	SYNTAX INTEGER
	{
		reset(1),
		unknown(254),
		unsupported(255)
	}
	ACCESS read-write
	STATUS mandatory
	DESCRIPTION
		"This is a write-only variable which is used to reset
		all currently running CRC-based performance counters
		and starts a new measurement interval.
		
		This command resets all 15 minute and 24 hour counters
		for all current counters and the stored last interval.
		
		The only legal parameter is 'reset(1)'."
	::= { pmrwActionEntry 3 }

pmrwActionBerStart OBJECT-TYPE
	SYNTAX INTEGER
	{
		abort(1),
		oneMin(2),
		tenMin(3),
		oneHour(4),
		oneDay(5),
		oneMinDirV(6),
		tenMinDirV(7),
		oneHourDirV(8),
		oneDayDirV(9),
		oneMinRoundTrip(10),
		tenMinRoundTrip(11),
		oneHourRoundTrip(12),
		oneDayRoundTrip(13),
		oneMinMcs(14),
		tenMinMcs(15),
		oneHourMcs(16),
		oneDayMcs(17),
		oneMinData(18),
		tenMinData(19),
		oneHourData(20),
		oneDayData(21),
		oneMinMcsLocal(22),
		tenMinMcsLocal(23),
		oneHourMcsLocal(24),
		oneDayMcsLocal(25),
		oneMinG703If(26),
		tenMinG703If(27),
		oneHourG703If(28),
		oneDayG703If(29),
		oneMinDataIf(30),
		tenMinDataIf(31),
		oneHourDataIf(32),
		oneDayDataIf(33),
		unknown(254),
		unsupported(255)
	}
	ACCESS read-write
	STATUS mandatory
	DESCRIPTION
		"This is a write-only variable which is used to start (and 
		stop) the Bit Error Ration measurement.
		
		1	Abort			Stop a running BER measurement
		2	OneMin			Start a BER measurement for the duration of 1 minute
		3	TenMin			Start a BER measurement for the duration of 10 minutes
		4	OneHour			Start a BER measurement for the duration of 1 hour
		5	OneDay			Start a BER measurement for the duration of 24 hours
		6	OneMinDirV		Start a BER measurement duration is/was 1 minute (direction V)
		7	TenMinDirV		Start a BER measurement duration is/was 10 minutes (direction V)
		8	OneHourDirV		Start a BER measurement duration is/was 1 hour (direction V)
		9	OneDayDirV		Start a BER measurement duration is/was 24 hours (direction V)
		10	OneMinRoundTrip		Start a BER measurement duration is/was 1 minute (round trip)
		11	TenMinRoundTrip		Start a BER measurement duration is/was 10 minutes (round trip)
		12	OneHourRoundTrip	Start a BER measurement duration is/was 1 hour (round trip)
		13	OneDayRoundTrip		Start a BER measurement duration is/was 24 hours (round trip)
		14	OneMinMcs		Start a BER measurement duration is/was 1 minute (MCS)
		15	TenMinMcs		Start a BER measurement duration is/was 10 minutes (MCS)
		16	OneHourMcs		Start a BER measurement duration is/was 1 hour (MCS)
		17	OneDayMcs		Start a BER measurement duration is/was 24 hours (MCS)
		18	OneMinData		Start a BER measurement duration is/was 1 minute (U side Data, var speed)
		19	TenMinData		Start a BER measurement duration is/was 10 minutes (U side Data, var speed)
		20	OneHourData		Start a BER measurement duration is/was 1 hour (U side Data, var speed)
		21	OneDayData		Start a BER measurement duration is/was 24 hours (U side Data, var speed)
		22	OneMinMcsLocal		Start a BER measurement duration is/was 1 minute (MCS local)
		23	TenMinMcsLocal		Start a BER measurement duration is/was 10 minutes (MCS local)
		24	OneHourMcsLocal		Start a BER measurement duration is/was 1 hour (MCS local)
		25	OneDayMcsLocal		Start a BER measurement duration is/was 24 hours (MCS local)
		26	OneMinG703If		Start a BER measurement duration is/was 1 minute (G.703 Interface)
		27	TenMinG703If		Start a BER measurement duration is/was 10 minutes (G.703 Interface)
		28	OneHourG703If		Start a BER measurement duration is/was 1 hour (G.703 Interface)
		29	OneDayG703If		Start a BER measurement duration is/was 24 hours (G.703 Interface)
		30	OneMinDataIf		Start a BER measurement duration is/was 1 minute (Data Interface)
		31	TenMinDataIf		Start a BER measurement duration is/was 10 minutes (Data Interface)
		32	OneHourDataIf		Start a BER measurement duration is/was 1 hour (Data Interface)
		33	OneDayDataIf		Start a BER measurement duration is/was 24 hours (Data Interface)
		254	unknown value
		255	unsupported variable for addressed device"
	::= { pmrwActionEntry 4 }

pmrwActionProbingStart OBJECT-TYPE
	SYNTAX OCTET STRING(SIZE(6))
	ACCESS read-write
	STATUS mandatory
	DESCRIPTION
		"Selection of bandwidths to use for line probing
				
		 			Bandwidth
		Byte 0
			bit  0		reserved
			bit  1		reserved
			bit  2		 192 kbit/s
			bit  3		 256 kbit/s
			bit  4		 320 kbit/s
			bit  5		 384 kbit/s
			bit  6		 448 kbit/s
			bit  7		 512 kbit/s
		Byte 1	
			bit  0		 576 kbit/s
			bit  1		 640 kbit/s
			bit  2		 704 kbit/s
			bit  3		 768 kbit/s
			bit  4		 832 kbit/s
			bit  5		 896 kbit/s
			bit  6		 960 kbit/s
			bit  7		 1024 kbit/s
		Byte 2	
			bit  0		 1088 kbit/s
			bit  1		 1152 kbit/s
			bit  2		 1216 kbit/s
			bit  3		 1280 kbit/s
			bit  4		 1344 kbit/s
			bit  5		 1408 kbit/s
			bit  6		 1472 kbit/s
			bit  7		 1536 kbit/s
		Byte 3	
			bit  0		 1600 kbit/s
			bit  1		 1664 kbit/s
			bit  2		 1728 kbit/s
			bit  3		 1792 kbit/s
			bit  4		 1856 kbit/s
			bit  5		 1920 kbit/s
			bit  6		 1984 kbit/s
			bit  7		 2048 kbit/s
		Byte 4	
			bit  0		 2112 kbit/s
			bit  1		 2176 kbit/s
			bit  2		 2240 kbit/s
			bit  3		 2304 kbit/s
			bit  4		 unused
			bit  5		 unused
			bit  6		 unused
			bit  7		 unused
		 Byte 5 contains a value specifying the validity of the
		 result of a read operation:
		 1	Ok	Values returned are valid
		 254		unknown values
		 255		unsupported variable for addressed device"
			
	::= { pmrwActionEntry 5 }

pmrwActionResetPMPacket OBJECT-TYPE
	SYNTAX INTEGER
	{
		resetLocal(1),
		resetFar(2),
		unknown(254),
		unsupported(255)
	}
	ACCESS read-write
	STATUS mandatory
	DESCRIPTION
		"This is a write-only variable which is used to reset
		all currently running Local L2Switch performance counters.
		1	resetLocal	Reset local counters
		2	resetFar	Reset far counters"
	::= { pmrwActionEntry 6 }

--==============================================================================
--==============================================================================
--
--      Download
--
--==============================================================================
--==============================================================================
	download	OBJECT IDENTIFIER ::= { linksVers3 7 }

--------------------------------------------------------------------------------
--	Far Download State
--------------------------------------------------------------------------------
downloadFarTable OBJECT-TYPE
	SYNTAX SEQUENCE OF DownloadFarEntry
	ACCESS not-accessible
	STATUS mandatory
	DESCRIPTION ""
	::= { download 1 }

downloadFarEntry OBJECT-TYPE
	SYNTAX DownloadFarEntry
	ACCESS not-accessible
	STATUS mandatory
	DESCRIPTION ""
	INDEX { downloadFarPortIndex, downloadFarLinkIndex }
	::= { downloadFarTable 1 }

DownloadFarEntry ::=
	SEQUENCE
	{
		downloadFarPortIndex INTEGER,
		downloadFarLinkIndex INTEGER,
		downloadFarState INTEGER,
		downloadFarTotalBlocks INTEGER,
		downloadFarProgress INTEGER,
		downloadFarTarget INTEGER
	}

downloadFarPortIndex OBJECT-TYPE
	SYNTAX INTEGER
	ACCESS read-only
	STATUS mandatory
	DESCRIPTION
		"This variable addresses the port number of the proxy
		and is used as index for the other elements in the Table"
	::= { downloadFarEntry 1 }

downloadFarLinkIndex OBJECT-TYPE
	SYNTAX INTEGER
	ACCESS read-only
	STATUS mandatory
	DESCRIPTION
		"This variable addresses the slot number of the OMI sub-rack
		and is used as index for the other elements in the Table"
	::= {downloadFarEntry 2 }

downloadFarState OBJECT-TYPE
	SYNTAX INTEGER
	{
		notStarted(1),
		pending(2),
		abortedLd(3),
		erasingFlash(4),
		running(5),
		failed(6),
		complete(7),
		unknown(254),
		unsupported(255)
	}
	ACCESS read-only
	STATUS mandatory
	DESCRIPTION
		"Returns the state of the download
		1	NotStarted	Never started a download for this device
		2	Pending		Waiting for download start response from NT
		3	AbortedLd	Remote download not started because of lokal download running
		4	ErasingFlash	Flash EEPROM of this device is being erased
		5	Running		Download for this device is running
		6	Failed		Last download for this device failed
		7	Complete	Last download for this device was successful
		254			unknown value
		255			unsupported variable for addressed device"
	::= { downloadFarEntry 3 }

downloadFarTotalBlocks OBJECT-TYPE
	SYNTAX INTEGER
	ACCESS read-only
	STATUS mandatory
	DESCRIPTION
		"Returns the size of the firmware being downloaded to the far device
		in blocks of 128 bytes
		0xFFFE			unknown value
		0xFFFF			unsupported variable for addressed device"
	::= { downloadFarEntry 4 }

downloadFarProgress OBJECT-TYPE
	SYNTAX INTEGER
	ACCESS read-only
	STATUS mandatory
	DESCRIPTION
		"Returns the number of 128 byte blocks that have already been downloaded
		0xFFFE			unknown value
		0xFFFF			unsupported variable for addressed device"
	::= { downloadFarEntry 5 }

downloadFarTarget OBJECT-TYPE
	SYNTAX INTEGER
	{
		notDownloading(1),
		nt(2),
		reg11(4),
		reg12(5),
		reg21(6),
		reg22(7),
		reg31(8),
		reg32(9),
		reg41(10),
		reg42(11),
		reg51(12),
		reg52(13),
		reg61(14),
		reg62(15),
		reg71(16),
		reg72(17),
		reg81(18),
		reg82(19),
		reg13(20),
		reg14(21),
		reg23(22),
		reg24(23),
		reg33(24),
		reg34(25),
		reg43(26),
		reg44(27),
		reg53(28),
		reg54(29),
		reg63(30),
		reg64(31),
		reg73(32),
		reg74(33),
		reg83(34),
		reg84(35),
		unknown(254),
		unsupported(255)
	}
	ACCESS read-only
	STATUS mandatory
	DESCRIPTION
		"Returns the device for which a remote download is active
		NotDownloading 1  No remote download is active
		Nt             2  Remote download to NT active
		Reg11          4  Remote download to regenerator section 1 wire pair 1
		Reg12          5  Remote download to regenerator section 1 wire pair 2
		Reg21          6  Remote download to regenerator section 2 wire pair 1
		Reg22          7  Remote download to regenerator section 2 wire pair 2
		Reg31          8  Remote download to regenerator section 3 wire pair 1
		Reg32          9  Remote download to regenerator section 3 wire pair 2
		Reg41         10  Remote download to regenerator section 4 wire pair 1
		Reg42         11  Remote download to regenerator section 4 wire pair 2
		Reg51         12  Remote download to regenerator section 5 wire pair 1
		Reg52         13  Remote download to regenerator section 5 wire pair 2
		Reg61         14  Remote download to regenerator section 6 wire pair 1
		Reg62         15  Remote download to regenerator section 6 wire pair 2
		Reg71         16  Remote download to regenerator section 7 wire pair 1
		Reg72         17  Remote download to regenerator section 7 wire pair 2
		Reg81         18  Remote download to regenerator section 8 wire pair 1
		Reg82         19  Remote download to regenerator section 8 wire pair 2
		Reg13         20  Remote download to regenerator section 1 wire pair 3
		Reg14         21  Remote download to regenerator section 1 wire pair 4
		Reg23         22  Remote download to regenerator section 2 wire pair 3
		Reg24         23  Remote download to regenerator section 2 wire pair 4
		Reg33         24  Remote download to regenerator section 3 wire pair 3
		Reg34         25  Remote download to regenerator section 3 wire pair 4
		Reg43         26  Remote download to regenerator section 4 wire pair 3
		Reg44         27  Remote download to regenerator section 4 wire pair 4
		Reg53         28  Remote download to regenerator section 5 wire pair 3
		Reg54         29  Remote download to regenerator section 5 wire pair 4
		Reg63         30  Remote download to regenerator section 6 wire pair 3
		Reg64         31  Remote download to regenerator section 6 wire pair 4
		Reg73         32  Remote download to regenerator section 7 wire pair 3
		Reg74         33  Remote download to regenerator section 7 wire pair 4
		Reg83         34  Remote download to regenerator section 8 wire pair 3
		Reg84         35  Remote download to regenerator section 8 wire pair 4
                   254  unknown value
				       255  unsupported variable for addressed device"
	::= { downloadFarEntry 6 }

--------------------------------------------------------------------------------
--	Download Starting and Aborting
--------------------------------------------------------------------------------
downloadActionTable OBJECT-TYPE
	SYNTAX SEQUENCE OF DownloadActionEntry
	ACCESS not-accessible
	STATUS mandatory
	DESCRIPTION ""
	::= { download 2 }

downloadActionEntry OBJECT-TYPE
	SYNTAX DownloadActionEntry
	ACCESS not-accessible
	STATUS mandatory
	DESCRIPTION ""
	INDEX { downloadActionPortIndex, downloadActionLinkIndex }
	::= { downloadActionTable 1 }

DownloadActionEntry ::=
	SEQUENCE
	{
		downloadActionPortIndex INTEGER,
		downloadActionLinkIndex INTEGER,
		downloadActionStart INTEGER,
		downloadActionAbort INTEGER
	}

downloadActionPortIndex OBJECT-TYPE
	SYNTAX INTEGER
	ACCESS read-only
	STATUS mandatory
	DESCRIPTION
		"This variable addresses the port number of the proxy
		and is used as index for the other elements in the Table"
	::= { downloadActionEntry 1 }

downloadActionLinkIndex OBJECT-TYPE
	SYNTAX INTEGER
	ACCESS read-only
	STATUS mandatory
	DESCRIPTION
		"This variable addresses the slot number of the OMI sub-rack
		and is used as index for the other elements in the Table"
	::= { downloadActionEntry 2 }


downloadActionStart OBJECT-TYPE
	SYNTAX INTEGER
	{
		activBank(1),
		passiveBank(2),
		unknown(254),
		unsupported(255)
	}
	ACCESS read-write
	STATUS mandatory
	DESCRIPTION
		"This is a write-only variable which is used to start
		remote download from the selcted bank.
		1	ActiveBank	Use active bank of LT for remote download
		2	PassiveBank	Use passive bank of LT for remote download
		254			unknown value
		255			unsupported variable for addressed device"
	::= { downloadActionEntry 3 }

downloadActionAbort OBJECT-TYPE
	SYNTAX INTEGER
	{
		abort(1),
		unknown(254),
		unsupported(255)
	}
	ACCESS read-write
	STATUS mandatory
	DESCRIPTION
		"This is a write-only variable which is used to abort
		the currently running remote download.
		
		The only legal parameter is 'abort(1)'."
	::= { downloadActionEntry 4 }

--------------------------------------------------------------------------------
--	SRU Download Starting and Aborting
--------------------------------------------------------------------------------
downloadSruActionTable OBJECT-TYPE
	SYNTAX SEQUENCE OF DownloadSruActionEntry
	ACCESS not-accessible
	STATUS mandatory
	DESCRIPTION ""
	::= { download 3 }

downloadSruActionEntry OBJECT-TYPE
	SYNTAX DownloadSruActionEntry
	ACCESS not-accessible
	STATUS mandatory
	DESCRIPTION ""
	INDEX { downloadSruActionPortIndex, downloadSruActionLinkIndex, downloadSruActionRegIndex }
	::= { downloadSruActionTable 1 }

DownloadSruActionEntry ::=
	SEQUENCE
	{
		downloadSruActionPortIndex INTEGER,
		downloadSruActionLinkIndex INTEGER,
		downloadSruActionRegIndex INTEGER,
		downloadSruActionStart INTEGER,
		downloadSruActionAbort INTEGER
	}

downloadSruActionPortIndex OBJECT-TYPE
	SYNTAX INTEGER
	ACCESS read-only
	STATUS mandatory
	DESCRIPTION
		"This variable addresses the port number of the proxy
		and is used as index for the other elements in the Table"
	::= { downloadSruActionEntry 1 }

downloadSruActionLinkIndex OBJECT-TYPE
	SYNTAX INTEGER
	ACCESS read-only
	STATUS mandatory
	DESCRIPTION
		"This variable addresses the slot number of the OMI sub-rack
		and is used as index for the other elements in the Table"
	::= { downloadSruActionEntry 2 }


downloadSruActionRegIndex OBJECT-TYPE
	SYNTAX INTEGER
	{
		reg11(3),
		reg12(4),
		reg21(5),
		reg22(6),
		reg31(7),
		reg32(8),
		reg41(9),
		reg42(10),
		reg51(11),
		reg52(12),
		reg61(13),
		reg62(14),
		reg71(15),
		reg72(16),
		reg81(17),
		reg82(18),
		reg13(19),
		reg14(20),
		reg23(21),
		reg24(22),
		reg33(23),
		reg34(24),
		reg43(25),
		reg44(26),
		reg53(27),
		reg54(28),
		reg63(29),
		reg64(30),
		reg73(31),
		reg74(32),
		reg83(33),
		reg84(34)
	}
	ACCESS read-only
	STATUS mandatory
	DESCRIPTION
		"This variable addresses the regenerator device"
	::= { downloadSruActionEntry 3 }


downloadSruActionStart OBJECT-TYPE
	SYNTAX INTEGER
	{
		activBank(1),
		passiveBank(2),
		unknown(254),
		unsupported(255)
	}
	ACCESS read-write
	STATUS mandatory
	DESCRIPTION
		"This is a write-only variable which is used to start
		remote download from the selcted bank.
		1	ActiveBank	Use active bank of LT for remote download
		2	PassiveBank	Use passive bank of LT for remote download
		254			unknown value
		255			unsupported variable for addressed device"
	::= { downloadSruActionEntry 4 }

downloadSruActionAbort OBJECT-TYPE
	SYNTAX INTEGER
	{
		abort(1),
		unknown(254),
		unsupported(255)
	}
	ACCESS read-write
	STATUS mandatory
	DESCRIPTION
		"This is a write-only variable which is used to abort
		the currently running remote download.
		
		The only legal parameter is 'abort(1)'."
	::= { downloadSruActionEntry 5 }

--------------------------------------------------------------------------------
--	Download State
--------------------------------------------------------------------------------
downloadStateTable OBJECT-TYPE
	SYNTAX SEQUENCE OF DownloadStateEntry
	ACCESS not-accessible
	STATUS mandatory
	DESCRIPTION ""
	::= { download 4 }

downloadStateEntry OBJECT-TYPE
	SYNTAX DownloadStateEntry
	ACCESS not-accessible
	STATUS mandatory
	DESCRIPTION ""
	INDEX { downloadStatePortIndex, downloadStateLinkIndex }
	::= { downloadStateTable 1 }

DownloadStateEntry ::=
	SEQUENCE
	{
		downloadStatePortIndex INTEGER,
		downloadStateLinkIndex INTEGER,
		downloadStateInstance INTEGER,
		downloadStateTarget INTEGER,
		downloadStateState INTEGER,
		downloadStateTotalBlocks INTEGER,
		downloadStateProgress INTEGER
	}

downloadStatePortIndex OBJECT-TYPE
	SYNTAX INTEGER
	ACCESS read-only
	STATUS mandatory
	DESCRIPTION
		"This variable addresses the port number of the proxy
		and is used as index for the other elements in the Table"
	::= { downloadStateEntry 1 }

downloadStateLinkIndex OBJECT-TYPE
	SYNTAX INTEGER
	ACCESS read-only
	STATUS mandatory
	DESCRIPTION
		"This variable addresses the slot number of the OMI sub-rack
		and is used as index for the other elements in the Table"
	::= {downloadStateEntry 2 }

downloadStateInstance OBJECT-TYPE
	SYNTAX INTEGER
	{
		system1(1),
		system2(2),
		system3(3),
		system4(4),
		unknown(254),
		unsupported(255)
	}
	ACCESS read-only
	STATUS mandatory
	DESCRIPTION
		"Returns the instance of the system for which a download is active"
	::= { downloadStateEntry 3 }

downloadStateTarget OBJECT-TYPE
	SYNTAX INTEGER
	{
		notDownloading(1),
		lt(2),
		nt(3),
		reg11(4),
		reg12(5),
		reg21(6),
		reg22(7),
		reg31(8),
		reg32(9),
		reg41(10),
		reg42(11),
		reg51(12),
		reg52(13),
		reg61(14),
		reg62(15),
		reg71(16),
		reg72(17),
		reg81(18),
		reg82(19),
		reg13(20),
		reg14(21),
		reg23(22),
		reg24(23),
		reg33(24),
		reg34(25),
		reg43(26),
		reg44(27),
		reg53(28),
		reg54(29),
		reg63(30),
		reg64(31),
		reg73(32),
		reg74(33),
		reg83(34),
		reg84(35),
		unknown(254),
		unsupported(255)
	}
	ACCESS read-only
	STATUS mandatory
	DESCRIPTION
		"Returns the device for which a download is active
		NotDownloading 1  No download is active
		Lt             2  Local download
		Nt             3  Remote download to NT active
		Reg11          4  Remote download to regenerator section 1 wire pair 1
		Reg12          5  Remote download to regenerator section 1 wire pair 2
		Reg21          6  Remote download to regenerator section 2 wire pair 1
		Reg22          7  Remote download to regenerator section 2 wire pair 2
		Reg31          8  Remote download to regenerator section 3 wire pair 1
		Reg32          9  Remote download to regenerator section 3 wire pair 2
		Reg41         10  Remote download to regenerator section 4 wire pair 1
		Reg42         11  Remote download to regenerator section 4 wire pair 2
		Reg51         12  Remote download to regenerator section 5 wire pair 1
		Reg52         13  Remote download to regenerator section 5 wire pair 2
		Reg61         14  Remote download to regenerator section 6 wire pair 1
		Reg62         15  Remote download to regenerator section 6 wire pair 2
		Reg71         16  Remote download to regenerator section 7 wire pair 1
		Reg72         17  Remote download to regenerator section 7 wire pair 2
		Reg81         18  Remote download to regenerator section 8 wire pair 1
		Reg82         19  Remote download to regenerator section 8 wire pair 2
		Reg13         20  Remote download to regenerator section 1 wire pair 3
		Reg14         21  Remote download to regenerator section 1 wire pair 4
		Reg23         22  Remote download to regenerator section 2 wire pair 3
		Reg24         23  Remote download to regenerator section 2 wire pair 4
		Reg33         24  Remote download to regenerator section 3 wire pair 3
		Reg34         25  Remote download to regenerator section 3 wire pair 4
		Reg43         26  Remote download to regenerator section 4 wire pair 3
		Reg44         27  Remote download to regenerator section 4 wire pair 4
		Reg53         28  Remote download to regenerator section 5 wire pair 3
		Reg54         29  Remote download to regenerator section 5 wire pair 4
		Reg63         30  Remote download to regenerator section 6 wire pair 3
		Reg64         31  Remote download to regenerator section 6 wire pair 4
		Reg73         32  Remote download to regenerator section 7 wire pair 3
		Reg74         33  Remote download to regenerator section 7 wire pair 4
		Reg83         34  Remote download to regenerator section 8 wire pair 3
		Reg84         35  Remote download to regenerator section 8 wire pair 4
		             254  unknown value
		             255  unsupported variable for addressed device"
	::= { downloadStateEntry 4 }

downloadStateState OBJECT-TYPE
	SYNTAX INTEGER
	{
		notStarted(1),
		pending(2),
		abortedLd(3),
		erasingFlash(4),
		running(5),
		failed(6),
		complete(7),
		unknown(254),
		unsupported(255)
	}
	ACCESS read-only
	STATUS mandatory
	DESCRIPTION
		"Returns the state of the download
		1	NotStarted	Never started a download for this device
		2	Pending		Waiting for download start response from NT
		3	AbortedLd	Remote download not started because of lokal download running
		4	ErasingFlash	Flash EEPROM of this device is being erased
		5	Running		Download for this device is running
		6	Failed		Last download for this device failed
		7	Complete	Last download for this device was successful
		254			unknown value
		255			unsupported variable for addressed device"
	::= { downloadStateEntry 5 }

downloadStateTotalBlocks OBJECT-TYPE
	SYNTAX INTEGER
	ACCESS read-only
	STATUS mandatory
	DESCRIPTION
		"Returns the size of the firmware being downloaded to the device
		in blocks of 128 bytes
		0xFFFE			unknown value
		0xFFFF			unsupported variable for addressed device"
	::= { downloadStateEntry 6 }

downloadStateProgress OBJECT-TYPE
	SYNTAX INTEGER
	ACCESS read-only
	STATUS mandatory
	DESCRIPTION
		"Returns the number of 128 byte blocks that have already been downloaded
		0xFFFE			unknown value
		0xFFFF			unsupported variable for addressed device"
	::= { downloadStateEntry 7 }

--------------------------------------------------------------------------------
--	Download Remote Dwl Possible
--------------------------------------------------------------------------------
downloadRemDwlPossibleTable OBJECT-TYPE
	SYNTAX SEQUENCE OF DownloadRemDwlPossibleEntry
	ACCESS not-accessible
	STATUS mandatory
	DESCRIPTION ""
	::= { download 5 }

downloadRemDwlPossibleEntry OBJECT-TYPE
	SYNTAX DownloadRemDwlPossibleEntry
	ACCESS not-accessible
	STATUS mandatory
	DESCRIPTION ""
	INDEX { downloadRemDwlPossiblePortIndex, downloadRemDwlPossibleLinkIndex }
	::= { downloadRemDwlPossibleTable 1 }

DownloadRemDwlPossibleEntry ::=
	SEQUENCE
	{
		downloadRemDwlPossiblePortIndex INTEGER,
		downloadRemDwlPossibleLinkIndex INTEGER,
		downloadRemDwlPossibleNt INTEGER,
		downloadRemDwlPossibleReg1Wp1 INTEGER,
		downloadRemDwlPossibleReg2Wp1 INTEGER,
		downloadRemDwlPossibleReg3Wp1 INTEGER,
		downloadRemDwlPossibleReg4Wp1 INTEGER,
		downloadRemDwlPossibleReg5Wp1 INTEGER,
		downloadRemDwlPossibleReg6Wp1 INTEGER,
		downloadRemDwlPossibleReg7Wp1 INTEGER,
		downloadRemDwlPossibleReg8Wp1 INTEGER,
		downloadRemDwlPossibleReg1Wp2 INTEGER,
		downloadRemDwlPossibleReg2Wp2 INTEGER,
		downloadRemDwlPossibleReg3Wp2 INTEGER,
		downloadRemDwlPossibleReg4Wp2 INTEGER,
		downloadRemDwlPossibleReg5Wp2 INTEGER,
		downloadRemDwlPossibleReg6Wp2 INTEGER,
		downloadRemDwlPossibleReg7Wp2 INTEGER,
		downloadRemDwlPossibleReg8Wp2 INTEGER,
		downloadRemDwlPossibleReg1Wp3 INTEGER,
		downloadRemDwlPossibleReg2Wp3 INTEGER,
		downloadRemDwlPossibleReg3Wp3 INTEGER,
		downloadRemDwlPossibleReg4Wp3 INTEGER,
		downloadRemDwlPossibleReg5Wp3 INTEGER,
		downloadRemDwlPossibleReg6Wp3 INTEGER,
		downloadRemDwlPossibleReg7Wp3 INTEGER,
		downloadRemDwlPossibleReg8Wp3 INTEGER,
		downloadRemDwlPossibleReg1Wp4 INTEGER,
		downloadRemDwlPossibleReg2Wp4 INTEGER,
		downloadRemDwlPossibleReg3Wp4 INTEGER,
		downloadRemDwlPossibleReg4Wp4 INTEGER,
		downloadRemDwlPossibleReg5Wp4 INTEGER,
		downloadRemDwlPossibleReg6Wp4 INTEGER,
		downloadRemDwlPossibleReg7Wp4 INTEGER,
		downloadRemDwlPossibleReg8Wp4 INTEGER
	}

downloadRemDwlPossiblePortIndex OBJECT-TYPE
	SYNTAX INTEGER
	ACCESS read-only
	STATUS mandatory
	DESCRIPTION
		"This variable addresses the port number of the proxy
		and is used as index for the other elements in the Table"
	::= { downloadRemDwlPossibleEntry 1 }

downloadRemDwlPossibleLinkIndex OBJECT-TYPE
	SYNTAX INTEGER
	ACCESS read-only
	STATUS mandatory
	DESCRIPTION
		"This variable addresses the slot number of the OMI sub-rack
		and is used as index for the other elements in the Table"
	::= {downloadRemDwlPossibleEntry 2 }

downloadRemDwlPossibleNt OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 3 }

downloadRemDwlPossibleReg1Wp1 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 4 }

downloadRemDwlPossibleReg2Wp1 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 5 }

downloadRemDwlPossibleReg3Wp1 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 6 }

downloadRemDwlPossibleReg4Wp1 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 7 }

downloadRemDwlPossibleReg5Wp1 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 8 }

downloadRemDwlPossibleReg6Wp1 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 9 }

downloadRemDwlPossibleReg7Wp1 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 10 }

downloadRemDwlPossibleReg8Wp1 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 11 }

downloadRemDwlPossibleReg1Wp2 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 12 }

downloadRemDwlPossibleReg2Wp2 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 13 }

downloadRemDwlPossibleReg3Wp2 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 14 }

downloadRemDwlPossibleReg4Wp2 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 15 }

downloadRemDwlPossibleReg5Wp2 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 16 }

downloadRemDwlPossibleReg6Wp2 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 17 }

downloadRemDwlPossibleReg7Wp2 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 18 }

downloadRemDwlPossibleReg8Wp2 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 19 }

downloadRemDwlPossibleReg1Wp3 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 20 }

downloadRemDwlPossibleReg2Wp3 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 21 }

downloadRemDwlPossibleReg3Wp3 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 22 }

downloadRemDwlPossibleReg4Wp3 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 23 }

downloadRemDwlPossibleReg5Wp3 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 24 }

downloadRemDwlPossibleReg6Wp3 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 25 }

downloadRemDwlPossibleReg7Wp3 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 26 }

downloadRemDwlPossibleReg8Wp3 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 27 }

downloadRemDwlPossibleReg1Wp4 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 28 }

downloadRemDwlPossibleReg2Wp4 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 29 }

downloadRemDwlPossibleReg3Wp4 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 30 }

downloadRemDwlPossibleReg4Wp4 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 31 }

downloadRemDwlPossibleReg5Wp4 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 32 }

downloadRemDwlPossibleReg6Wp4 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 33 }

downloadRemDwlPossibleReg7Wp4 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 34 }

downloadRemDwlPossibleReg8Wp4 OBJECT-TYPE
	SYNTAX INTEGER
	ACCESS read-only
	STATUS mandatory
	DESCRIPTION
		"Indicates whether a remote download is possible or not.
		The value is bit-coded:
		bit0	Active bank download possible (far NE compatible)
		bit1	Active bank download not possible (far NE offline or not compatible)
		bit2	Active bank unknown, no compatibility list available
		bit3	not used
		bit4	Passive bank download possible (far NE compatible)
		bit5	Passive bank download not possible (far NE offline or not compatible)
		bit6	Passive bank unknown, no compatibility list available
		bit7	unsupported variable for addressed device"
	::= { downloadRemDwlPossibleEntry 35 }

--------------------------------------------------------------------------------
--	Download Bank Swap Possible
--------------------------------------------------------------------------------
downloadSwapPossibleTable OBJECT-TYPE
	SYNTAX SEQUENCE OF DownloadSwapPossibleEntry
	ACCESS not-accessible
	STATUS mandatory
	DESCRIPTION ""
	::= { download 6 }

downloadSwapPossibleEntry OBJECT-TYPE
	SYNTAX DownloadSwapPossibleEntry
	ACCESS not-accessible
	STATUS mandatory
	DESCRIPTION ""
	INDEX { downloadSwapPossiblePortIndex, downloadSwapPossibleLinkIndex }
	::= { downloadSwapPossibleTable 1 }

DownloadSwapPossibleEntry ::=
	SEQUENCE
	{
		downloadSwapPossiblePortIndex INTEGER,
		downloadSwapPossibleLinkIndex INTEGER,
		downloadSwapPossibleLocal INTEGER,
		downloadSwapPossibleNt INTEGER,
		downloadSwapPossibleReg1Wp1 INTEGER,
		downloadSwapPossibleReg2Wp1 INTEGER,
		downloadSwapPossibleReg3Wp1 INTEGER,
		downloadSwapPossibleReg4Wp1 INTEGER,
		downloadSwapPossibleReg5Wp1 INTEGER,
		downloadSwapPossibleReg6Wp1 INTEGER,
		downloadSwapPossibleReg7Wp1 INTEGER,
		downloadSwapPossibleReg8Wp1 INTEGER,
		downloadSwapPossibleReg1Wp2 INTEGER,
		downloadSwapPossibleReg2Wp2 INTEGER,
		downloadSwapPossibleReg3Wp2 INTEGER,
		downloadSwapPossibleReg4Wp2 INTEGER,
		downloadSwapPossibleReg5Wp2 INTEGER,
		downloadSwapPossibleReg6Wp2 INTEGER,
		downloadSwapPossibleReg7Wp2 INTEGER,
		downloadSwapPossibleReg8Wp2 INTEGER,
		downloadSwapPossibleReg1Wp3 INTEGER,
		downloadSwapPossibleReg2Wp3 INTEGER,
		downloadSwapPossibleReg3Wp3 INTEGER,
		downloadSwapPossibleReg4Wp3 INTEGER,
		downloadSwapPossibleReg5Wp3 INTEGER,
		downloadSwapPossibleReg6Wp3 INTEGER,
		downloadSwapPossibleReg7Wp3 INTEGER,
		downloadSwapPossibleReg8Wp3 INTEGER,
		downloadSwapPossibleReg1Wp4 INTEGER,
		downloadSwapPossibleReg2Wp4 INTEGER,
		downloadSwapPossibleReg3Wp4 INTEGER,
		downloadSwapPossibleReg4Wp4 INTEGER,
		downloadSwapPossibleReg5Wp4 INTEGER,
		downloadSwapPossibleReg6Wp4 INTEGER,
		downloadSwapPossibleReg7Wp4 INTEGER,
		downloadSwapPossibleReg8Wp4 INTEGER
	}

downloadSwapPossiblePortIndex OBJECT-TYPE
	SYNTAX INTEGER
	ACCESS read-only
	STATUS mandatory
	DESCRIPTION
		"This variable addresses the port number of the proxy
		and is used as index for the other elements in the Table"
	::= { downloadSwapPossibleEntry 1 }

downloadSwapPossibleLinkIndex OBJECT-TYPE
	SYNTAX INTEGER
	ACCESS read-only
	STATUS mandatory
	DESCRIPTION
		"This variable addresses the slot number of the OMI sub-rack
		and is used as index for the other elements in the Table"
	::= {downloadSwapPossibleEntry 2 }

downloadSwapPossibleLocal OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 3 }

downloadSwapPossibleNt OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 4 }

downloadSwapPossibleReg1Wp1 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 5 }

downloadSwapPossibleReg2Wp1 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 6 }

downloadSwapPossibleReg3Wp1 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 7 }

downloadSwapPossibleReg4Wp1 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 8 }

downloadSwapPossibleReg5Wp1 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 9 }

downloadSwapPossibleReg6Wp1 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 10 }

downloadSwapPossibleReg7Wp1 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 11 }

downloadSwapPossibleReg8Wp1 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 12 }

downloadSwapPossibleReg1Wp2 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 13 }

downloadSwapPossibleReg2Wp2 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 14 }

downloadSwapPossibleReg3Wp2 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 15 }

downloadSwapPossibleReg4Wp2 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 16 }

downloadSwapPossibleReg5Wp2 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 17 }

downloadSwapPossibleReg6Wp2 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 18 }

downloadSwapPossibleReg7Wp2 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 19 }

downloadSwapPossibleReg8Wp2 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 20 }

downloadSwapPossibleReg1Wp3 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 21 }

downloadSwapPossibleReg2Wp3 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 22 }

downloadSwapPossibleReg3Wp3 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 23 }

downloadSwapPossibleReg4Wp3 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 24 }

downloadSwapPossibleReg5Wp3 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 25 }

downloadSwapPossibleReg6Wp3 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 26 }

downloadSwapPossibleReg7Wp3 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 27 }

downloadSwapPossibleReg8Wp3 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 28 }

downloadSwapPossibleReg1Wp4 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 29 }

downloadSwapPossibleReg2Wp4 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 30 }

downloadSwapPossibleReg3Wp4 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 31 }

downloadSwapPossibleReg4Wp4 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 32 }

downloadSwapPossibleReg5Wp4 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 33 }

downloadSwapPossibleReg6Wp4 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 34 }

downloadSwapPossibleReg7Wp4 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 35 }

downloadSwapPossibleReg8Wp4 OBJECT-TYPE
	SYNTAX INTEGER
	{
		swapNotPossible(1),
		swapPossible(2),
		unknown(254),
		unsupported(255)
	}
	ACCESS read-only
	STATUS mandatory
	DESCRIPTION
		"Indicates whether a firmware bank swap is possible or not.
		1	SwapNotPossible	Bank swap is not possible
		2	SwapPossible	Bank swap is possible
		254			unknown value
		255			unsupported variable for addressed device"
	::= { downloadSwapPossibleEntry 36 }

--==============================================================================
--==============================================================================
--
--      Traps
--
--==============================================================================
--==============================================================================
	extendedTraps	OBJECT IDENTIFIER ::= { linksVers3 8 }

--------------------------------------------------------------------------------
--	Extended Traps
--------------------------------------------------------------------------------
extendedTrapsTable OBJECT-TYPE
	SYNTAX SEQUENCE OF ExtendedTrapsEntry
	ACCESS not-accessible
	STATUS mandatory
	DESCRIPTION ""
	::= { extendedTraps 1 }

extendedTrapsEntry OBJECT-TYPE
	SYNTAX ExtendedTrapsEntry
	ACCESS not-accessible
	STATUS mandatory
	DESCRIPTION ""
	INDEX { extendedTrapsPortIndex, extendedTrapsLinkIndex }
	::= { extendedTrapsTable 1 }

ExtendedTrapsEntry ::=
	SEQUENCE
	{
		extendedTrapsPortIndex INTEGER,
		extendedTrapsLinkIndex INTEGER,
		extendedTrapsType INTEGER
	}

extendedTrapsPortIndex OBJECT-TYPE
	SYNTAX INTEGER
	ACCESS read-only
	STATUS mandatory
	DESCRIPTION
		"This variable addresses the port number of the proxy
		and is used as index for the other elements in the Table"
	::= { extendedTrapsEntry 1 }

extendedTrapsLinkIndex OBJECT-TYPE
	SYNTAX INTEGER
	ACCESS read-only
	STATUS mandatory
	DESCRIPTION
		"This variable addresses the slot number of the OMI sub-rack
		and is used as index for the other elements in the Table"
	::= {extendedTrapsEntry 2 }

extendedTrapsType OBJECT-TYPE
	SYNTAX INTEGER
	{
		lineConfigChange(1),
		alarmConfigChange(2),
		rdwlState(3),
		rebootRemote(4),
		ldwlState(5),
		lineProbing(6),
		userDataChange(7),
		ledStateChange(8),
		systemConfigChange(9),
		teDataAvailable(10),
		teSessionEnd(11),
		tePwrStationAlCfg(12),
		pwdLost(13),
		link(14),
		authentication(15),
		multipleUsers(16),
		stp(17),
		acl(18),
		cfgChangeL2Switch(19),
		unknown(254),
		unsupported(255)
	}
	ACCESS read-only
	STATUS mandatory
	DESCRIPTION
		"This variable is only used as an attachement on the extended snmp trap
		1	LineConfigChange	The line configuration has changed
		2	AlarmConfigChange	The alarm configuration has changed
		3	RDWLState		The state of the remote download has changed
		4	RebootRemote		The remote device has rebooted
		5	LDWLState		The state of the local download has changed
		6	LineProbing		The lineprobing is terminated
		7	UserDataChange		The user data string has changed
		8	LEDStateChange		The LED state has changed
		9	SystemConfigChange	The number of wire pairs has changed
		10	TEDataAvailable		Terminal emulation offers data for terminal output
		11	TESessionEnd		End of terminal session on line card (not OMII)
		12	TEPwrStationAlCfg		Change of Power Station Alarms (to OMII)
		13	PwdLost		Password lost
		14	Link		FE or GbE link status changed
		15	Authentication		Authentication status changed
		16	MultipleUsers		Multiple users status changed
		17	STP		Spanning Tree Protocol status changed
		18	ACL		Access Control Lists status changed
		19	CfgChangeL2Switch		L2 Switch configuration data changed
		254				unknown value
		255				unsupported variable for addressed device"
	::= { extendedTrapsEntry 3 }

--==============================================================================
--==============================================================================
--
--      SM RW
--
--==============================================================================
--==============================================================================
	smrw	OBJECT IDENTIFIER ::= { linksVers3 9 }

--------------------------------------------------------------------------------
--	SM RW	SM Read & Write
--------------------------------------------------------------------------------
smrwOmiTable OBJECT-TYPE
	SYNTAX SEQUENCE OF SmrwOmiEntry
	ACCESS not-accessible
	STATUS mandatory
	DESCRIPTION ""
	::= {smrw 1 }

smrwOmiEntry OBJECT-TYPE
	SYNTAX SmrwOmiEntry
	ACCESS not-accessible
	STATUS mandatory
	DESCRIPTION ""
	INDEX { smrwOmiPortIndex }
	::= { smrwOmiTable 1 }

SmrwOmiEntry ::=
	SEQUENCE
	{
		smrwOmiPortIndex INTEGER,
		smrwOmiLCTLocalMgmt INTEGER,
		smrwOmiLCTRemoteMgmt INTEGER,
		smrwOmiSNMPv1-v2Mgmt INTEGER,
		smrwOmiSNMPv3Mgmt INTEGER,
		smrwOmiCLIMgmt INTEGER,
		smrwOmiWebMgmt INTEGER
	}

smrwOmiPortIndex OBJECT-TYPE
	SYNTAX INTEGER
	ACCESS read-only
	STATUS mandatory
	DESCRIPTION
		"This variable is used as index for the other elements in the Table"
	::= { smrwOmiEntry 1 }

smrwOmiLCTLocalMgmt OBJECT-TYPE
	SYNTAX INTEGER
	{
		noAccess(1),
		roAccess(2),
		rwAccess(3),
		unknown(254),
		unsupported(255)
	}
	ACCESS read-only
	STATUS mandatory
	DESCRIPTION
		"This is a read-only variable which is used to get
		LCT local management status:
		1	NO_ACCESS
		2	RO_ACCESS
		3	RW_ACCESS
		254	unknown value
		255	unsupported value"
	::= { smrwOmiEntry 2 }

smrwOmiLCTRemoteMgmt OBJECT-TYPE
	SYNTAX INTEGER
	{
		noAccess(1),
		roAccess(2),
		rwAccess(3),
		unknown(254),
		unsupported(255)
	}
	ACCESS read-write
	STATUS mandatory
	DESCRIPTION
		"This is a read-write variable which is used to get/set
		LCT remote management status:
		1	NO_ACCESS
		2	RO_ACCESS
		3	RW_ACCESS
		254	unknown value
		255	unsupported value"
	::= { smrwOmiEntry 3 }

smrwOmiSNMPv1-v2Mgmt OBJECT-TYPE
	SYNTAX INTEGER
	{
		noAccess(1),
		roAccess(2),
		rwAccess(3),
		unknown(254),
		unsupported(255)
	}
	ACCESS read-write
	STATUS mandatory
	DESCRIPTION
		"This is a read-write variable which is used to get/set
		SNMPv1 and SNMPv2 management status:
		1	NO_ACCESS
		2	RO_ACCESS
		3	RW_ACCESS
		254	unknown value
		255	unsupported value"
	::= { smrwOmiEntry 4 }

smrwOmiSNMPv3Mgmt OBJECT-TYPE
	SYNTAX INTEGER
	{
		noAccess(1),
		roAccess(2),
		rwAccess(3),
		unknown(254),
		unsupported(255)
	}
	ACCESS read-write
	STATUS mandatory
	DESCRIPTION
		"This is a read-write variable which is used to get/set
		SNMPv3 management status:
		1	NO_ACCESS
		2	RO_ACCESS
		3	RW_ACCESS
		254	unknown value
		255	unsupported value"
	::= { smrwOmiEntry 5 }

smrwOmiCLIMgmt OBJECT-TYPE
	SYNTAX INTEGER
	{
		noAccess(1),
		roAccess(2),
		rwAccess(3),
		unknown(254),
		unsupported(255)
	}
	ACCESS read-write
	STATUS mandatory
	DESCRIPTION
		"This is a read-write variable which is used to get/set
		CLI management status:
		1	NO_ACCESS
		2	RO_ACCESS
		3	RW_ACCESS
		254	unknown value
		255	unsupported value"
	::= { smrwOmiEntry 6 }

smrwOmiWebMgmt OBJECT-TYPE
	SYNTAX INTEGER
	{
		noAccess(1),
		roAccess(2),
		rwAccess(3),
		unknown(254),
		unsupported(255)
	}
	ACCESS read-only
	STATUS mandatory
	DESCRIPTION
		"This is a read-only variable which is used to get
		Web management status:
		1	NO_ACCESS
		2	RO_ACCESS
		3	RW_ACCESS
		254	unknown value
		255	unsupported value"
	::= { smrwOmiEntry 7 }

--==============================================================================
--==============================================================================
--
--      OMPP over SNMP
--
--==============================================================================
--==============================================================================
	omppOverSNMP	OBJECT IDENTIFIER ::= { linksVers3 10 }

omppOverSNMPTable OBJECT-TYPE
	SYNTAX SEQUENCE OF OmppOverSNMPEntry
	ACCESS not-accessible
	STATUS mandatory
	DESCRIPTION ""
	::= { omppOverSNMP 1 }

omppOverSNMPEntry OBJECT-TYPE
	SYNTAX OmppOverSNMPEntry
	ACCESS not-accessible
	STATUS mandatory
	DESCRIPTION ""
	INDEX { omppOverSNMPPortIndex, omppOverSNMPLinkIndex, IMPLIED omppOverSNMPInvokeInfo }
	::= { omppOverSNMPTable 1 }

OmppOverSNMPEntry ::=
	SEQUENCE
	{
		omppOverSNMPPortIndex INTEGER,
		omppOverSNMPLinkIndex INTEGER,
		omppOverSNMPInvokeInfo OCTET STRING,
		omppOverSNMPGetData OCTET STRING,
		omppOverSNMPSetData OCTET STRING
	}

omppOverSNMPPortIndex OBJECT-TYPE
	SYNTAX INTEGER
	ACCESS read-only
	STATUS mandatory
	DESCRIPTION "This variable addresses the port number of the proxy
		and is used as index for the other elements in the Table"
	::= { omppOverSNMPEntry 1 }

omppOverSNMPLinkIndex OBJECT-TYPE
	SYNTAX INTEGER
	ACCESS read-only
	STATUS mandatory
	DESCRIPTION "This variable addresses the slot number of the OMI sub-rack
		and is used as index for the other elements in the Table"
	::= {omppOverSNMPEntry 2 }

omppOverSNMPInvokeInfo OBJECT-TYPE
	SYNTAX OCTET STRING (SIZE(1..255))
	ACCESS read-only
	STATUS mandatory
	DESCRIPTION "OMPP Invoke Telegram Data (only L7)"
	::= { omppOverSNMPEntry 3 }

omppOverSNMPGetData OBJECT-TYPE
	SYNTAX OCTET STRING
	ACCESS read-only
	STATUS mandatory
	DESCRIPTION "Confirm Telegram Data (Get,read)"
	::= { omppOverSNMPEntry 4 }
   
omppOverSNMPSetData OBJECT-TYPE
	SYNTAX OCTET STRING
	ACCESS read-write
	STATUS mandatory
	DESCRIPTION "Additional OMPP Invoke Telegram Data (Set, write)"
	::= { omppOverSNMPEntry 5 }
   
--------------------------------------------------------------------------------
END
